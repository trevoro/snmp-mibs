-- varfix Thu Dec 22 10:57:54 EST 1994 user: craig
-- File created using agent2concat
-- By: craig
-- Date: Thu Dec 22 10:57:39 EST 1994


LANART-AGENT DEFINITIONS ::= BEGIN

--
-- FILE: /bigguy/users/craig/mibs/src/rfc/rfc1155.smi
--

-- Changes to rfc1155 (SMI):
--      Removed EXPORTS.
--      Added explicit definitions of ccitt, null, iso, org, and dod.
--      Commented out OBJECT-TYPE macro definition (since will use
--        the definition from RFC-1212).
--      Commented out definitions of syntax types and replaced
--        with SMIC directives to enable them.



        -- no IMPORTS
		  IMPORTS
		  	IpAddress, NetworkAddress, Counter, Gauge, TimeTicks, OBJECT-TYPE FROM RFC1155-SMI
			TRAP-TYPE FROM RFC-1215;


        -- Define OIDs
        ccitt        OBJECT IDENTIFIER ::= { 0 }
        null         OBJECT IDENTIFIER ::= { ccitt 0 }

        iso          OBJECT IDENTIFIER ::= { 1 }
        org          OBJECT IDENTIFIER ::= { iso 3 }
        dod          OBJECT IDENTIFIER ::= { org 6 }
        internet     OBJECT IDENTIFIER ::= { dod 1 }
        directory    OBJECT IDENTIFIER ::= { internet 1 }
        mgmt         OBJECT IDENTIFIER ::= { internet 2 }
        experimental OBJECT IDENTIFIER ::= { internet 3 }
        private      OBJECT IDENTIFIER ::= { internet 4 }
        enterprises  OBJECT IDENTIFIER ::= { private 1 }

        -- Make builtin items known
--        SMI NetworkAddress
--        SMI IpAddress
--        SMI Counter
--        SMI Gauge
--        SMI TimeTicks
--        SMI Opaque


        -- definition of object types

        --    OBJECT-TYPE MACRO ::=
        --    BEGIN
        --        TYPE NOTATION ::= "SYNTAX" type (TYPE ObjectSyntax)
        --                          "ACCESS" Access
        --                          "STATUS" Status
        --        VALUE NOTATION ::= value (VALUE ObjectName)
        --
        --        Access ::= "read-only"
        --                        | "read-write"
        --                        | "write-only"
        --                        | "not-accessible"
        --        Status ::= "mandatory"
        --                        | "optional"
        --                        | "obsolete"
        --    END
        --
        -- names of objects in the MIB
        --
        --       ObjectName ::= OBJECT IDENTIFIER
        --
        -- syntax of objects in the MIB
        --
        --       ObjectSyntax ::=
        --           CHOICE {
        --               simple
        --                   SimpleSyntax,
               -- note that simple SEQUENCEs are not directly
               -- mentioned here to keep things simple (i.e.,
               -- prevent mis-use).  However, application-wide
               -- types which are IMPLICITly encoded simple
               -- SEQUENCEs may appear in the following CHOICE
        --
        --               application-wide
        --                   ApplicationSyntax
        --           }
        --
        --          SimpleSyntax ::=
        --              CHOICE {
        --                  number INTEGER,
        --                  string OCTET STRING,
        --                  object OBJECT IDENTIFIER,
        --                  empty  NULL
        --              }
        --
        --          ApplicationSyntax ::=
        --              CHOICE {
        --                  address NetworkAddress,
        --                  counter Counter,
        --                  gauge Gauge,
        --                  ticks TimeTicks,
        --                  arbitrary Opaque
                  -- other application-wide types, as they are
                  -- defined, will be added here
        --              }
        --
        --
                  -- application-wide types

        --          NetworkAddress ::=
        --              CHOICE {
        --                  internet IpAddress
        --              }
        --
        --          IpAddress ::=
        --              [APPLICATION 0]
        --                  IMPLICIT OCTET STRING (SIZE (4))
        --
        --          Counter ::=
        --              [APPLICATION 1]
        --                  IMPLICIT INTEGER (0..4294967295)
        --
        --          Gauge ::=
        --              [APPLICATION 2]
        --                  IMPLICIT INTEGER (0..4294967295)
        --
        --          TimeTicks ::=
        --              [APPLICATION 3]
        --                  IMPLICIT INTEGER (0..4294967295)
        --
        --          Opaque ::=
        --              [APPLICATION 4]
        --                  IMPLICIT OCTET STRING

--
-- FILE: /bigguy/users/craig/mibs/src/rfc/RFC-1212.smi
--

-- changes to RFC-1212 (Concise MIB OBJECT-TYPE definition):
--      Removed IMPORTS.
--      Commented out OBJECT-TYPE macro definition and replaced
--        with SMIC directive to enable it.




    -- Make builtin items known
--    SMI OBJECT-TYPE


        --  OBJECT-TYPE MACRO ::=
        --  BEGIN
        --      TYPE NOTATION ::=
                                          -- must conform to
                                          -- RFC1155's ObjectSyntax
        --                        "SYNTAX" type(ObjectSyntax)
        --                        "ACCESS" Access
        --                        "STATUS" Status
        --                        DescrPart
        --                        ReferPart
        --                        IndexPart
        --                        DefValPart
        --      VALUE NOTATION ::= value (VALUE ObjectName)
        --
        --      Access ::= "read-only"
        --                      | "read-write"
        --                      | "write-only"
        --                      | "not-accessible"
        --      Status ::= "mandatory"
        --                      | "optional"
        --                      | "obsolete"
        --                      | "deprecated"
        --
        --      DescrPart ::=
        --                 "DESCRIPTION" value (description DisplayString)
        --                      | empty
        --
        --      ReferPart ::=
        --                 "REFERENCE" value (reference DisplayString)
        --                      | empty
        --
        --      IndexPart ::=
        --                 "INDEX" "{" IndexTypes "}"
        --                      | empty
        --      IndexTypes ::=
        --                 IndexType | IndexTypes "," IndexType
        --      IndexType ::=
                                  -- if indexobject, use the SYNTAX
                                  -- value of the correspondent
                                  -- OBJECT-TYPE invocation
        --                 value (indexobject ObjectName)
                                  -- otherwise use named SMI type
                                  -- must conform to IndexSyntax below
        --                      | type (indextype)
        --
        --      DefValPart ::=
        --                 "DEFVAL" "{" value (defvalue ObjectSyntax) "}"
        --                      | empty
        --  END
        --
        --  IndexSyntax ::=
        --      CHOICE {
        --          number
        --              INTEGER (0..MAX),
        --          string
        --              OCTET STRING,
        --          object
        --              OBJECT IDENTIFIER,
        --          address
        --              NetworkAddress,
        --          ipAddress
        --              IpAddress
        --      }

--
-- FILE: /bigguy/users/craig/mibs/src/rfc/rfc1213.mib
--

-- Changes to rfc1213 (MIB-II):
--      No changes needed.




          --  This MIB module uses the extended OBJECT-TYPE macro as
          --  defined in [14];


          --  MIB-II (same prefix as MIB-I)

          mib-2      OBJECT IDENTIFIER ::= { mgmt 1 }

          -- textual conventions

          DisplayString ::=
              OCTET STRING
          -- This data type is used to model textual information taken
          -- from the NVT ASCII character set.  By convention, objects
          -- with this syntax are declared as having
          --
          --      SIZE (0..255)

          PhysAddress ::=
              OCTET STRING
          -- This data type is used to model media addresses.  For many
          -- types of media, this will be in a binary representation.
          -- For example, an ethernet address would be represented as
          -- a string of 6 octets.


          -- groups in MIB-II

          system       OBJECT IDENTIFIER ::= { mib-2 1 }

          interfaces   OBJECT IDENTIFIER ::= { mib-2 2 }

          at           OBJECT IDENTIFIER ::= { mib-2 3 }

          ip           OBJECT IDENTIFIER ::= { mib-2 4 }

          icmp         OBJECT IDENTIFIER ::= { mib-2 5 }

          tcp          OBJECT IDENTIFIER ::= { mib-2 6 }

          udp          OBJECT IDENTIFIER ::= { mib-2 7 }

          egp          OBJECT IDENTIFIER ::= { mib-2 8 }

          -- historical (some say hysterical)
          -- cmot      OBJECT IDENTIFIER ::= { mib-2 9 }

          transmission OBJECT IDENTIFIER ::= { mib-2 10 }

          snmp         OBJECT IDENTIFIER ::= { mib-2 11 }


          -- the System group

          -- Implementation of the System group is mandatory for all
          -- systems.  If an agent is not configured to have a value
          -- for any of these variables, a string of length 0 is
          -- returned.

          sysDescr OBJECT-TYPE
              SYNTAX  DisplayString (SIZE (0..255))
              ACCESS  read-only
              STATUS  mandatory
              DESCRIPTION
                      "A textual description of the entity.  This value
                      should include the full name and version
                      identification of the system's hardware type,
                      software operating-system, and networking
                      software.  It is mandatory that this only contain
                      printable ASCII characters."
              ::= { system 1 }

          sysObjectID OBJECT-TYPE
              SYNTAX  OBJECT IDENTIFIER
              ACCESS  read-only
              STATUS  mandatory
              DESCRIPTION
                      "The vendor's authoritative identification of the
                      network management subsystem contained in the
                      entity.  This value is allocated within the SMI
                      enterprises subtree (1.3.6.1.4.1) and provides an
                      easy and unambiguous means for determining `what
                      kind of box' is being managed.  For example, if
                      vendor `Flintstones, Inc.' was assigned the
                      subtree 1.3.6.1.4.1.4242, it could assign the
                      identifier 1.3.6.1.4.1.4242.1.1 to its `Fred
                      Router'."
              ::= { system 2 }

          sysUpTime OBJECT-TYPE
              SYNTAX  TimeTicks
              ACCESS  read-only
              STATUS  mandatory
              DESCRIPTION
                      "The time (in hundredths of a second) since the
                      network management portion of the system was last
                      re-initialized."
              ::= { system 3 }

          sysContact OBJECT-TYPE
              SYNTAX  DisplayString (SIZE (0..255))
              ACCESS  read-write
              STATUS  mandatory
              DESCRIPTION
                      "The textual identification of the contact person
                      for this managed node, together with information
                      on how to contact this person."
              ::= { system 4 }

          sysName OBJECT-TYPE
              SYNTAX  DisplayString (SIZE (0..255))
              ACCESS  read-write
              STATUS  mandatory
              DESCRIPTION
                      "An administratively-assigned name for this
                      managed node.  By convention, this is the node's
                      fully-qualified domain name."
              ::= { system 5 }

          sysLocation OBJECT-TYPE
              SYNTAX  DisplayString (SIZE (0..255))
              ACCESS  read-write
              STATUS  mandatory
              DESCRIPTION
                      "The physical location of this node (e.g.,
                      `telephone closet, 3rd floor')."
              ::= { system 6 }

          sysServices OBJECT-TYPE
              SYNTAX  INTEGER (0..127)
              ACCESS  read-only
              STATUS  mandatory
              DESCRIPTION
                      "A value which indicates the set of services that
                      this entity primarily offers.

                      The value is a sum.  This sum initially takes the
                      value zero, Then, for each layer, L, in the range
                      1 through 7, that this node performs transactions
                      for, 2 raised to (L - 1) is added to the sum.  For
                      example, a node which performs primarily routing
                      functions would have a value of 4 (2^(3-1)).  In
                      contrast, a node which is a host offering
                      application services would have a value of 72
                      (2^(4-1) + 2^(7-1)).  Note that in the context of
                      the Internet suite of protocols, values should be
                      calculated accordingly:

                           layer  functionality
                               1  physical (e.g., repeaters)
                               2  datalink/subnetwork (e.g., bridges)
                               3  internet (e.g., IP gateways)
                               4  end-to-end  (e.g., IP hosts)
                               7  applications (e.g., mail relays)

                      For systems including OSI protocols, layers 5 and
                      6 may also be counted."
              ::= { system 7 }


          -- the Interfaces group

          -- Implementation of the Interfaces group is mandatory for
          -- all systems.

          ifNumber OBJECT-TYPE
              SYNTAX  INTEGER
              ACCESS  read-only
              STATUS  mandatory
              DESCRIPTION
                      "The number of network interfaces (regardless of
                      their current state) present on this system."
              ::= { interfaces 1 }


          -- the Interfaces table

          -- The Interfaces table contains information on the entity's
          -- interfaces.  Each interface is thought of as being
          -- attached to a `subnetwork'.  Note that this term should
          -- not be confused with `subnet' which refers to an
          -- addressing partitioning scheme used in the Internet suite
          -- of protocols.

          ifTable OBJECT-TYPE
              SYNTAX  SEQUENCE OF IfEntry
              ACCESS  not-accessible
              STATUS  mandatory
              DESCRIPTION
                      "A list of interface entries.  The number of
                      entries is given by the value of ifNumber."
              ::= { interfaces 2 }

          ifEntry OBJECT-TYPE
              SYNTAX  IfEntry
              ACCESS  not-accessible
              STATUS  mandatory
              DESCRIPTION
                      "An interface entry containing objects at the
                      subnetwork layer and below for a particular
                      interface."
              INDEX   { ifIndex }
              ::= { ifTable 1 }

          IfEntry ::=
              SEQUENCE {
                  ifIndex
                      INTEGER,
                  ifDescr
                      DisplayString,
                  ifType
                      INTEGER,
                  ifMtu
                      INTEGER,
                  ifSpeed
                      Gauge,
                  ifPhysAddress
                      PhysAddress,
                  ifAdminStatus
                      INTEGER,
                  ifOperStatus
                      INTEGER,
                  ifLastChange
                      TimeTicks,
                  ifInOctets
                      Counter,
                  ifInUcastPkts
                      Counter,
                  ifInNUcastPkts
                      Counter,
                  ifInDiscards
                      Counter,
                  ifInErrors
                      Counter,
                  ifInUnknownProtos
                      Counter,
                  ifOutOctets
                      Counter,
                  ifOutUcastPkts
                      Counter,
                  ifOutNUcastPkts
                      Counter,
                  ifOutDiscards
                      Counter,
                  ifOutErrors
                      Counter,
                  ifOutQLen
                      Gauge,
                  ifSpecific
                      OBJECT IDENTIFIER
              }

          ifIndex OBJECT-TYPE
              SYNTAX  INTEGER
              ACCESS  read-only
              STATUS  mandatory
              DESCRIPTION
                      "A unique value for each interface.  Its value
                      ranges between 1 and the value of ifNumber.  The
                      value for each interface must remain constant at
                      least from one re-initialization of the entity's
                      network management system to the next re-
                      initialization."
              ::= { ifEntry 1 }

          ifDescr OBJECT-TYPE
              SYNTAX  DisplayString (SIZE (0..255))
              ACCESS  read-only
              STATUS  mandatory
              DESCRIPTION
                      "A textual string containing information about the
                      interface.  This string should include the name of
                      the manufacturer, the product name and the version
                      of the hardware interface."
              ::= { ifEntry 2 }

          ifType OBJECT-TYPE
              SYNTAX  INTEGER {
                          other(1),          -- none of the following
                          regular1822(2),
                          hdh1822(3),
                          ddn-x25(4),
                          rfc877-x25(5),
                          ethernet-csmacd(6),
                          iso88023-csmacd(7),
                          iso88024-tokenBus(8),
                          iso88025-tokenRing(9),
                          iso88026-man(10),
                          starLan(11),
                          proteon-10Mbit(12),
                          proteon-80Mbit(13),
                          hyperchannel(14),
                          fddi(15),
                          lapb(16),
                          sdlc(17),
                          ds1(18),           -- T-1
                          e1(19),            -- european equiv. of T-1
                          basicISDN(20),
                          primaryISDN(21),   -- proprietary serial
                          propPointToPointSerial(22),
                          ppp(23),
                          softwareLoopback(24),
                          eon(25),            -- CLNP over IP [11]
                          ethernet-3Mbit(26),
                          nsip(27),           -- XNS over IP
                          slip(28),           -- generic SLIP
                          ultra(29),          -- ULTRA technologies
                          ds3(30),            -- T-3
                          sip(31),            -- SMDS
                          frame-relay(32)
                      }
              ACCESS  read-only
              STATUS  mandatory
              DESCRIPTION
                      "The type of interface, distinguished according to
                      the physical/link protocol(s) immediately `below'
                      the network layer in the protocol stack."
              ::= { ifEntry 3 }

          ifMtu OBJECT-TYPE
              SYNTAX  INTEGER
              ACCESS  read-only
              STATUS  mandatory
              DESCRIPTION
                      "The size of the largest datagram which can be
                      sent/received on the interface, specified in
                      octets.  For interfaces that are used for
                      transmitting network datagrams, this is the size
                      of the largest network datagram that can be sent
                      on the interface."
              ::= { ifEntry 4 }

          ifSpeed OBJECT-TYPE
              SYNTAX  Gauge
              ACCESS  read-only
              STATUS  mandatory
              DESCRIPTION
                      "An estimate of the interface's current bandwidth
                      in bits per second.  For interfaces which do not
                      vary in bandwidth or for those where no accurate
                      estimation can be made, this object should contain
                      the nominal bandwidth."
              ::= { ifEntry 5 }

          ifPhysAddress OBJECT-TYPE
              SYNTAX  PhysAddress
              ACCESS  read-only
              STATUS  mandatory
              DESCRIPTION
                      "The interface's address at the protocol layer
                      immediately `below' the network layer in the
                      protocol stack.  For interfaces which do not have
                      such an address (e.g., a serial line), this object
                      should contain an octet string of zero length."
              ::= { ifEntry 6 }

          ifAdminStatus OBJECT-TYPE
              SYNTAX  INTEGER {
                          up(1),       -- ready to pass packets
                          down(2),
                          testing(3)   -- in some test mode
                      }
              ACCESS  read-write
              STATUS  mandatory
              DESCRIPTION
                      "The desired state of the interface.  The
                      testing(3) state indicates that no operational
                      packets can be passed."
              ::= { ifEntry 7 }

          ifOperStatus OBJECT-TYPE
              SYNTAX  INTEGER {
                          up(1),       -- ready to pass packets
                          down(2),
                          testing(3)   -- in some test mode
                      }
              ACCESS  read-only
              STATUS  mandatory
              DESCRIPTION
                      "The current operational state of the interface.
                      The testing(3) state indicates that no operational
                      packets can be passed."
              ::= { ifEntry 8 }

          ifLastChange OBJECT-TYPE
              SYNTAX  TimeTicks
              ACCESS  read-only
              STATUS  mandatory
              DESCRIPTION
                      "The value of sysUpTime at the time the interface
                      entered its current operational state.  If the
                      current state was entered prior to the last re-
                      initialization of the local network management
                      subsystem, then this object contains a zero
                      value."
              ::= { ifEntry 9 }

          ifInOctets OBJECT-TYPE
              SYNTAX  Counter
              ACCESS  read-only
              STATUS  mandatory
              DESCRIPTION
                      "The total number of octets received on the
                      interface, including framing characters."
              ::= { ifEntry 10 }

          ifInUcastPkts OBJECT-TYPE
              SYNTAX  Counter
              ACCESS  read-only
              STATUS  mandatory
              DESCRIPTION
                      "The number of subnetwork-unicast packets
                      delivered to a higher-layer protocol."
              ::= { ifEntry 11 }

          ifInNUcastPkts OBJECT-TYPE
              SYNTAX  Counter
              ACCESS  read-only
              STATUS  mandatory
              DESCRIPTION
                      "The number of non-unicast (i.e., subnetwork-
                      broadcast or subnetwork-multicast) packets
                      delivered to a higher-layer protocol."
              ::= { ifEntry 12 }

          ifInDiscards OBJECT-TYPE
              SYNTAX  Counter
              ACCESS  read-only
              STATUS  mandatory
              DESCRIPTION
                      "The number of inbound packets which were chosen
                      to be discarded even though no errors had been
                      detected to prevent their being deliverable to a
                      higher-layer protocol.  One possible reason for
                      discarding such a packet could be to free up
                      buffer space."
              ::= { ifEntry 13 }

          ifInErrors OBJECT-TYPE
              SYNTAX  Counter
              ACCESS  read-only
              STATUS  mandatory
              DESCRIPTION
                      "The number of inbound packets that contained
                      errors preventing them from being deliverable to a
                      higher-layer protocol."
              ::= { ifEntry 14 }
          ifInUnknownProtos OBJECT-TYPE
              SYNTAX  Counter
              ACCESS  read-only
              STATUS  mandatory
              DESCRIPTION
                      "The number of packets received via the interface
                      which were discarded because of an unknown or
                      unsupported protocol."
              ::= { ifEntry 15 }

          ifOutOctets OBJECT-TYPE
              SYNTAX  Counter
              ACCESS  read-only
              STATUS  mandatory
              DESCRIPTION
                      "The total number of octets transmitted out of the
                      interface, including framing characters."
              ::= { ifEntry 16 }

          ifOutUcastPkts OBJECT-TYPE
              SYNTAX  Counter
              ACCESS  read-only
              STATUS  mandatory
              DESCRIPTION
                      "The total number of packets that higher-level
                      protocols requested be transmitted to a
                      subnetwork-unicast address, including those that
                      were discarded or not sent."
              ::= { ifEntry 17 }

          ifOutNUcastPkts OBJECT-TYPE
              SYNTAX  Counter
              ACCESS  read-only
              STATUS  mandatory
              DESCRIPTION
                      "The total number of packets that higher-level
                      protocols requested be transmitted to a non-
                      unicast (i.e., a subnetwork-broadcast or
                      subnetwork-multicast) address, including those
                      that were discarded or not sent."
              ::= { ifEntry 18 }

          ifOutDiscards OBJECT-TYPE
              SYNTAX  Counter
              ACCESS  read-only
              STATUS  mandatory
              DESCRIPTION
                      "The number of outbound packets which were chosen
                      to be discarded even though no errors had been
                      detected to prevent their being transmitted.  One
                      possible reason for discarding such a packet could
                      be to free up buffer space."
              ::= { ifEntry 19 }

          ifOutErrors OBJECT-TYPE
              SYNTAX  Counter
              ACCESS  read-only
              STATUS  mandatory
              DESCRIPTION
                      "The number of outbound packets that could not be
                      transmitted because of errors."
              ::= { ifEntry 20 }

          ifOutQLen OBJECT-TYPE
              SYNTAX  Gauge
              ACCESS  read-only
              STATUS  mandatory
              DESCRIPTION
                      "The length of the output packet queue (in
                      packets)."
              ::= { ifEntry 21 }

          ifSpecific OBJECT-TYPE
              SYNTAX  OBJECT IDENTIFIER
              ACCESS  read-only
              STATUS  mandatory
              DESCRIPTION
                      "A reference to MIB definitions specific to the
                      particular media being used to realize the
                      interface.  For example, if the interface is
                      realized by an ethernet, then the value of this
                      object refers to a document defining objects
                      specific to ethernet.  If this information is not
                      present, its value should be set to the OBJECT
                      IDENTIFIER { 0 0 }, which is a syntatically valid
                      object identifier, and any conformant
                      implementation of ASN.1 and BER must be able to
                      generate and recognize this value."
              ::= { ifEntry 22 }


          -- the Address Translation group

          -- Implementation of the Address Translation group is
          -- mandatory for all systems.  Note however that this group
          -- is deprecated by MIB-II. That is, it is being included
          -- solely for compatibility with MIB-I nodes, and will most
          -- likely be excluded from MIB-III nodes.  From MIB-II and
          -- onwards, each network protocol group contains its own
          -- address translation tables.

          -- The Address Translation group contains one table which is
          -- the union across all interfaces of the translation tables
          -- for converting a NetworkAddress (e.g., an IP address) into
          -- a subnetwork-specific address.  For lack of a better term,
          -- this document refers to such a subnetwork-specific address
          -- as a `physical' address.

          -- Examples of such translation tables are: for broadcast
          -- media where ARP is in use, the translation table is
          -- equivalent to the ARP cache; or, on an X.25 network where
          -- non-algorithmic translation to X.121 addresses is
          -- required, the translation table contains the
          -- NetworkAddress to X.121 address equivalences.

          atTable OBJECT-TYPE
              SYNTAX  SEQUENCE OF AtEntry
              ACCESS  not-accessible
              STATUS  deprecated
              DESCRIPTION
                      "The Address Translation tables contain the
                      NetworkAddress to `physical' address equivalences.
                      Some interfaces do not use translation tables for
                      determining address equivalences (e.g., DDN-X.25
                      has an algorithmic method); if all interfaces are
                      of this type, then the Address Translation table
                      is empty, i.e., has zero entries."
              ::= { at 1 }

          atEntry OBJECT-TYPE
              SYNTAX  AtEntry
              ACCESS  not-accessible
              STATUS  deprecated
              DESCRIPTION
                      "Each entry contains one NetworkAddress to
                      `physical' address equivalence."
              INDEX   { atIfIndex,
                        atNetAddress }
              ::= { atTable 1 }

          AtEntry ::=
              SEQUENCE {
                  atIfIndex
                      INTEGER,
                  atPhysAddress
                      PhysAddress,
                  atNetAddress
                      NetworkAddress
              }

          atIfIndex OBJECT-TYPE
              SYNTAX  INTEGER
              ACCESS  read-write
              STATUS  deprecated
              DESCRIPTION
                      "The interface on which this entry's equivalence
                      is effective.  The interface identified by a
                      particular value of this index is the same
                      interface as identified by the same value of
                      ifIndex."
              ::= { atEntry 1 }

          atPhysAddress OBJECT-TYPE
              SYNTAX  PhysAddress
              ACCESS  read-write
              STATUS  deprecated
              DESCRIPTION
                      "The media-dependent `physical' address.

                      Setting this object to a null string (one of zero
                      length) has the effect of invaliding the
                      corresponding entry in the atTable object.  That
                      is, it effectively dissasociates the interface
                      identified with said entry from the mapping
                      identified with said entry.  It is an
                      implementation-specific matter as to whether the
                      agent removes an invalidated entry from the table.
                      Accordingly, management stations must be prepared
                      to receive tabular information from agents that
                      corresponds to entries not currently in use.
                      Proper interpretation of such entries requires
                      examination of the relevant atPhysAddress object."
              ::= { atEntry 2 }

          atNetAddress OBJECT-TYPE
              SYNTAX  NetworkAddress
              ACCESS  read-write
              STATUS  deprecated
              DESCRIPTION
                      "The NetworkAddress (e.g., the IP address)
                      corresponding to the media-dependent `physical'
                      address."
              ::= { atEntry 3 }


          -- the IP group

          -- Implementation of the IP group is mandatory for all
          -- systems.

          ipForwarding OBJECT-TYPE
              SYNTAX  INTEGER {
                          forwarding(1),    -- acting as a gateway
                          not-forwarding(2) -- NOT acting as a gateway
                      }
              ACCESS  read-write
              STATUS  mandatory
              DESCRIPTION
                      "The indication of whether this entity is acting
                      as an IP gateway in respect to the forwarding of
                      datagrams received by, but not addressed to, this
                      entity.  IP gateways forward datagrams.  IP hosts
                      do not (except those source-routed via the host).

                      Note that for some managed nodes, this object may
                      take on only a subset of the values possible.
                      Accordingly, it is appropriate for an agent to
                      return a `badValue' response if a management
                      station attempts to change this object to an
                      inappropriate value."
              ::= { ip 1 }

          ipDefaultTTL OBJECT-TYPE
              SYNTAX  INTEGER
              ACCESS  read-write
              STATUS  mandatory
              DESCRIPTION
                      "The default value inserted into the Time-To-Live
                      field of the IP header of datagrams originated at
                      this entity, whenever a TTL value is not supplied
                      by the transport layer protocol."
              ::= { ip 2 }

          ipInReceives OBJECT-TYPE
              SYNTAX  Counter
              ACCESS  read-only
              STATUS  mandatory
              DESCRIPTION
                      "The total number of input datagrams received from
                      interfaces, including those received in error."
              ::= { ip 3 }

          ipInHdrErrors OBJECT-TYPE
              SYNTAX  Counter
              ACCESS  read-only
              STATUS  mandatory
              DESCRIPTION
                      "The number of input datagrams discarded due to
                      errors in their IP headers, including bad
                      checksums, version number mismatch, other format
                      errors, time-to-live exceeded, errors discovered
                      in processing their IP options, etc."
              ::= { ip 4 }

          ipInAddrErrors OBJECT-TYPE
              SYNTAX  Counter
              ACCESS  read-only
              STATUS  mandatory
              DESCRIPTION
                      "The number of input datagrams discarded because
                      the IP address in their IP header's destination
                      field was not a valid address to be received at
                      this entity.  This count includes invalid
                      addresses (e.g., 0.0.0.0) and addresses of
                      unsupported Classes (e.g., Class E).  For entities
                      which are not IP Gateways and therefore do not
                      forward datagrams, this counter includes datagrams
                      discarded because the destination address was not
                      a local address."
              ::= { ip 5 }

          ipForwDatagrams OBJECT-TYPE
              SYNTAX  Counter
              ACCESS  read-only
              STATUS  mandatory
              DESCRIPTION
                      "The number of input datagrams for which this
                      entity was not their final IP destination, as a
                      result of which an attempt was made to find a
                      route to forward them to that final destination.
                      In entities which do not act as IP Gateways, this
                      counter will include only those packets which were
                      Source-Routed via this entity, and the Source-
                      Route option processing was successful."
              ::= { ip 6 }

          ipInUnknownProtos OBJECT-TYPE
              SYNTAX  Counter
              ACCESS  read-only
              STATUS  mandatory
              DESCRIPTION
                      "The number of locally-addressed datagrams
                      received successfully but discarded because of an
                      unknown or unsupported protocol."
              ::= { ip 7 }

          ipInDiscards OBJECT-TYPE
              SYNTAX  Counter
              ACCESS  read-only
              STATUS  mandatory
              DESCRIPTION
                      "The number of input IP datagrams for which no
                      problems were encountered to prevent their
                      continued processing, but which were discarded
                      (e.g., for lack of buffer space).  Note that this
                      counter does not include any datagrams discarded
                      while awaiting re-assembly."
              ::= { ip 8 }

          ipInDelivers OBJECT-TYPE
              SYNTAX  Counter
              ACCESS  read-only
              STATUS  mandatory
              DESCRIPTION
                      "The total number of input datagrams successfully
                      delivered to IP user-protocols (including ICMP)."
              ::= { ip 9 }

          ipOutRequests OBJECT-TYPE
              SYNTAX  Counter
              ACCESS  read-only
              STATUS  mandatory
              DESCRIPTION
                      "The total number of IP datagrams which local IP
                      user-protocols (including ICMP) supplied to IP in
                      requests for transmission.  Note that this counter
                      does not include any datagrams counted in
                      ipForwDatagrams."
              ::= { ip 10 }

          ipOutDiscards OBJECT-TYPE
              SYNTAX  Counter
              ACCESS  read-only
              STATUS  mandatory
              DESCRIPTION
                      "The number of output IP datagrams for which no
                      problem was encountered to prevent their
                      transmission to their destination, but which were
                      discarded (e.g., for lack of buffer space).  Note
                      that this counter would include datagrams counted
                      in ipForwDatagrams if any such packets met this
                      (discretionary) discard criterion."
              ::= { ip 11 }

          ipOutNoRoutes OBJECT-TYPE
              SYNTAX  Counter
              ACCESS  read-only
              STATUS  mandatory
              DESCRIPTION
                      "The number of IP datagrams discarded because no
                      route could be found to transmit them to their
                      destination.  Note that this counter includes any
                      packets counted in ipForwDatagrams which meet this
                      `no-route' criterion.  Note that this includes any
                      datagarms which a host cannot route because all of
                      its default gateways are down."
              ::= { ip 12 }

          ipReasmTimeout OBJECT-TYPE
              SYNTAX  INTEGER
              ACCESS  read-only
              STATUS  mandatory
              DESCRIPTION
                      "The maximum number of seconds which received
                      fragments are held while they are awaiting
                      reassembly at this entity."
              ::= { ip 13 }

          ipReasmReqds OBJECT-TYPE
              SYNTAX  Counter
              ACCESS  read-only
              STATUS  mandatory
              DESCRIPTION
                      "The number of IP fragments received which needed
                      to be reassembled at this entity."
              ::= { ip 14 }

          ipReasmOKs OBJECT-TYPE
              SYNTAX  Counter
              ACCESS  read-only
              STATUS  mandatory
              DESCRIPTION
                      "The number of IP datagrams successfully re-
                      assembled."
              ::= { ip 15 }

          ipReasmFails OBJECT-TYPE
              SYNTAX  Counter
              ACCESS  read-only
              STATUS  mandatory
              DESCRIPTION
                      "The number of failures detected by the IP re-
                      assembly algorithm (for whatever reason: timed
                      out, errors, etc).  Note that this is not
                      necessarily a count of discarded IP fragments
                      since some algorithms (notably the algorithm in
                      RFC 815) can lose track of the number of fragments
                      by combining them as they are received."
              ::= { ip 16 }

          ipFragOKs OBJECT-TYPE
              SYNTAX  Counter
              ACCESS  read-only
              STATUS  mandatory
              DESCRIPTION
                      "The number of IP datagrams that have been
                      successfully fragmented at this entity."
              ::= { ip 17 }

          ipFragFails OBJECT-TYPE
              SYNTAX  Counter
              ACCESS  read-only
              STATUS  mandatory
              DESCRIPTION
                      "The number of IP datagrams that have been
                      discarded because they needed to be fragmented at
                      this entity but could not be, e.g., because their
                      Don't Fragment flag was set."
              ::= { ip 18 }

          ipFragCreates OBJECT-TYPE
              SYNTAX  Counter
              ACCESS  read-only
              STATUS  mandatory
              DESCRIPTION
                      "The number of IP datagram fragments that have
                      been generated as a result of fragmentation at
                      this entity."
              ::= { ip 19 }

          -- the IP address table

          -- The IP address table contains this entity's IP addressing
          -- information.

          ipAddrTable OBJECT-TYPE
              SYNTAX  SEQUENCE OF IpAddrEntry
              ACCESS  not-accessible
              STATUS  mandatory
              DESCRIPTION
                      "The table of addressing information relevant to
                      this entity's IP addresses."
              ::= { ip 20 }

          ipAddrEntry OBJECT-TYPE
              SYNTAX  IpAddrEntry
              ACCESS  not-accessible
              STATUS  mandatory
              DESCRIPTION
                      "The addressing information for one of this
                      entity's IP addresses."
              INDEX   { ipAdEntAddr }
              ::= { ipAddrTable 1 }

          IpAddrEntry ::=
              SEQUENCE {
                  ipAdEntAddr
                      IpAddress,
                  ipAdEntIfIndex
                      INTEGER,
                  ipAdEntNetMask
                      IpAddress,
                  ipAdEntBcastAddr
                      INTEGER,
                  ipAdEntReasmMaxSize
                      INTEGER (0..65535)
              }

          ipAdEntAddr OBJECT-TYPE
              SYNTAX  IpAddress
              ACCESS  read-only
              STATUS  mandatory
              DESCRIPTION
                      "The IP address to which this entry's addressing
                      information pertains."
              ::= { ipAddrEntry 1 }

          ipAdEntIfIndex OBJECT-TYPE
              SYNTAX  INTEGER
              ACCESS  read-only
              STATUS  mandatory
              DESCRIPTION
                      "The index value which uniquely identifies the
                      interface to which this entry is applicable.  The
                      interface identified by a particular value of this
                      index is the same interface as identified by the
                      same value of ifIndex."
              ::= { ipAddrEntry 2 }

          ipAdEntNetMask OBJECT-TYPE
              SYNTAX  IpAddress
              ACCESS  read-only
              STATUS  mandatory
              DESCRIPTION
                      "The subnet mask associated with the IP address of
                      this entry.  The value of the mask is an IP
                      address with all the network bits set to 1 and all
                      the hosts bits set to 0."
              ::= { ipAddrEntry 3 }

          ipAdEntBcastAddr OBJECT-TYPE
              SYNTAX  INTEGER
              ACCESS  read-only
              STATUS  mandatory
              DESCRIPTION
                      "The value of the least-significant bit in the IP
                      broadcast address used for sending datagrams on
                      the (logical) interface associated with the IP
                      address of this entry.  For example, when the
                      Internet standard all-ones broadcast address is
                      used, the value will be 1.  This value applies to
                      both the subnet and network broadcasts addresses
                      used by the entity on this (logical) interface."
              ::= { ipAddrEntry 4 }

          ipAdEntReasmMaxSize OBJECT-TYPE
              SYNTAX  INTEGER (0..65535)
              ACCESS  read-only
              STATUS  mandatory
              DESCRIPTION
                      "The size of the largest IP datagram which this
                      entity can re-assemble from incoming IP fragmented
                      datagrams received on this interface."
              ::= { ipAddrEntry 5 }

          -- the IP routing table

          -- The IP routing table contains an entry for each route
          -- presently known to this entity.

          ipRouteTable OBJECT-TYPE
              SYNTAX  SEQUENCE OF IpRouteEntry
              ACCESS  not-accessible
              STATUS  mandatory
              DESCRIPTION
                      "This entity's IP Routing table."
              ::= { ip 21 }

          ipRouteEntry OBJECT-TYPE
              SYNTAX  IpRouteEntry
              ACCESS  not-accessible
              STATUS  mandatory
              DESCRIPTION
                      "A route to a particular destination."
              INDEX   { ipRouteDest }
              ::= { ipRouteTable 1 }

          IpRouteEntry ::=
              SEQUENCE {
                  ipRouteDest
                      IpAddress,
                  ipRouteIfIndex
                      INTEGER,
                  ipRouteMetric1
                      INTEGER,
                  ipRouteMetric2
                      INTEGER,
                  ipRouteMetric3
                      INTEGER,
                  ipRouteMetric4
                      INTEGER,
                  ipRouteNextHop
                      IpAddress,
                  ipRouteType
                      INTEGER,
                  ipRouteProto
                      INTEGER,
                  ipRouteAge
                      INTEGER,
                  ipRouteMask
                      IpAddress,
                  ipRouteMetric5
                      INTEGER,
                  ipRouteInfo
                      OBJECT IDENTIFIER
              }

          ipRouteDest OBJECT-TYPE
              SYNTAX  IpAddress
              ACCESS  read-write
              STATUS  mandatory
              DESCRIPTION
                      "The destination IP address of this route.  An
                      entry with a value of 0.0.0.0 is considered a
                      default route.  Multiple routes to a single
                      destination can appear in the table, but access to
                      such multiple entries is dependent on the table-
                      access mechanisms defined by the network
                      management protocol in use."
              ::= { ipRouteEntry 1 }

          ipRouteIfIndex OBJECT-TYPE
              SYNTAX  INTEGER
              ACCESS  read-write
              STATUS  mandatory
              DESCRIPTION
                      "The index value which uniquely identifies the
                      local interface through which the next hop of this
                      route should be reached.  The interface identified
                      by a particular value of this index is the same
                      interface as identified by the same value of
                      ifIndex."
              ::= { ipRouteEntry 2 }

          ipRouteMetric1 OBJECT-TYPE
              SYNTAX  INTEGER
              ACCESS  read-write
              STATUS  mandatory
              DESCRIPTION
                      "The primary routing metric for this route.  The
                      semantics of this metric are determined by the
                      routing-protocol specified in the route's
                      ipRouteProto value.  If this metric is not used,
                      its value should be set to -1."
              ::= { ipRouteEntry 3 }

          ipRouteMetric2 OBJECT-TYPE
              SYNTAX  INTEGER
              ACCESS  read-write
              STATUS  mandatory
              DESCRIPTION
                      "An alternate routing metric for this route.  The
                      semantics of this metric are determined by the
                      routing-protocol specified in the route's
                      ipRouteProto value.  If this metric is not used,
                      its value should be set to -1."
              ::= { ipRouteEntry 4 }

          ipRouteMetric3 OBJECT-TYPE
              SYNTAX  INTEGER
              ACCESS  read-write
              STATUS  mandatory
              DESCRIPTION
                      "An alternate routing metric for this route.  The
                      semantics of this metric are determined by the
                      routing-protocol specified in the route's
                      ipRouteProto value.  If this metric is not used,
                      its value should be set to -1."
              ::= { ipRouteEntry 5 }

          ipRouteMetric4 OBJECT-TYPE
              SYNTAX  INTEGER
              ACCESS  read-write
              STATUS  mandatory
              DESCRIPTION
                      "An alternate routing metric for this route.  The
                      semantics of this metric are determined by the
                      routing-protocol specified in the route's
                      ipRouteProto value.  If this metric is not used,
                      its value should be set to -1."
              ::= { ipRouteEntry 6 }

          ipRouteNextHop OBJECT-TYPE
              SYNTAX  IpAddress
              ACCESS  read-write
              STATUS  mandatory
              DESCRIPTION
                      "The IP address of the next hop of this route.
                      (In the case of a route bound to an interface
                      which is realized via a broadcast media, the value
                      of this field is the agent's IP address on that
                      interface.)"
              ::= { ipRouteEntry 7 }

          ipRouteType OBJECT-TYPE
              SYNTAX  INTEGER {
                          other(1),        -- none of the following

                          invalid(2),      -- an invalidated route
                                           -- route to directly

                          direct(3),       -- connected (sub-)network

                                           -- route to a non-local
                          indirect(4)      -- host/network/sub-network
                      }
              ACCESS  read-write
              STATUS  mandatory
              DESCRIPTION
                      "The type of route.  Note that the values
                      direct(3) and indirect(4) refer to the notion of
                      direct and indirect routing in the IP
                      architecture.

                      Setting this object to the value invalid(2) has
                      the effect of invalidating the corresponding entry
                      in the ipRouteTable object.  That is, it
                      effectively dissasociates the destination
                      identified with said entry from the route
                      identified with said entry.  It is an
                      implementation-specific matter as to whether the
                      agent removes an invalidated entry from the table.
                      Accordingly, management stations must be prepared
                      to receive tabular information from agents that
                      corresponds to entries not currently in use.
                      Proper interpretation of such entries requires
                      examination of the relevant ipRouteType object."
              ::= { ipRouteEntry 8 }

          ipRouteProto OBJECT-TYPE
              SYNTAX  INTEGER {
                          other(1),       -- none of the following

                                          -- non-protocol information,
                                          -- e.g., manually configured
                          local(2),       -- entries

                                          -- set via a network
                          netmgmt(3),     -- management protocol

                                          -- obtained via ICMP,
                          icmp(4),        -- e.g., Redirect

                                          -- the remaining values are
                                          -- all gateway routing
                                          -- protocols
                          egp(5),
                          ggp(6),
                          hello(7),
                          rip(8),
                          is-is(9),
                          es-is(10),
                          ciscoIgrp(11),
                          bbnSpfIgp(12),
                          ospf(13),
                          bgp(14)
                      }
              ACCESS  read-only
              STATUS  mandatory
              DESCRIPTION
                      "The routing mechanism via which this route was
                      learned.  Inclusion of values for gateway routing
                      protocols is not intended to imply that hosts
                      should support those protocols."
              ::= { ipRouteEntry 9 }

          ipRouteAge OBJECT-TYPE
              SYNTAX  INTEGER
              ACCESS  read-write
              STATUS  mandatory
              DESCRIPTION
                      "The number of seconds since this route was last
                      updated or otherwise determined to be correct.
                      Note that no semantics of `too old' can be implied
                      except through knowledge of the routing protocol
                      by which the route was learned."
              ::= { ipRouteEntry 10 }

          ipRouteMask OBJECT-TYPE
              SYNTAX  IpAddress
              ACCESS  read-write
              STATUS  mandatory
              DESCRIPTION
                      "Indicate the mask to be logical-ANDed with the
                      destination address before being compared to the
                      value in the ipRouteDest field.  For those systems
                      that do not support arbitrary subnet masks, an
                      agent constructs the value of the ipRouteMask by
                      determining whether the value of the correspondent
                      ipRouteDest field belong to a class-A, B, or C
                      network, and then using one of:

                           mask           network
                           255.0.0.0      class-A
                           255.255.0.0    class-B
                           255.255.255.0  class-C

                      If the value of the ipRouteDest is 0.0.0.0 (a
                      default route), then the mask value is also
                      0.0.0.0.  It should be noted that all IP routing
                      subsystems implicitly use this mechanism."
              ::= { ipRouteEntry 11 }

          ipRouteMetric5 OBJECT-TYPE
              SYNTAX  INTEGER
              ACCESS  read-write
              STATUS  mandatory
              DESCRIPTION
                      "An alternate routing metric for this route.  The
                      semantics of this metric are determined by the
                      routing-protocol specified in the route's
                      ipRouteProto value.  If this metric is not used,
                      its value should be set to -1."
              ::= { ipRouteEntry 12 }

          ipRouteInfo OBJECT-TYPE
              SYNTAX  OBJECT IDENTIFIER
              ACCESS  read-only
              STATUS  mandatory
              DESCRIPTION
                      "A reference to MIB definitions specific to the
                      particular routing protocol which is responsible
                      for this route, as determined by the value
                      specified in the route's ipRouteProto value.  If
                      this information is not present, its value should
                      be set to the OBJECT IDENTIFIER { 0 0 }, which is
                      a syntatically valid object identifier, and any
                      conformant implementation of ASN.1 and BER must be
                      able to generate and recognize this value."
              ::= { ipRouteEntry 13 }


          -- the IP Address Translation table

          -- The IP address translation table contain the IpAddress to
          -- `physical' address equivalences.  Some interfaces do not
          -- use translation tables for determining address
          -- equivalences (e.g., DDN-X.25 has an algorithmic method);
          -- if all interfaces are of this type, then the Address
          -- Translation table is empty, i.e., has zero entries.

          ipNetToMediaTable OBJECT-TYPE
              SYNTAX  SEQUENCE OF IpNetToMediaEntry
              ACCESS  not-accessible
              STATUS  mandatory
              DESCRIPTION
                      "The IP Address Translation table used for mapping
                      from IP addresses to physical addresses."
              ::= { ip 22 }

          ipNetToMediaEntry OBJECT-TYPE
              SYNTAX  IpNetToMediaEntry
              ACCESS  not-accessible
              STATUS  mandatory
              DESCRIPTION
                      "Each entry contains one IpAddress to `physical'
                      address equivalence."
              INDEX   { ipNetToMediaIfIndex,
                        ipNetToMediaNetAddress }
              ::= { ipNetToMediaTable 1 }

          IpNetToMediaEntry ::=
              SEQUENCE {
                  ipNetToMediaIfIndex
                      INTEGER,
                  ipNetToMediaPhysAddress
                      PhysAddress,
                  ipNetToMediaNetAddress
                      IpAddress,
                  ipNetToMediaType
                      INTEGER
              }

          ipNetToMediaIfIndex OBJECT-TYPE
              SYNTAX  INTEGER
              ACCESS  read-write
              STATUS  mandatory
              DESCRIPTION
                      "The interface on which this entry's equivalence
                      is effective.  The interface identified by a
                      particular value of this index is the same
                      interface as identified by the same value of
                      ifIndex."
              ::= { ipNetToMediaEntry 1 }

          ipNetToMediaPhysAddress OBJECT-TYPE
              SYNTAX  PhysAddress
              ACCESS  read-write
              STATUS  mandatory
              DESCRIPTION
                      "The media-dependent `physical' address."
              ::= { ipNetToMediaEntry 2 }

          ipNetToMediaNetAddress OBJECT-TYPE
              SYNTAX  IpAddress
              ACCESS  read-only
              STATUS  mandatory
              DESCRIPTION
                      "The IpAddress corresponding to the media-
                      dependent `physical' address."
              ::= { ipNetToMediaEntry 3 }

          ipNetToMediaType OBJECT-TYPE
              SYNTAX  INTEGER {
                          other(1),        -- none of the following
                          invalid(2),      -- an invalidated mapping
                          dynamic(3),
                          static(4)
                      }
              ACCESS  read-write
              STATUS  mandatory
              DESCRIPTION
                      "The type of mapping.

                      Setting this object to the value invalid(2) has
                      the effect of invalidating the corresponding entry
                      in the ipNetToMediaTable.  That is, it effectively
                      dissasociates the interface identified with said
                      entry from the mapping identified with said entry.
                      It is an implementation-specific matter as to
                      whether the agent removes an invalidated entry
                      from the table.  Accordingly, management stations
                      must be prepared to receive tabular information
                      from agents that corresponds to entries not
                      currently in use.  Proper interpretation of such
                      entries requires examination of the relevant
                      ipNetToMediaType object."
              ::= { ipNetToMediaEntry 4 }


          -- additional IP objects

          ipRoutingDiscards OBJECT-TYPE
              SYNTAX  Counter
              ACCESS  read-only
              STATUS  mandatory
              DESCRIPTION
                      "The number of routing entries which were chosen
                      to be discarded even though they are valid.  One
                      possible reason for discarding such an entry could
                      be to free-up buffer space for other routing
                      entries."
              ::= { ip 23 }


          -- the ICMP group

          -- Implementation of the ICMP group is mandatory for all
          -- systems.

          icmpInMsgs OBJECT-TYPE
              SYNTAX  Counter
              ACCESS  read-only
              STATUS  mandatory
              DESCRIPTION
                      "The total number of ICMP messages which the
                      entity received.  Note that this counter includes
                      all those counted by icmpInErrors."
              ::= { icmp 1 }

          icmpInErrors OBJECT-TYPE
              SYNTAX  Counter
              ACCESS  read-only
              STATUS  mandatory
              DESCRIPTION
                      "The number of ICMP messages which the entity
                      received but determined as having ICMP-specific
                      errors (bad ICMP checksums, bad length, etc.)."
              ::= { icmp 2 }

          icmpInDestUnreachs OBJECT-TYPE
              SYNTAX  Counter
              ACCESS  read-only
              STATUS  mandatory
              DESCRIPTION
                      "The number of ICMP Destination Unreachable
                      messages received."
              ::= { icmp 3 }

          icmpInTimeExcds OBJECT-TYPE
              SYNTAX  Counter
              ACCESS  read-only
              STATUS  mandatory
              DESCRIPTION
                      "The number of ICMP Time Exceeded messages
                      received."
              ::= { icmp 4 }

          icmpInParmProbs OBJECT-TYPE
              SYNTAX  Counter
              ACCESS  read-only
              STATUS  mandatory
              DESCRIPTION
                      "The number of ICMP Parameter Problem messages
                      received."
              ::= { icmp 5 }

          icmpInSrcQuenchs OBJECT-TYPE
              SYNTAX  Counter
              ACCESS  read-only
              STATUS  mandatory
              DESCRIPTION
                      "The number of ICMP Source Quench messages
                      received."
              ::= { icmp 6 }

          icmpInRedirects OBJECT-TYPE
              SYNTAX  Counter
              ACCESS  read-only
              STATUS  mandatory
              DESCRIPTION
                      "The number of ICMP Redirect messages received."
              ::= { icmp 7 }

          icmpInEchos OBJECT-TYPE
              SYNTAX  Counter
              ACCESS  read-only
              STATUS  mandatory
              DESCRIPTION
                      "The number of ICMP Echo (request) messages
                      received."
              ::= { icmp 8 }

          icmpInEchoReps OBJECT-TYPE
              SYNTAX  Counter
              ACCESS  read-only
              STATUS  mandatory
              DESCRIPTION
                      "The number of ICMP Echo Reply messages received."
              ::= { icmp 9 }

          icmpInTimestamps OBJECT-TYPE
              SYNTAX  Counter
              ACCESS  read-only
              STATUS  mandatory
              DESCRIPTION
                      "The number of ICMP Timestamp (request) messages
                      received."
              ::= { icmp 10 }

          icmpInTimestampReps OBJECT-TYPE
              SYNTAX  Counter
              ACCESS  read-only
              STATUS  mandatory
              DESCRIPTION
                      "The number of ICMP Timestamp Reply messages
                      received."
              ::= { icmp 11 }

          icmpInAddrMasks OBJECT-TYPE
              SYNTAX  Counter
              ACCESS  read-only
              STATUS  mandatory
              DESCRIPTION
                      "The number of ICMP Address Mask Request messages
                      received."
              ::= { icmp 12 }

          icmpInAddrMaskReps OBJECT-TYPE
              SYNTAX  Counter
              ACCESS  read-only
              STATUS  mandatory
              DESCRIPTION
                      "The number of ICMP Address Mask Reply messages
                      received."
              ::= { icmp 13 }

          icmpOutMsgs OBJECT-TYPE
              SYNTAX  Counter
              ACCESS  read-only
              STATUS  mandatory
              DESCRIPTION
                      "The total number of ICMP messages which this
                      entity attempted to send.  Note that this counter
                      includes all those counted by icmpOutErrors."
              ::= { icmp 14 }

          icmpOutErrors OBJECT-TYPE
              SYNTAX  Counter
              ACCESS  read-only
              STATUS  mandatory
              DESCRIPTION
                      "The number of ICMP messages which this entity did
                      not send due to problems discovered within ICMP
                      such as a lack of buffers.  This value should not
                      include errors discovered outside the ICMP layer
                      such as the inability of IP to route the resultant
                      datagram.  In some implementations there may be no
                      types of error which contribute to this counter's
                      value."
              ::= { icmp 15 }

          icmpOutDestUnreachs OBJECT-TYPE
              SYNTAX  Counter
              ACCESS  read-only
              STATUS  mandatory
              DESCRIPTION
                      "The number of ICMP Destination Unreachable
                      messages sent."
              ::= { icmp 16 }

          icmpOutTimeExcds OBJECT-TYPE
              SYNTAX  Counter
              ACCESS  read-only
              STATUS  mandatory
              DESCRIPTION
                      "The number of ICMP Time Exceeded messages sent."
              ::= { icmp 17 }

          icmpOutParmProbs OBJECT-TYPE
              SYNTAX  Counter
              ACCESS  read-only
              STATUS  mandatory
              DESCRIPTION
                      "The number of ICMP Parameter Problem messages
                      sent."
              ::= { icmp 18 }

          icmpOutSrcQuenchs OBJECT-TYPE
              SYNTAX  Counter
              ACCESS  read-only
              STATUS  mandatory
              DESCRIPTION
                      "The number of ICMP Source Quench messages sent."
              ::= { icmp 19 }

          icmpOutRedirects OBJECT-TYPE
              SYNTAX  Counter
              ACCESS  read-only
              STATUS  mandatory
              DESCRIPTION
                      "The number of ICMP Redirect messages sent.  For a
                      host, this object will always be zero, since hosts
                      do not send redirects."
              ::= { icmp 20 }

          icmpOutEchos OBJECT-TYPE
              SYNTAX  Counter
              ACCESS  read-only
              STATUS  mandatory
              DESCRIPTION
                      "The number of ICMP Echo (request) messages sent."
              ::= { icmp 21 }

          icmpOutEchoReps OBJECT-TYPE
              SYNTAX  Counter
              ACCESS  read-only
              STATUS  mandatory
              DESCRIPTION
                      "The number of ICMP Echo Reply messages sent."
              ::= { icmp 22 }

          icmpOutTimestamps OBJECT-TYPE
              SYNTAX  Counter
              ACCESS  read-only
              STATUS  mandatory
              DESCRIPTION
                      "The number of ICMP Timestamp (request) messages
                      sent."
              ::= { icmp 23 }

          icmpOutTimestampReps OBJECT-TYPE
              SYNTAX  Counter
              ACCESS  read-only
              STATUS  mandatory
              DESCRIPTION
                      "The number of ICMP Timestamp Reply messages
                      sent."
              ::= { icmp 24 }

          icmpOutAddrMasks OBJECT-TYPE
              SYNTAX  Counter
              ACCESS  read-only
              STATUS  mandatory
              DESCRIPTION
                      "The number of ICMP Address Mask Request messages
                      sent."
              ::= { icmp 25 }

          icmpOutAddrMaskReps OBJECT-TYPE
              SYNTAX  Counter
              ACCESS  read-only
              STATUS  mandatory
              DESCRIPTION
                      "The number of ICMP Address Mask Reply messages
                      sent."
              ::= { icmp 26 }


          -- the TCP group

          -- Implementation of the TCP group is mandatory for all
          -- systems that implement the TCP.

          -- Note that instances of object types that represent
          -- information about a particular TCP connection are
          -- transient; they persist only as long as the connection
          -- in question.

          tcpRtoAlgorithm OBJECT-TYPE
              SYNTAX  INTEGER {
                          other(1),    -- none of the following

                          constant(2), -- a constant rto
                          rsre(3),     -- MIL-STD-1778, Appendix B
                          vanj(4)      -- Van Jacobson's algorithm [10]
                      }
              ACCESS  read-only
              STATUS  mandatory
              DESCRIPTION
                      "The algorithm used to determine the timeout value
                      used for retransmitting unacknowledged octets."
              ::= { tcp 1 }

          tcpRtoMin OBJECT-TYPE
              SYNTAX  INTEGER
              ACCESS  read-only
              STATUS  mandatory
              DESCRIPTION
                      "The minimum value permitted by a TCP
                      implementation for the retransmission timeout,
                      measured in milliseconds.  More refined semantics
                      for objects of this type depend upon the algorithm
                      used to determine the retransmission timeout.  In
                      particular, when the timeout algorithm is rsre(3),
                      an object of this type has the semantics of the
                      LBOUND quantity described in RFC 793."
              ::= { tcp 2 }


          tcpRtoMax OBJECT-TYPE
              SYNTAX  INTEGER
              ACCESS  read-only
              STATUS  mandatory
              DESCRIPTION
                      "The maximum value permitted by a TCP
                      implementation for the retransmission timeout,
                      measured in milliseconds.  More refined semantics
                      for objects of this type depend upon the algorithm
                      used to determine the retransmission timeout.  In
                      particular, when the timeout algorithm is rsre(3),
                      an object of this type has the semantics of the
                      UBOUND quantity described in RFC 793."
              ::= { tcp 3 }

          tcpMaxConn OBJECT-TYPE
              SYNTAX  INTEGER
              ACCESS  read-only
              STATUS  mandatory
              DESCRIPTION
                      "The limit on the total number of TCP connections
                      the entity can support.  In entities where the
                      maximum number of connections is dynamic, this
                      object should contain the value -1."
              ::= { tcp 4 }

          tcpActiveOpens OBJECT-TYPE
              SYNTAX  Counter
              ACCESS  read-only
              STATUS  mandatory
              DESCRIPTION
                      "The number of times TCP connections have made a
                      direct transition to the SYN-SENT state from the
                      CLOSED state."
              ::= { tcp 5 }

          tcpPassiveOpens OBJECT-TYPE
              SYNTAX  Counter
              ACCESS  read-only
              STATUS  mandatory
              DESCRIPTION
                      "The number of times TCP connections have made a
                      direct transition to the SYN-RCVD state from the
                      LISTEN state."
              ::= { tcp 6 }

          tcpAttemptFails OBJECT-TYPE
              SYNTAX  Counter
              ACCESS  read-only
              STATUS  mandatory
              DESCRIPTION
                      "The number of times TCP connections have made a
                      direct transition to the CLOSED state from either
                      the SYN-SENT state or the SYN-RCVD state, plus the
                      number of times TCP connections have made a direct
                      transition to the LISTEN state from the SYN-RCVD
                      state."
              ::= { tcp 7 }

          tcpEstabResets OBJECT-TYPE
              SYNTAX  Counter
              ACCESS  read-only
              STATUS  mandatory
              DESCRIPTION
                      "The number of times TCP connections have made a
                      direct transition to the CLOSED state from either
                      the ESTABLISHED state or the CLOSE-WAIT state."
              ::= { tcp 8 }

          tcpCurrEstab OBJECT-TYPE
              SYNTAX  Gauge
              ACCESS  read-only
              STATUS  mandatory
              DESCRIPTION
                      "The number of TCP connections for which the
                      current state is either ESTABLISHED or CLOSE-
                      WAIT."
              ::= { tcp 9 }

          tcpInSegs OBJECT-TYPE
              SYNTAX  Counter
              ACCESS  read-only
              STATUS  mandatory
              DESCRIPTION
                      "The total number of segments received, including
                      those received in error.  This count includes
                      segments received on currently established
                      connections."
              ::= { tcp 10 }

          tcpOutSegs OBJECT-TYPE
              SYNTAX  Counter
              ACCESS  read-only
              STATUS  mandatory
              DESCRIPTION
                      "The total number of segments sent, including
                      those on current connections but excluding those
                      containing only retransmitted octets."
              ::= { tcp 11 }

          tcpRetransSegs OBJECT-TYPE
              SYNTAX  Counter
              ACCESS  read-only
              STATUS  mandatory
              DESCRIPTION
                      "The total number of segments retransmitted - that
                      is, the number of TCP segments transmitted
                      containing one or more previously transmitted
                      octets."
              ::= { tcp 12 }


          -- the TCP Connection table

          -- The TCP connection table contains information about this
          -- entity's existing TCP connections.

          tcpConnTable OBJECT-TYPE
              SYNTAX  SEQUENCE OF TcpConnEntry
              ACCESS  not-accessible
              STATUS  mandatory
              DESCRIPTION
                      "A table containing TCP connection-specific
                      information."
              ::= { tcp 13 }

          tcpConnEntry OBJECT-TYPE
              SYNTAX  TcpConnEntry
              ACCESS  not-accessible
              STATUS  mandatory
              DESCRIPTION
                      "Information about a particular current TCP
                      connection.  An object of this type is transient,
                      in that it ceases to exist when (or soon after)
                      the connection makes the transition to the CLOSED
                      state."
              INDEX   { tcpConnLocalAddress,
                        tcpConnLocalPort,
                        tcpConnRemAddress,
                        tcpConnRemPort }
              ::= { tcpConnTable 1 }

          TcpConnEntry ::=
              SEQUENCE {
                  tcpConnState
                      INTEGER,
                  tcpConnLocalAddress
                      IpAddress,
                  tcpConnLocalPort
                      INTEGER (0..65535),
                  tcpConnRemAddress
                      IpAddress,
                  tcpConnRemPort
                      INTEGER (0..65535)
              }

          tcpConnState OBJECT-TYPE
              SYNTAX  INTEGER {
                          closed(1),
                          listen(2),
                          synSent(3),
                          synReceived(4),
                          established(5),
                          finWait1(6),
                          finWait2(7),
                          closeWait(8),
                          lastAck(9),
                          closing(10),
                          timeWait(11),
                          deleteTCB(12)
                      }
              ACCESS  read-write
              STATUS  mandatory
              DESCRIPTION
                      "The state of this TCP connection.

                      The only value which may be set by a management
                      station is deleteTCB(12).  Accordingly, it is
                      appropriate for an agent to return a `badValue'
                      response if a management station attempts to set
                      this object to any other value.

                      If a management station sets this object to the
                      value deleteTCB(12), then this has the effect of
                      deleting the TCB (as defined in RFC 793) of the
                      corresponding connection on the managed node,
                      resulting in immediate termination of the
                      connection.

                      As an implementation-specific option, a RST
                      segment may be sent from the managed node to the
                      other TCP endpoint (note however that RST segments
                      are not sent reliably)."
              ::= { tcpConnEntry 1 }

          tcpConnLocalAddress OBJECT-TYPE
              SYNTAX  IpAddress
              ACCESS  read-only
              STATUS  mandatory
              DESCRIPTION
                      "The local IP address for this TCP connection.  In
                      the case of a connection in the listen state which
                      is willing to accept connections for any IP
                      interface associated with the node, the value
                      0.0.0.0 is used."
              ::= { tcpConnEntry 2 }

          tcpConnLocalPort OBJECT-TYPE
              SYNTAX  INTEGER (0..65535)
              ACCESS  read-only
              STATUS  mandatory
              DESCRIPTION
                      "The local port number for this TCP connection."
              ::= { tcpConnEntry 3 }

          tcpConnRemAddress OBJECT-TYPE
              SYNTAX  IpAddress
              ACCESS  read-only
              STATUS  mandatory
              DESCRIPTION
                      "The remote IP address for this TCP connection."
              ::= { tcpConnEntry 4 }

          tcpConnRemPort OBJECT-TYPE
              SYNTAX  INTEGER (0..65535)
              ACCESS  read-only
              STATUS  mandatory
              DESCRIPTION
                      "The remote port number for this TCP connection."
              ::= { tcpConnEntry 5 }


          -- additional TCP objects

          tcpInErrs OBJECT-TYPE
              SYNTAX  Counter
              ACCESS  read-only
              STATUS  mandatory
              DESCRIPTION
                      "The total number of segments received in error
                      (e.g., bad TCP checksums)."
              ::= { tcp 14 }

          tcpOutRsts OBJECT-TYPE
              SYNTAX  Counter
              ACCESS  read-only
              STATUS  mandatory
              DESCRIPTION
                      "The number of TCP segments sent containing the
                      RST flag."
              ::= { tcp 15 }


          -- the UDP group

          -- Implementation of the UDP group is mandatory for all
          -- systems which implement the UDP.

          udpInDatagrams OBJECT-TYPE
              SYNTAX  Counter
              ACCESS  read-only
              STATUS  mandatory
              DESCRIPTION
                      "The total number of UDP datagrams delivered to
                      UDP users."
              ::= { udp 1 }

          udpNoPorts OBJECT-TYPE
              SYNTAX  Counter
              ACCESS  read-only
              STATUS  mandatory
              DESCRIPTION
                      "The total number of received UDP datagrams for
                      which there was no application at the destination
                      port."
              ::= { udp 2 }

          udpInErrors OBJECT-TYPE
              SYNTAX  Counter
              ACCESS  read-only
              STATUS  mandatory
              DESCRIPTION
                      "The number of received UDP datagrams that could
                      not be delivered for reasons other than the lack
                      of an application at the destination port."
              ::= { udp 3 }

          udpOutDatagrams OBJECT-TYPE
              SYNTAX  Counter
              ACCESS  read-only
              STATUS  mandatory
              DESCRIPTION
                      "The total number of UDP datagrams sent from this
                      entity."
              ::= { udp 4 }


          -- the UDP Listener table

          -- The UDP listener table contains information about this
          -- entity's UDP end-points on which a local application is
          -- currently accepting datagrams.

          udpTable OBJECT-TYPE
              SYNTAX  SEQUENCE OF UdpEntry
              ACCESS  not-accessible
              STATUS  mandatory
              DESCRIPTION
                      "A table containing UDP listener information."
              ::= { udp 5 }

          udpEntry OBJECT-TYPE
              SYNTAX  UdpEntry
              ACCESS  not-accessible
              STATUS  mandatory
              DESCRIPTION
                      "Information about a particular current UDP
                      listener."
              INDEX   { udpLocalAddress, udpLocalPort }
              ::= { udpTable 1 }

          UdpEntry ::=
              SEQUENCE {
                  udpLocalAddress
                      IpAddress,
                  udpLocalPort
                      INTEGER (0..65535)
              }

          udpLocalAddress OBJECT-TYPE
              SYNTAX  IpAddress
              ACCESS  read-only
              STATUS  mandatory
              DESCRIPTION
                      "The local IP address for this UDP listener.  In
                      the case of a UDP listener which is willing to
                      accept datagrams for any IP interface associated
                      with the node, the value 0.0.0.0 is used."
              ::= { udpEntry 1 }

          udpLocalPort OBJECT-TYPE
              SYNTAX  INTEGER (0..65535)
              ACCESS  read-only
              STATUS  mandatory
              DESCRIPTION
                      "The local port number for this UDP listener."
              ::= { udpEntry 2 }


          -- the EGP group

          -- Implementation of the EGP group is mandatory for all
          -- systems which implement the EGP.






          -- the EGP Neighbor table

          -- The EGP neighbor table contains information about this
          -- entity's EGP neighbors.




















          -- additional EGP objects



          -- the Transmission group

          -- Based on the transmission media underlying each interface
          -- on a system, the corresponding portion of the Transmission
          -- group is mandatory for that system.

          -- When Internet-standard definitions for managing
          -- transmission media are defined, the transmission group is
          -- used to provide a prefix for the names of those objects.

          -- Typically, such definitions reside in the experimental
          -- portion of the MIB until they are "proven", then as a
          -- part of the Internet standardization process, the
          -- definitions are accordingly elevated and a new object
          -- identifier, under the transmission group is defined. By
          -- convention, the name assigned is:
          --
          --     type OBJECT IDENTIFIER    ::= { transmission number }
          --
          -- where "type" is the symbolic value used for the media in
          -- the ifType column of the ifTable object, and "number" is
          -- the actual integer value corresponding to the symbol.


          -- the SNMP group

          -- Implementation of the SNMP group is mandatory for all
          -- systems which support an SNMP protocol entity.  Some of
          -- the objects defined below will be zero-valued in those
          -- SNMP implementations that are optimized to support only
          -- those functions specific to either a management agent or
          -- a management station.  In particular, it should be
          -- observed that the objects below refer to an SNMP entity,
          -- and there may be several SNMP entities residing on a
          -- managed node (e.g., if the node is hosting acting as
          -- a management station).

          snmpInPkts OBJECT-TYPE
              SYNTAX  Counter
              ACCESS  read-only
              STATUS  mandatory
              DESCRIPTION
                      "The total number of Messages delivered to the
                      SNMP entity from the transport service."
              ::= { snmp 1 }

          snmpOutPkts OBJECT-TYPE
              SYNTAX  Counter
              ACCESS  read-only
              STATUS  mandatory
              DESCRIPTION
                      "The total number of SNMP Messages which were
                      passed from the SNMP protocol entity to the
                      transport service."
              ::= { snmp 2 }

          snmpInBadVersions OBJECT-TYPE
              SYNTAX  Counter
              ACCESS  read-only
              STATUS  mandatory
              DESCRIPTION
                      "The total number of SNMP Messages which were
                      delivered to the SNMP protocol entity and were for
                      an unsupported SNMP version."
              ::= { snmp 3 }

          snmpInBadCommunityNames OBJECT-TYPE
              SYNTAX  Counter
              ACCESS  read-only
              STATUS  mandatory
              DESCRIPTION
                      "The total number of SNMP Messages delivered to
                      the SNMP protocol entity which used a SNMP
                      community name not known to said entity."
              ::= { snmp 4 }

          snmpInBadCommunityUses OBJECT-TYPE
              SYNTAX  Counter
              ACCESS  read-only
              STATUS  mandatory
              DESCRIPTION
                      "The total number of SNMP Messages delivered to
                      the SNMP protocol entity which represented an SNMP
                      operation which was not allowed by the SNMP
                      community named in the Message."
              ::= { snmp 5 }

          snmpInASNParseErrs OBJECT-TYPE
              SYNTAX  Counter
              ACCESS  read-only
              STATUS  mandatory
              DESCRIPTION
                      "The total number of ASN.1 or BER errors
                      encountered by the SNMP protocol entity when
                      decoding received SNMP Messages."
              ::= { snmp 6 }

          -- { snmp 7 } is not used

          snmpInTooBigs OBJECT-TYPE
              SYNTAX  Counter
              ACCESS  read-only
              STATUS  mandatory
              DESCRIPTION
                      "The total number of SNMP PDUs which were
                      delivered to the SNMP protocol entity and for
                      which the value of the error-status field is
                      `tooBig'."
              ::= { snmp 8 }

          snmpInNoSuchNames OBJECT-TYPE
              SYNTAX  Counter
              ACCESS  read-only
              STATUS  mandatory
              DESCRIPTION
                      "The total number of SNMP PDUs which were
                      delivered to the SNMP protocol entity and for
                      which the value of the error-status field is
                      `noSuchName'."
              ::= { snmp 9 }

          snmpInBadValues OBJECT-TYPE
              SYNTAX  Counter
              ACCESS  read-only
              STATUS  mandatory
              DESCRIPTION
                      "The total number of SNMP PDUs which were
                      delivered to the SNMP protocol entity and for
                      which the value of the error-status field is
                      `badValue'."
              ::= { snmp 10 }

          snmpInReadOnlys OBJECT-TYPE
              SYNTAX  Counter
              ACCESS  read-only
              STATUS  mandatory
              DESCRIPTION
                      "The total number valid SNMP PDUs which were
                      delivered to the SNMP protocol entity and for
                      which the value of the error-status field is
                      `readOnly'.  It should be noted that it is a
                      protocol error to generate an SNMP PDU which
                      contains the value `readOnly' in the error-status
                      field, as such this object is provided as a means
                      of detecting incorrect implementations of the
                      SNMP."
              ::= { snmp 11 }

          snmpInGenErrs OBJECT-TYPE
              SYNTAX  Counter
              ACCESS  read-only
              STATUS  mandatory
              DESCRIPTION
                      "The total number of SNMP PDUs which were
                      delivered to the SNMP protocol entity and for
                      which the value of the error-status field is
                      `genErr'."
              ::= { snmp 12 }

          snmpInTotalReqVars OBJECT-TYPE
              SYNTAX  Counter
              ACCESS  read-only
              STATUS  mandatory
              DESCRIPTION
                      "The total number of MIB objects which have been
                      retrieved successfully by the SNMP protocol entity
                      as the result of receiving valid SNMP Get-Request
                      and Get-Next PDUs."
              ::= { snmp 13 }

          snmpInTotalSetVars OBJECT-TYPE
              SYNTAX  Counter
              ACCESS  read-only
              STATUS  mandatory
              DESCRIPTION
                      "The total number of MIB objects which have been
                      altered successfully by the SNMP protocol entity
                      as the result of receiving valid SNMP Set-Request
                      PDUs."
              ::= { snmp 14 }

          snmpInGetRequests OBJECT-TYPE
              SYNTAX  Counter
              ACCESS  read-only
              STATUS  mandatory
              DESCRIPTION
                      "The total number of SNMP Get-Request PDUs which
                      have been accepted and processed by the SNMP
                      protocol entity."
              ::= { snmp 15 }

          snmpInGetNexts OBJECT-TYPE
              SYNTAX  Counter
              ACCESS  read-only
              STATUS  mandatory
              DESCRIPTION
                      "The total number of SNMP Get-Next PDUs which have
                      been accepted and processed by the SNMP protocol
                      entity."
              ::= { snmp 16 }

          snmpInSetRequests OBJECT-TYPE
              SYNTAX  Counter
              ACCESS  read-only
              STATUS  mandatory
              DESCRIPTION
                      "The total number of SNMP Set-Request PDUs which
                      have been accepted and processed by the SNMP
                      protocol entity."
              ::= { snmp 17 }

          snmpInGetResponses OBJECT-TYPE
              SYNTAX  Counter
              ACCESS  read-only
              STATUS  mandatory
              DESCRIPTION
                      "The total number of SNMP Get-Response PDUs which
                      have been accepted and processed by the SNMP
                      protocol entity."
              ::= { snmp 18 }

          snmpInTraps OBJECT-TYPE
              SYNTAX  Counter
              ACCESS  read-only
              STATUS  mandatory
              DESCRIPTION
                      "The total number of SNMP Trap PDUs which have
                      been accepted and processed by the SNMP protocol
                      entity."
              ::= { snmp 19 }

          snmpOutTooBigs OBJECT-TYPE
              SYNTAX  Counter
              ACCESS  read-only
              STATUS  mandatory
              DESCRIPTION
                      "The total number of SNMP PDUs which were
                      generated by the SNMP protocol entity and for
                      which the value of the error-status field is
                      `tooBig.'"
              ::= { snmp 20 }

          snmpOutNoSuchNames OBJECT-TYPE
              SYNTAX  Counter
              ACCESS  read-only
              STATUS  mandatory
              DESCRIPTION
                      "The total number of SNMP PDUs which were
                      generated by the SNMP protocol entity and for
                      which the value of the error-status is
                      `noSuchName'."
              ::= { snmp 21 }

          snmpOutBadValues OBJECT-TYPE
              SYNTAX  Counter
              ACCESS  read-only
              STATUS  mandatory
              DESCRIPTION
                      "The total number of SNMP PDUs which were
                      generated by the SNMP protocol entity and for
                      which the value of the error-status field is
                      `badValue'."
              ::= { snmp 22 }

          -- { snmp 23 } is not used

          snmpOutGenErrs OBJECT-TYPE
              SYNTAX  Counter
              ACCESS  read-only
              STATUS  mandatory
              DESCRIPTION
                      "The total number of SNMP PDUs which were
                      generated by the SNMP protocol entity and for
                      which the value of the error-status field is
                      `genErr'."
              ::= { snmp 24 }

          snmpOutGetRequests OBJECT-TYPE
              SYNTAX  Counter
              ACCESS  read-only
              STATUS  mandatory
              DESCRIPTION
                      "The total number of SNMP Get-Request PDUs which
                      have been generated by the SNMP protocol entity."
              ::= { snmp 25 }

          snmpOutGetNexts OBJECT-TYPE
              SYNTAX  Counter
              ACCESS  read-only
              STATUS  mandatory
              DESCRIPTION
                      "The total number of SNMP Get-Next PDUs which have
                      been generated by the SNMP protocol entity."
              ::= { snmp 26 }

          snmpOutSetRequests OBJECT-TYPE
              SYNTAX  Counter
              ACCESS  read-only
              STATUS  mandatory
              DESCRIPTION
                      "The total number of SNMP Set-Request PDUs which
                      have been generated by the SNMP protocol entity."
              ::= { snmp 27 }

          snmpOutGetResponses OBJECT-TYPE
              SYNTAX  Counter
              ACCESS  read-only
              STATUS  mandatory
              DESCRIPTION
                      "The total number of SNMP Get-Response PDUs which
                      have been generated by the SNMP protocol entity."
              ::= { snmp 28 }

          snmpOutTraps OBJECT-TYPE
              SYNTAX  Counter
              ACCESS  read-only
              STATUS  mandatory
              DESCRIPTION
                      "The total number of SNMP Trap PDUs which have
                      been generated by the SNMP protocol entity."
              ::= { snmp 29 }

          snmpEnableAuthenTraps OBJECT-TYPE
              SYNTAX  INTEGER { enabled(1), disabled(2) }
              ACCESS  read-write
              STATUS  mandatory
              DESCRIPTION
                      "Indicates whether the SNMP agent process is
                      permitted to generate authentication-failure
                      traps.  The value of this object overrides any
                      configuration information; as such, it provides a
                      means whereby all authentication-failure traps may
                      be disabled.

                      Note that it is strongly recommended that this
                      object be stored in non-volatile memory so that it
                      remains constant between re-initializations of the
                      network management system."
              ::= { snmp 30 }


--
-- FILE: /bigguy/users/craig/mibs/src/rfc/rfc1215.smi
--

-- Changes for rfc1215 (Concise TRAP):
--      Added MODULE definition.
--      Commented out TRAP-TYPE macro definition and replaced
--        with SMIC directive to enable it.




    -- Make builtin items known

--    SMI TRAP-TYPE

        --  TRAP-TYPE MACRO ::=
        --  BEGIN
        --      TYPE NOTATION ::= "ENTERPRISE" value
        --                            (enterprise OBJECT IDENTIFIER)
        --                        VarPart
        --                        DescrPart
        --                        ReferPart
        --      VALUE NOTATION ::= value (VALUE INTEGER)
        --
        --      VarPart ::=
        --                 "VARIABLES" "{" VarTypes "}"
        --                      | empty
        --      VarTypes ::=
        --                 VarType | VarTypes "," VarType
        --      VarType ::=
        --                 value (vartype ObjectName)
        --
        --      DescrPart ::=
        --                 "DESCRIPTION" value (description DisplayString)
        --                      | empty
        --
        --      ReferPart ::=
        --                 "REFERENCE" value (reference DisplayString)
        --                      | empty
        --
        --  END


--
-- FILE: /bigguy/users/craig/mibs/src/rfc/rfc1286.mib
--

-- Changes to RFC1286 (Bridge MIB):
--      Removed imported but unused Gauge.



   -- RFC1286
   -- December 91


   -- All representations of MAC addresses in this MIB Module use,
   -- as a textual convention (i.e. this convention does not affect
   -- their encoding), the data type:

   MacAddress ::= OCTET STRING (SIZE (6))    -- a 6 octet address in
                                             -- the "canonical" order
   -- defined by IEEE 802.1a, i.e., as if it were transmitted least
   -- significant bit first, even though 802.5 (in contrast to other
   -- 802.x protocols) requires MAC addresses to be transmitted most
   -- significant bit first.
   --
   -- 16-bit addresses, if needed, are represented by setting their
   -- upper 4 octets to all 0's, i.e., AAFF would be represented
   -- as 00000000AAFF.


   -- Similarly, all representations of Bridge-Id in this MIB Module
   -- use, as a textual convention (i.e. this convention does not affect
   -- their encoding), the data type:

   BridgeId ::= OCTET STRING (SIZE (8))   -- the Bridge-Identifier as
                                          -- used in the Spanning Tree
   -- Protocol to uniquely identify a bridge.  Its first two octets
   -- (in network byte order) contain a priority value and its last
   -- 6 octets contain the MAC address used to refer to a bridge in a
   -- unique fashion (typically, the numerically smallest MAC address
   -- of all ports on the bridge).
   -- Several objects in this MIB module represent values of timers
   -- used by the Spanning Tree Protocol.  In this MIB, these timers
   -- have values in units of hundreths of a second (i.e. 1/100 secs).
   -- These timers, when stored in a Spanning Tree Protocol's BPDU,
   -- are in units of 1/256 seconds.  Note, however, that 802.1d/D9
   -- specifies a settable granularity of no more than 1 second for
   -- these timers.  To avoid ambiguity, a data type is defined here
   -- as a textual convention and all representation of these timers
   -- in this MIB module are defined using this data type.  An algorithm
   -- is also defined for converting between the different units, to
   -- ensure a timer's value is not distorted by multiple conversions.
   -- The data type is:

   Timeout ::= INTEGER      -- a STP timer in units of 1/100 seconds

   -- To convert a Timeout value into a value in units of
   -- 1/256 seconds, the following algorithm should be used:
   --
   --      b  = floor( (n * 256) / 100)
   --
   -- where:
   --      floor   =  quotient [ignore remainder]
   --      n is the value in 1/100 second units
   --      b is the value in 1/256 second units
   --
   -- To convert the value from 1/256 second units back to
   -- 1/100 seconds, the following algorithm should be used:
   --
   --      n = ceiling( (b * 100) / 256)
   --
   -- where:
   --      ceiling =  quotient [if remainder is 0], or
   --                 quotient + 1 [if remainder is non-zero]
   --      n is the value in 1/100 second units
   --      b is the value in 1/256 second units
   --
   -- Note: it is important that the arithmetic operations are done
   -- in the order specified (i.e., multiply first, divide second).

   dot1dBridge   OBJECT IDENTIFIER ::= { mib-2 17 }

   -- groups in the Bridge MIB

   dot1dBase     OBJECT IDENTIFIER ::= { dot1dBridge 1 }

   dot1dStp      OBJECT IDENTIFIER ::= { dot1dBridge 2 }

   dot1dSr       OBJECT IDENTIFIER ::= { dot1dBridge 3 }

   dot1dTp       OBJECT IDENTIFIER ::= { dot1dBridge 4 }

   dot1dStatic   OBJECT IDENTIFIER ::= { dot1dBridge 5 }


   -- the dot1dBase group

   -- Implementation of the dot1dBase group is mandatory for all
   -- bridges.




   -- The Generic Bridge Port Table










   -- the dot1dStp group

   -- Implementation of the dot1dStp group is optional.  It is
   -- implemented by those bridges that support the Spanning Tree
   -- Protocol.  Transparent, Source Route, and SRT bridges will
   -- implement this group only if they support the Spanning Tree
   -- Protocol.

















   -- The Spanning Tree Port Table















   -- the dot1dSr group

   -- Implementation of the dot1dSr group is optional.  It is
   -- implemented by those bridges that support the source route
   -- bridging mode, including Source Route and SRT bridges.









   -- It would be nice if we could use ifMtu as the size of the
   -- largest frame, but we can't because ifMtu is defined to be
   -- the size that the (inter-)network layer can use which can
   -- differ from the MAC layer (especially if several layers of
   -- encapsulation are used).













   -- the dot1dTp group

   -- Implementation of the dot1dTp group is optional.  It is
   -- implemented by those bridges that support the transparent
   -- bridging mode.  A transparent or SRT bridge will implement
   -- this group.





   --  The Forwarding Database for Transparent Bridges








   --  Port Table for Transparent Bridges





   -- It would be nice if we could use ifMtu as the size of the
   -- largest INFO field, but we can't because ifMtu is defined
   -- to be the size that the (inter-)network layer can use which
   -- can differ from the MAC layer (especially if several layers
   -- of encapsulation are used).





   -- The Static (Destination-Address Filtering) Database

   -- Implementation of this group is optional.









   -- Traps for use by Bridges

   -- Traps for the Spanning Tree Protocol

   newRoot TRAP-TYPE
       ENTERPRISE  dot1dBridge
       DESCRIPTION
               "The newRoot trap indicates that the sending agent
               has become the new root of the Spanning Tree; the
               trap is sent by a bridge soon after its election
               as the new root, e.g., upon expiration of the
               Topology Change Timer immediately subsequent to
               its election."
       ::= 1

   topologyChange TRAP-TYPE
       ENTERPRISE  dot1dBridge
       DESCRIPTION
               "A topologyChange trap is sent by a bridge when
               any of its configured ports transitions from the
               Learning state to the Forwarding state, or from
               the Forwarding state to the Blocking state.  The
               trap is not sent if a newRoot trap is sent for the
               same transition."
       ::= 2


--
-- FILE: /bigguy/users/craig/mibs/src/rfc/rfc1368.mib
--

-- IMPORTed MacAddress from RFC1286



   snmpDot3RptrMgt OBJECT IDENTIFIER ::= { mib-2 22 }

   -- All representations of MAC addresses in this MIB Module use,
   -- as a textual convention (i.e., this convention does not affect
   -- their encoding), the data type:

--   MacAddress ::= OCTET STRING (SIZE (6))    
	-- a 6 octet address in the "canonical" order
   -- defined by IEEE 802.1a, i.e., as if it were transmitted least
   -- significant bit first.


   --                      References
   --
   -- The following references are used throughout this MIB:
   --
   -- [IEEE 802.3 Std]
   --    refers to IEEE 802.3/ISO 8802-3 Information processing
   --    systems - Local area networks - Part 3: Carrier sense
   --    multiple access with collision detection (CSMA/CD)
   --    access method and physical layer specifications
   --    (2nd edition, September 21, 1990).
   --
   -- [IEEE 802.3 Rptr Mgt]
   --    refers to IEEE P802.3K, 'Layer Management for 10 Mb/s
   --    Baseband Repeaters, Section 19,' Draft Supplement to
   --    ANSI/IEEE 802.3, (Draft 8, April 9, 1992)

   --                      MIB Groups
   --
   -- The rptrBasicPackage group is mandatory.
   -- The rptrMonitorPackage and rptrAddrTrackPackage
   -- groups are optional.

   rptrBasicPackage
       OBJECT IDENTIFIER ::= { snmpDot3RptrMgt 1 }

   rptrMonitorPackage
       OBJECT IDENTIFIER ::= { snmpDot3RptrMgt 2 }

   rptrAddrTrackPackage
       OBJECT IDENTIFIER ::= { snmpDot3RptrMgt 3 }

   -- object identifiers for organizing the information
   -- in the groups by repeater, port-group, and port

   rptrRptrInfo
       OBJECT IDENTIFIER ::= { rptrBasicPackage 1 }
   rptrGroupInfo
       OBJECT IDENTIFIER ::= { rptrBasicPackage 2 }
   rptrPortInfo
       OBJECT IDENTIFIER ::= { rptrBasicPackage 3 }

   rptrMonitorRptrInfo
       OBJECT IDENTIFIER ::= { rptrMonitorPackage 1 }
   rptrMonitorGroupInfo
       OBJECT IDENTIFIER ::= { rptrMonitorPackage 2 }


   rptrMonitorPortInfo
       OBJECT IDENTIFIER ::= { rptrMonitorPackage 3 }

   rptrAddrTrackRptrInfo     -- this subtree is currently unused
       OBJECT IDENTIFIER ::= { rptrAddrTrackPackage 1 }
   rptrAddrTrackGroupInfo    -- this subtree is currently unused
       OBJECT IDENTIFIER ::= { rptrAddrTrackPackage 2 }
   rptrAddrTrackPortInfo
       OBJECT IDENTIFIER ::= { rptrAddrTrackPackage 3 }

   --
   --                    The BASIC GROUP
   --
   -- Implementation of the Basic Group is mandatory for all
   -- managed repeaters.

   --
   -- Basic Repeater Information
   --
   -- Configuration, status, and control objects for the overall
   -- repeater
   --

   rptrGroupCapacity OBJECT-TYPE
       SYNTAX    INTEGER (1..1024)
       ACCESS    read-only
       STATUS    mandatory
       DESCRIPTION
                      "The rptrGroupCapacity is the number of groups
                      that can be contained within the repeater.  Within
                      each managed repeater, the groups are uniquely
                      numbered in the range from 1 to rptrGroupCapacity.

                      Some groups may not be present in the repeater, in
                      which case the actual number of groups present
                      will be less than rptrGroupCapacity.  The number
                      of groups present will never be greater than
                      rptrGroupCapacity.

                      Note:  In practice, this will generally be the
                      number of field-replaceable units (i.e., modules,
                      cards, or boards) that can fit in the physical
                      repeater enclosure, and the group numbers will
                      correspond to numbers marked on the physical
                      enclosure."
   REFERENCE
               "Reference IEEE 802.3 Rptr Mgt, 19.2.3.2,
               aRepeaterGroupCapacity."


   ::= { rptrRptrInfo 1 }

   rptrOperStatus OBJECT-TYPE
       SYNTAX  INTEGER {
                   other(1),            -- undefined or unknown status
                   ok(2),               -- no known failures
                   rptrFailure(3),      -- repeater-related failure
                   groupFailure(4),     -- group-related failure
                   portFailure(5),      -- port-related failure
                   generalFailure(6)    -- failure, unspecified type
               }
       ACCESS    read-only
       STATUS    mandatory
       DESCRIPTION
              "The rptrOperStatus object indicates the
              operational state of the repeater.  The
              rptrHealthText object may be consulted for more
              specific information about the state of the
              repeater's health.

              In the case of multiple kinds of failures (e.g.,
              repeater failure and port failure), the value of
              this attribute shall reflect the highest priority
              failure in the following order:

                   rptrFailure(3)
                   groupFailure(4)
                   portFailure(5)
                   generalFailure(6)."
       REFERENCE
               "Reference IEEE 802.3 Rptr Mgt, 19.2.3.2,
               aRepeaterHealthState."
       ::= { rptrRptrInfo 2 }

   rptrHealthText OBJECT-TYPE
       SYNTAX    DisplayString (SIZE (0..255))
       ACCESS    read-only
       STATUS    mandatory
       DESCRIPTION
               "The health text object is a text string that
               provides information relevant to the operational
               state of the repeater. Agents may use this string
               to provide detailed information on current
               failures, including how they were detected, and/or
               instructions for problem resolution. The contents
               are agent-specific."
       REFERENCE
               "Reference IEEE 802.3 Rptr Mgt, 19.2.3.2,


               aRepeaterHealthText."
       ::= { rptrRptrInfo 3 }

   rptrReset OBJECT-TYPE
       SYNTAX    INTEGER {
                     noReset(1),
                     reset(2)
                 }
       ACCESS    read-write
       STATUS    mandatory
       DESCRIPTION
               "Setting this object to reset(2) causes a
               transition to the START state of Fig 9-2 in
               section 9 [IEEE 802.3 Std].

               Setting this object to noReset(1) has no effect.
               The agent will always return the value noReset(1)
               when this object is read.

               This action does not reset the management counters
               defined in this document nor does it affect the
               portAdminStatus parameters.  Included in this
               action is the execution of a disruptive Self-Test
               with the following characteristics:  a) The nature
               of the tests is not specified.  b) The test resets
               the repeater but without affecting management
               information about the repeater.  c) The test does
               not inject packets onto any segment.  d) Packets
               received during the test may or may not be
               transferred.  e) The test does not interfere with
               management functions.

               As a result of this action a rptrResetEvent trap
               should be sent."
       REFERENCE
               "Reference IEEE 802.3 Rptr Mgt, 19.2.3.3,
               acResetRepeater."
       ::= { rptrRptrInfo 4 }

   rptrNonDisruptTest OBJECT-TYPE
       SYNTAX    INTEGER {
                     noSelfTest(1),
                     selfTest(2)
                 }
       ACCESS    read-write
       STATUS    mandatory
       DESCRIPTION
               "Setting this object to selfTest(2) causes the


               repeater to perform a agent-specific, non-
               disruptive self-test that has the following
               characteristics:  a) The nature of the tests is
               not specified.  b) The test does not change the
               state of the repeater or management information
               about the repeater.  c) The test does not inject
               packets onto any segment.  d) The test does not
               prevent the relay of any packets.  e) The test
               does not interfere with management functions.

               After performing this test the agent will update
               the repeater health information and send a
               rptrHealth trap.

               Setting this object to noSelfTest(1) has no
               effect.  The agent will always return the value
               noSelfTest(1) when this object is read."
       REFERENCE
               "Reference IEEE 802.3 Rptr Mgt, 19.2.3.3,
               acExecuteNonDisruptiveSelfTest."
       ::= { rptrRptrInfo 5 }

   rptrTotalPartitionedPorts OBJECT-TYPE
       SYNTAX    Gauge
       ACCESS    read-only
       STATUS    mandatory
       DESCRIPTION
               "This object returns the total number of ports in
               the repeater whose current state meets all three
               of the following criteria:  rptrPortOperStatus
               does not have the value notPresent(3),
               rptrPortAdminStatus is enabled(1), and
               rptrPortAutoPartitionState is autoPartitioned(2)."
       ::= { rptrRptrInfo 6 }

   --
   -- The Basic Port Group Table
   --

   rptrGroupTable OBJECT-TYPE
       SYNTAX    SEQUENCE OF RptrGroupEntry
       ACCESS    not-accessible
       STATUS    mandatory
       DESCRIPTION
               "Table of descriptive and status information about
               the groups of ports."
       ::= { rptrGroupInfo 1 }


   rptrGroupEntry OBJECT-TYPE
       SYNTAX    RptrGroupEntry
       ACCESS    not-accessible
       STATUS    mandatory
       DESCRIPTION
               "An entry in the table, containing information
               about a single group of ports."
       INDEX    { rptrGroupIndex }
       ::= { rptrGroupTable 1 }

   RptrGroupEntry ::=
       SEQUENCE {
           rptrGroupIndex
               INTEGER,
           rptrGroupDescr
               DisplayString,
           rptrGroupObjectID
               OBJECT IDENTIFIER,
           rptrGroupOperStatus
               INTEGER,
           rptrGroupLastOperStatusChange
               TimeTicks,
           rptrGroupPortCapacity
               INTEGER
       }

   rptrGroupIndex OBJECT-TYPE
       SYNTAX    INTEGER (1..1024)
       ACCESS    read-only
       STATUS    mandatory
       DESCRIPTION
               "This object identifies the group within the
               repeater for which this entry contains
               information.  This value is never greater than
               rptrGroupCapacity."
       REFERENCE
               "Reference IEEE 802.3 Rptr Mgt, 19.2.5.2,
               aGroupID."
       ::= { rptrGroupEntry 1 }

   rptrGroupDescr OBJECT-TYPE
       SYNTAX    DisplayString (SIZE (0..255))
       ACCESS    read-only
       STATUS    mandatory
       DESCRIPTION
               "A textual description of the group.  This value
               should include the full name and version
               identification of the group's hardware type and


               indicate how the group is differentiated from
               other groups in the repeater.  Plug-in Module, Rev
               A' or 'Barney Rubble 10BASE-T 4-port SIMM socket
               Version 2.1' are examples of valid group
               descriptions.

               It is mandatory that this only contain printable
               ASCII characters."
       ::= { rptrGroupEntry 2 }

   rptrGroupObjectID OBJECT-TYPE
       SYNTAX    OBJECT IDENTIFIER
       ACCESS    read-only
       STATUS    mandatory
       DESCRIPTION
               "The vendor's authoritative identification of the
               group.  This value is allocated within the SMI
               enterprises subtree (1.3.6.1.4.1) and provides a
               straight-forward and unambiguous means for
               determining what kind of group is being managed.

               For example, this object could take the value
               1.3.6.1.4.1.4242.1.2.14 if vendor 'Flintstones,
               Inc.' was assigned the subtree 1.3.6.1.4.1.4242,
               and had assigned the identifier
               1.3.6.1.4.1.4242.1.2.14 to its 'Wilma Flintstone
               6-Port FOIRL Plug-in Module.'"
       ::= { rptrGroupEntry 3 }

   rptrGroupOperStatus OBJECT-TYPE
       SYNTAX    INTEGER {
                     other(1),
                     operational(2),
                     malfunctioning(3),
                     notPresent(4),
                     underTest(5),
                     resetInProgress(6)
                 }
       ACCESS    read-only
       STATUS    mandatory
       DESCRIPTION
               "An object that indicates the operational status
               of the group.

               A status of notPresent(4) indicates that the group
               is temporarily or permanently physically and/or
               logically not a part of the repeater.  It is an
               implementation-specific matter as to whether the


               agent effectively removes notPresent entries from
               the table.

               A status of operational(2) indicates that the
               group is functioning, and a status of
               malfunctioning(3) indicates that the group is
               malfunctioning in some way."
       ::= { rptrGroupEntry 4 }

   rptrGroupLastOperStatusChange OBJECT-TYPE
       SYNTAX    TimeTicks
       ACCESS    read-only
       STATUS    mandatory
       DESCRIPTION
               "An object that contains the value of sysUpTime at
               the time that the value of the rptrGroupOperStatus
               object for this group last changed.

               A value of zero indicates that the group's oper
               status has not changed since the agent last
               restarted."
       ::= { rptrGroupEntry 5 }

   rptrGroupPortCapacity OBJECT-TYPE
       SYNTAX    INTEGER (1..1024)
       ACCESS    read-only
       STATUS    mandatory
       DESCRIPTION
               "The rptrGroupPortCapacity is the number of ports
               that can be contained within the group.  Valid
               range is 1-1024.  Within each group, the ports are
               uniquely numbered in the range from 1 to
               rptrGroupPortCapacity.

               Note:  In practice, this will generally be the
               number of ports on a module, card, or board, and
               the port numbers will correspond to numbers marked
               on the physical embodiment."
       REFERENCE
               "Reference IEEE 802.3 Rptr Mgt, 19.2.5.2,
               aGroupPortCapacity."
       ::= { rptrGroupEntry 6 }


   --
   -- The Basic Port Table
   --

   rptrPortTable OBJECT-TYPE
       SYNTAX    SEQUENCE OF RptrPortEntry
       ACCESS    not-accessible
       STATUS    mandatory
       DESCRIPTION
               "Table of descriptive and status information about
               the ports."
       ::= { rptrPortInfo 1 }

   rptrPortEntry OBJECT-TYPE
       SYNTAX    RptrPortEntry
       ACCESS    not-accessible
       STATUS    mandatory
       DESCRIPTION
               "An entry in the table, containing information
               about a single port."
       INDEX    { rptrPortGroupIndex, rptrPortIndex }
       ::= { rptrPortTable 1 }

   RptrPortEntry ::=
       SEQUENCE {
           rptrPortGroupIndex
               INTEGER,
           rptrPortIndex
               INTEGER,
           rptrPortAdminStatus
               INTEGER,
           rptrPortAutoPartitionState
               INTEGER,
           rptrPortOperStatus
               INTEGER
       }

   rptrPortGroupIndex OBJECT-TYPE
       SYNTAX    INTEGER (1..1024)
       ACCESS    read-only
       STATUS    mandatory
       DESCRIPTION
               "This object identifies the group containing the
               port for which this entry contains information."
       ::= { rptrPortEntry 1 }

   rptrPortIndex OBJECT-TYPE
       SYNTAX    INTEGER (1..1024)


       ACCESS    read-only
       STATUS    mandatory
       DESCRIPTION
               "This object identifies the port within the group
               for which this entry contains information.  This
               value can never be greater than
               rptrGroupPortCapacity for the associated group."
       REFERENCE
               "Reference IEEE 802.3 Rptr Mgt, 19.2.6.2,
               aPortID."
       ::= { rptrPortEntry 2 }

   rptrPortAdminStatus OBJECT-TYPE
       SYNTAX    INTEGER {
                     enabled(1),
                     disabled(2)
                 }
       ACCESS    read-write
       STATUS    mandatory
       DESCRIPTION
               "Setting this object to disabled(2) disables the
               port.  A disabled port neither transmits nor
               receives.  Once disabled, a port must be
               explicitly enabled to restore operation.  A port
               which is disabled when power is lost or when a
               reset is exerted shall remain disabled when normal
               operation resumes.

               The admin status takes precedence over auto-
               partition and functionally operates between the
               auto-partition mechanism and the AUI/PMA.

               Setting this object to enabled(1) enables the port
               and exerts a BEGIN on the port's auto-partition
               state machine.
               (In effect, when a port is disabled, the value of
               rptrPortAutoPartitionState for that port is frozen
               until the port is next enabled.  When the port
               becomes enabled, the rptrPortAutoPartitionState
               becomes notAutoPartitioned(1), regardless of its
               pre-disabling state.)"
       REFERENCE
               "Reference IEEE 802.3 Rptr Mgt, 19.2.6.2,
               aPortAdminState and 19.2.6.3, acPortAdminControl."
       ::= { rptrPortEntry 3 }

   rptrPortAutoPartitionState OBJECT-TYPE
       SYNTAX    INTEGER {


                     notAutoPartitioned(1),
                     autoPartitioned(2)
                 }
       ACCESS    read-only
       STATUS    mandatory
       DESCRIPTION
               "The autoPartitionState flag indicates whether the
               port is currently partitioned by the repeater's
               auto-partition protection.

               The conditions that cause port partitioning are
               specified in partition state machine in Section 9
               [IEEE 802.3 Std].  They are not differentiated
               here."
       REFERENCE
               "Reference IEEE 802.3 Rptr Mgt, 19.2.6.2,
               aAutoPartitionState."
       ::= { rptrPortEntry 4 }

   rptrPortOperStatus  OBJECT-TYPE
       SYNTAX    INTEGER {
                     operational(1),
                     notOperational(2),
                     notPresent(3)
                 }
       ACCESS    read-only
       STATUS    mandatory
       DESCRIPTION
               "This object indicates the port's operational
               status.  The notPresent(3) status indicates the
               port is physically removed (note this may or may
               not be possible depending on the type of port.)

               The operational(1) status indicates that the port
               is enabled (see rptrPortAdminStatus) and working,
               even though it might be auto-partitioned (see
               rptrPortAutoPartitionState).

               If this object has the value operational(1) and
               rptrPortAdminStatus is set to disabled(2), it is
               expected that this object's value will change to
               notOperational(2) soon after."
       ::= { rptrPortEntry 5 }


   --
   --                    The MONITOR GROUP
   --
   -- Implementation of this group is optional, but within the
   -- group all elements are mandatory.  If a managed repeater
   -- implements any part of this group, the entire group shall
   -- be implemented.

   --
   -- Repeater Monitor Information
   --
   -- Performance monitoring statistics for the repeater
   --

   rptrMonitorTransmitCollisions OBJECT-TYPE
       SYNTAX    Counter
       ACCESS    read-only
       STATUS    mandatory
       DESCRIPTION
               "This counter is incremented every time the
               repeater state machine enters the TRANSMIT
               COLLISION state from any state other than ONE PORT
               LEFT (Ref: Fig 9-2, IEEE 802.3 Std).

               The approximate minimum time for rollover of this
               counter is 16 hours."
       REFERENCE
               "Reference IEEE 802.3 Rptr Mgt, 19.2.3.2,
               aTransmitCollisions."
       ::= { rptrMonitorRptrInfo 1 }

   --
   -- The Group Monitor Table
   --

   rptrMonitorGroupTable OBJECT-TYPE
       SYNTAX    SEQUENCE OF RptrMonitorGroupEntry
       ACCESS    not-accessible
       STATUS    mandatory
       DESCRIPTION
               "Table of performance and error statistics for the
               groups."
       ::= { rptrMonitorGroupInfo 1 }

   rptrMonitorGroupEntry OBJECT-TYPE
       SYNTAX    RptrMonitorGroupEntry


       ACCESS    not-accessible
       STATUS    mandatory
       DESCRIPTION
               "An entry in the table, containing total
               performance and error statistics for a single
               group.  Regular retrieval of the information in
               this table provides a means of tracking the
               performance and health of the networked devices
               attached to this group's ports.

               The counters in this table are redundant in the
               sense that they are the summations of information
               already available through other objects.  However,
               these sums provide a considerable optimization of
               network management traffic over the otherwise
               necessary retrieval of the individual counters
               included in each sum."
       INDEX    { rptrMonitorGroupIndex }
       ::= { rptrMonitorGroupTable 1 }

   RptrMonitorGroupEntry ::=
       SEQUENCE {
           rptrMonitorGroupIndex
               INTEGER,
           rptrMonitorGroupTotalFrames
               Counter,
           rptrMonitorGroupTotalOctets
               Counter,
           rptrMonitorGroupTotalErrors
               Counter
       }

   rptrMonitorGroupIndex OBJECT-TYPE
       SYNTAX    INTEGER (1..1024)
       ACCESS    read-only
       STATUS    mandatory
       DESCRIPTION
               "This object identifies the group within the
               repeater for which this entry contains
               information."
       ::= { rptrMonitorGroupEntry 1 }

   rptrMonitorGroupTotalFrames OBJECT-TYPE
       SYNTAX    Counter
       ACCESS    read-only
       STATUS    mandatory
       DESCRIPTION
               "The total number of frames of valid frame length


               that have been received on the ports in this
               group.  This counter is the summation of the
               values of the rptrMonitorPortReadableFrames
               counters for all of the ports in the group.

               This statistic provides one of the parameters
               necessary for obtaining the packet error rate.
               The approximate minimum time for rollover of this
               counter is 80 hours."
       ::= { rptrMonitorGroupEntry 2 }

   rptrMonitorGroupTotalOctets OBJECT-TYPE
       SYNTAX    Counter
       ACCESS    read-only
       STATUS    mandatory
       DESCRIPTION
               "The total number of octets contained in the valid
               frames that have been received on the ports in
               this group.  This counter is the summation of the
               values of the rptrMonitorPortReadableOctets
               counters for all of the ports in the group.

               This statistic provides an indicator of the total
               data transferred.  The approximate minimum time
               for rollover of this counter is 58 minutes."
       ::= { rptrMonitorGroupEntry 3 }

   rptrMonitorGroupTotalErrors OBJECT-TYPE
       SYNTAX    Counter
       ACCESS    read-only
       STATUS    mandatory
       DESCRIPTION
               "The total number of errors which have occurred on
               all of the ports in this group.  This counter is
               the summation of the values of the
               rptrMonitorPortTotalErrors counters for all of the
               ports in the group."
       ::= { rptrMonitorGroupEntry 4 }

   --
   -- The Port Monitor Table
   --

   rptrMonitorPortTable OBJECT-TYPE
       SYNTAX    SEQUENCE OF RptrMonitorPortEntry
       ACCESS    not-accessible
       STATUS    mandatory


       DESCRIPTION
               "Table of performance and error statistics for the
               ports."
       ::= { rptrMonitorPortInfo 1 }

   rptrMonitorPortEntry OBJECT-TYPE
       SYNTAX    RptrMonitorPortEntry
       ACCESS    not-accessible
       STATUS    mandatory
       DESCRIPTION
               "An entry in the table, containing performance and
               error statistics for a single port."
       INDEX    { rptrMonitorPortGroupIndex, rptrMonitorPortIndex }
       ::= { rptrMonitorPortTable 1 }

   RptrMonitorPortEntry ::=
       SEQUENCE {
           rptrMonitorPortGroupIndex
               INTEGER,
           rptrMonitorPortIndex
               INTEGER,
           rptrMonitorPortReadableFrames
               Counter,
           rptrMonitorPortReadableOctets
               Counter,
           rptrMonitorPortFCSErrors
               Counter,
           rptrMonitorPortAlignmentErrors
               Counter,
           rptrMonitorPortFrameTooLongs
               Counter,
           rptrMonitorPortShortEvents
               Counter,
           rptrMonitorPortRunts
               Counter,
           rptrMonitorPortCollisions
               Counter,
           rptrMonitorPortLateEvents
               Counter,
           rptrMonitorPortVeryLongEvents
               Counter,
           rptrMonitorPortDataRateMismatches
               Counter,
           rptrMonitorPortAutoPartitions
               Counter,
           rptrMonitorPortTotalErrors
               Counter
       }


   rptrMonitorPortGroupIndex OBJECT-TYPE
       SYNTAX    INTEGER (1..1024)
       ACCESS    read-only
       STATUS    mandatory
       DESCRIPTION
               "This object identifies the group containing the
               port for which this entry contains information."
       ::= { rptrMonitorPortEntry 1 }

   rptrMonitorPortIndex OBJECT-TYPE
       SYNTAX    INTEGER (1..1024)
       ACCESS    read-only
       STATUS    mandatory
       DESCRIPTION
               "This object identifies the port within the group
               for which this entry contains information."
       REFERENCE
               "Reference IEEE 802.3 Rptr Mgt, 19.2.6.2,
               aPortID."
       ::= { rptrMonitorPortEntry 2 }

   rptrMonitorPortReadableFrames OBJECT-TYPE
       SYNTAX    Counter
       ACCESS    read-only
       STATUS    mandatory
       DESCRIPTION
               "This object is the number of frames of valid
               frame length that have been received on this port.
               This counter is incremented by one for each frame
               received on this port whose OctetCount is greater
               than or equal to minFrameSize and less than or
               equal to maxFrameSize (Ref: IEEE 802.3 Std,
               4.4.2.1) and for which the FCSError and
               CollisionEvent signals are not asserted.

               This statistic provides one of the parameters
               necessary for obtaining the packet error rate.
               The approximate minimum time for rollover of this
               counter is 80 hours."
       REFERENCE
               "Reference IEEE 802.3 Rptr Mgt, 19.2.6.2,
               aReadableFrames."
       ::= { rptrMonitorPortEntry 3 }

   rptrMonitorPortReadableOctets OBJECT-TYPE
       SYNTAX    Counter
       ACCESS    read-only
       STATUS    mandatory


       DESCRIPTION
               "This object is the number of octets contained in
               valid frames that have been received on this port.
               This counter is incremented by OctetCount for each
               frame received on this port which has been
               determined to be a readable frame.

               This statistic provides an indicator of the total
               data transferred.  The approximate minimum time
               for rollover of this counter is 58 minutes."
       REFERENCE
               "Reference IEEE 802.3 Rptr Mgt, 19.2.6.2,
               aReadableOctets."
       ::= { rptrMonitorPortEntry 4 }

   rptrMonitorPortFCSErrors OBJECT-TYPE
       SYNTAX    Counter
       ACCESS    read-only
       STATUS    mandatory
       DESCRIPTION
               "This counter is incremented by one for each frame
               received on this port with the FCSError signal
               asserted and the FramingError and CollisionEvent
               signals deasserted and whose OctetCount is greater
               than or equal to minFrameSize and less than or
               equal to maxFrameSize (Ref: 4.4.2.1, IEEE 802.3
               Std).

               The approximate minimum time for rollover of this
               counter is 80 hours."
       REFERENCE
               "Reference IEEE 802.3 Rptr Mgt, 19.2.6.2,
               aFrameCheckSequenceErrors."
       ::= { rptrMonitorPortEntry 5 }

   rptrMonitorPortAlignmentErrors OBJECT-TYPE
       SYNTAX    Counter
       ACCESS    read-only
       STATUS    mandatory
       DESCRIPTION
               "This counter is incremented by one for each frame
               received on this port with the FCSError and
               FramingError signals asserted and CollisionEvent
               signal deasserted and whose OctetCount is greater
               than or equal to minFrameSize and less than or
               equal to maxFrameSize (Ref: IEEE 802.3 Std,
               4.4.2.1).  If rptrMonitorPortAlignmentErrors is
               incremented then the rptrMonitorPortFCSErrors


               Counter shall not be incremented for the same
               frame.

               The approximate minimum time for rollover of this
               counter is 80 hours."
       REFERENCE
               "Reference IEEE 802.3 Rptr Mgt, 19.2.6.2,
               aAlignmentErrors."
       ::= { rptrMonitorPortEntry 6 }

   rptrMonitorPortFrameTooLongs OBJECT-TYPE
       SYNTAX    Counter
       ACCESS    read-only
       STATUS    mandatory
       DESCRIPTION
               "This counter is incremented by one for each frame
               received on this port whose OctetCount is greater
               than maxFrameSize (Ref: 4.4.2.1, IEEE 802.3 Std).
               If rptrMonitorPortFrameTooLongs is incremented
               then neither the rptrMonitorPortAlignmentErrors
               nor the rptrMonitorPortFCSErrors counter shall be
               incremented for the frame.

               The approximate minimum time for rollover of this
               counter is 61 days."
       REFERENCE
               "Reference IEEE 802.3 Rptr Mgt, 19.2.6.2,
               aFramesTooLong."
       ::= { rptrMonitorPortEntry 7 }

   rptrMonitorPortShortEvents OBJECT-TYPE
       SYNTAX    Counter
       ACCESS    read-only
       STATUS    mandatory
       DESCRIPTION
               "This counter is incremented by one for each
               CarrierEvent on this port with ActivityDuration
               less than ShortEventMaxTime.  ShortEventMaxTime is
               greater than 74 bit times and less than 82 bit
               times.  ShortEventMaxTime has tolerances included
               to provide for circuit losses between a
               conformance test point at the AUI and the
               measurement point within the state machine.

               Note:  shortEvents may indicate externally
               generated noise hits which will cause the repeater
               to transmit Runts to its other ports, or propagate
               a collision (which may be late) back to the


               transmitting DTE and damaged frames to the rest of
               the network.

               Implementors may wish to consider selecting the
               ShortEventMaxTime towards the lower end of the
               allowed tolerance range to accommodate bit losses
               suffered through physical channel devices not
               budgeted for within this standard.

               The approximate minimum time for rollover of this
               counter is 16 hours."
       REFERENCE
               "Reference IEEE 802.3 Rptr Mgt, 19.2.6.2,
               aShortEvents."
       ::= { rptrMonitorPortEntry 8 }

   rptrMonitorPortRunts OBJECT-TYPE
       SYNTAX    Counter
       ACCESS    read-only
       STATUS    mandatory
       DESCRIPTION
               "This counter is incremented by one for each
               CarrierEvent on this port that meets one of the
               following two conditions.  Only one test need be
               made.  a) The ActivityDuration is greater than
               ShortEventMaxTime and less than ValidPacketMinTime
               and the CollisionEvent signal is deasserted.  b)
               The OctetCount is less than 64, the
               ActivityDuration is greater than ShortEventMaxTime
               and the CollisionEvent signal is deasserted.
               ValidPacketMinTime is greater than or equal to 552
               bit times and less than 565 bit times.

               An event whose length is greater than 74 bit times
               but less than 82 bit times shall increment either
               the shortEvents counter or the runts counter but
               not both.  A CarrierEvent greater than or equal to
               552 bit times but less than 565 bit times may or
               may not be counted as a runt.

               ValidPacketMinTime has tolerances included to
               provide for circuit losses between a conformance
               test point at the AUI and the measurement point
               within the state machine.

               Runts usually indicate collision fragments, a
               normal network event.  In certain situations
               associated with large diameter networks a


               percentage of runts may exceed ValidPacketMinTime.

               The approximate minimum time for rollover of this
               counter is 16 hours."
       REFERENCE
               "Reference IEEE 802.3 Rptr Mgt, 19.2.6.2, aRunts."
       ::= { rptrMonitorPortEntry 9 }

   rptrMonitorPortCollisions OBJECT-TYPE
       SYNTAX    Counter
       ACCESS    read-only
       STATUS    mandatory
       DESCRIPTION
               "This counter is incremented by one for any
               CarrierEvent signal on any port for which the
               CollisionEvent signal on this port is asserted.

               The approximate minimum time for rollover of this
               counter is 16 hours."
       REFERENCE
               "Reference IEEE 802.3 Rptr Mgt, 19.2.6.2,
               aCollisions."
       ::= { rptrMonitorPortEntry 10 }

   rptrMonitorPortLateEvents OBJECT-TYPE
       SYNTAX    Counter
       ACCESS    read-only
       STATUS    mandatory
       DESCRIPTION
               "This counter is incremented by one for each
               CarrierEvent on this port in which the CollIn(X)
               variable transitions to the value SQE (Ref:
               9.6.6.2, IEEE 802.3 Std) while the
               ActivityDuration is greater than the
               LateEventThreshold.  Such a CarrierEvent is
               counted twice, as both a collision and as a
               lateEvent.

               The LateEventThreshold is greater than 480 bit
               times and less than 565 bit times.
               LateEventThreshold has tolerances included to
               permit an implementation to build a single
               threshold to serve as both the LateEventThreshold
               and ValidPacketMinTime threshold.

               The approximate minimum time for rollover of this
               counter is 81 hours."
       REFERENCE


               "Reference IEEE 802.3 Rptr Mgt, 19.2.6.2,
               aLateEvents."
       ::= { rptrMonitorPortEntry 11 }

   rptrMonitorPortVeryLongEvents OBJECT-TYPE
       SYNTAX    Counter
       ACCESS    read-only
       STATUS    mandatory
       DESCRIPTION
               "This counter is incremented by one for each
               CarrierEvent on this port whose ActivityDuration
               is greater than the MAU Jabber Lockup Protection
               timer TW3 (Ref: 9.6.1 & 9.6.5, IEEE 802.3 Std).
               Other counters may be incremented as appropriate."
       REFERENCE
               "Reference IEEE 802.3 Rptr Mgt, 19.2.6.2,
               aVeryLongEvents."
       ::= { rptrMonitorPortEntry 12 }

   rptrMonitorPortDataRateMismatches OBJECT-TYPE
       SYNTAX    Counter
       ACCESS    read-only
       STATUS    mandatory
       DESCRIPTION
               "This counter is incremented by one for each frame
               received on this port that meets all of the
               following conditions:  a) The CollisionEvent
               signal is not asserted.  b) The ActivityDuration
               is greater than ValidPacketMinTime.  c) The
               frequency (data rate) is detectably mismatched
               from the local transmit frequency.  The exact
               degree of mismatch is vendor specific and is to be
               defined by the vendor for conformance testing.

               When this event occurs, other counters whose
               increment conditions were satisfied may or may not
               also be incremented, at the implementor's
               discretion.  Whether or not the repeater was able
               to maintain data integrity is beyond the scope of
               this standard."
       REFERENCE
               "Reference IEEE 802.3 Rptr Mgt, 19.2.6.2,
               aDataRateMismatches."
       ::= { rptrMonitorPortEntry 13 }

   rptrMonitorPortAutoPartitions OBJECT-TYPE
       SYNTAX    Counter
       ACCESS    read-only


       STATUS    mandatory
       DESCRIPTION
               "This counter is incremented by one for each time
               the repeater has automatically partitioned this
               port.  The conditions that cause port partitioning
               are specified in the partition state machine in
               Section 9 [IEEE 802.3 Std].  They are not
               differentiated here."
       REFERENCE
               "Reference IEEE 802.3 Rptr Mgt, 19.2.6.2,
               aAutoPartitions."
       ::= { rptrMonitorPortEntry 14 }

   rptrMonitorPortTotalErrors OBJECT-TYPE
       SYNTAX    Counter
       ACCESS    read-only
       STATUS    mandatory
       DESCRIPTION
               "The total number of errors which have occurred on
               this port.  This counter is the summation of the
               values of other error counters (for the same
               port), namely:

                   rptrMonitorPortFCSErrors,
                   rptrMonitorPortAlignmentErrors,
                   rptrMonitorPortFrameTooLongs,
                   rptrMonitorPortShortEvents,
                   rptrMonitorPortLateEvents,
                   rptrMonitorPortVeryLongEvents, and
                   rptrMonitorPortDataRateMismatches.

               This counter is redundant in the sense that it is
               the summation of information already available
               through other objects.  However, it is included
               specifically because the regular retrieval of this
               object as a means of tracking the health of a port
               provides a considerable optimization of network
               management traffic over the otherwise necessary
               retrieval of the summed counters."
       ::= { rptrMonitorPortEntry 15 }

   --
   --                    The ADDRESS TRACKING GROUP
   --
   -- Implementation of this group is optional; it is appropriate
   -- for all systems which have the necessary metering.  If a
   -- managed repeater implements any part of this group, the entire


   -- group shall be implemented.

   --
   -- The Port Address Tracking Table
   --

   rptrAddrTrackTable OBJECT-TYPE
       SYNTAX    SEQUENCE OF RptrAddrTrackEntry
       ACCESS    not-accessible
       STATUS    mandatory
       DESCRIPTION
               "Table of address mapping information about the
               ports."
       ::= { rptrAddrTrackPortInfo 1 }

   rptrAddrTrackEntry OBJECT-TYPE
       SYNTAX    RptrAddrTrackEntry
       ACCESS    not-accessible
       STATUS    mandatory
       DESCRIPTION
               "An entry in the table, containing address mapping
               information about a single port."
       INDEX    { rptrAddrTrackGroupIndex, rptrAddrTrackPortIndex }
       ::= { rptrAddrTrackTable 1 }

   RptrAddrTrackEntry ::=
       SEQUENCE {
           rptrAddrTrackGroupIndex
               INTEGER,
           rptrAddrTrackPortIndex
               INTEGER,
           rptrAddrTrackLastSourceAddress
               MacAddress,
           rptrAddrTrackSourceAddrChanges
               Counter
       }

   rptrAddrTrackGroupIndex OBJECT-TYPE
       SYNTAX    INTEGER (1..1024)
       ACCESS    read-only
       STATUS    mandatory
       DESCRIPTION
               "This object identifies the group containing the
               port for which this entry contains information."
       ::= { rptrAddrTrackEntry 1 }

   rptrAddrTrackPortIndex OBJECT-TYPE
       SYNTAX    INTEGER (1..1024)


       ACCESS    read-only
       STATUS    mandatory
       DESCRIPTION
               "This object identifies the port within the group
               for which this entry contains information."
       REFERENCE
               "Reference IEEE 802.3 Rptr Mgt, 19.2.6.2,
               aPortID."
       ::= { rptrAddrTrackEntry 2 }

   rptrAddrTrackLastSourceAddress OBJECT-TYPE
       SYNTAX    MacAddress
       ACCESS    read-only
       STATUS    mandatory
       DESCRIPTION
               "This object is the SourceAddress of the last
               readable frame (i.e., counted by
               rptrMonitorPortReadableFrames) received by this
               port."
       REFERENCE
               "Reference IEEE 802.3 Rptr Mgt, 19.2.6.2,
               aLastSourceAddress."
       ::= { rptrAddrTrackEntry 3 }

   rptrAddrTrackSourceAddrChanges OBJECT-TYPE
       SYNTAX    Counter
       ACCESS    read-only
       STATUS    mandatory
       DESCRIPTION
               "This counter is incremented by one for each time
               that the rptrAddrTrackLastSourceAddress attribute
               for this port has changed.

               This may indicate whether a link is connected to a
               single DTE or another multi-user segment.
               The approximate minimum time for rollover of this
               counter is 81 hours."
       REFERENCE
               "Reference IEEE 802.3 Rptr Mgt, 19.2.6.2,
               aSourceAddressChanges."
       ::= { rptrAddrTrackEntry 4 }

   -- Traps for use by Repeaters

   -- Traps are defined using the conventions in RFC 1215 [8].

   rptrHealth TRAP-TYPE


       ENTERPRISE  snmpDot3RptrMgt
       VARIABLES   { rptrOperStatus }
       DESCRIPTION
               "The rptrHealth trap conveys information related
               to the operational status of the repeater.  This
               trap is sent only when the oper status of the
               repeater changes.

               The rptrHealth trap must contain the
               rptrOperStatus object.  The agent may optionally
               include the rptrHealthText object in the varBind
               list.  See the rptrOperStatus and rptrHealthText
               objects for descriptions of the information that
               is sent.

               The agent must throttle the generation of
               consecutive rptrHealth traps so that there is at
               least a five-second gap between them."
       REFERENCE
               "Reference IEEE 802.3 Rptr Mgt, 19.2.3.4,
               hubHealth notification."
       ::= 1

   rptrGroupChange TRAP-TYPE
       ENTERPRISE  snmpDot3RptrMgt
       VARIABLES   { rptrGroupIndex }
       DESCRIPTION
               "This trap is sent when a change occurs in the
               group structure of a repeater.  This occurs only
               when a group is logically or physically removed
               from or added to a repeater.  The varBind list
               contains the identifier of the group that was
               removed or added.

               The agent must throttle the generation of
               consecutive rptrGroupChange traps for the same
               group so that there is at least a five-second gap
               between them."
       REFERENCE
               "Reference IEEE 802.3 Rptr Mgt, 19.2.3.4,
               groupMapChange notification."
       ::= 2

   rptrResetEvent TRAP-TYPE
       ENTERPRISE  snmpDot3RptrMgt
       VARIABLES   { rptrOperStatus }
       DESCRIPTION
               "The rptrResetEvent trap conveys information


               related to the operational status of the repeater.
               This trap is sent on completion of a repeater
               reset action.  A repeater reset action is defined
               as an a transition to the START state of Fig 9-2
               in section 9 [IEEE 802.3 Std], when triggered by a
               management command (e.g., an SNMP Set on the
               rptrReset object).

               The agent must throttle the generation of
               consecutive rptrResetEvent traps so that there is
               at least a five-second gap between them.

               The rptrResetEvent trap is not sent when the agent
               restarts and sends an SNMP coldStart or warmStart
               trap.  However, it is recommended that a repeater
               agent send the rptrOperStatus object as an
               optional object with its coldStart and warmStart
               trap PDUs.

               The rptrOperStatus object must be included in the
               varbind list sent with this trap.  The agent may
               optionally include the rptrHealthText object as
               well."
       REFERENCE
               "Reference IEEE 802.3 Rptr Mgt, 19.2.3.4, hubReset
               notification."
       ::= 3


--
-- FILE: /bigguy/users/craig/mibs/src/other/lanart.mib
--



lanart		OBJECT IDENTIFIER ::= { enterprises 712 }

laMib1		OBJECT IDENTIFIER ::= { lanart 1 }

laProducts	OBJECT IDENTIFIER ::= { laMib1 1 }

laHubMib	OBJECT IDENTIFIER ::= { laMib1 2 }

laSys		OBJECT IDENTIFIER ::= { laHubMib 1 }
laTpPort	OBJECT IDENTIFIER ::= { laHubMib 2 }

	-- The following OIDs are used in sysOID
	--
laTpHub		OBJECT IDENTIFIER ::= { laProducts 1 }

	-- The following OIDs are used in groupOID
	--

-- laTpHub[1-3] were added to fill in missing nodes in the OID tree.

laTpHub1 	OBJECT IDENTIFIER ::= { laTpHub 1 }
etm120x		OBJECT IDENTIFIER ::= { laTpHub1 12 }
etm160x		OBJECT IDENTIFIER ::= { laTpHub1 16 }
etm240x		OBJECT IDENTIFIER ::= { laTpHub1 24 }

laTpHub2 	OBJECT IDENTIFIER ::= { laTpHub 2 }
ete120x		OBJECT IDENTIFIER ::= { laTpHub2 12 }
ete160x		OBJECT IDENTIFIER ::= { laTpHub2 16 }
ete240x		OBJECT IDENTIFIER ::= { laTpHub2 24 }

laTpHub3 	OBJECT IDENTIFIER ::= { laTpHub 3 }
bbAui		OBJECT IDENTIFIER ::= { laTpHub3 0 }
bbAuiTp		OBJECT IDENTIFIER ::= { laTpHub3 1 }
bbAuiBnc	OBJECT IDENTIFIER ::= { laTpHub3 2 }
bbAuiTpBnc	OBJECT IDENTIFIER ::= { laTpHub3 3 }
bbAui10BASE-FL	OBJECT IDENTIFIER ::= { laTpHub3 4 }


laSysConfig  OBJECT-TYPE
              SYNTAX  INTEGER {
			save(1),
			load(2),
			factory(3),
			ok(4),
			failed(5)
		      }
              ACCESS  read-write
              STATUS  mandatory
              DESCRIPTION
                       "Setting this object to save(1) will save all
			configuration variables to non-volatile memory.

			Setting this object to load(2) will configure
			the hub according to the stored configuration.

			Setting this object to factory(3) will configure
			the hub according to the factory settings.

			A return value of ok(4) means the non-volatile memory
			is operational.
			A return value of failed(5) means the non-volatile
			memory has failed."
              ::= { laSys 1 }

laJoystick    OBJECT-TYPE
              SYNTAX  INTEGER {
			enabled(1),
			disabled(2)
		      }
              ACCESS  read-write
              STATUS  mandatory
              DESCRIPTION
		       "Setting this object to disabled(2) prevents
			use of the four-position switch on the front
			panel.  Resetting this object to enabled(1)
			allows use of the switch."
              ::= { laSys 2 }

laLinkAlert   OBJECT-TYPE
              SYNTAX  INTEGER {
			enabled(1),
			disabled(2),
			not-applicable(3)
		      }
              ACCESS  read-write
              STATUS  mandatory
              DESCRIPTION
		       "Setting this object enables or disables the
			LinkALERT feature of the backbone 10BASE-T
			or 10BASE-FL port.

			A return value of not-applicable indicates that
			none of the backbone ports feature LinkALERT."
              ::= { laSys 3 }


laTpPortTable OBJECT-TYPE
       SYNTAX    SEQUENCE OF LaTpPortEntry
       ACCESS    not-accessible
       STATUS    mandatory
       DESCRIPTION
               "Table of descriptive and status information about
               the ports."
       ::= { laTpPort 1 }

laTpPortEntry OBJECT-TYPE
       SYNTAX    LaTpPortEntry
       ACCESS    not-accessible
       STATUS    mandatory
       DESCRIPTION
               "An entry in the table, containing information
               about a single port."
       INDEX    { laTpPortGroupIndex, laTpPortIndex }
       ::= { laTpPortTable 1 }

   LaTpPortEntry ::=
       SEQUENCE {
		laTpPortGroupIndex
			INTEGER,
		laTpPortIndex
			INTEGER,
		laTpLinkTest
			INTEGER,
		laTpAutoPolarity
			INTEGER
       }


   laTpPortGroupIndex OBJECT-TYPE
       SYNTAX    INTEGER (1..1024)
       ACCESS    read-only
       STATUS    mandatory
       DESCRIPTION
               "This object identifies the group containing the
               port for which this entry contains information."
       ::= { laTpPortEntry 1 }

   laTpPortIndex OBJECT-TYPE
       SYNTAX    INTEGER (1..1024)
       ACCESS    read-only
       STATUS    mandatory
       DESCRIPTION
               "This object identifies the port within the group
               for which this entry contains information."
       ::= { laTpPortEntry 2 }

   
   laTpLinkTest OBJECT-TYPE
       SYNTAX    INTEGER {
                     enabled(1),
                     disabled(2),
		     failed(3),
		     not-applicable(4)
                 }
       ACCESS    read-write
       STATUS    mandatory
       DESCRIPTION
               "Setting this object to disabled(2) disables the
		link test feature.  This may be useful for
		interoperation with pre-10BASE-T equipment.
		Setting this object to enabled(1) enables the
		feature.

		A return value of failed(3) indicates a link test
		failure for this port.
		A return value of not-applicable(4) indicates that
		the specified port does not have a link test."
       ::= { laTpPortEntry 3 }

   laTpAutoPolarity OBJECT-TYPE
       SYNTAX    INTEGER {
                     enabled(1),
                     disabled(2),
		     corrected(3),
		     not-applicable(4)
                 }
       ACCESS    read-write
       STATUS    mandatory
       DESCRIPTION
               "Setting this object to disabled(2) disables the
		auto polarity test for this port.
		Setting this object to enabled(1) enables the feature.

		A return value of corrected(3) indicates that the
		polarity test has sensed a reversal on the receive
		wiring pair, and has corrected this fault by inverting
		its receive signal.
		A return value of not-applicable(4) indicates that
		the specified port does not support polarity correction."
       ::= { laTpPortEntry 4 }

END
