-- An experimental MIB description for bull objects
-- February 1991



Bull-MIB DEFINITIONS ::= BEGIN

IMPORTS
		DisplayString FROM SNMPv2-TC
        enterprises, OBJECT-TYPE, Gauge, Counter
                FROM RFC1155-SMI;


bull            OBJECT IDENTIFIER ::= { enterprises 107 }
bull-products   OBJECT IDENTIFIER ::= { bull 1 }
bull-DPX2       OBJECT IDENTIFIER ::= { bull-products 1 }
bull-mibs       OBJECT IDENTIFIER ::= { bull 2 }
bull-mibs-mib1  OBJECT IDENTIFIER ::= { bull-mibs 1 }
bull-System     OBJECT IDENTIFIER ::= { bull-mibs-mib1 1 }
bull-Streams    OBJECT IDENTIFIER ::= { bull-mibs-mib1 2 }
bull-Ether      OBJECT IDENTIFIER ::= { bull-mibs-mib1 3 }
bull-Serial     OBJECT IDENTIFIER ::= { bull-mibs-mib1 4 }
bull-X25        OBJECT IDENTIFIER ::= { bull-mibs-mib1 5 }
bull-NMFX       OBJECT IDENTIFIER ::= { bull-mibs-mib1 6 }

-- object types

-- the products group

bull-DPX2-100 OBJECT-TYPE
    SYNTAX  DisplayString (SIZE(0..255))
    ACCESS  read-only
    STATUS  optional
              DESCRIPTION ""
    ::= { bull-DPX2 1 }

bull-DPX2-200 OBJECT-TYPE
    SYNTAX  DisplayString (SIZE(0..255))
    ACCESS  read-only
    STATUS  optional
              DESCRIPTION ""
    ::= { bull-DPX2 2 }

bull-DPX2-300 OBJECT-TYPE
    SYNTAX  DisplayString (SIZE(0..255))
    ACCESS  read-only
    STATUS  optional
              DESCRIPTION ""
    ::= { bull-DPX2 3 }

-- the Streams group

bullStrTable OBJECT-TYPE
    -- this group gives General STREAMS Memory Statistics.
    -- for 4 types of resources:
    --        streams, queues, message blocks, data blocks
    -- for each type is given # of : in use, total use, maximum use
    --          allocation fail, total allocated.
    SYNTAX  SEQUENCE OF BullStrEntry
    ACCESS  not-accessible
    STATUS  mandatory
    DESCRIPTION
            "Status information of Streams usage."
    ::= {bull-Streams 1 }

bullStrEntry OBJECT-TYPE
    SYNTAX  BullStrEntry
    ACCESS  not-accessible
    STATUS  mandatory
    DESCRIPTION
            "Status information of Streams usage
            for a specific type of buffer."
    INDEX   { bullStrType }
    ::= { bullStrTable 1 }

BullStrEntry ::=
    SEQUENCE {
        bullStrType
            INTEGER,
        bullStrAlloc
            INTEGER,
        bullStrInuse
            Gauge,
        bullStrMaxs
            Counter,
        bullStrTotals
            Counter,
        bullStrFails
            Counter
    }

bullStrType OBJECT-TYPE
    SYNTAX  INTEGER {
            streams(1),
            queues(2),
            messages(3),
            blocks(4)
           }
    ACCESS  read-only
    STATUS  mandatory
    DESCRIPTION
            "An index value that uniquely identifies a
            type of buffer."
    ::= { bullStrEntry 1 }

bullStrAlloc OBJECT-TYPE
    SYNTAX  INTEGER
    ACCESS  read-only
    STATUS  mandatory
              DESCRIPTION ""
    ::= { bullStrEntry 2 }

bullStrInuse OBJECT-TYPE
    SYNTAX  Gauge
    ACCESS  read-only
    STATUS  mandatory
              DESCRIPTION ""
    ::= { bullStrEntry 3 }

bullStrMaxs OBJECT-TYPE
    SYNTAX  Counter
    ACCESS  read-only
    STATUS  mandatory
              DESCRIPTION ""
    ::= { bullStrEntry 4 }

bullStrTotals OBJECT-TYPE
    SYNTAX  Counter
    ACCESS  read-only
    STATUS  mandatory
              DESCRIPTION ""
    ::= { bullStrEntry 5 }

bullStrFails OBJECT-TYPE
    SYNTAX  Counter
    ACCESS  read-only
    STATUS  mandatory
              DESCRIPTION ""
    ::= { bullStrEntry 6 }

bullBlkTable OBJECT-TYPE
    -- this group gives STREAM Data Block Statistics per classes
    -- for 10 types of blocks (classes represent size of block in octets):
    -- class 1 -> 4, class 2 -> 16, class 3 -> 64, class 4 -> 128,
    -- class 5 -> 256, class 6 -> 512, class 7 -> 1024, class 8 -> 2048,
    -- class 9 -> 4096, class 10 -> 8192
    -- for each class is given # of : in use, total use, maximum use
    --          allocation fail, allocated with low priority,
    --          allocated with medium priority, total allocated. 
    SYNTAX  SEQUENCE OF BullBlkEntry
    ACCESS  not-accessible
    STATUS  mandatory
    DESCRIPTION
            "Status information of data Blocks usage."
    ::= {bull-Streams 2 }

bullBlkEntry OBJECT-TYPE
    SYNTAX  BullBlkEntry
    ACCESS  not-accessible
    STATUS  mandatory
    DESCRIPTION
            "Status information of data Blocks usage
            for a specific type of block."
    INDEX   { bullBlkclass }
    ::= { bullBlkTable 1 }


BullBlkEntry ::=
    SEQUENCE {
        bullBlkClass
            INTEGER,
        bullBlkSize
            INTEGER,
        bullBlkAlloc
            INTEGER,
        bullBlkInuse
            Gauge,
        bullBlkLowpris
            Counter,
        bullBlkMedpris
            Counter,
        bullBlkMaxs
            Counter,
        bullBlkTotals
            Counter,
        bullBlkFails
            Counter
    }

bullBlkClass OBJECT-TYPE
    SYNTAX  INTEGER (1..10)
    ACCESS  read-only
    STATUS  mandatory
    DESCRIPTION
            "An index value that uniquely identifies a
            type of block."
    ::= { bullBlkEntry 1 }

bullBlkAlloc OBJECT-TYPE
    SYNTAX  INTEGER
    ACCESS  read-only
    STATUS  mandatory
              DESCRIPTION ""
    ::= { bullBlkEntry 2 }

bullBlkInuse OBJECT-TYPE
    SYNTAX  Gauge
    ACCESS  read-only
    STATUS  mandatory
              DESCRIPTION ""
    ::= { bullBlkEntry 3 }

bullBlkLowpris OBJECT-TYPE
    SYNTAX  Counter
    ACCESS  read-only
    STATUS  mandatory
              DESCRIPTION ""
    ::= { bullBlkEntry 5 }

bullBlkMedpris OBJECT-TYPE
    SYNTAX  Counter
    ACCESS  read-only
    STATUS  mandatory
              DESCRIPTION ""
    ::= { bullBlkEntry 6 }

bullBlkMaxs OBJECT-TYPE
    SYNTAX  Counter
    ACCESS  read-only
    STATUS  mandatory
              DESCRIPTION ""
    ::= { bullBlkEntry 7 }

bullBlkTotals OBJECT-TYPE
    SYNTAX  Counter
    ACCESS  read-only
    STATUS  mandatory
              DESCRIPTION ""
    ::= { bullBlkEntry 8 }

bullBlkFails OBJECT-TYPE
    SYNTAX  Counter
    ACCESS  read-only
    STATUS  mandatory
              DESCRIPTION ""
    ::= { bullBlkEntry 9 }


END
