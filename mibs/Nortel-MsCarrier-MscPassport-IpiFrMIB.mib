Nortel-MsCarrier-MscPassport-IpiFrMIB
DEFINITIONS ::= BEGIN



IMPORTS

      OBJECT-TYPE
   FROM RFC-1212

      IpAddress
   FROM RFC1155-SMI

      mscPassportMIBs,
      mscComponents
   FROM Nortel-MsCarrier-MscPassport-UsefulDefinitionsMIB

      Counter32,
      RowPointer,
      DisplayString,
      StorageType,
      RowStatus,
      Integer32,
      Unsigned32
   FROM Nortel-MsCarrier-MscPassport-StandardTextualConventionsMIB

      AsciiString,
      Hex,
      NonReplicated,
      HexString,
      EnterpriseDateAndTime,
      DigitString
   FROM Nortel-MsCarrier-MscPassport-TextualConventionsMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     IpiFr Enterprise MIB."

ipiFrMIB OBJECT IDENTIFIER ::= { mscPassportMIBs 35 }










-- IP Interface over Frame Relay
-- 
-- The IP interface over Frame Relay component allows external 
-- Network Management Stations using Frame Relay PVC 
-- connections to perform the network management functions on the 
-- Passport module.
-- 
-- Network Management Stations can be directly connected to a 
-- Passport module with a FrameRelay PVC connection, or indirectly 
-- connected via an IP routing capable device which has a FrameRelay 
-- PVC connection to the Passport module.

mscIpiFr OBJECT IDENTIFIER ::= { mscComponents 50 }



mscIpiFrRowStatusTable OBJECT-TYPE
   SYNTAX     SEQUENCE OF MscIpiFrRowStatusEntry
   ACCESS     not-accessible
   STATUS     mandatory
   DESCRIPTION
     "This entry controls the addition and deletion of 
      mscIpiFr components."
::= { mscIpiFr 1 }

mscIpiFrRowStatusEntry OBJECT-TYPE
   SYNTAX     MscIpiFrRowStatusEntry
   ACCESS     not-accessible
   STATUS     mandatory
   DESCRIPTION
     "A single entry in the table represents a single 
      mscIpiFr component."
   INDEX {
      mscIpiFrIndex }
::= { mscIpiFrRowStatusTable 1 }

MscIpiFrRowStatusEntry ::= SEQUENCE {
   mscIpiFrRowStatus
      RowStatus,
   mscIpiFrComponentName
      DisplayString,
   mscIpiFrStorageType
      StorageType,
   mscIpiFrIndex
      NonReplicated }

mscIpiFrRowStatus OBJECT-TYPE
   SYNTAX     RowStatus 
   ACCESS     read-write
   STATUS     mandatory
   DESCRIPTION
     "This variable is used as the basis for SNMP naming of
      mscIpiFr components.
      These components can be added and deleted."
::= { mscIpiFrRowStatusEntry 1 }

mscIpiFrComponentName OBJECT-TYPE
   SYNTAX     DisplayString 
   ACCESS     read-only
   STATUS     mandatory
   DESCRIPTION
     "This variable provides the component's string name for
      use with the ASCII Console Interface"
::= { mscIpiFrRowStatusEntry 2 }

mscIpiFrStorageType OBJECT-TYPE
   SYNTAX     StorageType 
   ACCESS     read-only
   STATUS     mandatory
   DESCRIPTION
     "This variable represents the storage type value for the
      mscIpiFr tables."
::= { mscIpiFrRowStatusEntry 4 }

mscIpiFrIndex OBJECT-TYPE
   SYNTAX     NonReplicated 
   ACCESS     not-accessible
   STATUS     mandatory
   DESCRIPTION
     "This variable represents the index for the mscIpiFr tables."
::= { mscIpiFrRowStatusEntry 10 }

mscIpiFrProvTable OBJECT-TYPE
   SYNTAX     SEQUENCE OF MscIpiFrProvEntry
   ACCESS     not-accessible
   STATUS     mandatory
   DESCRIPTION
     "This group provides the provisionable attributes for the IpiFr 
      component."
::= { mscIpiFr 10 }

mscIpiFrProvEntry OBJECT-TYPE
   SYNTAX     MscIpiFrProvEntry
   ACCESS     not-accessible
   STATUS     mandatory
   DESCRIPTION
     "An entry in the mscIpiFrProvTable."
   INDEX {
      mscIpiFrIndex }
::= { mscIpiFrProvTable 1 }

MscIpiFrProvEntry ::= SEQUENCE {
   mscIpiFrIpAddress
      IpAddress,
   mscIpiFrMaximumNumberOfLcn
      Unsigned32,
   mscIpiFrSubnetMask
      IpAddress }

mscIpiFrIpAddress OBJECT-TYPE
   SYNTAX     IpAddress 
   ACCESS     read-write
   STATUS     mandatory
   DESCRIPTION
     "This attribute specifies the unique Internet Protocol (IP) Address 
      that represents the IP address of the IPI service."
   DEFVAL     { '00000000'H }  -- "0.0.0.0"
::= { mscIpiFrProvEntry 1 }

mscIpiFrMaximumNumberOfLcn OBJECT-TYPE
   SYNTAX     Unsigned32 (24)
   ACCESS     read-only
   STATUS     mandatory
   DESCRIPTION
     "This attribute specifies the maximum number of LCNs that are 
      supported on this service. It specifies the maximum number of 
      connections from external network management sites to this IpiFr 
      service."
   DEFVAL     { 24 }
::= { mscIpiFrProvEntry 2 }

mscIpiFrSubnetMask OBJECT-TYPE
   SYNTAX     IpAddress 
   ACCESS     read-write
   STATUS     mandatory
   DESCRIPTION
     "This attribute specifies the subnetwork mask for the IPI service."
   DEFVAL     { 'ff000000'H }  -- "255.0.0.0"
::= { mscIpiFrProvEntry 3 }


-- IpiFr Dna
-- This is the description of the Ipi Frame Relay Dna component. It is 
-- offers a subset of the generic Dna component attributes

mscIpiFrDna OBJECT IDENTIFIER ::= { mscIpiFr 2 }



mscIpiFrDnaRowStatusTable OBJECT-TYPE
   SYNTAX     SEQUENCE OF MscIpiFrDnaRowStatusEntry
   ACCESS     not-accessible
   STATUS     mandatory
   DESCRIPTION
     "This entry controls the addition and deletion of 
      mscIpiFrDna components."
::= { mscIpiFrDna 1 }

mscIpiFrDnaRowStatusEntry OBJECT-TYPE
   SYNTAX     MscIpiFrDnaRowStatusEntry
   ACCESS     not-accessible
   STATUS     mandatory
   DESCRIPTION
     "A single entry in the table represents a single 
      mscIpiFrDna component."
   INDEX {
      mscIpiFrIndex,
      mscIpiFrDnaIndex }
::= { mscIpiFrDnaRowStatusTable 1 }

MscIpiFrDnaRowStatusEntry ::= SEQUENCE {
   mscIpiFrDnaRowStatus
      RowStatus,
   mscIpiFrDnaComponentName
      DisplayString,
   mscIpiFrDnaStorageType
      StorageType,
   mscIpiFrDnaIndex
      NonReplicated }

mscIpiFrDnaRowStatus OBJECT-TYPE
   SYNTAX     RowStatus 
   ACCESS     read-only
   STATUS     mandatory
   DESCRIPTION
     "This variable is used as the basis for SNMP naming of
      mscIpiFrDna components.
      These components cannot be added nor deleted."
::= { mscIpiFrDnaRowStatusEntry 1 }

mscIpiFrDnaComponentName OBJECT-TYPE
   SYNTAX     DisplayString 
   ACCESS     read-only
   STATUS     mandatory
   DESCRIPTION
     "This variable provides the component's string name for
      use with the ASCII Console Interface"
::= { mscIpiFrDnaRowStatusEntry 2 }

mscIpiFrDnaStorageType OBJECT-TYPE
   SYNTAX     StorageType 
   ACCESS     read-only
   STATUS     mandatory
   DESCRIPTION
     "This variable represents the storage type value for the
      mscIpiFrDna tables."
::= { mscIpiFrDnaRowStatusEntry 4 }

mscIpiFrDnaIndex OBJECT-TYPE
   SYNTAX     NonReplicated 
   ACCESS     not-accessible
   STATUS     mandatory
   DESCRIPTION
     "This variable represents the index for the mscIpiFrDna tables."
::= { mscIpiFrDnaRowStatusEntry 10 }

mscIpiFrDnaAddressTable OBJECT-TYPE
   SYNTAX     SEQUENCE OF MscIpiFrDnaAddressEntry
   ACCESS     not-accessible
   STATUS     mandatory
   DESCRIPTION
     "Address group contains attributes common to all Dna's. Every Dna 
      used in the network is defined with this group of 2 attributes. String 
      of address digits is complemented by type of address and Npi. 
      These attributes are used to interpret format of the address digits."
::= { mscIpiFrDna 10 }

mscIpiFrDnaAddressEntry OBJECT-TYPE
   SYNTAX     MscIpiFrDnaAddressEntry
   ACCESS     not-accessible
   STATUS     mandatory
   DESCRIPTION
     "An entry in the mscIpiFrDnaAddressTable."
   INDEX {
      mscIpiFrIndex,
      mscIpiFrDnaIndex }
::= { mscIpiFrDnaAddressTable 1 }

MscIpiFrDnaAddressEntry ::= SEQUENCE {
   mscIpiFrDnaNumberingPlanIndicator
      INTEGER,
   mscIpiFrDnaDataNetworkAddress
      DigitString }

mscIpiFrDnaNumberingPlanIndicator OBJECT-TYPE
   SYNTAX     INTEGER  {
                 x121(0),
                 e164(1) }
   ACCESS     read-write
   STATUS     mandatory
   DESCRIPTION
     "This attribute indicates the Numbering Plan Indicator (NPI) of the 
      Dna that is entered. Address may belong to X.121 or E.164 plans. 
      X.121 is used in packet svitched data networks."
   DEFVAL     { x121 }
::= { mscIpiFrDnaAddressEntry 1 }

mscIpiFrDnaDataNetworkAddress OBJECT-TYPE
   SYNTAX     DigitString (SIZE (1..15))
   ACCESS     read-write
   STATUS     mandatory
   DESCRIPTION
     "Dna attribute contains digits which form unique identifier of the 
      customer interface. It can be compared (approximation only) to 
      telephone number where phone number identifies unique telephone 
      set. Dna digits are selected and assigned by network operators. 
      MaximumLenOfDna is 15digits."
::= { mscIpiFrDnaAddressEntry 2 }

mscIpiFrDnaOutgoingOptionsTable OBJECT-TYPE
   SYNTAX     SEQUENCE OF MscIpiFrDnaOutgoingOptionsEntry
   ACCESS     not-accessible
   STATUS     mandatory
   DESCRIPTION
     "OutgoingOptions group defines call options of a Dna for calls 
      which are made out of the interface represented by Dna. All these 
      options are not used for calls arriving to the interface represented by 
      Dna."
::= { mscIpiFrDna 11 }

mscIpiFrDnaOutgoingOptionsEntry OBJECT-TYPE
   SYNTAX     MscIpiFrDnaOutgoingOptionsEntry
   ACCESS     not-accessible
   STATUS     mandatory
   DESCRIPTION
     "An entry in the mscIpiFrDnaOutgoingOptionsTable."
   INDEX {
      mscIpiFrIndex,
      mscIpiFrDnaIndex }
::= { mscIpiFrDnaOutgoingOptionsTable 1 }

MscIpiFrDnaOutgoingOptionsEntry ::= SEQUENCE {
   mscIpiFrDnaOutCalls
      INTEGER,
   mscIpiFrDnaOutDefaultPriority
      INTEGER,
   mscIpiFrDnaOutDefaultPathSensitivity
      INTEGER,
   mscIpiFrDnaOutPathSensitivityOverRide
      INTEGER,
   mscIpiFrDnaDefaultTransferPriority
      INTEGER,
   mscIpiFrDnaTransferPriorityOverRide
      INTEGER }

mscIpiFrDnaOutCalls OBJECT-TYPE
   SYNTAX     INTEGER  {
                 disallowed(0),
                 allowed(1) }
   ACCESS     read-only
   STATUS     mandatory
   DESCRIPTION
     "This attribute, if set to a value of allowed indicates that outgoing 
      calls (from the DTE to the network) can be made using this 
      particular Dna. If set to a value of disallowed , then outgoing calls 
      cannot be made using this Dna - such calls will be cleared by the 
      local DCE. This attribute corresponds to the CCITT 'Outgoing Calls 
      Barred' feature for Dnas in that outgoing calls are barred if this 
      attribute is set to a value of disallowed. Either outCalls, or incCalls 
      (or both) must be set to a value of allowed for this Dna to be 
      useable."
   DEFVAL     { disallowed }
::= { mscIpiFrDnaOutgoingOptionsEntry 1 }

mscIpiFrDnaOutDefaultPriority OBJECT-TYPE
   SYNTAX     INTEGER  {
                 normal(0),
                 high(1) }
   ACCESS     read-only
   STATUS     mandatory
   DESCRIPTION
     "This attribute, if set to normal indicates that the default priority for 
      outgoing calls (from the DTE to the network) using this particular 
      Dna is normal priority - if the priority is not specified by the DTE.  
      If this attribute is set to high then the default priority for outgoing 
      calls using this particular Dna is high priority.
      
      It can be overridden by the discardPriority under DLCI Direct Call 
      subcomponent."
   DEFVAL     { high }
::= { mscIpiFrDnaOutgoingOptionsEntry 7 }

mscIpiFrDnaOutDefaultPathSensitivity OBJECT-TYPE
   SYNTAX     INTEGER  {
                 throughput(0),
                 delay(1) }
   ACCESS     read-write
   STATUS     obsolete
   DESCRIPTION
     "This attribute specifies the default class of path sensitivity to 
      network for all outgoing calls using this particular Dna. The chosen 
      default class of path sensitivity applies to all outgoing calls 
      established using this Dna. 
      
      This attribute, if set to a value of throughput, indicates that the 
      default class is throughput sensitive. If set to a value of delay, then 
      the default class is delay sensitive. The default of 
      outDefaultPathSensitivity is delay."
   DEFVAL     { delay }
::= { mscIpiFrDnaOutgoingOptionsEntry 11 }

mscIpiFrDnaOutPathSensitivityOverRide OBJECT-TYPE
   SYNTAX     INTEGER  {
                 no(0),
                 yes(1) }
   ACCESS     read-write
   STATUS     obsolete
   DESCRIPTION
     "If this attribute is set to in the call request, the called end will use 
      the calling end provisioning data on path sensitivity to override its 
      own provisioning data.
      
      The default of outPathSensitivityOverRide is yes."
   DEFVAL     { yes }
::= { mscIpiFrDnaOutgoingOptionsEntry 12 }

mscIpiFrDnaDefaultTransferPriority OBJECT-TYPE
   SYNTAX     INTEGER  {
                 normal(0),
                 high(9) }
   ACCESS     read-write
   STATUS     mandatory
   DESCRIPTION
     "This attribute specifies the default transfer priority to network for 
      all outgoing calls using this particular Dna. It is overRidden by 
      the transferPriority provisioned in the DLCI Direct Call sub-
      component.
      
      The transfer priority is a preference specified by an application 
      according to its delay-sensitivity requirement. Frames with high
      transfer priority are served by the network before the frames with 
      normal priority. 
      
      Each transfer priority contains a predetermined setting for trunk 
      queue (interrupting, delay or throughput), routing metric (delay or 
      throughput). 
      
      When the transfer priority is set at high, the trunk queue is set to 
      high, the routing metric is set to delay.
      
      When the transfer priority is set at normal, the trunk queue is set to 
      normal, the routing metric is set to throughput.
      
      The default of defaultTransferPriority is high."
   DEFVAL     { high }
::= { mscIpiFrDnaOutgoingOptionsEntry 18 }

mscIpiFrDnaTransferPriorityOverRide OBJECT-TYPE
   SYNTAX     INTEGER  {
                 no(0),
                 yes(1) }
   ACCESS     read-write
   STATUS     mandatory
   DESCRIPTION
     "When this attribute is set to yes, the called end will use the calling 
      end provisioning data on transfer priority to override its own 
      provisioning data. If it is set no, the called end will use its own 
      provisioning data on transfer priority.
      
      For more information about transfer priority, please refer to the 
      previous attribute defaultTransferPriority.
      
      The default of transferPriorityOverRide is yes."
   DEFVAL     { yes }
::= { mscIpiFrDnaOutgoingOptionsEntry 19 }

mscIpiFrDnaIncomingOptionsTable OBJECT-TYPE
   SYNTAX     SEQUENCE OF MscIpiFrDnaIncomingOptionsEntry
   ACCESS     not-accessible
   STATUS     mandatory
   DESCRIPTION
     "IncomingOptions defines set of options for incoming calls. These 
      options are used for calls arriving to the interface represented by 
      Dna. For calls originated from the interfasce, IncomingOptions 
      attributes are not used."
::= { mscIpiFrDna 12 }

mscIpiFrDnaIncomingOptionsEntry OBJECT-TYPE
   SYNTAX     MscIpiFrDnaIncomingOptionsEntry
   ACCESS     not-accessible
   STATUS     mandatory
   DESCRIPTION
     "An entry in the mscIpiFrDnaIncomingOptionsTable."
   INDEX {
      mscIpiFrIndex,
      mscIpiFrDnaIndex }
::= { mscIpiFrDnaIncomingOptionsTable 1 }

MscIpiFrDnaIncomingOptionsEntry ::= SEQUENCE {
   mscIpiFrDnaIncCalls
      INTEGER,
   mscIpiFrDnaIncAccess
      INTEGER }

mscIpiFrDnaIncCalls OBJECT-TYPE
   SYNTAX     INTEGER  {
                 disallowed(0),
                 allowed(1) }
   ACCESS     read-only
   STATUS     mandatory
   DESCRIPTION
     "This attribute, if set to a value of allowed  indicates that incoming 
      calls (from the network to the DTE) can be made to this Dna. If set 
      to a value of disallowed, then incoming calls cannot be made to this 
      Dna - such calls will be cleared by the local DCE. This attribute 
      corresponds to the CCITT 'Incoming Calls Barred' feature for Dna's 
      in that incoming calls are barred if this attribute is set to a value of 
      disallowed.
      
      Either outCalls, or incCalls (or both) must be set to a value of 
      allowed for this Dna to be useable."
   DEFVAL     { allowed }
::= { mscIpiFrDnaIncomingOptionsEntry 1 }

mscIpiFrDnaIncAccess OBJECT-TYPE
   SYNTAX     INTEGER  {
                 disallowed(0),
                 allowed(1) }
   ACCESS     read-write
   STATUS     mandatory
   DESCRIPTION
     "This attribute is an extension of the Closed User Group (CUG) 
      facility, as follows:
      This attribute, if set to a value of allowed indicates that incoming 
      calls (from the network to the DTE) from the open (non-CUG) part 
      of the network are permitted. It also permits incoming calls from 
      DTEs that have Outgoing Access capabilities. If set to a value of 
      disallowed, then such calls cannot be made to this Dna - such calls 
      will be cleared by the local DCE.
      This attribute corresponds to the CCITT 'Closed User Group with 
      Incoming Access' feature for Dnas in that incoming access is 
      granted if this attribute is set to a value of allowed."
   DEFVAL     { disallowed }
::= { mscIpiFrDnaIncomingOptionsEntry 9 }

mscIpiFrDnaCallOptionsTable OBJECT-TYPE
   SYNTAX     SEQUENCE OF MscIpiFrDnaCallOptionsEntry
   ACCESS     not-accessible
   STATUS     mandatory
   DESCRIPTION
     "CallOptions group defines additional options for calls not related 
      directly to direction of a call."
::= { mscIpiFrDna 13 }

mscIpiFrDnaCallOptionsEntry OBJECT-TYPE
   SYNTAX     MscIpiFrDnaCallOptionsEntry
   ACCESS     not-accessible
   STATUS     mandatory
   DESCRIPTION
     "An entry in the mscIpiFrDnaCallOptionsTable."
   INDEX {
      mscIpiFrIndex,
      mscIpiFrDnaIndex }
::= { mscIpiFrDnaCallOptionsTable 1 }

MscIpiFrDnaCallOptionsEntry ::= SEQUENCE {
   mscIpiFrDnaServiceCategory
      INTEGER,
   mscIpiFrDnaAccountClass
      Unsigned32,
   mscIpiFrDnaServiceExchange
      Unsigned32 }

mscIpiFrDnaServiceCategory OBJECT-TYPE
   SYNTAX     INTEGER  {
                 gsp(0),
                 x25(1),
                 enhancedIti(2),
                 ncs(3),
                 mlti(4),
                 sm(5),
                 ici(6),
                 dsp3270(7),
                 iam(8),
                 mlhi(9),
                 term3270(10),
                 iti(11),
                 bsi(13),
                 hostIti(14),
                 x75(15),
                 hdsp3270(16),
                 api3201(20),
                 sdlc(21),
                 snaMultiHost(22),
                 redirectionServ(23),
                 trSnaTpad(24),
                 offnetNui(25),
                 gasServer(26),
                 vapServer(28),
                 vapAgent(29),
                 frameRelay(30),
                 ipiVc(31),
                 ipiFr(32) }
   ACCESS     read-only
   STATUS     mandatory
   DESCRIPTION
     "This attribute is assigned for each different type of service within 
      which this Dna is configured. It is placed into the Service Category 
      attribute in the accounting record by both ends of the Vc."
   DEFVAL     { ipiFr }
::= { mscIpiFrDnaCallOptionsEntry 1 }

mscIpiFrDnaAccountClass OBJECT-TYPE
   SYNTAX     Unsigned32 (0..255)
   ACCESS     read-write
   STATUS     mandatory
   DESCRIPTION
     "This attribute specifies the accounting class which is reserved for 
      network operations usage. Its value is returned in the accounting 
      record in the local and remote service type attributes. Use of this 
      attribute is decided by network operator and it is an arbitrary 
      number."
   DEFVAL     { 0 }
::= { mscIpiFrDnaCallOptionsEntry 10 }

mscIpiFrDnaServiceExchange OBJECT-TYPE
   SYNTAX     Unsigned32 (0..255)
   ACCESS     read-write
   STATUS     mandatory
   DESCRIPTION
     "This attribute is an arbitrary number, entered by the network 
      operator. It is included in the accounting record created by Vc."
   DEFVAL     { 0 }
::= { mscIpiFrDnaCallOptionsEntry 12 }


-- 
-- IpiFr Dna ClosedUserGroup
-- This group defines options associated with national or international 
-- CUG Identifier. Other DNAs in the network can have CUGs defined 
-- which groups these DNAs by CUG interlockCode. If DNAs are 
-- defined with CUGs, calls from DNAs which do not have the same 
-- interlockCode defined are refused. Attributes incAccess and 
-- outAccess can override this rule. IpiFr handles only incoming calls. 
-- Therefore, Closed User Group for this interface is defined for 
-- validation of incoming PVC calls only.

mscIpiFrDnaCug OBJECT IDENTIFIER ::= { mscIpiFrDna 2 }



mscIpiFrDnaCugRowStatusTable OBJECT-TYPE
   SYNTAX     SEQUENCE OF MscIpiFrDnaCugRowStatusEntry
   ACCESS     not-accessible
   STATUS     mandatory
   DESCRIPTION
     "This entry controls the addition and deletion of 
      mscIpiFrDnaCug components."
::= { mscIpiFrDnaCug 1 }

mscIpiFrDnaCugRowStatusEntry OBJECT-TYPE
   SYNTAX     MscIpiFrDnaCugRowStatusEntry
   ACCESS     not-accessible
   STATUS     mandatory
   DESCRIPTION
     "A single entry in the table represents a single 
      mscIpiFrDnaCug component."
   INDEX {
      mscIpiFrIndex,
      mscIpiFrDnaIndex,
      mscIpiFrDnaCugIndex }
::= { mscIpiFrDnaCugRowStatusTable 1 }

MscIpiFrDnaCugRowStatusEntry ::= SEQUENCE {
   mscIpiFrDnaCugRowStatus
      RowStatus,
   mscIpiFrDnaCugComponentName
      DisplayString,
   mscIpiFrDnaCugStorageType
      StorageType,
   mscIpiFrDnaCugIndex
      Integer32 }

mscIpiFrDnaCugRowStatus OBJECT-TYPE
   SYNTAX     RowStatus 
   ACCESS     read-write
   STATUS     mandatory
   DESCRIPTION
     "This variable is used as the basis for SNMP naming of
      mscIpiFrDnaCug components.
      These components can be added and deleted."
::= { mscIpiFrDnaCugRowStatusEntry 1 }

mscIpiFrDnaCugComponentName OBJECT-TYPE
   SYNTAX     DisplayString 
   ACCESS     read-only
   STATUS     mandatory
   DESCRIPTION
     "This variable provides the component's string name for
      use with the ASCII Console Interface"
::= { mscIpiFrDnaCugRowStatusEntry 2 }

mscIpiFrDnaCugStorageType OBJECT-TYPE
   SYNTAX     StorageType 
   ACCESS     read-only
   STATUS     mandatory
   DESCRIPTION
     "This variable represents the storage type value for the
      mscIpiFrDnaCug tables."
::= { mscIpiFrDnaCugRowStatusEntry 4 }

mscIpiFrDnaCugIndex OBJECT-TYPE
   SYNTAX     Integer32 (0..255)
   ACCESS     not-accessible
   STATUS     mandatory
   DESCRIPTION
     "This variable represents the index for the mscIpiFrDnaCug tables."
::= { mscIpiFrDnaCugRowStatusEntry 10 }

mscIpiFrDnaCugCugOptionsTable OBJECT-TYPE
   SYNTAX     SEQUENCE OF MscIpiFrDnaCugCugOptionsEntry
   ACCESS     not-accessible
   STATUS     mandatory
   DESCRIPTION
     "This group defines options for a CUG. Attributes in this group 
      define ClosedUserGroup options associated with interlockCode. 
      DNA's with the same CUG (interlockCode) can make calls within 
      this group. Various combinations which permit or prevent calls in 
      the same CUG group are defined here."
::= { mscIpiFrDnaCug 10 }

mscIpiFrDnaCugCugOptionsEntry OBJECT-TYPE
   SYNTAX     MscIpiFrDnaCugCugOptionsEntry
   ACCESS     not-accessible
   STATUS     mandatory
   DESCRIPTION
     "An entry in the mscIpiFrDnaCugCugOptionsTable."
   INDEX {
      mscIpiFrIndex,
      mscIpiFrDnaIndex,
      mscIpiFrDnaCugIndex }
::= { mscIpiFrDnaCugCugOptionsTable 1 }

MscIpiFrDnaCugCugOptionsEntry ::= SEQUENCE {
   mscIpiFrDnaCugType
      INTEGER,
   mscIpiFrDnaCugDnic
      DigitString,
   mscIpiFrDnaCugInterlockCode
      Unsigned32,
   mscIpiFrDnaCugIncCalls
      INTEGER }

mscIpiFrDnaCugType OBJECT-TYPE
   SYNTAX     INTEGER  {
                 national(0),
                 international(1) }
   ACCESS     read-write
   STATUS     mandatory
   DESCRIPTION
     "This attribute specifies the CUG type - the CUG is either a national 
      CUG, or an international CUG. International closed user groups are 
      usually established between DTEs for which there is an X.75 
      Gateway between; whereas national closed user groups are usually 
      established between DTEs for which there is no X.75 Gateway 
      between. (National CUGs cannot normally traverse an X.75 
      Gateway).
      If this attribute is set to national, then the CUG is a national CUG, 
      in which case, the dnic should be left at its default value since it is 
      not part of a national CUG. If this attribute is set to international, 
      then the CUG is an international CUG, in which case, the dnic 
      should be set appropriately as part of the CUG interlockCode."
   DEFVAL     { national }
::= { mscIpiFrDnaCugCugOptionsEntry 1 }

mscIpiFrDnaCugDnic OBJECT-TYPE
   SYNTAX     DigitString (SIZE (4))
   ACCESS     read-write
   STATUS     mandatory
   DESCRIPTION
     "This attribute specifies the dnic (Data Network ID Code) of the 
      CUG by which packet networks are identified. This attribute is not 
      applicable if the CUG is a national CUG, as specified by the CUG 
      type attribute. There are usually 1 or 2 dnics assigned per country, 
      for public networks. The U.S. is an exception where each BOC has 
      a dnic. Also, a group of private networks can have its own dnic.
      
      dnic value is not an arbitrary number. It is assigned by international 
      agreement and controlled by CCITT."
   DEFVAL     { '30303030'H }  -- "0000"
::= { mscIpiFrDnaCugCugOptionsEntry 2 }

mscIpiFrDnaCugInterlockCode OBJECT-TYPE
   SYNTAX     Unsigned32 (0..65535)
   ACCESS     read-write
   STATUS     mandatory
   DESCRIPTION
     "This attribute specifies the CUG identifier of a national or 
      international CUG call. It is an arbitrary number and it also can be 
      called CUG in some descriptions. Interfaces (DNA's) defined with 
      this number can make calls to DNA's with the same interlockCode."
   DEFVAL     { 65535 }
::= { mscIpiFrDnaCugCugOptionsEntry 3 }

mscIpiFrDnaCugIncCalls OBJECT-TYPE
   SYNTAX     INTEGER  {
                 disallowed(0),
                 allowed(1) }
   ACCESS     read-write
   STATUS     mandatory
   DESCRIPTION
     "This attribute, if set to allowed indicates that incoming calls (from 
      the network to the DTE) can be made using this particular CUG. If 
      set to disallowed, then incoming calls cannot be made using this 
      CUG - such calls will be cleared by the local DCE.
      This attribute corresponds to the CCITT 'Incoming Calls Barred' 
      feature for CUGs in that incoming calls are barred if this attribute is 
      set to a value of disallowed."
   DEFVAL     { allowed }
::= { mscIpiFrDnaCugCugOptionsEntry 6 }


-- IpiFr Lcn/n 
-- 
-- This component represents one Logical Channel Number 
-- responsible for logical connection with the PVC. There can be up to 
-- 24 instances of Lcn on the IpiFr component.

mscIpiFrLcn OBJECT IDENTIFIER ::= { mscIpiFr 4 }



mscIpiFrLcnRowStatusTable OBJECT-TYPE
   SYNTAX     SEQUENCE OF MscIpiFrLcnRowStatusEntry
   ACCESS     not-accessible
   STATUS     mandatory
   DESCRIPTION
     "This entry controls the addition and deletion of 
      mscIpiFrLcn components."
::= { mscIpiFrLcn 1 }

mscIpiFrLcnRowStatusEntry OBJECT-TYPE
   SYNTAX     MscIpiFrLcnRowStatusEntry
   ACCESS     not-accessible
   STATUS     mandatory
   DESCRIPTION
     "A single entry in the table represents a single 
      mscIpiFrLcn component."
   INDEX {
      mscIpiFrIndex,
      mscIpiFrLcnIndex }
::= { mscIpiFrLcnRowStatusTable 1 }

MscIpiFrLcnRowStatusEntry ::= SEQUENCE {
   mscIpiFrLcnRowStatus
      RowStatus,
   mscIpiFrLcnComponentName
      DisplayString,
   mscIpiFrLcnStorageType
      StorageType,
   mscIpiFrLcnIndex
      Integer32 }

mscIpiFrLcnRowStatus OBJECT-TYPE
   SYNTAX     RowStatus 
   ACCESS     read-write
   STATUS     mandatory
   DESCRIPTION
     "This variable is used as the basis for SNMP naming of
      mscIpiFrLcn components.
      These components can be added and deleted."
::= { mscIpiFrLcnRowStatusEntry 1 }

mscIpiFrLcnComponentName OBJECT-TYPE
   SYNTAX     DisplayString 
   ACCESS     read-only
   STATUS     mandatory
   DESCRIPTION
     "This variable provides the component's string name for
      use with the ASCII Console Interface"
::= { mscIpiFrLcnRowStatusEntry 2 }

mscIpiFrLcnStorageType OBJECT-TYPE
   SYNTAX     StorageType 
   ACCESS     read-only
   STATUS     mandatory
   DESCRIPTION
     "This variable represents the storage type value for the
      mscIpiFrLcn tables."
::= { mscIpiFrLcnRowStatusEntry 4 }

mscIpiFrLcnIndex OBJECT-TYPE
   SYNTAX     Integer32 (16..39)
   ACCESS     not-accessible
   STATUS     mandatory
   DESCRIPTION
     "This variable represents the index for the mscIpiFrLcn tables."
::= { mscIpiFrLcnRowStatusEntry 10 }

mscIpiFrLcnStateTable OBJECT-TYPE
   SYNTAX     SEQUENCE OF MscIpiFrLcnStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mscIpiFrLcn 10 }

mscIpiFrLcnStateEntry OBJECT-TYPE
   SYNTAX     MscIpiFrLcnStateEntry
   ACCESS     not-accessible
   STATUS     mandatory
   DESCRIPTION
     "An entry in the mscIpiFrLcnStateTable."
   INDEX {
      mscIpiFrIndex,
      mscIpiFrLcnIndex }
::= { mscIpiFrLcnStateTable 1 }

MscIpiFrLcnStateEntry ::= SEQUENCE {
   mscIpiFrLcnAdminState
      INTEGER,
   mscIpiFrLcnOperationalState
      INTEGER,
   mscIpiFrLcnUsageState
      INTEGER,
   mscIpiFrLcnAvailabilityStatus
      OCTET STRING,
   mscIpiFrLcnProceduralStatus
      OCTET STRING,
   mscIpiFrLcnControlStatus
      OCTET STRING,
   mscIpiFrLcnAlarmStatus
      OCTET STRING,
   mscIpiFrLcnStandbyStatus
      INTEGER,
   mscIpiFrLcnUnknownStatus
      INTEGER }

mscIpiFrLcnAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mscIpiFrLcnStateEntry 1 }

mscIpiFrLcnOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mscIpiFrLcnStateEntry 2 }

mscIpiFrLcnUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mscIpiFrLcnStateEntry 3 }

mscIpiFrLcnAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mscIpiFrLcnStateEntry 4 }

mscIpiFrLcnProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mscIpiFrLcnStateEntry 5 }

mscIpiFrLcnControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mscIpiFrLcnStateEntry 6 }

mscIpiFrLcnAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mscIpiFrLcnStateEntry 7 }

mscIpiFrLcnStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mscIpiFrLcnStateEntry 8 }

mscIpiFrLcnUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mscIpiFrLcnStateEntry 9 }

mscIpiFrLcnOperTable OBJECT-TYPE
   SYNTAX     SEQUENCE OF MscIpiFrLcnOperEntry
   ACCESS     not-accessible
   STATUS     mandatory
   DESCRIPTION
     "This group contains status of the internal IP network interface."
::= { mscIpiFrLcn 11 }

mscIpiFrLcnOperEntry OBJECT-TYPE
   SYNTAX     MscIpiFrLcnOperEntry
   ACCESS     not-accessible
   STATUS     mandatory
   DESCRIPTION
     "An entry in the mscIpiFrLcnOperTable."
   INDEX {
      mscIpiFrIndex,
      mscIpiFrLcnIndex }
::= { mscIpiFrLcnOperTable 1 }

MscIpiFrLcnOperEntry ::= SEQUENCE {
   mscIpiFrLcnIpInterfaceDevice
      INTEGER,
   mscIpiFrLcnOpRemoteIpAddress
      IpAddress,
   mscIpiFrLcnPacketsSent
      Counter32,
   mscIpiFrLcnPacketsReceived
      Counter32,
   mscIpiFrLcnDiscardTxPackets
      Counter32,
   mscIpiFrLcnDiscardRcvPackets
      Counter32 }

mscIpiFrLcnIpInterfaceDevice OBJECT-TYPE
   SYNTAX     INTEGER  {
                 inactive(0),
                 active(1) }
   ACCESS     read-only
   STATUS     mandatory
   DESCRIPTION
     "The status of the internal IP network interface is inactive until either 
      the remoteIpAddress attribute is provisioned, or an IP packet is 
      exchanged between a Network Management Station and the internal 
      IP network interface (via the LCN). At this point, the status changes 
      to active."
   DEFVAL     { inactive }
::= { mscIpiFrLcnOperEntry 1 }

mscIpiFrLcnOpRemoteIpAddress OBJECT-TYPE
   SYNTAX     IpAddress 
   ACCESS     read-only
   STATUS     mandatory
   DESCRIPTION
     "This attribute indicates the IP address of the remote network device 
      connected to this interface. The value is either 0.0.0.0 until the frist 
      data packe tis received from the remote end, or is the value 
      provisioned in remoteIpAddress."
   DEFVAL     { '00000000'H }  -- "0.0.0.0"
::= { mscIpiFrLcnOperEntry 2 }

mscIpiFrLcnPacketsSent OBJECT-TYPE
   SYNTAX     Counter32 
   ACCESS     read-only
   STATUS     mandatory
   DESCRIPTION
     "This attribute counts the number of IP packets sent from this 
      interface."
::= { mscIpiFrLcnOperEntry 3 }

mscIpiFrLcnPacketsReceived OBJECT-TYPE
   SYNTAX     Counter32 
   ACCESS     read-only
   STATUS     mandatory
   DESCRIPTION
     "This attribute counts the number of IP packets received from the 
      remote network device."
::= { mscIpiFrLcnOperEntry 4 }

mscIpiFrLcnDiscardTxPackets OBJECT-TYPE
   SYNTAX     Counter32 
   ACCESS     read-only
   STATUS     mandatory
   DESCRIPTION
     "This attribute counts the number of IP packets destined to the 
      remote end which were discarded by this interface."
::= { mscIpiFrLcnOperEntry 5 }

mscIpiFrLcnDiscardRcvPackets OBJECT-TYPE
   SYNTAX     Counter32 
   ACCESS     read-only
   STATUS     mandatory
   DESCRIPTION
     "This attribute counts the number of IP packets received from the 
      remote end which were discarded by this interface."
::= { mscIpiFrLcnOperEntry 6 }

mscIpiFrLcnProvTable OBJECT-TYPE
   SYNTAX     SEQUENCE OF MscIpiFrLcnProvEntry
   ACCESS     not-accessible
   STATUS     mandatory
   DESCRIPTION
     "This group provides the provisionable attributes for the IpiFR Lcn 
      component."
::= { mscIpiFrLcn 12 }

mscIpiFrLcnProvEntry OBJECT-TYPE
   SYNTAX     MscIpiFrLcnProvEntry
   ACCESS     not-accessible
   STATUS     mandatory
   DESCRIPTION
     "An entry in the mscIpiFrLcnProvTable."
   INDEX {
      mscIpiFrIndex,
      mscIpiFrLcnIndex }
::= { mscIpiFrLcnProvTable 1 }

MscIpiFrLcnProvEntry ::= SEQUENCE {
   mscIpiFrLcnRemoteIpAddress
      IpAddress }

mscIpiFrLcnRemoteIpAddress OBJECT-TYPE
   SYNTAX     IpAddress 
   ACCESS     read-write
   STATUS     mandatory
   DESCRIPTION
     "This attribute specifies the IP address of the remote device 
      connected to this Lcn interface. This device can be a host, and / or a 
      gateway. If the device is a gateway, and StaticRoutes are defined 
      using this gateway, it is recommended that this attribute be set. It is 
      also recommended to set this attribute, if management applications 
      such as Software Download and SNMP, which can initiate IP traffic 
      with Network Management Stations, are potentially using this Lcn 
      interface. IP routing information within IpiFr is not known or 
      activated for this Lcn interface until the remoteIpAddress is known.
      
      When the destination IpAddress is left at its default value of 0.0.0.0, 
      the calling IP address is learnt from the first data packet received."
   DEFVAL     { '00000000'H }  -- "0.0.0.0"
::= { mscIpiFrLcnProvEntry 1 }


-- IPIFR Lcn/x DC
-- This component defines direct call options for calls issued without 
-- operator intervention. Connection is complete and can be initiated 
-- automatically.

mscIpiFrLcnDc OBJECT IDENTIFIER ::= { mscIpiFrLcn 2 }



mscIpiFrLcnDcRowStatusTable OBJECT-TYPE
   SYNTAX     SEQUENCE OF MscIpiFrLcnDcRowStatusEntry
   ACCESS     not-accessible
   STATUS     mandatory
   DESCRIPTION
     "This entry controls the addition and deletion of 
      mscIpiFrLcnDc components."
::= { mscIpiFrLcnDc 1 }

mscIpiFrLcnDcRowStatusEntry OBJECT-TYPE
   SYNTAX     MscIpiFrLcnDcRowStatusEntry
   ACCESS     not-accessible
   STATUS     mandatory
   DESCRIPTION
     "A single entry in the table represents a single 
      mscIpiFrLcnDc component."
   INDEX {
      mscIpiFrIndex,
      mscIpiFrLcnIndex,
      mscIpiFrLcnDcIndex }
::= { mscIpiFrLcnDcRowStatusTable 1 }

MscIpiFrLcnDcRowStatusEntry ::= SEQUENCE {
   mscIpiFrLcnDcRowStatus
      RowStatus,
   mscIpiFrLcnDcComponentName
      DisplayString,
   mscIpiFrLcnDcStorageType
      StorageType,
   mscIpiFrLcnDcIndex
      NonReplicated }

mscIpiFrLcnDcRowStatus OBJECT-TYPE
   SYNTAX     RowStatus 
   ACCESS     read-only
   STATUS     mandatory
   DESCRIPTION
     "This variable is used as the basis for SNMP naming of
      mscIpiFrLcnDc components.
      These components cannot be added nor deleted."
::= { mscIpiFrLcnDcRowStatusEntry 1 }

mscIpiFrLcnDcComponentName OBJECT-TYPE
   SYNTAX     DisplayString 
   ACCESS     read-only
   STATUS     mandatory
   DESCRIPTION
     "This variable provides the component's string name for
      use with the ASCII Console Interface"
::= { mscIpiFrLcnDcRowStatusEntry 2 }

mscIpiFrLcnDcStorageType OBJECT-TYPE
   SYNTAX     StorageType 
   ACCESS     read-only
   STATUS     mandatory
   DESCRIPTION
     "This variable represents the storage type value for the
      mscIpiFrLcnDc tables."
::= { mscIpiFrLcnDcRowStatusEntry 4 }

mscIpiFrLcnDcIndex OBJECT-TYPE
   SYNTAX     NonReplicated 
   ACCESS     not-accessible
   STATUS     mandatory
   DESCRIPTION
     "This variable represents the index for the mscIpiFrLcnDc tables."
::= { mscIpiFrLcnDcRowStatusEntry 10 }

mscIpiFrLcnDcOptionsTable OBJECT-TYPE
   SYNTAX     SEQUENCE OF MscIpiFrLcnDcOptionsEntry
   ACCESS     not-accessible
   STATUS     mandatory
   DESCRIPTION
     "Options group defines attributes associated with direct call. It 
      defines complete connection in terms of path and call options. This 
      connection can be permanent (pvc) or, in future release, switched 
      (svc). It can have facilities. The total number of bytes of facilities 
      including the facility codes, and all of the facility data from all of 
      the four classes of facilities:
      CCITT_Facilities
      DTE_Facilities
      National_Facilities
      International_Facilities
      must not exceed 512 bytes."
::= { mscIpiFrLcnDc 10 }

mscIpiFrLcnDcOptionsEntry OBJECT-TYPE
   SYNTAX     MscIpiFrLcnDcOptionsEntry
   ACCESS     not-accessible
   STATUS     mandatory
   DESCRIPTION
     "An entry in the mscIpiFrLcnDcOptionsTable."
   INDEX {
      mscIpiFrIndex,
      mscIpiFrLcnIndex,
      mscIpiFrLcnDcIndex }
::= { mscIpiFrLcnDcOptionsTable 1 }

MscIpiFrLcnDcOptionsEntry ::= SEQUENCE {
   mscIpiFrLcnDcRemoteNpi
      INTEGER,
   mscIpiFrLcnDcRemoteDna
      DigitString,
   mscIpiFrLcnDcRemoteDlci
      Unsigned32,
   mscIpiFrLcnDcType
      INTEGER,
   mscIpiFrLcnDcTransferPriority
      INTEGER,
   mscIpiFrLcnDcDiscardPriority
      INTEGER }

mscIpiFrLcnDcRemoteNpi OBJECT-TYPE
   SYNTAX     INTEGER  {
                 x121(0),
                 e164(1) }
   ACCESS     read-write
   STATUS     mandatory
   DESCRIPTION
     "RemoteNumbering Plan Indicator (Npi) indicates the numbering 
      plan used in the remoteDna."
   DEFVAL     { x121 }
::= { mscIpiFrLcnDcOptionsEntry 3 }

mscIpiFrLcnDcRemoteDna OBJECT-TYPE
   SYNTAX     DigitString (SIZE (1..15))
   ACCESS     read-write
   STATUS     mandatory
   DESCRIPTION
     "This attribute specifies the Data Network Address (Dna) of the 
      remote. This is the called (destination) DTE address (Dna) to which 
      this direct call will be sent.  Initially, the called DTE address 
      attribute must be present, that is, there must be a valid destination 
      address.  However, it may be possible in the future to configure the 
      direct call with a mnemonic address, in which case, this attribute 
      will contain a zero-length Dna, and the mnemonic address will be 
      carried as one of the facilities."
::= { mscIpiFrLcnDcOptionsEntry 4 }

mscIpiFrLcnDcRemoteDlci OBJECT-TYPE
   SYNTAX     Unsigned32 (16..1007)
   ACCESS     read-write
   STATUS     mandatory
   DESCRIPTION
     "This attribute provides the value of the remote DLCI (Data Link 
      Connection Identifier)"
::= { mscIpiFrLcnDcOptionsEntry 5 }

mscIpiFrLcnDcType OBJECT-TYPE
   SYNTAX     INTEGER  {
                 permanentMaster(1),
                 permanentSlave(2) }
   ACCESS     read-only
   STATUS     mandatory
   DESCRIPTION
     "This attribute specifies the type of Vc call:
      permanentMaster, 
      permanentSlave, 
      
      If the value is set to permanentMaster, then a permanent 
      connection will be established between 2 ends. The remote end 
      must be defined as a permanentSlave, permanentBackupSlave or 
      permanentSlaveWithBackup. The connection cannot be established 
      if the remote end is defined as anything else. The end defined as 
      permanentMaster always initiates the calls. It will attempt to call 
      once per minute.
      
      If the value is set to permanentSlave then a permanent connection 
      will be established between 2 ends. The remote end must be defined 
      as a permanentMaster. The connection cannot be established if the 
      remote end is defined as anything else. The permanentSlave end 
      will attempt to call once per minute."
   DEFVAL     { permanentSlave }
::= { mscIpiFrLcnDcOptionsEntry 6 }

mscIpiFrLcnDcTransferPriority OBJECT-TYPE
   SYNTAX     INTEGER  {
                 normal(0),
                 high(9),
                 useDnaDefTP(255) }
   ACCESS     read-write
   STATUS     mandatory
   DESCRIPTION
     "This attribute specifies the transfer priority to network for the 
      outgoing calls using this particular DLCI. It overRides the 
      defaultTransferPriority provisioned in its associated Dna 
      component.
      
      The transfer priority is a preference specified by an application 
      according to its delay-sensitivity requirement. Frames with high 
      transfer priority are served by the network before the frames with 
      normal priority.
      
      Each transfer priority contains a predetermined setting for trunk 
      queue (interrupting, delay or throughput), routing metric (delay or 
      throughput). 
      
      When the transfer priority is set at high, the trunk queue is set to 
      high, the routing metric is set to delay.
      
      When the transfer priority is set at normal, the trunk queue is set to 
      normal, the routing metric is set to throughput.
      
      The default of transferPriority is useDnaDefTP. It means using the 
      provisioning value under defaultTransferPriority of its associated 
      Dna for this DLCI."
   DEFVAL     { useDnaDefTP }
::= { mscIpiFrLcnDcOptionsEntry 9 }

mscIpiFrLcnDcDiscardPriority OBJECT-TYPE
   SYNTAX     INTEGER  {
                 normal(0),
                 high(1),
                 useDnaDefPriority(3) }
   ACCESS     read-write
   STATUS     mandatory
   DESCRIPTION
     "This attribute specifies the discard priority for outgoing call using 
      this DLCI. 
      
      The discard priority has three provisioning values: normal, high, 
      and useDnaDefPriority. Traffic with normal priority are discarded 
      first than the traffic with high priority. The Dna default value 
      (provisioned by outDefaultPriority) is taken if this attribute is set 
      to the value useDnaDefPriority.
      
      The default of discardPriority is useDnaDefPriority."
   DEFVAL     { useDnaDefPriority }
::= { mscIpiFrLcnDcOptionsEntry 10 }

mscIpiFrLcnDcNfaTable OBJECT-TYPE
   SYNTAX     SEQUENCE OF MscIpiFrLcnDcNfaEntry
   ACCESS     not-accessible
   STATUS     obsolete
   DESCRIPTION
     "This is the i'th National facility required for this direct call. Within 
      the provisioning system, the user specifies the facility code along 
      with the facility parameters. The facility is represented internally as 
      a hexadecimal string following the X.25 CCITT representation for 
      facility data.
      
      Two explicit attributes discardPriority and transferPriority are 
      created to replace H.01 and H.30 in the group 
      VcsDirectCallOptionsProv of this file. The migrate escape here 
      (DcComponent::migrateFaxEscape) propagates the old 
      provisioning data under H.01. 
      
      The rule of the above propagation are: 0 in H.01 is equivalent to 
      discardPriority 0; 1 in H.01 is equivalent to discardPriority 1. And 
      0 in H.30 is equivalent to transferPriority normal; 1 in H.30 is 
      equivalent to transferPriority high.
      
      Please refer to discardPriority and transferPriority for more 
      information on how to use them."
::= { mscIpiFrLcnDc 222 }

mscIpiFrLcnDcNfaEntry OBJECT-TYPE
   SYNTAX     MscIpiFrLcnDcNfaEntry
   ACCESS     not-accessible
   STATUS     obsolete
   DESCRIPTION
     "An entry in the mscIpiFrLcnDcNfaTable."
   INDEX {
      mscIpiFrIndex,
      mscIpiFrLcnIndex,
      mscIpiFrLcnDcIndex,
      mscIpiFrLcnDcNfaIndex }
::= { mscIpiFrLcnDcNfaTable 1 }

MscIpiFrLcnDcNfaEntry ::= SEQUENCE {
   mscIpiFrLcnDcNfaIndex
      Integer32,
   mscIpiFrLcnDcNfaValue
      HexString,
   mscIpiFrLcnDcNfaRowStatus
      RowStatus }

mscIpiFrLcnDcNfaIndex OBJECT-TYPE
   SYNTAX     Integer32 (1)
   ACCESS     not-accessible
   STATUS     obsolete
   DESCRIPTION
     "This variable represents the index for the mscIpiFrLcnDcNfaTable."
::= { mscIpiFrLcnDcNfaEntry 1 }

mscIpiFrLcnDcNfaValue OBJECT-TYPE
   SYNTAX     HexString (SIZE (0..128))
   ACCESS     read-write
   STATUS     obsolete
   DESCRIPTION
     "This variable represents an individual value for the
      mscIpiFrLcnDcNfaTable."
::= { mscIpiFrLcnDcNfaEntry 2 }

mscIpiFrLcnDcNfaRowStatus OBJECT-TYPE
   SYNTAX     RowStatus 
   ACCESS     write-only
   STATUS     obsolete
   DESCRIPTION
     "This variable is used to control the addition and deletion 
      of individual values of the mscIpiFrLcnDcNfaTable."
::= { mscIpiFrLcnDcNfaEntry 3 }


-- This component defines attributes collected by Frame Relay Vc.

mscIpiFrLcnVc OBJECT IDENTIFIER ::= { mscIpiFrLcn 3 }



mscIpiFrLcnVcRowStatusTable OBJECT-TYPE
   SYNTAX     SEQUENCE OF MscIpiFrLcnVcRowStatusEntry
   ACCESS     not-accessible
   STATUS     mandatory
   DESCRIPTION
     "This entry controls the addition and deletion of 
      mscIpiFrLcnVc components."
::= { mscIpiFrLcnVc 1 }

mscIpiFrLcnVcRowStatusEntry OBJECT-TYPE
   SYNTAX     MscIpiFrLcnVcRowStatusEntry
   ACCESS     not-accessible
   STATUS     mandatory
   DESCRIPTION
     "A single entry in the table represents a single 
      mscIpiFrLcnVc component."
   INDEX {
      mscIpiFrIndex,
      mscIpiFrLcnIndex,
      mscIpiFrLcnVcIndex }
::= { mscIpiFrLcnVcRowStatusTable 1 }

MscIpiFrLcnVcRowStatusEntry ::= SEQUENCE {
   mscIpiFrLcnVcRowStatus
      RowStatus,
   mscIpiFrLcnVcComponentName
      DisplayString,
   mscIpiFrLcnVcStorageType
      StorageType,
   mscIpiFrLcnVcIndex
      NonReplicated }

mscIpiFrLcnVcRowStatus OBJECT-TYPE
   SYNTAX     RowStatus 
   ACCESS     read-only
   STATUS     mandatory
   DESCRIPTION
     "This variable is used as the basis for SNMP naming of
      mscIpiFrLcnVc components.
      These components cannot be added nor deleted."
::= { mscIpiFrLcnVcRowStatusEntry 1 }

mscIpiFrLcnVcComponentName OBJECT-TYPE
   SYNTAX     DisplayString 
   ACCESS     read-only
   STATUS     mandatory
   DESCRIPTION
     "This variable provides the component's string name for
      use with the ASCII Console Interface"
::= { mscIpiFrLcnVcRowStatusEntry 2 }

mscIpiFrLcnVcStorageType OBJECT-TYPE
   SYNTAX     StorageType 
   ACCESS     read-only
   STATUS     mandatory
   DESCRIPTION
     "This variable represents the storage type value for the
      mscIpiFrLcnVc tables."
::= { mscIpiFrLcnVcRowStatusEntry 4 }

mscIpiFrLcnVcIndex OBJECT-TYPE
   SYNTAX     NonReplicated 
   ACCESS     not-accessible
   STATUS     mandatory
   DESCRIPTION
     "This variable represents the index for the mscIpiFrLcnVc tables."
::= { mscIpiFrLcnVcRowStatusEntry 10 }

mscIpiFrLcnVcCadTable OBJECT-TYPE
   SYNTAX     SEQUENCE OF MscIpiFrLcnVcCadEntry
   ACCESS     not-accessible
   STATUS     mandatory
   DESCRIPTION
     "This group represents operational call data related to Frame Relay 
      Vc. It can be displayed only for Frame Relay Vc which is created by 
      application."
::= { mscIpiFrLcnVc 10 }

mscIpiFrLcnVcCadEntry OBJECT-TYPE
   SYNTAX     MscIpiFrLcnVcCadEntry
   ACCESS     not-accessible
   STATUS     mandatory
   DESCRIPTION
     "An entry in the mscIpiFrLcnVcCadTable."
   INDEX {
      mscIpiFrIndex,
      mscIpiFrLcnIndex,
      mscIpiFrLcnVcIndex }
::= { mscIpiFrLcnVcCadTable 1 }

MscIpiFrLcnVcCadEntry ::= SEQUENCE {
   mscIpiFrLcnVcType
      INTEGER,
   mscIpiFrLcnVcState
      INTEGER,
   mscIpiFrLcnVcPreviousState
      INTEGER,
   mscIpiFrLcnVcDiagnosticCode
      Unsigned32,
   mscIpiFrLcnVcPreviousDiagnosticCode
      Unsigned32,
   mscIpiFrLcnVcCalledNpi
      INTEGER,
   mscIpiFrLcnVcCalledDna
      DigitString,
   mscIpiFrLcnVcCalledLcn
      Unsigned32,
   mscIpiFrLcnVcCallingNpi
      INTEGER,
   mscIpiFrLcnVcCallingDna
      DigitString,
   mscIpiFrLcnVcCallingLcn
      Unsigned32,
   mscIpiFrLcnVcAccountingEnabled
      INTEGER,
   mscIpiFrLcnVcFastSelectCall
      INTEGER,
   mscIpiFrLcnVcPathReliability
      INTEGER,
   mscIpiFrLcnVcAccountingEnd
      INTEGER,
   mscIpiFrLcnVcPriority
      INTEGER,
   mscIpiFrLcnVcSegmentSize
      Unsigned32,
   mscIpiFrLcnVcMaxSubnetPktSize
      Unsigned32,
   mscIpiFrLcnVcRcosToNetwork
      INTEGER,
   mscIpiFrLcnVcRcosFromNetwork
      INTEGER,
   mscIpiFrLcnVcEmissionPriorityToNetwork
      INTEGER,
   mscIpiFrLcnVcEmissionPriorityFromNetwork
      INTEGER,
   mscIpiFrLcnVcDataPath
      AsciiString }

mscIpiFrLcnVcType OBJECT-TYPE
   SYNTAX     INTEGER  {
                 svc(0),
                 pvc(1),
                 spvc(2),
                 frf10spvc(3) }
   ACCESS     read-only
   STATUS     mandatory
   DESCRIPTION
     "This attribute displays the type of call, pvc,svc,spvc or frf10spvc."
::= { mscIpiFrLcnVcCadEntry 1 }

mscIpiFrLcnVcState OBJECT-TYPE
   SYNTAX     INTEGER  {
                 creating(0),
                 readyP1(1),
                 dteWaitingP2(2),
                 dceWaitingP3(3),
                 dataTransferP4(4),
                 unsupportedP5(5),
                 dteClearRequestP6(6),
                 dceClearIndicationP7(7),
                 termination(8) }
   ACCESS     read-only
   STATUS     mandatory
   DESCRIPTION
     "This attribute displays the state of call control. P5 state is not 
      supported but is listed for completness. Transitions from one state to 
      another take very short time. state most often displayed is 
      dataTransferP4."
::= { mscIpiFrLcnVcCadEntry 2 }

mscIpiFrLcnVcPreviousState OBJECT-TYPE
   SYNTAX     INTEGER  {
                 creating(0),
                 readyP1(1),
                 dteWaitingP2(2),
                 dceWaitingP3(3),
                 dataTransferP4(4),
                 unsupportedP5(5),
                 dteClearRequestP6(6),
                 dceClearIndicationP7(7),
                 termination(8) }
   ACCESS     read-only
   STATUS     mandatory
   DESCRIPTION
     "This attribute displays the previous state of call control. This is a 
      valuable field to determine how the processing is progressing."
::= { mscIpiFrLcnVcCadEntry 3 }

mscIpiFrLcnVcDiagnosticCode OBJECT-TYPE
   SYNTAX     Unsigned32 (0..255)
   ACCESS     read-only
   STATUS     mandatory
   DESCRIPTION
     "This attribute displays the internal substate of call control. It is used 
      to further refine state of call processing."
::= { mscIpiFrLcnVcCadEntry 4 }

mscIpiFrLcnVcPreviousDiagnosticCode OBJECT-TYPE
   SYNTAX     Unsigned32 (0..255)
   ACCESS     read-only
   STATUS     mandatory
   DESCRIPTION
     "This attribute displays the internal substate of call control. It is used 
      to further refine state of call processing."
::= { mscIpiFrLcnVcCadEntry 5 }

mscIpiFrLcnVcCalledNpi OBJECT-TYPE
   SYNTAX     INTEGER  {
                 x121(0),
                 e164(1) }
   ACCESS     read-only
   STATUS     mandatory
   DESCRIPTION
     "This attribute displays the Numbering Plan Indicator (NPI) of the 
      called end."
::= { mscIpiFrLcnVcCadEntry 6 }

mscIpiFrLcnVcCalledDna OBJECT-TYPE
   SYNTAX     DigitString (SIZE (1..15))
   ACCESS     read-only
   STATUS     mandatory
   DESCRIPTION
     "This attribute displays the Data Network Address (Dna) of the 
      called (destination) DTE to which this call is sent. This address if 
      defined at recieving end will complete Vc connection."
::= { mscIpiFrLcnVcCadEntry 7 }

mscIpiFrLcnVcCalledLcn OBJECT-TYPE
   SYNTAX     Unsigned32 (1..65535)
   ACCESS     read-only
   STATUS     mandatory
   DESCRIPTION
     "This attribute displays the Logical Channel Number of the called 
      end. It is valid only after both ends of Vc exchanged relevant 
      information."
::= { mscIpiFrLcnVcCadEntry 8 }

mscIpiFrLcnVcCallingNpi OBJECT-TYPE
   SYNTAX     INTEGER  {
                 x121(0),
                 e164(1) }
   ACCESS     read-only
   STATUS     mandatory
   DESCRIPTION
     "This attribute displays the Numbering Plan Indicator (NPI) of the 
      calling end."
::= { mscIpiFrLcnVcCadEntry 9 }

mscIpiFrLcnVcCallingDna OBJECT-TYPE
   SYNTAX     DigitString (SIZE (1..15))
   ACCESS     read-only
   STATUS     mandatory
   DESCRIPTION
     "This attribute displays the Data Network Address (Dna) of the 
      calling end."
::= { mscIpiFrLcnVcCadEntry 10 }

mscIpiFrLcnVcCallingLcn OBJECT-TYPE
   SYNTAX     Unsigned32 (1..65535)
   ACCESS     read-only
   STATUS     mandatory
   DESCRIPTION
     "This attribute displays the Logical Channel Number of the calling 
      end."
::= { mscIpiFrLcnVcCadEntry 11 }

mscIpiFrLcnVcAccountingEnabled OBJECT-TYPE
   SYNTAX     INTEGER  {
                 yes(0),
                 no(1) }
   ACCESS     read-only
   STATUS     mandatory
   DESCRIPTION
     "This attribute indicates that this optional section of accounting 
      record is suppressed or permitted. If accountingEnabled is yes, 
      conditions for generation of accounting record were met. These 
      conditions include billing options, vc recovery conditions and 
      Module wide accounting data options."
::= { mscIpiFrLcnVcCadEntry 12 }

mscIpiFrLcnVcFastSelectCall OBJECT-TYPE
   SYNTAX     INTEGER  {
                 no(0),
                 yes(1) }
   ACCESS     read-only
   STATUS     mandatory
   DESCRIPTION
     "This attribute displays that this is a fast select call."
::= { mscIpiFrLcnVcCadEntry 13 }

mscIpiFrLcnVcPathReliability OBJECT-TYPE
   SYNTAX     INTEGER  {
                 high(0),
                 normal(1) }
   ACCESS     read-only
   STATUS     mandatory
   DESCRIPTION
     "This attribute displays the path reliability."
::= { mscIpiFrLcnVcCadEntry 19 }

mscIpiFrLcnVcAccountingEnd OBJECT-TYPE
   SYNTAX     INTEGER  {
                 callingEnd(0),
                 calledEnd(1) }
   ACCESS     read-only
   STATUS     mandatory
   DESCRIPTION
     "This attribute indicates if this end should generate an accounting 
      record. Normally, callingEnd is the end to generate an accounting 
      record."
::= { mscIpiFrLcnVcCadEntry 20 }

mscIpiFrLcnVcPriority OBJECT-TYPE
   SYNTAX     INTEGER  {
                 normal(0),
                 high(1) }
   ACCESS     read-only
   STATUS     mandatory
   DESCRIPTION
     "This attribute displays whether the call is a normal or a high 
      priority call."
::= { mscIpiFrLcnVcCadEntry 21 }

mscIpiFrLcnVcSegmentSize OBJECT-TYPE
   SYNTAX     Unsigned32 (0..4096)
   ACCESS     read-only
   STATUS     mandatory
   DESCRIPTION
     "This attribute displays the segment size (in bytes) used on the call. 
      It is used to calculate the number of segments transmitted and 
      received."
::= { mscIpiFrLcnVcCadEntry 22 }

mscIpiFrLcnVcMaxSubnetPktSize OBJECT-TYPE
   SYNTAX     Unsigned32 (0..4096)
   ACCESS     read-only
   STATUS     mandatory
   DESCRIPTION
     "This attribute indicates the maximum packet size allowed on the Vc."
::= { mscIpiFrLcnVcCadEntry 27 }

mscIpiFrLcnVcRcosToNetwork OBJECT-TYPE
   SYNTAX     INTEGER  {
                 throughput(0),
                 delay(1),
                 multimedia(2) }
   ACCESS     read-only
   STATUS     mandatory
   DESCRIPTION
     "This attribute indicates the routing metric routing class of service to
      the network."
::= { mscIpiFrLcnVcCadEntry 28 }

mscIpiFrLcnVcRcosFromNetwork OBJECT-TYPE
   SYNTAX     INTEGER  {
                 throughput(0),
                 delay(1),
                 multimedia(2) }
   ACCESS     read-only
   STATUS     mandatory
   DESCRIPTION
     "This attribute displays the routing metric Routing Class of Service 
      from the Network."
::= { mscIpiFrLcnVcCadEntry 29 }

mscIpiFrLcnVcEmissionPriorityToNetwork OBJECT-TYPE
   SYNTAX     INTEGER  {
                 normal(0),
                 high(1),
                 interrupting(2) }
   ACCESS     read-only
   STATUS     mandatory
   DESCRIPTION
     "This attribute displays the network internal emission priotity to the 
      network."
::= { mscIpiFrLcnVcCadEntry 30 }

mscIpiFrLcnVcEmissionPriorityFromNetwork OBJECT-TYPE
   SYNTAX     INTEGER  {
                 normal(0),
                 high(1),
                 interrupting(2) }
   ACCESS     read-only
   STATUS     mandatory
   DESCRIPTION
     "This attribute displays the network internal emission priotity from 
      the network."
::= { mscIpiFrLcnVcCadEntry 31 }

mscIpiFrLcnVcDataPath OBJECT-TYPE
   SYNTAX     AsciiString (SIZE (0..32))
   ACCESS     read-only
   STATUS     mandatory
   DESCRIPTION
     "This attribute indicates the data path used by the connection. The 
      data path is provisioned in Dna and DirectCall components. The 
      displayed value of this attribute can be different from the 
      provisioned value.
      
      If the connection is using dprsOnly data path, the string 
      dprsOnly is displayed. (dynamic packet routing system)
      
      If the connection is using dprsMcsOnly data path, the string 
      dprsMcsOnly is displayed.
      
      If the connection is using dprsMcsFirst data path, the string 
      dprsMcsFirst is displayed."
::= { mscIpiFrLcnVcCadEntry 32 }

mscIpiFrLcnVcIntdTable OBJECT-TYPE
   SYNTAX     SEQUENCE OF MscIpiFrLcnVcIntdEntry
   ACCESS     not-accessible
   STATUS     mandatory
   DESCRIPTION
     "This group defines display of interval data collected by Vc. Data in 
      this group is variable and may depend on time when this display 
      command is issued."
::= { mscIpiFrLcnVc 11 }

mscIpiFrLcnVcIntdEntry OBJECT-TYPE
   SYNTAX     MscIpiFrLcnVcIntdEntry
   ACCESS     not-accessible
   STATUS     mandatory
   DESCRIPTION
     "An entry in the mscIpiFrLcnVcIntdTable."
   INDEX {
      mscIpiFrIndex,
      mscIpiFrLcnIndex,
      mscIpiFrLcnVcIndex }
::= { mscIpiFrLcnVcIntdTable 1 }

MscIpiFrLcnVcIntdEntry ::= SEQUENCE {
   mscIpiFrLcnVcCallReferenceNumber
      Hex,
   mscIpiFrLcnVcElapsedTimeTillNow
      Unsigned32,
   mscIpiFrLcnVcSegmentsRx
      Unsigned32,
   mscIpiFrLcnVcSegmentsSent
      Unsigned32,
   mscIpiFrLcnVcStartTime
      EnterpriseDateAndTime,
   mscIpiFrLcnVcCallReferenceNumberDecimal
      Unsigned32 }

mscIpiFrLcnVcCallReferenceNumber OBJECT-TYPE
   SYNTAX     Hex (0..16777215)
   ACCESS     read-only
   STATUS     obsolete
   DESCRIPTION
     "This attribute is obsolete. It is replaced by the callReferenceNumber 
      attribute to display the call reference number in decimal. The 
      SNMP reference for the callReferenceNumber attribute is 
      callReferenceNumberDecimal."
::= { mscIpiFrLcnVcIntdEntry 1 }

mscIpiFrLcnVcElapsedTimeTillNow OBJECT-TYPE
   SYNTAX     Unsigned32 (0..16777215)
   ACCESS     read-only
   STATUS     mandatory
   DESCRIPTION
     "This attribute displays the elapsed time representing the period of 
      this interval data. It is elapsed time in 0.1 second increments since 
      Vc started."
::= { mscIpiFrLcnVcIntdEntry 2 }

mscIpiFrLcnVcSegmentsRx OBJECT-TYPE
   SYNTAX     Unsigned32 (0..16777215)
   ACCESS     read-only
   STATUS     mandatory
   DESCRIPTION
     "This attribute displays the number of segments received at the time 
      command was issued. This is the segment received count 
      maintained by accounting at each end of the Vc. This counter is 
      updated only when the packet cannot be successfully delivered out 
      of the sink Vc and to the sink AP Conditions in which packets may 
      be discarded by the sink Vc include: missing packets due to subnet 
      discards, segmentation protocol violations due to subnet discard, 
      duplicated and out-of-ranged packets and packets that arrive while 
      Vc is in path recovery state."
::= { mscIpiFrLcnVcIntdEntry 3 }

mscIpiFrLcnVcSegmentsSent OBJECT-TYPE
   SYNTAX     Unsigned32 (0..16777215)
   ACCESS     read-only
   STATUS     mandatory
   DESCRIPTION
     "This attribute displays the number of segments sent at the time 
      command was issued. This is the segment sent count maintained by 
      accounting at the source Vc. Vc only counts packets that Vc thinks 
      can be delivered successfully into the subnet. In reality, these 
      packets may be dropped by trunking, for instance. This counter is 
      not updated when splitting fails, when Vc is in a path recovery state, 
      when packet forwarding fails to forward this packet and when 
      subsequent packets have to be discarded as we want to minimize the 
      chance of out-of-sequence and do not intentionally send out-of-
      sequenced packets into the subnet."
::= { mscIpiFrLcnVcIntdEntry 4 }

mscIpiFrLcnVcStartTime OBJECT-TYPE
   SYNTAX     EnterpriseDateAndTime (SIZE (0 | 19))
   ACCESS     read-only
   STATUS     mandatory
   DESCRIPTION
     "This attribute displays the start time of this interval period. If Vc 
      spans 12 hour time or time of day change startTime reflects new 
      time as recorded at 12 hour periods or time of day changes."
::= { mscIpiFrLcnVcIntdEntry 5 }

mscIpiFrLcnVcCallReferenceNumberDecimal OBJECT-TYPE
   SYNTAX     Unsigned32 (0..4294967295)
   ACCESS     read-only
   STATUS     mandatory
   DESCRIPTION
     "This attribute displays the call reference number which is a unique 
      number generated by the switch.The same Call Reference Number 
      is stored in the interval data (accounting record) at both ends of the 
      call. It can be used as one of the attributes in matching duplicate 
      records generated at each end of the call."
::= { mscIpiFrLcnVcIntdEntry 7 }

mscIpiFrLcnVcFrdTable OBJECT-TYPE
   SYNTAX     SEQUENCE OF MscIpiFrLcnVcFrdEntry
   ACCESS     not-accessible
   STATUS     mandatory
   DESCRIPTION
     "This group defines Frame Relay attributes collected by Frame Relay 
      Vc.
      The purpose of Vc attributes is to aid end users and verification 
      people to understand the Vc internal behavior. This is particularly 
      useful when the network has experienced abnormality and we want 
      to isolate problems and pinpoint trouble spots. 
      Attributes are collected on a per Vc basis. Until a need is identified, 
      statistics are not collected at a processor level. Each attribute is 
      stored in a 32 bit field and is initialized to zero when a Vc enters 
      into the data transfer state. When a PVC is disconnected and then 
      connected again, the attributes will be reset. Attributes cannot be 
      reset through other methods. 
      Frame Relay Vc uses a best effort data packet delivery protocol and 
      a different packet segmentation and combination methods from the 
      General Vc. The Frame Relay Vc uses the same call setup and 
      control mechanism (e.g. the support of non-flow control data 
      packets) as in a General Vc. Most General Vc statistics and internal 
      variables are used in a Frame Relay Vc and are displayed by 
      software developers"
::= { mscIpiFrLcnVc 12 }

mscIpiFrLcnVcFrdEntry OBJECT-TYPE
   SYNTAX     MscIpiFrLcnVcFrdEntry
   ACCESS     not-accessible
   STATUS     mandatory
   DESCRIPTION
     "An entry in the mscIpiFrLcnVcFrdTable."
   INDEX {
      mscIpiFrIndex,
      mscIpiFrLcnIndex,
      mscIpiFrLcnVcIndex }
::= { mscIpiFrLcnVcFrdTable 1 }

MscIpiFrLcnVcFrdEntry ::= SEQUENCE {
   mscIpiFrLcnVcFrmCongestedToSubnet
      Unsigned32,
   mscIpiFrLcnVcCannotForwardToSubnet
      Unsigned32,
   mscIpiFrLcnVcNotDataXferToSubnet
      Unsigned32,
   mscIpiFrLcnVcOutOfRangeFrmFromSubnet
      Unsigned32,
   mscIpiFrLcnVcCombErrorsFromSubnet
      Unsigned32,
   mscIpiFrLcnVcDuplicatesFromSubnet
      Unsigned32,
   mscIpiFrLcnVcNotDataXferFromSubnet
      Unsigned32,
   mscIpiFrLcnVcFrmLossTimeouts
      Unsigned32,
   mscIpiFrLcnVcOoSeqByteCntExceeded
      Unsigned32,
   mscIpiFrLcnVcPeakOoSeqPktCount
      Unsigned32,
   mscIpiFrLcnVcPeakOoSeqFrmForwarded
      Unsigned32,
   mscIpiFrLcnVcSendSequenceNumber
      Unsigned32,
   mscIpiFrLcnVcPktRetryTimeouts
      Unsigned32,
   mscIpiFrLcnVcPeakRetryQueueSize
      Unsigned32,
   mscIpiFrLcnVcSubnetRecoveries
      Unsigned32,
   mscIpiFrLcnVcOoSeqPktCntExceeded
      Unsigned32,
   mscIpiFrLcnVcPeakOoSeqByteCount
      Unsigned32 }

mscIpiFrLcnVcFrmCongestedToSubnet OBJECT-TYPE
   SYNTAX     Unsigned32 (0..5000)
   ACCESS     read-only
   STATUS     mandatory
   DESCRIPTION
     "This attribute displays the number of frames from link discarded 
      due to lack of resources. It keeps track of the number of frames 
      from link that have to be discarded. The discard reasons include 
      insufficient memory for splitting the frame into smaller subnet 
      packet size."
::= { mscIpiFrLcnVcFrdEntry 2 }

mscIpiFrLcnVcCannotForwardToSubnet OBJECT-TYPE
   SYNTAX     Unsigned32 (0..5000)
   ACCESS     read-only
   STATUS     mandatory
   DESCRIPTION
     "This attribute displays the number of discarded packets that can not 
      be forwarded into the subnet because of subnet congestion.
      Number of frames from link discarded due to failure in forwarding 
      a packet from Vc into the subnet.- This attribute is increased when 
      packet forwarding fails to forward a packet into the subnet. If a 
      frame is split into multiple subnet packets and a partial packet has 
      to be discarded, all subsequent partial packets that have not yet been 
      delivered to the subnet will be discarded as well."
::= { mscIpiFrLcnVcFrdEntry 3 }

mscIpiFrLcnVcNotDataXferToSubnet OBJECT-TYPE
   SYNTAX     Unsigned32 (0..5000)
   ACCESS     read-only
   STATUS     mandatory
   DESCRIPTION
     "This attribute records the number of frames from link discarded 
      when the Vc tries to recover from internal path failure."
::= { mscIpiFrLcnVcFrdEntry 4 }

mscIpiFrLcnVcOutOfRangeFrmFromSubnet OBJECT-TYPE
   SYNTAX     Unsigned32 (0..5000)
   ACCESS     read-only
   STATUS     mandatory
   DESCRIPTION
     "This attribute displays the number of frames from subnet discarded 
      due to out of sequence range for arriving too late."
::= { mscIpiFrLcnVcFrdEntry 5 }

mscIpiFrLcnVcCombErrorsFromSubnet OBJECT-TYPE
   SYNTAX     Unsigned32 (0..5000)
   ACCESS     read-only
   STATUS     mandatory
   DESCRIPTION
     "This attribute records the number of subnet packets discarded at the 
      sink Vc due to the Vc segmentation and combination protocol error. 
      Usually, this occurs when the subnet discards packets and thus this 
      statistics can be used to guest the number of subnet packets that are 
      not delivered to the Vc. It cannot be used as an actual measure 
      because some subnet packets may have been delivered to Vc but 
      have to be discarded because these are partial packets to a frame in 
      which some other partial packets have not been properly delivered 
      to Vc"
::= { mscIpiFrLcnVcFrdEntry 6 }

mscIpiFrLcnVcDuplicatesFromSubnet OBJECT-TYPE
   SYNTAX     Unsigned32 (0..5000)
   ACCESS     read-only
   STATUS     mandatory
   DESCRIPTION
     "This attribute displays the number of subnet packets discarded due 
      to duplication. Although packets are not retransmitted by the Frame 
      Relay Vc, it is possible for the subnet to retransmit packets. When 
      packets are out-of-sequenced and copies of the same packets arrive, 
      then this attribute is increased."
::= { mscIpiFrLcnVcFrdEntry 7 }

mscIpiFrLcnVcNotDataXferFromSubnet OBJECT-TYPE
   SYNTAX     Unsigned32 (0..5000)
   ACCESS     read-only
   STATUS     mandatory
   DESCRIPTION
     "This attribute displays the number of subnet packets discarded when 
      data transfer is suspended in Vc recovery."
::= { mscIpiFrLcnVcFrdEntry 8 }

mscIpiFrLcnVcFrmLossTimeouts OBJECT-TYPE
   SYNTAX     Unsigned32 (0..5000)
   ACCESS     read-only
   STATUS     mandatory
   DESCRIPTION
     "This attribute displays the number of lost frame timer expiries.
      When this count is excessive, the network is very congested and 
      packets have been discarded in the subnet."
::= { mscIpiFrLcnVcFrdEntry 9 }

mscIpiFrLcnVcOoSeqByteCntExceeded OBJECT-TYPE
   SYNTAX     Unsigned32 (0..5000)
   ACCESS     read-only
   STATUS     mandatory
   DESCRIPTION
     "This attribute displays the number times that the out of sequence 
      byte threshold is exceeded. When the threshold is exceeded, this 
      condition is treated as if the loss frame timer has expired and all 
      frames queued at the sink Vc are delivered to the AP. We need to 
      keep this count to examine if the threshold is engineered properly. 
      This should be used in conjunction with the peak value of out-of-
      sequenced queue and the number of times the loss frame timer has 
      expired. This count should be relatively small when compared with 
      loss frame timer expiry count."
::= { mscIpiFrLcnVcFrdEntry 10 }

mscIpiFrLcnVcPeakOoSeqPktCount OBJECT-TYPE
   SYNTAX     Unsigned32 (0..5000)
   ACCESS     read-only
   STATUS     mandatory
   DESCRIPTION
     "This attribute displays the frame relay peak packet count of the out 
      of sequence queue. This attribute records the maximum queue 
      length of the out-of-sequenced queue. The counter can be used to 
      deduce the message buffer requirement on a Vc."
::= { mscIpiFrLcnVcFrdEntry 11 }

mscIpiFrLcnVcPeakOoSeqFrmForwarded OBJECT-TYPE
   SYNTAX     Unsigned32 (0..5000)
   ACCESS     read-only
   STATUS     mandatory
   DESCRIPTION
     "This attribute displays the frame relay peak size of the 
      sequence packet queue. The subnet may deliver packets out-of-
      sequenced. These packets are then queued in an out-of-sequenced 
      queue, waiting for a packet with the expected sequence number to 
      come. When that packet arrives, this attribute records the maximum 
      number of packets that were out-of-sequenced, but now have 
      become in-sequenced. The statistics is used to measure expected 
      queue size due to normal subnet packet disorder (not due to subnet 
      packet discard). Current implementation also uses this statistics to 
      set a maximum size for the out-of-sequenced queue."
::= { mscIpiFrLcnVcFrdEntry 12 }

mscIpiFrLcnVcSendSequenceNumber OBJECT-TYPE
   SYNTAX     Unsigned32 (0..5000)
   ACCESS     read-only
   STATUS     mandatory
   DESCRIPTION
     "This attribute displays the Vc internal packet's send sequence 
      number. Note that a 'packet' in this context, may be either a user 
      data packet, or an OAM frame."
::= { mscIpiFrLcnVcFrdEntry 13 }

mscIpiFrLcnVcPktRetryTimeouts OBJECT-TYPE
   SYNTAX     Unsigned32 (0..5000)
   ACCESS     read-only
   STATUS     mandatory
   DESCRIPTION
     "This attribute displays the number of packets which have 
      retransmission time-outs. When this count is excessive, the network 
      is very congested and packets have been discarded in the subnet."
::= { mscIpiFrLcnVcFrdEntry 15 }

mscIpiFrLcnVcPeakRetryQueueSize OBJECT-TYPE
   SYNTAX     Unsigned32 (0..5000)
   ACCESS     read-only
   STATUS     mandatory
   DESCRIPTION
     "This attribute displays the peak size of retransmission queue.
      This attribute is used as an indicator of the acknowledgment 
      behavior across the subnet. Records the largest body of 
      unacknowledged packets."
::= { mscIpiFrLcnVcFrdEntry 16 }

mscIpiFrLcnVcSubnetRecoveries OBJECT-TYPE
   SYNTAX     Unsigned32 (0..5000)
   ACCESS     read-only
   STATUS     mandatory
   DESCRIPTION
     "This attribute displays the number of successful Vc recovery 
      attempts."
::= { mscIpiFrLcnVcFrdEntry 17 }

mscIpiFrLcnVcOoSeqPktCntExceeded OBJECT-TYPE
   SYNTAX     Unsigned32 (0..255)
   ACCESS     read-only
   STATUS     mandatory
   DESCRIPTION
     "This attribute displays the number times that the out of sequence 
      packet threshold is exceeded. When the threshold is exceeded, this 
      condition is treated as if the loss frame timer has expired and all 
      frames queued at the sink Vc are delivered to the AP. We need to 
      keep this count to examine if the threshold is engineered properly. 
      This should be used in conjunction with the peak value of out-of-
      sequenced queue and the number of times the loss frame timer has 
      expired. This count should be relatively small when compared with 
      loss frame timer expiry count."
::= { mscIpiFrLcnVcFrdEntry 19 }

mscIpiFrLcnVcPeakOoSeqByteCount OBJECT-TYPE
   SYNTAX     Unsigned32 (0..50000)
   ACCESS     read-only
   STATUS     mandatory
   DESCRIPTION
     "This attribute displays the frame relay peak byte count of the out of 
      sequence queue. This attribute records the maximum queue length 
      of the out-of-sequenced queue. The counter can be used to deduce 
      the message buffer requirement on a Vc."
::= { mscIpiFrLcnVcFrdEntry 20 }

mscIpiFrLcnVcDmepTable OBJECT-TYPE
   SYNTAX     SEQUENCE OF MscIpiFrLcnVcDmepEntry
   ACCESS     not-accessible
   STATUS     mandatory
   DESCRIPTION
     "This attribute displays the data path used by the connection. Data 
      path is provisioned in Dna and DirectCall components.
      
      If the connection is using dprsOnly data path, this attribute is 
      empty.
      
      If the connection is using dprsMcsOnly or dprsMcsFirst data path, 
      this attribute displays component name of the dprsMcsEndPoint."
::= { mscIpiFrLcnVc 417 }

mscIpiFrLcnVcDmepEntry OBJECT-TYPE
   SYNTAX     MscIpiFrLcnVcDmepEntry
   ACCESS     not-accessible
   STATUS     mandatory
   DESCRIPTION
     "An entry in the mscIpiFrLcnVcDmepTable."
   INDEX {
      mscIpiFrIndex,
      mscIpiFrLcnIndex,
      mscIpiFrLcnVcIndex,
      mscIpiFrLcnVcDmepValue }
::= { mscIpiFrLcnVcDmepTable 1 }

MscIpiFrLcnVcDmepEntry ::= SEQUENCE {
   mscIpiFrLcnVcDmepValue
      RowPointer }

mscIpiFrLcnVcDmepValue OBJECT-TYPE
   SYNTAX     RowPointer 
   ACCESS     read-only
   STATUS     mandatory
   DESCRIPTION
     "This variable represents both the value and the index for the
      mscIpiFrLcnVcDmepTable."
::= { mscIpiFrLcnVcDmepEntry 1 }


-- IpiFr StaticRoute/destIpAddress
-- 
-- This component contains information for setting up a static routes 
-- on the IpiFr service. These provisioned static IP routes allow the 
-- ability to specify IP routes to Network Management Stations which 
-- are not directly connected to the Passport module. The component 
-- is indexed by a destination IP Address. It represents the static IP 
-- route to a particular IP host, subnetwork, or network. The default 
-- route IP address is indexed by 0.0.0.0 .
-- 
-- Note that subnetwork routes are identified using IpiFr's provisioned 
-- subnetMask. This subnetMask only applies to the IP network for 
-- which IpiFr's IP Address belongs. Therefore, subnetwork routes are 
-- only supported for this local IP network.

mscIpiFrSr OBJECT IDENTIFIER ::= { mscIpiFr 5 }



mscIpiFrSrRowStatusTable OBJECT-TYPE
   SYNTAX     SEQUENCE OF MscIpiFrSrRowStatusEntry
   ACCESS     not-accessible
   STATUS     mandatory
   DESCRIPTION
     "This entry controls the addition and deletion of 
      mscIpiFrSr components."
::= { mscIpiFrSr 1 }

mscIpiFrSrRowStatusEntry OBJECT-TYPE
   SYNTAX     MscIpiFrSrRowStatusEntry
   ACCESS     not-accessible
   STATUS     mandatory
   DESCRIPTION
     "A single entry in the table represents a single 
      mscIpiFrSr component."
   INDEX {
      mscIpiFrIndex,
      mscIpiFrSrIndex }
::= { mscIpiFrSrRowStatusTable 1 }

MscIpiFrSrRowStatusEntry ::= SEQUENCE {
   mscIpiFrSrRowStatus
      RowStatus,
   mscIpiFrSrComponentName
      DisplayString,
   mscIpiFrSrStorageType
      StorageType,
   mscIpiFrSrIndex
      IpAddress }

mscIpiFrSrRowStatus OBJECT-TYPE
   SYNTAX     RowStatus 
   ACCESS     read-write
   STATUS     mandatory
   DESCRIPTION
     "This variable is used as the basis for SNMP naming of
      mscIpiFrSr components.
      These components can be added and deleted."
::= { mscIpiFrSrRowStatusEntry 1 }

mscIpiFrSrComponentName OBJECT-TYPE
   SYNTAX     DisplayString 
   ACCESS     read-only
   STATUS     mandatory
   DESCRIPTION
     "This variable provides the component's string name for
      use with the ASCII Console Interface"
::= { mscIpiFrSrRowStatusEntry 2 }

mscIpiFrSrStorageType OBJECT-TYPE
   SYNTAX     StorageType 
   ACCESS     read-only
   STATUS     mandatory
   DESCRIPTION
     "This variable represents the storage type value for the
      mscIpiFrSr tables."
::= { mscIpiFrSrRowStatusEntry 4 }

mscIpiFrSrIndex OBJECT-TYPE
   SYNTAX     IpAddress 
   ACCESS     not-accessible
   STATUS     mandatory
   DESCRIPTION
     "This variable represents the index for the mscIpiFrSr tables."
::= { mscIpiFrSrRowStatusEntry 10 }

mscIpiFrSrProvTable OBJECT-TYPE
   SYNTAX     SEQUENCE OF MscIpiFrSrProvEntry
   ACCESS     not-accessible
   STATUS     mandatory
   DESCRIPTION
     "This group provides the provisionable parameters for setting up a 
      static route."
::= { mscIpiFrSr 10 }

mscIpiFrSrProvEntry OBJECT-TYPE
   SYNTAX     MscIpiFrSrProvEntry
   ACCESS     not-accessible
   STATUS     mandatory
   DESCRIPTION
     "An entry in the mscIpiFrSrProvTable."
   INDEX {
      mscIpiFrIndex,
      mscIpiFrSrIndex }
::= { mscIpiFrSrProvTable 1 }

MscIpiFrSrProvEntry ::= SEQUENCE {
   mscIpiFrSrGatewayIpAddress
      IpAddress }

mscIpiFrSrGatewayIpAddress OBJECT-TYPE
   SYNTAX     IpAddress 
   ACCESS     read-write
   STATUS     mandatory
   DESCRIPTION
     "The attribute specifies the IP Address of the next hop in this route to 
      the destination IP Address. For this static route to be active, the 
      value of this attribute must match the opRemoteIpAddress attribute 
      of one of the Lcn components."
   DEFVAL     { '00000000'H }  -- "0.0.0.0"
::= { mscIpiFrSrProvEntry 1 }

mscIpiFrSrBGtyIpaTable OBJECT-TYPE
   SYNTAX     SEQUENCE OF MscIpiFrSrBGtyIpaEntry
   ACCESS     not-accessible
   STATUS     mandatory
   DESCRIPTION
     "The attribute specifies an ordered list of alternative gateways to use 
      for the route to the destination IP Address. This attribute is only 
      supported for the default route. 
      
      If the Lcn interface of the current gateway IP Address fails, then the 
      backupGatewayIpAddresses, listed in this attribute, are searched, in 
      order, for a gatewayIpAddress with an enabled Lcn. If found, the 
      static route to this destination IP Address is updated to use the 
      found gateway IP Address.
      
      Note that an Lcn interface can fail due to either the Vc through the 
      Passport Network failing, or an Lmi indication that the far-end link 
      is failed."
::= { mscIpiFrSr 327 }

mscIpiFrSrBGtyIpaEntry OBJECT-TYPE
   SYNTAX     MscIpiFrSrBGtyIpaEntry
   ACCESS     not-accessible
   STATUS     mandatory
   DESCRIPTION
     "An entry in the mscIpiFrSrBGtyIpaTable."
   INDEX {
      mscIpiFrIndex,
      mscIpiFrSrIndex,
      mscIpiFrSrBGtyIpaIndex }
::= { mscIpiFrSrBGtyIpaTable 1 }

MscIpiFrSrBGtyIpaEntry ::= SEQUENCE {
   mscIpiFrSrBGtyIpaIndex
      Integer32,
   mscIpiFrSrBGtyIpaValue
      IpAddress,
   mscIpiFrSrBGtyIpaRowStatus
      RowStatus }

mscIpiFrSrBGtyIpaIndex OBJECT-TYPE
   SYNTAX     Integer32 (1..23)
   ACCESS     not-accessible
   STATUS     mandatory
   DESCRIPTION
     "This variable represents the index for the mscIpiFrSrBGtyIpaTable."
::= { mscIpiFrSrBGtyIpaEntry 1 }

mscIpiFrSrBGtyIpaValue OBJECT-TYPE
   SYNTAX     IpAddress 
   ACCESS     read-write
   STATUS     mandatory
   DESCRIPTION
     "This variable represents an individual value for the
      mscIpiFrSrBGtyIpaTable."
::= { mscIpiFrSrBGtyIpaEntry 2 }

mscIpiFrSrBGtyIpaRowStatus OBJECT-TYPE
   SYNTAX     RowStatus 
   ACCESS     write-only
   STATUS     mandatory
   DESCRIPTION
     "This variable is used to control the addition and deletion 
      of individual values of the mscIpiFrSrBGtyIpaTable."
::= { mscIpiFrSrBGtyIpaEntry 3 }

-- 
-- *** THIS SUBTREE CURRENTLY NOT IMPLEMENTED ***
-- 

-- IpiFr Route/destIpAddress
-- 
-- This dynamic component represents an active IP route within the 
-- IpiFr service. The component is indexed by the destination IP 
-- Address of the IP route. It represents the IP route to a particular IP 
-- host, subnetwork, or network. The default route IP address is 
-- indexed by 0.0.0.0 .
-- 
-- Note that only an active route is shown as an IpiFr Route/
-- <IP_Address> . A provisioned static route (i.e. IpiFr StaticRoute/
-- <IP_Address>) will be listed as an active route only if it's Lcn 
-- interface is enabled (i.e. the associated Vc through the Passport 
-- network is up, and the FrameRelay Lmi is reporting the far-end link 
-- is up ) .
-- 

mscIpiFrR OBJECT IDENTIFIER ::= { mscIpiFr 6 }



mscIpiFrRRowStatusTable OBJECT-TYPE
   SYNTAX     SEQUENCE OF MscIpiFrRRowStatusEntry
   ACCESS     not-accessible
   STATUS     mandatory
   DESCRIPTION
     "*** THIS TABLE CURRENTLY NOT IMPLEMENTED ***

      This entry controls the addition and deletion of 
      mscIpiFrR components."
::= { mscIpiFrR 1 }

mscIpiFrRRowStatusEntry OBJECT-TYPE
   SYNTAX     MscIpiFrRRowStatusEntry
   ACCESS     not-accessible
   STATUS     mandatory
   DESCRIPTION
     "A single entry in the table represents a single 
      mscIpiFrR component."
   INDEX {
      mscIpiFrIndex,
      mscIpiFrRIndex }
::= { mscIpiFrRRowStatusTable 1 }

MscIpiFrRRowStatusEntry ::= SEQUENCE {
   mscIpiFrRRowStatus
      RowStatus,
   mscIpiFrRComponentName
      DisplayString,
   mscIpiFrRStorageType
      StorageType,
   mscIpiFrRIndex
      IpAddress }

mscIpiFrRRowStatus OBJECT-TYPE
   SYNTAX     RowStatus 
   ACCESS     read-only
   STATUS     mandatory
   DESCRIPTION
     "This variable is used as the basis for SNMP naming of
      mscIpiFrR components.
      These components cannot be added nor deleted."
::= { mscIpiFrRRowStatusEntry 1 }

mscIpiFrRComponentName OBJECT-TYPE
   SYNTAX     DisplayString 
   ACCESS     read-only
   STATUS     mandatory
   DESCRIPTION
     "This variable provides the component's string name for
      use with the ASCII Console Interface"
::= { mscIpiFrRRowStatusEntry 2 }

mscIpiFrRStorageType OBJECT-TYPE
   SYNTAX     StorageType 
   ACCESS     read-only
   STATUS     mandatory
   DESCRIPTION
     "This variable represents the storage type value for the
      mscIpiFrR tables."
::= { mscIpiFrRRowStatusEntry 4 }

mscIpiFrRIndex OBJECT-TYPE
   SYNTAX     IpAddress 
   ACCESS     not-accessible
   STATUS     mandatory
   DESCRIPTION
     "This variable represents the index for the mscIpiFrR tables."
::= { mscIpiFrRRowStatusEntry 10 }

mscIpiFrROperTable OBJECT-TYPE
   SYNTAX     SEQUENCE OF MscIpiFrROperEntry
   ACCESS     not-accessible
   STATUS     mandatory
   DESCRIPTION
     "*** THIS TABLE CURRENTLY NOT IMPLEMENTED ***

      This group contains operational status of the static route"
::= { mscIpiFrR 10 }

mscIpiFrROperEntry OBJECT-TYPE
   SYNTAX     MscIpiFrROperEntry
   ACCESS     not-accessible
   STATUS     mandatory
   DESCRIPTION
     "An entry in the mscIpiFrROperTable."
   INDEX {
      mscIpiFrIndex,
      mscIpiFrRIndex }
::= { mscIpiFrROperTable 1 }

MscIpiFrROperEntry ::= SEQUENCE {
   mscIpiFrRGtyIpAddr
      IpAddress,
   mscIpiFrRLcnIf
      Unsigned32,
   mscIpiFrRType
      INTEGER }

mscIpiFrRGtyIpAddr OBJECT-TYPE
   SYNTAX     IpAddress 
   ACCESS     read-only
   STATUS     mandatory
   DESCRIPTION
     "The attribute specifies the IP Address of the next hop in this route to 
      the destination IP Address."
   DEFVAL     { '00000000'H }  -- "0.0.0.0"
::= { mscIpiFrROperEntry 1 }

mscIpiFrRLcnIf OBJECT-TYPE
   SYNTAX     Unsigned32 (16..39)
   ACCESS     read-only
   STATUS     mandatory
   DESCRIPTION
     "This attribute specifies the Lcn interface used by this IP route."
::= { mscIpiFrROperEntry 3 }

mscIpiFrRType OBJECT-TYPE
   SYNTAX     INTEGER  {
                 host(1),
                 subnet(2),
                 network(3) }
   ACCESS     read-only
   STATUS     mandatory
   DESCRIPTION
     "This attribute indicates whether a route is going to a host or a 
      subnet or a network."
::= { mscIpiFrROperEntry 4 }




-- 
-- Version and Compliance statements
-- 



-- Object-Group Statement:
-- A list of all current accessible leaf objects.

-- OBJECTS { mscIpiFrLcnDcComponentName,
--           mscIpiFrLcnVcRowStatus,
--           mscIpiFrDnaIncCalls,
--           mscIpiFrLcnVcStorageType,
--           mscIpiFrLcnVcRcosToNetwork,
--           mscIpiFrDnaIncAccess,
--           mscIpiFrLcnVcPreviousDiagnosticCode,
--           mscIpiFrStorageType,
--           mscIpiFrLcnVcEmissionPriorityFromNetwork,
--           mscIpiFrLcnVcOoSeqByteCntExceeded,
--           mscIpiFrDnaRowStatus,
--           mscIpiFrRType,
--           mscIpiFrLcnVcCombErrorsFromSubnet,
--           mscIpiFrLcnVcCallingDna,
--           mscIpiFrLcnVcPeakOoSeqFrmForwarded,
--           mscIpiFrDnaCugComponentName,
--           mscIpiFrDnaOutDefaultPriority,
--           mscIpiFrLcnVcSegmentsRx,
--           mscIpiFrDnaTransferPriorityOverRide,
--           mscIpiFrDnaCugInterlockCode,
--           mscIpiFrDnaServiceCategory,
--           mscIpiFrDnaServiceExchange,
--           mscIpiFrLcnUnknownStatus,
--           mscIpiFrLcnStandbyStatus,
--           mscIpiFrLcnVcNotDataXferFromSubnet,
--           mscIpiFrLcnStorageType,
--           mscIpiFrLcnVcDmepValue,
--           mscIpiFrRComponentName,
--           mscIpiFrLcnVcRcosFromNetwork,
--           mscIpiFrLcnVcMaxSubnetPktSize,
--           mscIpiFrIpAddress,
--           mscIpiFrLcnVcDuplicatesFromSubnet,
--           mscIpiFrLcnVcStartTime,
--           mscIpiFrSubnetMask,
--           mscIpiFrLcnControlStatus,
--           mscIpiFrLcnAdminState,
--           mscIpiFrSrBGtyIpaRowStatus,
--           mscIpiFrLcnVcDiagnosticCode,
--           mscIpiFrLcnDcRowStatus,
--           mscIpiFrComponentName,
--           mscIpiFrLcnRowStatus,
--           mscIpiFrLcnVcCallingLcn,
--           mscIpiFrSrBGtyIpaValue,
--           mscIpiFrLcnDcRemoteNpi,
--           mscIpiFrSrStorageType,
--           mscIpiFrDnaNumberingPlanIndicator,
--           mscIpiFrLcnVcOutOfRangeFrmFromSubnet,
--           mscIpiFrDnaCugStorageType,
--           mscIpiFrLcnVcCalledDna,
--           mscIpiFrLcnUsageState,
--           mscIpiFrLcnVcType,
--           mscIpiFrLcnDcRemoteDlci,
--           mscIpiFrLcnVcAccountingEnabled,
--           mscIpiFrLcnVcFrmLossTimeouts,
--           mscIpiFrDnaCugIncCalls,
--           mscIpiFrLcnDcDiscardPriority,
--           mscIpiFrLcnVcPreviousState,
--           mscIpiFrMaximumNumberOfLcn,
--           mscIpiFrLcnVcSubnetRecoveries,
--           mscIpiFrLcnVcOoSeqPktCntExceeded,
--           mscIpiFrLcnVcPeakRetryQueueSize,
--           mscIpiFrLcnIpInterfaceDevice,
--           mscIpiFrLcnVcDataPath,
--           mscIpiFrSrRowStatus,
--           mscIpiFrLcnDcTransferPriority,
--           mscIpiFrRGtyIpAddr,
--           mscIpiFrLcnVcSegmentSize,
--           mscIpiFrRStorageType,
--           mscIpiFrDnaCugRowStatus,
--           mscIpiFrLcnOpRemoteIpAddress,
--           mscIpiFrLcnPacketsSent,
--           mscIpiFrRRowStatus,
--           mscIpiFrLcnVcFastSelectCall,
--           mscIpiFrLcnVcComponentName,
--           mscIpiFrLcnPacketsReceived,
--           mscIpiFrLcnVcSegmentsSent,
--           mscIpiFrSrComponentName,
--           mscIpiFrLcnVcCallingNpi,
--           mscIpiFrLcnAvailabilityStatus,
--           mscIpiFrLcnDiscardTxPackets,
--           mscIpiFrDnaCugDnic,
--           mscIpiFrLcnVcPriority,
--           mscIpiFrLcnAlarmStatus,
--           mscIpiFrLcnVcCalledLcn,
--           mscIpiFrLcnVcPathReliability,
--           mscIpiFrLcnVcSendSequenceNumber,
--           mscIpiFrDnaComponentName,
--           mscIpiFrDnaAccountClass,
--           mscIpiFrLcnVcPktRetryTimeouts,
--           mscIpiFrLcnDcStorageType,
--           mscIpiFrLcnRemoteIpAddress,
--           mscIpiFrLcnVcState,
--           mscIpiFrRowStatus,
--           mscIpiFrLcnDcType,
--           mscIpiFrLcnOperationalState,
--           mscIpiFrDnaOutCalls,
--           mscIpiFrLcnVcEmissionPriorityToNetwork,
--           mscIpiFrLcnVcPeakOoSeqByteCount,
--           mscIpiFrSrGatewayIpAddress,
--           mscIpiFrLcnDcRemoteDna,
--           mscIpiFrLcnVcFrmCongestedToSubnet,
--           mscIpiFrLcnDiscardRcvPackets,
--           mscIpiFrLcnProceduralStatus,
--           mscIpiFrDnaDefaultTransferPriority,
--           mscIpiFrLcnVcAccountingEnd,
--           mscIpiFrDnaDataNetworkAddress,
--           mscIpiFrLcnVcCalledNpi,
--           mscIpiFrLcnVcCannotForwardToSubnet,
--           mscIpiFrLcnVcElapsedTimeTillNow,
--           mscIpiFrLcnComponentName,
--           mscIpiFrLcnVcPeakOoSeqPktCount,
--           mscIpiFrDnaStorageType,
--           mscIpiFrLcnVcNotDataXferToSubnet,
--           mscIpiFrDnaCugType,
--           mscIpiFrLcnVcCallReferenceNumberDecimal,
--           mscIpiFrRLcnIf }
-- STATUS  mandatory
-- DESCRIPTION
--   "A list of all current accessible leaf objects."

ipiFrGroup OBJECT IDENTIFIER ::= { ipiFrMIB 1 }
ipiFrGroupCA OBJECT IDENTIFIER ::= { ipiFrGroup 1 }
ipiFrGroupCA02 OBJECT IDENTIFIER ::= { ipiFrGroupCA 3 }
ipiFrGroupCA02A OBJECT IDENTIFIER ::= { ipiFrGroupCA02 2 }



-- Agent-Capabilities Statement:

-- PRODUCT-RELEASE "MscPassport Release 1.2 IpiFr."
-- STATUS          mandatory
-- DESCRIPTION     "Carrier Passport IpiFr MIB: MIB Version CA02A,
--                  Software Version CA02S9C."
-- SUPPORTS        Nortel-MsCarrier-MscPassport-IpiFrMIB
--    INCLUDES     { ipiFrGroupCA02A }

ipiFrCapabilities OBJECT IDENTIFIER ::= { ipiFrMIB 3 }
ipiFrCapabilitiesCA OBJECT IDENTIFIER ::= { ipiFrCapabilities 1 }
ipiFrCapabilitiesCA02 OBJECT IDENTIFIER ::= { ipiFrCapabilitiesCA 3 }
ipiFrCapabilitiesCA02A OBJECT IDENTIFIER ::= { ipiFrCapabilitiesCA02 2 }





END
