LANCITY-MIB DEFINITIONS ::= BEGIN

IMPORTS
    MODULE-IDENTITY
            FROM SNMPv2-SMI
    enterprises 
            FROM RFC1155-SMI
      ;

lancity MODULE-IDENTITY
    LAST-UPDATED    "9709061024Z" -- September 6, 1997
    ORGANIZATION    "Bay Networks Broadband Technologies Division"
    CONTACT-INFO
         "Dale Hokanson
          Postal: Bay Networks
                  Broadband Technologies Division
                  200 Bulfinch Drive
                  Andover, MA 01810
                  U.S.A.
          Phone:  +1 508 682 1600
          E-mail: support@lancity.com"

    DESCRIPTION
        "This is a header for the Lancity enterprise MIB. All objects appear
         elsewhere."
    ::= { enterprises 482 }

END
