STARNE-MIB DEFINITIONS ::= BEGIN

	IMPORTS
		IpAddress, enterprises, TimeTicks, Counter, Gauge 
			FROM RFC1155-SMI
		OBJECT-TYPE	
			FROM RFC-1212
		DisplayString	
			FROM RFC1213-MIB;

	-- Star Network Element Proprietary MIB definition

	samsung			OBJECT IDENTIFIER ::= { enterprises 236 }

	starNeMib		OBJECT IDENTIFIER ::= { samsung 5 }

	starSystem		OBJECT IDENTIFIER ::= { starNeMib 1 }
	starSlot		OBJECT IDENTIFIER ::= { starNeMib 2 }
	starPort		OBJECT IDENTIFIER ::= { starNeMib 3 }
	starConn		OBJECT IDENTIFIER ::= { starNeMib 4 }
	starBackbone	OBJECT IDENTIFIER ::= { starNeMib 5 }
	starTrap		OBJECT IDENTIFIER ::= { starNeMib 6 }

	----------------------------------------------------------------------
	-- System Generic Group
	----------------------------------------------------------------------
	starSysGeneric	OBJECT IDENTIFIER ::= { starSystem 1 }

	starNeId	OBJECT-TYPE
		SYNTAX	INTEGER (1..1023)
		ACCESS	read-only
		STATUS	mandatory
		DESCRIPTION
			"Star Node Identifier"
		::= { starSysGeneric 1 }

	starNeDescr	OBJECT-TYPE
		SYNTAX	DisplayString
		ACCESS	read-only
		STATUS	mandatory
		DESCRIPTION
			"Star Node Description"
		::= { starSysGeneric 2 }

	starNeMipAddress	OBJECT-TYPE
		SYNTAX	IpAddress
		ACCESS	read-only
		STATUS	mandatory
		DESCRIPTION
			"IP address that is used for inter-slot communication"
		::= { starSysGeneric 3 }

	starNeTimeofDay		OBJECT-TYPE
		SYNTAX	TimeTicks
		ACCESS	read-write
		STATUS	mandatory
		DESCRIPTION
			"Time of day in seconds since the epoch"
		::= { starSysGeneric 4 }

	starNeOperStatus	OBJECT-TYPE
		SYNTAX	INTEGER
		ACCESS	read-only
		STATUS	mandatory
		DESCRIPTION
			"Operational status of this Node"
		::= { starSysGeneric 5 }

	starNeReset	OBJECT-TYPE
		SYNTAX	INTEGER {
			notreset(1),
			reset(2)
		}
		ACCESS	read-write
		STATUS	mandatory
		DESCRIPTION
			"This object can be used to reset this Node"
		::= { starSysGeneric 6 }

	starNeSlotReset	OBJECT-TYPE
		SYNTAX	INTEGER
		ACCESS	write-only
		STATUS	mandatory
		DESCRIPTION
			"This object can be used to reset a slot"
		::= { starSysGeneric 7 }

	starNeSwDownload	OBJECT-TYPE
--		SYNTAX	INTEGER {
--			notdownloaded(1),
--			downloaded(2)
--		}
--		SYNTAX	OCTET STRING
-- STAda02930 HYOUNG 2000.9.22
		SYNTAX  DisplayString
		ACCESS	read-write
		STATUS	mandatory
		DESCRIPTION
			"This object can be used to initiate a software 
			 download"
		::= { starSysGeneric 8 }

	starNeHwVersion	OBJECT-TYPE
		SYNTAX	INTEGER
		ACCESS	read-only
		STATUS	mandatory
		DESCRIPTION
			"Specifies the hardware version for this Node"
		::= { starSysGeneric 9 }

	starNeBootSwVersion	OBJECT-TYPE
		SYNTAX	INTEGER
		ACCESS	read-only
		STATUS	mandatory
		DESCRIPTION
			"Specifies the boot software version for this Node"
		::= { starSysGeneric 10 }

	starNeSwVersion	OBJECT-TYPE
		SYNTAX	INTEGER
		ACCESS	read-only
		STATUS	mandatory
		DESCRIPTION
			"Specifies the running software version for this Node"
		::= { starSysGeneric 11 }

	starNeXCoordinate	OBJECT-TYPE
		SYNTAX	INTEGER
		ACCESS	read-write
		STATUS	mandatory
		DESCRIPTION
			"Specifies the geographic latitudinal coordinate for 
			 this Node.  Must be initially set by the NMS operator"
		::= { starSysGeneric 12 }

	starNeYCoordinate	OBJECT-TYPE
		SYNTAX	INTEGER
		ACCESS	read-write
		STATUS	mandatory
		DESCRIPTION
			"Specifies the geographic longitudinal coordinate for 
			 this Node.  Must be initially set by the NMS operator"
		::= { starSysGeneric 13 }

	starNeNodeManagerIP	OBJECT-TYPE
		SYNTAX	IpAddress
		ACCESS	read-only
		STATUS	mandatory
		DESCRIPTION
			"Specifies the IP address for the Node Manager"
		::= { starSysGeneric 14 }

	starNeMasterManagerIP	OBJECT-TYPE
		SYNTAX	IpAddress
		ACCESS	read-only
		STATUS	mandatory
		DESCRIPTION
			"Specifies the IP address for the Master Manager"
		::= { starSysGeneric 15 }

	starNeStandbyMasterManagerIP	OBJECT-TYPE
		SYNTAX	IpAddress
		ACCESS	read-only
		STATUS	mandatory
		DESCRIPTION
			"Specifies the IP address for the standby Master 
			 Manager"
		::= { starSysGeneric 16 }

	starNeAlive	OBJECT-TYPE
		SYNTAX	INTEGER {
			onespu(1),
			twospu(2)
		}
		ACCESS	read-only
		STATUS	mandatory
		DESCRIPTION
			"Star Node Alive Value"
		::= { starSysGeneric 17 }

	starMibRegister OBJECT-TYPE
		SYNTAX	INTEGER
		ACCESS	write-only
		STATUS	mandatory
		DESCRIPTION
			"The set value will be SLOT #. If a slot # is set,
			his MIB will be registered."
		::= { starSysGeneric 18 }

	starNeCurrentAlarmTftp OBJECT-TYPE
		SYNTAX	INTEGER
		ACCESS	write-only
		STATUS	mandatory
		DESCRIPTION
			""
		::= { starSysGeneric 19 }

	starNeCurrentTimeDescr OBJECT-TYPE
		SYNTAX	DisplayString
		ACCESS	read-write
		STATUS	mandatory
		DESCRIPTION
			"Time & date in string for NMS easy-looking
			19980601151000 when set
			1998.06.01 15:10:00 when get"
		::= { starSysGeneric 20 }

	-- added by sunah 99.8.13 --
    starNeSoftwareVersion OBJECT-TYPE
        SYNTAX  DisplayString
        ACCESS  read-only
        STATUS  mandatory
        DESCRIPTION
            "The Version of STAR Software"
        ::= { starSysGeneric 22 }
 
    starNeSoftwareType OBJECT-TYPE
        SYNTAX  INTEGER{
                star1(1)
        }
        ACCESS  read-only
        STATUS  mandatory
        DESCRIPTION
            "This value means the type of STAR Software"
        ::= { starSysGeneric 23 }
 
    starNeSwUpgradeDownload OBJECT-TYPE
        SYNTAX  INTEGER
        ACCESS  write-only
        STATUS  mandatory
        DESCRIPTION
            "If set, start download files to be upgraded"
        ::= { starSysGeneric 24 }
 
    starNeSwUpgradeCancel OBJECT-TYPE
        SYNTAX  INTEGER
        ACCESS  write-only
        STATUS  mandatory
        DESCRIPTION
            "If set, cancel downloading files to be upgraded"
        ::= { starSysGeneric 25 }
 
    starNeSwUpgradeActionTrigger OBJECT-TYPE
        SYNTAX  INTEGER
        ACCESS  write-only
        STATUS  mandatory
        DESCRIPTION
            "If set, trigger the renaming of *.NEW to *.Z or *.CFG and reset"
        ::= { starSysGeneric 26 }
 
    starNeSwUpgradedFiles OBJECT-TYPE
        SYNTAX  INTEGER
        ACCESS  read-only
        STATUS  mandatory
        DESCRIPTION
            "The value of the downloaded files by this time for upgrading"
        ::= { starSysGeneric 27 }
 
    starNeSwUpgradeCurrentFile OBJECT-TYPE
        SYNTAX  INTEGER
        ACCESS  read-only
        STATUS  mandatory
        DESCRIPTION
            "The value of the currently downloading file for upgrading"
        ::= { starSysGeneric 28 }
 
    starNeSwUpgradeStatus OBJECT-TYPE
        SYNTAX  INTEGER
        ACCESS  read-only
        STATUS  mandatory
        DESCRIPTION
            "The value of the status for upgrading"
        ::= { starSysGeneric 29 }
 

	-----------------------------------------------------------------------
	-- Star System Slot Redundency Info Group
	-----------------------------------------------------------------------
	starSysSlotRedundencyInfo	OBJECT IDENTIFIER ::= { starSystem 2 }

	starActiveSPUSlotNo	OBJECT-TYPE
		SYNTAX	INTEGER
		ACCESS  read-only		
		STATUS	mandatory
		DESCRIPTION
			"Slot # of active SPU"
		::= { starSysSlotRedundencyInfo 1 }

	starStandbySPUSlotNo	OBJECT-TYPE
		SYNTAX	INTEGER
		ACCESS  read-only		
		STATUS	mandatory
		DESCRIPTION
			"Slot # of standby SPU"
		::= { starSysSlotRedundencyInfo 2 }

	starActiveSCUSlotNo	OBJECT-TYPE
		SYNTAX	INTEGER
		ACCESS  read-only		
		STATUS	mandatory
		DESCRIPTION 
			"Slot # of active SCU"
		::= { starSysSlotRedundencyInfo 3 }

	starStandbySCUSlotNo	OBJECT-TYPE
		SYNTAX	INTEGER
		ACCESS  read-only		
		STATUS	mandatory
		DESCRIPTION 
			"Slot # of standby SSU"
		::= { starSysSlotRedundencyInfo 4 }

	starActiveSSUSlotNo	OBJECT-TYPE
		SYNTAX	INTEGER
		ACCESS  read-only		
		STATUS	mandatory
		DESCRIPTION 
			"Slot # of active SSU"
		::= { starSysSlotRedundencyInfo 5 }

	starStandbySSUSlotNo	OBJECT-TYPE
		SYNTAX	INTEGER
		ACCESS  read-only		
		STATUS	mandatory
		DESCRIPTION 
			"Slot # of standby SSU"
		::= { starSysSlotRedundencyInfo 6 }

	-----------------------------------------------------------------------
	-- Star System Config Manager Group
	-----------------------------------------------------------------------
	starConfigManager	OBJECT IDENTIFIER ::= { starSystem 3 }

	starCfAllChanged	OBJECT-TYPE
		SYNTAX	INTEGER {
			notchanged(1),
			changed(2)
		}
		ACCESS	read-write
		STATUS	mandatory
		DESCRIPTION
			"This object can be used to inform the Configuration
			 Manager that all configuration files have changed and
			 they should be re-loaded"
		::= { starConfigManager 1 }

	starCfFileChanged	OBJECT-TYPE
--		SYNTAX	OCTET STRING
-- STAda02930 HYOUNG 2000.9.22
		SYNTAX  DisplayString
		ACCESS	read-write
		STATUS	mandatory
		DESCRIPTION
			"This object can be used to inform the Configuration
			 Manager that one particular configuration file has 
			 been changed and should be re-loaded
			 Flag + FileId + IP address"
		::= { starConfigManager 2 }

	starCfBootFileName	OBJECT-TYPE
		SYNTAX	DisplayString
		ACCESS	read-only
		STATUS	mandatory
		DESCRIPTION
			"Specifies the filename of the Star Node boot image"
		::= { starConfigManager 3 }

	starCfShelf	OBJECT-TYPE
		SYNTAX	INTEGER {
			lower(1),
			upper(2)
		}
		ACCESS	read-write
		STATUS	mandatory
		DESCRIPTION
			"Specifies the Star shelf location within the rack.
			 This object must be set initially by the NMS 
			 operator"
		::= { starConfigManager 4 }

	starCfMaxSlots	OBJECT-TYPE
		SYNTAX	INTEGER (1..14)
		ACCESS	read-only
		STATUS	mandatory
		DESCRIPTION
			"Specifies the maximum number of slots in the Star 
			 chassis"
		::= { starConfigManager 5 }

	starCfBootSwitch	OBJECT-TYPE
		SYNTAX	INTEGER {
			flash(1),
			nodemgr(2),
			mastermgr(3)
		}
		ACCESS	read-write
		STATUS	mandatory
		DESCRIPTION
			"This object is used to specify the download source
			 at bootup time"
		::= { starConfigManager 6 }

	starCfInvalidateFlash	OBJECT-TYPE
		SYNTAX	INTEGER {
			valid(1),
			invalid(2)
		}
		ACCESS	read-write
		STATUS	mandatory
		DESCRIPTION
			"This object is used to inform the Star software at
			 bootup time to boot using the NMS, flash memory does
			 not contain valid information anymore"
		::= { starConfigManager 7 }

	starCfActivePSUNo	OBJECT-TYPE
		SYNTAX	INTEGER (1..4)
		ACCESS	read-only
		STATUS	mandatory
		DESCRIPTION
			"Number of current active power supply units"
		::= { starConfigManager 8 }

	starCfPSUOperStatus	OBJECT-TYPE
		SYNTAX	INTEGER {
			psu1on(1),
			psu1installed(2),
			psu2on(4),
			psu2installed(8),
			psu3on(16),
			psu3installed(32),
			psu4on(64),
			psu4installed(128)
		}
		ACCESS	read-only
		STATUS	mandatory
		DESCRIPTION
			"Operational and installed status of power supply units"
		::= { starConfigManager 9 }

	starCfFanStatus	OBJECT-TYPE
		SYNTAX	INTEGER {
				fan1on(1),
				fan2on(2),
				fan3on(4),
				fan4on(8)
		}
		ACCESS	read-only
		STATUS	mandatory
		DESCRIPTION
			"Operational status of Fan units"
		::= { starConfigManager 10 }

	starCfAluLedStatus	OBJECT-TYPE
		SYNTAX	INTEGER {
				critical(1),
				major(2),
				minor(4),
				history(8),
				aco(16),
				fanfail(32),
				buzzer(64)
		}
		ACCESS	read-only
		STATUS	mandatory
		DESCRIPTION
			"Alarm unit LED display status"
		::= { starConfigManager 11 }

	starCfAluCharacterDisplay	OBJECT-TYPE
		SYNTAX	DisplayString
		ACCESS	read-only
		STATUS	mandatory
		DESCRIPTION
			"Alarm unit character display"
		::= { starConfigManager 12 }

	starCfAluBrightness	OBJECT-TYPE
		SYNTAX	INTEGER (1..4)
		ACCESS	read-write
		STATUS	mandatory
		DESCRIPTION
			"Alarm unit LED brightness indicator, 1=0%, 2=25%,
			 3=50% and 4=70%"
		::= { starConfigManager 13 }

	starCfSlotInstalled	OBJECT-TYPE
		SYNTAX	INTEGER {
			slot1installed(1),
			slot2installed(2),
			slot3installed(4),
			slot4installed(8),
			slot5installed(16),
			slot6installed(32),
			slot7installed(64),
			slot8installed(128),
			slot9installed(256),
			slot10installed(512),
			slot11installed(1024),
			slot12installed(2048),
			slot13installed(4096),
			slot14installed(8192),
			slot15installed(16384)
		}
		ACCESS	read-only
		STATUS	mandatory
		DESCRIPTION
			"Slot installed status for each board in the Star Node"
		::= { starConfigManager 14 }

	-----------------------------------------------------------------------
	-- Star System Account Manager Group
	-----------------------------------------------------------------------
	starAccountManager	OBJECT IDENTIFIER ::= { starSystem 4 }

	starAmCDRFileGetCompleted	OBJECT-TYPE
		SYNTAX	INTEGER
		ACCESS	read-write
		STATUS	mandatory
		DESCRIPTION
			"This object can be used to indicate that NMS has
			 gotton AM file"
		::= { starAccountManager 1 }

	starAmCDRThresholdCount	OBJECT-TYPE
		SYNTAX	INTEGER
		ACCESS	read-write
		STATUS	mandatory
		DESCRIPTION
			"This object is the maximum count of 
			 AM file"
		::= { starAccountManager 2 }

	starAmCDRThresholdTime	OBJECT-TYPE
		SYNTAX	INTEGER
		ACCESS	read-write
		STATUS	mandatory
		DESCRIPTION
			"This object is the maximum time of 
			 AM file"
		::= { starAccountManager 3 }

	starAmCDRFileGetRequest	OBJECT-TYPE
		SYNTAX	INTEGER
		ACCESS	write-only
		STATUS	mandatory
		DESCRIPTION
			"CDR request from NMS"
		::= { starAccountManager 4 }

	starAmCDRFileCount	OBJECT-TYPE
		SYNTAX	INTEGER
		ACCESS	read-only
		STATUS	mandatory
		DESCRIPTION
			"CDR split file number"
		::= { starAccountManager 5 }

	starAmCDRMaxCount	OBJECT-TYPE
		SYNTAX	INTEGER
		ACCESS	read-write
		STATUS	mandatory
		DESCRIPTION
			"File Split count"
		::= { starAccountManager 6 }

	starAmCacheTimer	OBJECT-TYPE
		SYNTAX	INTEGER
		ACCESS	read-write
		STATUS	mandatory
		DESCRIPTION
			"CDR cache timer default is 5 sec"
		::= { starAccountManager 7 }

	starAmCacheCounter	OBJECT-TYPE
		SYNTAX	INTEGER
		ACCESS	read-write
		STATUS	mandatory
		DESCRIPTION
			"CDR cache counter default is 12"
		::= { starAccountManager 8 }

--	starAmPortCDRCollectTable  OBJECT-TYPE
--		SYNTAX  SEQUENCE OF AmPortCDRCollectEntry
--		ACCESS  not-accessible
--		STATUS  mandatory
--		DESCRIPTION
--			"This tabble is to change the collect status of PVCM in SIUs.
--			 But the functions of SPU send the change message to each Board."
--		::= { starAccountManager 5 }
-- 
--	starAmPortCDRCollectEntry  OBJECT-TYPE
--		SYNTAX  AmPortCDRCollectEntry
--		ACCESS  not-accessible
--		STATUS  mandatory
--		DESCRIPTION
--			""
--		INDEX   { starSlotIndex, starPortIndex }
--		::= { starAmPortCDRCollectTable 1 }
--
--	 AmPortCDRCollectEntry ::=
--		SEQUENCE {
--			starAmPortCDRCollectStatusChange	INTEGER
--		}
--
--	starAmPortCDRCollectStatusChange  OBJECT-TYPE
--		SYNTAX  INTEGER (1..2)
--		ACCESS  read-write
--		STATUS  mandatory
--		DESCRIPTION
--			"AM CDR collect interval status change on each board & port
--			 1: ON,   2: OFF "
--		::= { starAmPortCDRCollectEntry 1 }


	-----------------------------------------------------------------------
	-- Star System Fault Manager Group
	-----------------------------------------------------------------------
	starFaultManager	OBJECT IDENTIFIER ::= { starSystem 5 }

	starFmSendTrapThreshold	OBJECT-TYPE
		SYNTAX	INTEGER {
			critical(1),
			major(2),
			minor(3),
			cleared(4),
			all(5)
		}
		ACCESS	read-write
		STATUS	mandatory
		DESCRIPTION
			"Threshold level of alarms to be sent as traps to the
			 NMS Manager"
		::= { starFaultManager 1 }

	starFmLogNotify	OBJECT-TYPE
		SYNTAX	INTEGER
		ACCESS	write-only
		STATUS	mandatory
		DESCRIPTION
			"A notification for log file received from NMS
			 to STAR NE"
		::= { starFaultManager 2 }

	starFmLogFileInterval	OBJECT-TYPE
		SYNTAX	INTEGER
		ACCESS	read-write
		STATUS	mandatory
		DESCRIPTION
			"A log file upload interval time to NMS
			 from STAR NE"
		::= { starFaultManager 3 }

	-----------------------------------------------------------------------
	-- Star System Slot Status Table
	-----------------------------------------------------------------------
	starSysSlotStatusTable	OBJECT-TYPE
		SYNTAX  SEQUENCE OF SysSSDEntry
		ACCESS  not-accessible
		STATUS  mandatory
		DESCRIPTION
			"This table contains status information for all boards
			 in the STAR NE."
		::= { starSystem 6 }

	starSysSlotStatusEntry	OBJECT-TYPE
		SYNTAX	SysSSDEntry
		ACCESS	not-accessible
		STATUS	mandatory
		DESCRIPTION
			""
		INDEX	{ starSSDIndex }
		::= { starSysSlotStatusTable 1 }

	SysSSDEntry ::=
		SEQUENCE {
			starSSDIndex			INTEGER,
			starSSDBdEquipStatus	INTEGER,
			starSSDModuleType		INTEGER,
			starSSDInterfaceType	INTEGER,
			starSSDOperStatus		INTEGER,
			starSSDCpuFailStatus	INTEGER,
			starSSDPwrFailStatus	INTEGER,
			starSSDRealStatus		INTEGER,
			starSiuRednConfigStatus	INTEGER,
			starSiuRednOperStatus	INTEGER,
			starSiuRednSwitchOver	INTEGER
		}

	starSSDIndex	OBJECT-TYPE
		SYNTAX	INTEGER (1..15)
		ACCESS	read-only
		STATUS	mandatory
		DESCRIPTION
			"This object value will be slot #. This object
			 will be used as index of current table."
		::= { starSysSlotStatusEntry 1 }

	starSSDBdEquipStatus	OBJECT-TYPE
		SYNTAX	INTEGER {
			noEquip (1),
			equip(2)
		}
		ACCESS	read-only
		STATUS	mandatory
		DESCRIPTION
			"Specifies whether a board is equiped or not
			 in current slot."
		::= { starSysSlotStatusEntry 2 }

	starSSDModuleType	OBJECT-TYPE
		SYNTAX	INTEGER
		ACCESS	read-only
		STATUS	mandatory
		DESCRIPTION
			"Specifies type of board in this slot, AIU, 
			 PIU, etc"
		::= { starSysSlotStatusEntry 3 }

	starSSDInterfaceType	OBJECT-TYPE
		SYNTAX	INTEGER
		ACCESS	read-only
		STATUS	mandatory
		DESCRIPTION
			"Specifies interface of board in this slot, T1, 
			 E3, etc"
		::= { starSysSlotStatusEntry 4 }

	starSSDOperStatus	OBJECT-TYPE
		SYNTAX	INTEGER {
			delete(1),
			install(2),
			active(3),
			deactive(4)
		}
		ACCESS	read-only
		STATUS	mandatory
		DESCRIPTION
			"This object contains operation status information
			 of the board in indexed slot."
		::= { starSysSlotStatusEntry 5 }

	starSSDCpuFailStatus	OBJECT-TYPE
		SYNTAX	INTEGER {
			failed (1),
			normal(2)
		}
		ACCESS	read-only
		STATUS	mandatory
		DESCRIPTION
			"contains CPU fail status of the board in the
			 indexed module"
		::= { starSysSlotStatusEntry 6 }

	starSSDPwrFailStatus	OBJECT-TYPE
		SYNTAX	INTEGER {
			failed (1),
			normal(2)
		}
		ACCESS	read-only
		STATUS	mandatory
		DESCRIPTION
			"contains power supply fail status of the board in the 
			indexed module"
		::= { starSysSlotStatusEntry 7 }

	starSSDRealStatus	OBJECT-TYPE
		SYNTAX	INTEGER 
		ACCESS	read-only
		STATUS	mandatory
		DESCRIPTION
			"SSD Real Status information from SPU's ssd structure"
		::= { starSysSlotStatusEntry 8 }

	starSiuRednConfigStatus	OBJECT-TYPE
		SYNTAX	INTEGER {
			standalone  (0),
			primary     (1),
			secondary   (2),
			undefined   (3),
			maxRedund   (4)
		}
		ACCESS	read-only
		STATUS	mandatory
		DESCRIPTION
			"SIU Redundency config information from IRCM"
		::= { starSysSlotStatusEntry 9 }

	starSiuRednOperStatus	OBJECT-TYPE
		SYNTAX	INTEGER	{
			standalone  (0),
			active      (1),
			standby     (2),
			unknown     (3),
			failedRole  (4),
			maxRedund   (5)
		}
		ACCESS	read-only
		STATUS	mandatory
		DESCRIPTION
			"SIU Redundency current operational infomation from IRCM"
		::= { starSysSlotStatusEntry 10 }


	starSiuRednSwitchOver	OBJECT-TYPE
		SYNTAX	INTEGER 
		ACCESS	write-only
		STATUS	mandatory
		DESCRIPTION
			"SIU Redundency Switchover request from NMS"
		::= { starSysSlotStatusEntry 11 }

	-----------------------------------------------------------------------
	-- Star System Fault Control Table
	-----------------------------------------------------------------------
	starFaultControlTable	OBJECT-TYPE
			SYNTAX  SEQUENCE OF StarFaultControlEntry
			ACCESS  not-accessible
			STATUS  mandatory
			DESCRIPTION
			"This table includes the objects for controlling
			 the threshold value of a fault."
		::= { starSystem 7 }

	starFaultControlEntry	OBJECT-TYPE
		SYNTAX	StarFaultControlEntry
		ACCESS	not-accessible
		STATUS	mandatory
		DESCRIPTION
			""
		INDEX	{ starFaultSlotId, starFaultGroupId, starFaultSubId }
		::= { starFaultControlTable 1 }

	StarFaultControlEntry ::=
		SEQUENCE {
			starFaultSlotId			INTEGER,
			starFaultGroupId		INTEGER,
			starFaultSubId			INTEGER,
			starSeverity			INTEGER,
			starFaultThresholdType	INTEGER,
			starFaultHappenValue	INTEGER,
			starFaultClearValue		INTEGER
		}

	starFaultSlotId	OBJECT-TYPE
		SYNTAX	INTEGER
		ACCESS	read-only
		STATUS	mandatory
		DESCRIPTION
			"The 1st index of current table"
		::= { starFaultControlEntry 1 }

	starFaultGroupId	OBJECT-TYPE
		SYNTAX	INTEGER
		ACCESS	read-only
		STATUS	mandatory
		DESCRIPTION
			"The 2nd index of current table"
		::= { starFaultControlEntry 2 }

	starFaultSubId	OBJECT-TYPE
		SYNTAX	INTEGER
		ACCESS	read-only
		STATUS	mandatory
		DESCRIPTION
			"The 3rd index of current table"
		::= { starFaultControlEntry 3 }

	starSeverity	OBJECT-TYPE
		SYNTAX	INTEGER
		ACCESS	read-write
		STATUS	mandatory
		DESCRIPTION
			""
		::= { starFaultControlEntry 4 }

	starFaultThresholdType	OBJECT-TYPE
		SYNTAX	INTEGER
		ACCESS	read-write
		STATUS	mandatory
		DESCRIPTION
			""
		::= { starFaultControlEntry 5 }

	starFaultHappenValue	OBJECT-TYPE
		SYNTAX	INTEGER
		ACCESS	read-write
		STATUS	mandatory
		DESCRIPTION
			""
		::= { starFaultControlEntry 6 }

	starFaultClearValue	OBJECT-TYPE
		SYNTAX	INTEGER
		ACCESS	read-write
		STATUS	mandatory
		DESCRIPTION
			""
		::= { starFaultControlEntry 7 }

	-----------------------------------------------------------------------
	-- Star System Trap Control Table
	-----------------------------------------------------------------------
	starTrapControlTable	OBJECT-TYPE
		SYNTAX  SEQUENCE OF StarTrapControlEntry
		ACCESS  not-accessible
		STATUS  mandatory
		DESCRIPTION
			"This table includes the trap send condition
			 values."
		::= { starSystem 8 }

	starTrapControlEntry	OBJECT-TYPE
		SYNTAX	StarTrapControlEntry
		ACCESS	not-accessible
		STATUS	mandatory
		DESCRIPTION
			""
		INDEX	{ starTrapGroupId, starTrapSubId }
		::= { starTrapControlTable 1 }

	StarTrapControlEntry ::=
		SEQUENCE {
			starTrapGroupId			INTEGER,
			starTrapSubId			INTEGER,
			starTrapSendCondition	INTEGER
		}

	starTrapGroupId	OBJECT-TYPE
		SYNTAX	INTEGER
		ACCESS	read-only
		STATUS	mandatory
		DESCRIPTION
			""
		::= { starTrapControlEntry 1 }

	starTrapSubId	OBJECT-TYPE
		SYNTAX	INTEGER
		ACCESS	read-only
		STATUS	mandatory
		DESCRIPTION
			""
		::= { starTrapControlEntry 2 }

	starTrapSendCondition	OBJECT-TYPE
		SYNTAX	INTEGER
		ACCESS	read-write
		STATUS	mandatory
		DESCRIPTION
			""
		::= { starTrapControlEntry 3 }

	-----------------------------------------------------------------------
	-- Star MIP Route Table in RLSP
	-----------------------------------------------------------------------
	starMipRouteTable	   OBJECT-TYPE
		SYNTAX  SEQUENCE OF MipRouteEntry
		ACCESS  not-accessible
		STATUS  mandatory
		DESCRIPTION
			"The M-IP route table contains the next hop that
		 an IP packet should route to  this node in the network"
		::= { starSystem 9 }
 
	starMipRouteEntry   OBJECT-TYPE
		SYNTAX  MipRouteEntry
		ACCESS  not-accessible
		STATUS  mandatory
		DESCRIPTION
			""
		INDEX   { starMipDestNeId }
		::= { starMipRouteTable 1 }
 
	MipRouteEntry ::=
		SEQUENCE {
			starMipDestNeId		INTEGER,
			starMipSourceSlot	INTEGER,
			starMipSourcePort	INTEGER
		}
 
	starMipDestNeId	 OBJECT-TYPE
		SYNTAX  INTEGER
		ACCESS  read-only
		STATUS  mandatory
		DESCRIPTION
			" NeId of Next Hop connected to"
		::= { starMipRouteEntry 1 }
 
	starMipSourceSlot	   OBJECT-TYPE
		SYNTAX  INTEGER
		ACCESS  read-only
		STATUS  mandatory
		DESCRIPTION
			"Source Slot number in this NE"
		::= { starMipRouteEntry 2 }
 
	starMipSourcePort	   OBJECT-TYPE
		SYNTAX  INTEGER
		ACCESS  read-only
		STATUS  mandatory
		DESCRIPTION
			"Source port number in this NE "
		::= { starMipRouteEntry 3 }

	--------------------------------------------------------------
	--		STARacer SVC/ATC Mibs
	--------------------------------------------------------------
	starSvcAts  OBJECT IDENTIFIER ::= { starSystem 10 }
 
	starSvcAtsValue  OBJECT IDENTIFIER ::= { starSvcAts 1 }
 
	starSvcAtsRxReqCount	OBJECT-TYPE
		SYNTAX  INTEGER
		ACCESS  read-only
		STATUS  mandatory
		DESCRIPTION
		"This variable is received Request count from SVCM"
		::={ starSvcAtsValue 1 }
 
	starSvcAtsRxValidResponseCount  OBJECT-TYPE
		SYNTAX  INTEGER
		ACCESS  read-only
		STATUS  mandatory
		DESCRIPTION
		"This variable is Valid Response count from ATS"
		::={ starSvcAtsValue 2 }
 
	starSvcAtsRxInvalidResponseCount	OBJECT-TYPE
		SYNTAX  INTEGER
		ACCESS  read-only
		STATUS  mandatory
		DESCRIPTION
		"This variable is Invalid Response count from ATS"
		::={ starSvcAtsValue 3 }
 
	starSvcAtsNotCacheCount  OBJECT-TYPE
		SYNTAX  INTEGER
		ACCESS  read-only
		STATUS  mandatory
		DESCRIPTION
		"This variable is Response count which is not cached"
		::={ starSvcAtsValue 4 }
 
	starSvcAtsCachedReqCount	OBJECT-TYPE
		SYNTAX  INTEGER
		ACCESS  read-only
		STATUS  mandatory
		DESCRIPTION
		"This variable is Request count found from cache"
		::={ starSvcAtsValue 5 }
 
	starSvcAtsTCPConnTrialCount OBJECT-TYPE
		SYNTAX  INTEGER
		ACCESS  read-only
		STATUS  mandatory
		DESCRIPTION
		"This variable is count trying to TCP connection"
		::={ starSvcAtsValue 6 }
 
	--------------------------------------------------------------
	-- ATS Server Status Table
	--------------------------------------------------------------
	starSvcAtsStatusTable   OBJECT-TYPE
		SYNTAX  SEQUENCE OF SvcAtsStatusEntry
		ACCESS  not-accessible
		STATUS  mandatory
		DESCRIPTION
		"This table contains information about ATS Servers"
		::= { starSvcAts 2 }
 
	starSvcAtsStatusEntry OBJECT-TYPE
		SYNTAX  SvcAtsStatusEntry
		ACCESS  not-accessible
		STATUS  mandatory
		DESCRIPTION
		""
		INDEX   { starSvcAtsIndex }
		::= { starSvcAtsStatusTable 1 }
 
	SvcAtsStatusEntry ::=
		SEQUENCE	{
			starSvcAtsIndex			INTEGER,
			starSvcAtsServerStatus	INTEGER
			}
 
	starSvcAtsIndex OBJECT-TYPE
		SYNTAX  INTEGER
		ACCESS  read-only
		STATUS  mandatory
		DESCRIPTION
		"ATS Index : 1 for ATS1, 2 for ATS2 But The Server can be added !"
		::={ starSvcAtsStatusEntry 1 }
 
	starSvcAtsServerStatus  OBJECT-TYPE
		SYNTAX  INTEGER
		ACCESS  read-write
		STATUS  mandatory
		DESCRIPTION
		"This Variable is status of each ATS Server"
		::={ starSvcAtsStatusEntry 2 }

	-----------------------------------------------------------------------
	-- Star System Performance Manager
	-----------------------------------------------------------------------
	starPerformanceManager  OBJECT IDENTIFIER ::= { starSystem 11 }

	starPmReportInterval	OBJECT-TYPE
		SYNTAX  INTEGER
		ACCESS  read-write
		STATUS  mandatory
		DESCRIPTION
			"This object is to set the time interval of PM statistics report
			to NMS"
		::= { starPerformanceManager 1 }
 
	starPmCollectInterval   OBJECT-TYPE
		SYNTAX  INTEGER
		ACCESS  read-write
		STATUS  mandatory
		DESCRIPTION
			"This object is to set the time interval of PM statistics collect
			in SPU"
		::= { starPerformanceManager 2 }

--	starPmStatusChange		OBJECT-TYPE
--		SYNTAX  OCTET STRING
--		ACCESS  read-write
--		STATUS  mandatory
--		DESCRIPTION
--			"This tabble is to change the statistics status of PM in SIUs.
--			 But the functions of SPU send the change message to each Board.
--			 The value is OCTET STRING and Action/Slot/BitPort."
--		::= { starPerformanceManager 3 }

 
	starPmStatsChangeTable  OBJECT-TYPE
		SYNTAX  SEQUENCE OF PmStatsChangeEntry
		ACCESS  not-accessible
		STATUS  mandatory
		DESCRIPTION
			"This tabble is to change the statistics status of PM in SIUs.
			 But the functions of SPU send the change message to each Board."
		::= { starPerformanceManager 3 }
 
	starPmStatsChangeEntry  OBJECT-TYPE
		SYNTAX  PmStatsChangeEntry
		ACCESS  not-accessible
		STATUS  mandatory
		DESCRIPTION
			""
		INDEX   { starPmIndex }
		::= { starPmStatsChangeTable 1 }
 
	PmStatsChangeEntry ::=
		SEQUENCE {
			starPmIndex					INTEGER,
			starPmPortStatusChange		OCTET STRING,
			starPmConnStatusChange		OCTET STRING
		}
 
	starPmIndex  OBJECT-TYPE
		SYNTAX  INTEGER
		ACCESS  read-only
		STATUS  mandatory
		DESCRIPTION
			"PM Status Index"
		::= { starPmStatsChangeEntry 1 }
 
	starPmPortStatusChange  OBJECT-TYPE
		SYNTAX  OCTET STRING 
		ACCESS  read-write
		STATUS  mandatory
		DESCRIPTION
			"PM Statistic status change on each port
			 1: ON,   2: OFF,   3: RESET "
		::= { starPmStatsChangeEntry 2 }
 
	starPmConnStatusChange  OBJECT-TYPE
		SYNTAX  OCTET STRING 
		ACCESS  read-write
		STATUS  mandatory
		DESCRIPTION
			"PM Statistic status change on each connection
			 1: ON,   2: OFF,   3: RESET "
		::= { starPmStatsChangeEntry 3 }
 
--	starPmConnStatusChange  OBJECT-TYPE
--		SYNTAX  INTEGER (1..3)
--		ACCESS  read-write
--		STATUS  mandatory
--		DESCRIPTION
--			"PM Statistic status change on each connection
--			 1: ON,   2: OFF,   3: RESET "
--		::= { starPmStatsChangeEntry 2 }

	-----------------------------------------------------------------------
	-- Star System Slot Table
	-----------------------------------------------------------------------
	starSlotTable		OBJECT-TYPE 
		SYNTAX  SEQUENCE OF SlotEntry
		ACCESS  not-accessible
		STATUS  mandatory
		DESCRIPTION
			"This table contains information on each Star board in
			 a specific Node"
		::= { starSlot 1 }

	starSlotEntry	OBJECT-TYPE
		SYNTAX	SlotEntry
		ACCESS	not-accessible
		STATUS	mandatory
		DESCRIPTION
			""
		INDEX	{ starSlotIndex }
		::= { starSlotTable 1 }

	SlotEntry ::=
		SEQUENCE {
			starSlotIndex					INTEGER,
			starSlotModuleType				INTEGER,
			starSlotInterfaceType			INTEGER,
			starSlotModuleDescr				DisplayString,
			starSlotMaxPortNo				INTEGER,
			starSlotModuleCpuUtilization	INTEGER,
			starSlotModuleHwVersion			INTEGER,
			starSlotModuleSwVersion			DisplayString,
			starSlotLastInstalledTime		TimeTicks,
			starSlotSSBStatus				INTEGER,
			starSlotCellPathStatus			INTEGER,
			starSlotLineClkSource			INTEGER,
			starSlotVpiVciRange				INTEGER
		}

	starSlotIndex	OBJECT-TYPE
		SYNTAX	INTEGER (1..14)
		ACCESS	read-only
		STATUS	mandatory
		DESCRIPTION
			"Index into this table"
		::= { starSlotEntry 1 }

	starSlotModuleType	OBJECT-TYPE
		SYNTAX	INTEGER
		ACCESS	read-only
		STATUS	mandatory
		DESCRIPTION
			"Specifies type of board in this slot, AIU, 
			 PIU, etc"
		::= { starSlotEntry 2 }

	starSlotInterfaceType	OBJECT-TYPE
		SYNTAX	INTEGER
		ACCESS	read-only
		STATUS	mandatory
		DESCRIPTION
			"Specifies interface of board in this slot, T1, 
			 E3, etc"
		::= { starSlotEntry 3 }

	starSlotModuleDescr	OBJECT-TYPE
		SYNTAX	DisplayString
		ACCESS	read-only
		STATUS	mandatory
		DESCRIPTION
			"Character description of the board in this slot"
		::= { starSlotEntry 4 }

	starSlotMaxPortNo	OBJECT-TYPE
		SYNTAX	INTEGER
		ACCESS	read-only
		STATUS	mandatory
		DESCRIPTION
			"Maximum number of I/O ports in this slot"
		::= { starSlotEntry 5 }

	starSlotModuleCpuUtilization	OBJECT-TYPE
		SYNTAX	INTEGER (0..100)
		ACCESS	read-only
		STATUS	mandatory
		DESCRIPTION
			"Module CPU utilization in percentage * 100 units"
		::= { starSlotEntry 6 }

	starSlotModuleHwVersion	OBJECT-TYPE
		SYNTAX	INTEGER
		ACCESS	read-only
		STATUS	mandatory
		DESCRIPTION
			"Hardware version number of the hardware installed on
			 the board in this slot"
		::= { starSlotEntry 7 }

	starSlotModuleSwVersion	OBJECT-TYPE
		SYNTAX	DisplayString
		ACCESS	read-only
		STATUS	mandatory
		DESCRIPTION
			"Display version of the software running on
			 the board in this slot"
		::= { starSlotEntry 8 }

	starSlotLastInstalledTime	OBJECT-TYPE
		SYNTAX	TimeTicks
		ACCESS	read-only
		STATUS	mandatory
		DESCRIPTION
			"Recently installed sysUpTime of module in this slot"
		::= { starSlotEntry 9 }

	starSlotSSBStatus	OBJECT-TYPE
		SYNTAX	INTEGER
		ACCESS	read-only
		STATUS	mandatory
		DESCRIPTION
			"Status of the IPC hardware for this slot"
		::= { starSlotEntry 10 }

	starSlotCellPathStatus	OBJECT-TYPE
		SYNTAX	INTEGER
		ACCESS	read-only
		STATUS	mandatory
		DESCRIPTION
			"Future entry for status of the Cell Path of this slot"
		::= { starSlotEntry 11 }

	starSlotLineClkSource	OBJECT-TYPE
		SYNTAX	INTEGER
		ACCESS	read-only
		STATUS	mandatory
		DESCRIPTION
			""
		::= { starSlotEntry 12 }

	starSlotVpiVciRange	OBJECT-TYPE
		SYNTAX	INTEGER
		ACCESS	read-write
		STATUS	mandatory
		DESCRIPTION
			""
		::= { starSlotEntry 13 }

	-----------------------------------------------------------------------
	-- Star System SSU Info Subgroup
	-----------------------------------------------------------------------
	starSlotSSUInfo		OBJECT IDENTIFIER ::= { starSlot 4 }

	-----------------------------------------------------------------------
	-- Star System SSU Load Info Table
	-----------------------------------------------------------------------
	starSSULoadInfoTbl			OBJECT-TYPE
		SYNTAX  SEQUENCE OF  StarSSULoadInfoEntry
		ACCESS  not-accessible
		STATUS  mandatory
		DESCRIPTION
			"Load information about the calls going through the ssu."
		::= { starSlotSSUInfo 1 }

	starSSULoadInfoEntry		OBJECT-TYPE
		SYNTAX  StarSSULoadInfoEntry
		ACCESS  not-accessible
		STATUS  mandatory
		DESCRIPTION
			"An entry in the ssuLoadInfoTbl."
		INDEX { starSSULoadInfoSlotId }
		::= { starSSULoadInfoTbl 1 }

	StarSSULoadInfoEntry ::=
		SEQUENCE {
			starSSULoadInfoSlotId		INTEGER ,
			starSSULoadTotalConnections	INTEGER ,
			starSSULoadNumMcConnections	INTEGER ,
			starSSULoadHighMarkVbrIn	INTEGER ,
			starSSULoadTotalVbrIn		INTEGER ,
			starSSULoadLowMarkVbrIn		INTEGER ,
			starSSULoadHighMarkVbrOut   INTEGER ,
			starSSULoadTotalVbrOut		INTEGER ,
			starSSULoadLowMarkVbrOut	INTEGER ,
			starSSULoadHighMarkFbrIn	INTEGER ,
			starSSULoadTotalFbrIn		INTEGER ,
			starSSULoadLowMarkFbrIn		INTEGER ,
			starSSULoadHighMarkFbrOut   INTEGER ,
			starSSULoadTotalFbrOut		INTEGER ,
			starSSULoadLowMarkFbrOut	INTEGER
		}

	starSSULoadInfoSlotId	OBJECT-TYPE
		SYNTAX  INTEGER
		ACCESS  read-only
		STATUS  mandatory
		DESCRIPTION
			"This object indicates the slot id."
		::= { starSSULoadInfoEntry 1 }

	starSSULoadTotalConnections OBJECT-TYPE
		SYNTAX  INTEGER
		ACCESS  read-only
		STATUS  mandatory
		DESCRIPTION
			"This object indicates the total total number
			of connections handled by the SSU."
		::= { starSSULoadInfoEntry 2 }

	starSSULoadNumMcConnections OBJECT-TYPE
		SYNTAX  INTEGER
		ACCESS  read-only
		STATUS  mandatory
		DESCRIPTION
			"This object indicates the number of multicast
			 connections presently in the SSU."
		::= { starSSULoadInfoEntry 3 }
	
	starSSULoadHighMarkVbrIn	OBJECT-TYPE
		SYNTAX  INTEGER
		ACCESS  read-only
		STATUS  mandatory
		DESCRIPTION
			"This object indicates the highest incoming
			variable bit rate reached since the
			time of operation."
		::= { starSSULoadInfoEntry 4 }

	starSSULoadTotalVbrIn	 OBJECT-TYPE
		SYNTAX  INTEGER
		ACCESS  read-only
		STATUS  mandatory
		DESCRIPTION
			"This object indicates the total input
			variable bit rate that the card is currently
			handling."
		::= { starSSULoadInfoEntry 5 }

	starSSULoadLowMarkVbrIn	 OBJECT-TYPE
		SYNTAX  INTEGER
		ACCESS  read-only
		STATUS  mandatory
		DESCRIPTION
			"This object indicates the lowest incoming
			variable bit rate reached since the
			time of operation."
		::= { starSSULoadInfoEntry 6 }

	starSSULoadHighMarkVbrOut   OBJECT-TYPE
		SYNTAX  INTEGER
		ACCESS  read-only
		STATUS  mandatory
		DESCRIPTION
			"This object indicates the highest outgoing
			variable bit rate reached since the
			time of operation."
		::= { starSSULoadInfoEntry 7 }

	starSSULoadTotalVbrOut	OBJECT-TYPE
		SYNTAX  INTEGER
		ACCESS  read-only
		STATUS  mandatory
		DESCRIPTION
			"This object indicates the total output
			variable bit rate that the card is currently
			handling."
		::= { starSSULoadInfoEntry 8 }

	starSSULoadLowMarkVbrOut	OBJECT-TYPE
		SYNTAX  INTEGER
		ACCESS  read-only
		STATUS  mandatory
		DESCRIPTION
			"This object indicates the lowest outgoing
			variable bit rate reached since the
			time of operation."
		::= { starSSULoadInfoEntry 9 }

	starSSULoadHighMarkFbrIn	OBJECT-TYPE
		SYNTAX  INTEGER
		ACCESS  read-only
		STATUS  mandatory
		DESCRIPTION
			"This object indicates the highest incoming
			fixed bit rate reached since the
			time of operation."
		::= { starSSULoadInfoEntry 10 }

	starSSULoadTotalFbrIn	 OBJECT-TYPE
		SYNTAX  INTEGER
		ACCESS  read-only
		STATUS  mandatory
		DESCRIPTION
			"This object indicates the total
			input fixed bit rate that the card is
			currently handling."
		::= { starSSULoadInfoEntry 11 }

	starSSULoadLowMarkFbrIn	 OBJECT-TYPE
		SYNTAX  INTEGER
		ACCESS  read-only
		STATUS  mandatory
		DESCRIPTION
			"This object indicates the lowest incoming
			fixed bit rate reached since the
			time of operation."
		::= { starSSULoadInfoEntry 12 }

	starSSULoadHighMarkFbrOut   OBJECT-TYPE
		SYNTAX  INTEGER
		ACCESS  read-only
		STATUS  mandatory
		DESCRIPTION
			"This object indicates the highest outgoing
			fixed bit rate reached since the
			time of operation."
		::= { starSSULoadInfoEntry 13 }

	starSSULoadTotalFbrOut	OBJECT-TYPE
		SYNTAX  INTEGER
		ACCESS  read-only
		STATUS  mandatory
		DESCRIPTION
			"This object indicates the total
			output fixed bit rate that the card is
			currently handling."
		::= { starSSULoadInfoEntry 14 }

	starSSULoadLowMarkFbrOut	OBJECT-TYPE
		SYNTAX  INTEGER
		ACCESS  read-only
		STATUS  mandatory
		DESCRIPTION
			"This object indicates the lowest outgoing
			fixed bit rate reached since the
			time of operation."
		::= { starSSULoadInfoEntry 15 }

	-----------------------------------------------------------------------
	-- Star System SIU Load Info Table
	-----------------------------------------------------------------------
	starSSUSiuLoadInfoTbl	 OBJECT-TYPE
		SYNTAX  SEQUENCE OF  StarSSUSiuLoadInfoEntry
		ACCESS  not-accessible
		STATUS  mandatory
		DESCRIPTION
			"Load information about the SSU per SIU basis."
		::= { starSlotSSUInfo 2 }

	starSSUSiuLoadInfoEntry	 OBJECT-TYPE
		SYNTAX  StarSSUSiuLoadInfoEntry
		ACCESS  not-accessible
		STATUS  mandatory
		DESCRIPTION
			"An entry in the starSSUSiuLoadInfoTbl."
		INDEX { starSlotIdSiuLoadInfo, starSiuIdSiuLoadInfo }
		::= { starSSUSiuLoadInfoTbl 1 }

	StarSSUSiuLoadInfoEntry ::=
		SEQUENCE {
			starSlotIdSiuLoadInfo	 	INTEGER ,
			starSiuIdSiuLoadInfo		INTEGER ,
			starSSUSiuTotalConnections  INTEGER ,
			starSSUSiuNumMcConnections  INTEGER ,
			starSSUSiuTotalVbrIn		INTEGER ,
			starSSUSiuTotalVbrOut		INTEGER ,
			starSSUSiuTotalFbrIn		INTEGER ,
			starSSUSiuTotalFbrOut   	INTEGER
		}

	starSlotIdSiuLoadInfo	OBJECT-TYPE
		SYNTAX  INTEGER
		ACCESS  read-only
		STATUS  mandatory
		DESCRIPTION
			"This object indicates the slot id."
		::= { starSSUSiuLoadInfoEntry 1 }

	starSiuIdSiuLoadInfo   OBJECT-TYPE
		SYNTAX  INTEGER
		ACCESS  read-only
		STATUS  mandatory
		DESCRIPTION
			"This object indicates the ID of the SIU
			 about whom the information is to be retrived."
		::= { starSSUSiuLoadInfoEntry 2 }

	starSSUSiuTotalConnections  OBJECT-TYPE
		SYNTAX  INTEGER
		ACCESS  read-only
		STATUS  mandatory
		DESCRIPTION
			"This object indicates the total number of
			 connections that the SSU handles for that SIU." 
		::= { starSSUSiuLoadInfoEntry 3 }
   
	starSSUSiuNumMcConnections  OBJECT-TYPE
		SYNTAX  INTEGER
		ACCESS  read-only
		STATUS  mandatory
		DESCRIPTION
			"This object indicates the number of multicast
			 connections originating from the corresponding SIU." 
		::= { starSSUSiuLoadInfoEntry 4 }

	starSSUSiuTotalVbrIn		OBJECT-TYPE
		SYNTAX  INTEGER
		ACCESS  read-only
		STATUS  mandatory
		DESCRIPTION
			"This object indicates the total input 
			variable bit rate that the card is currently 
			handling per SIU." 
		::= { starSSUSiuLoadInfoEntry 5 }

	starSSUSiuTotalVbrOut	 OBJECT-TYPE
		SYNTAX  INTEGER
		ACCESS  read-only
		STATUS  mandatory
		DESCRIPTION
			"This object indicates the total output
			variable bit rate that the card is currently
			handling per SIU."
		::= { starSSUSiuLoadInfoEntry 6 }

	starSSUSiuTotalFbrIn		OBJECT-TYPE
		SYNTAX  INTEGER
		ACCESS  read-only
		STATUS  mandatory
		DESCRIPTION
			"This object indicates the total 
			input fixed bit rate that the card is
			currently handling per SIU."
		::= { starSSUSiuLoadInfoEntry 7 }

	starSSUSiuTotalFbrOut	 OBJECT-TYPE
		SYNTAX  INTEGER
		ACCESS  read-only
		STATUS  mandatory
		DESCRIPTION
			"This object indicates the total 
			output fixed bit rate that the card is
			currently handling per SIU."
		::= { starSSUSiuLoadInfoEntry 8 }

	-----------------------------------------------------------------------
	-- Star System SIU Port Load Info Table
	-----------------------------------------------------------------------
	starSSUSiuPortLoadInfoTbl   OBJECT-TYPE
		SYNTAX  SEQUENCE OF  StarSSUSiuPortLoadInfoEntry
		ACCESS  not-accessible
		STATUS  mandatory
		DESCRIPTION
			"Load information about the SSU per port per SIU basis."
		::= { starSlotSSUInfo 3 }

	starSSUSiuPortLoadInfoEntry OBJECT-TYPE
		SYNTAX  StarSSUSiuPortLoadInfoEntry
		ACCESS  not-accessible
		STATUS  mandatory
		DESCRIPTION
			"An entry in the starSSUSiuLoadInfoTbl."
		INDEX { starSlotIdPortLoadInfo, starSiuIdPortLoadInfo,
				starSiuPortIdPortLoadInfo}
		::= { starSSUSiuPortLoadInfoTbl 1 }

	StarSSUSiuPortLoadInfoEntry ::=
		SEQUENCE {
			starSlotIdPortLoadInfo			INTEGER ,
			starSiuIdPortLoadInfo			INTEGER ,
			starSiuPortIdPortLoadInfo		INTEGER ,
			starSSUSiuPortTotalConnections	INTEGER ,
			starSSUSiuPortNumMcConnections	INTEGER ,
			starSSUSiuPortTotalVbrIn		INTEGER ,
			starSSUSiuPortTotalVbrOut		INTEGER ,
			starSSUSiuPortTotalFbrIn		INTEGER ,
			starSSUSiuPortTotalFbrOut	 	INTEGER
		}

	starSlotIdPortLoadInfo  OBJECT-TYPE
		SYNTAX  INTEGER
		ACCESS  read-only
		STATUS  mandatory
		DESCRIPTION
			"This object indicates the slot id."
		::= { starSSUSiuPortLoadInfoEntry 1 }

	starSiuIdPortLoadInfo	 OBJECT-TYPE
		SYNTAX  INTEGER
		ACCESS  read-only
		STATUS  mandatory
		DESCRIPTION
			"This object indicates the ID of the SIU
			 about whom the information is to be retrived."
		::= { starSSUSiuPortLoadInfoEntry 2 }

	starSiuPortIdPortLoadInfo	 OBJECT-TYPE
		SYNTAX  INTEGER
		ACCESS  read-only
		STATUS  mandatory
		DESCRIPTION
			"This object indicates the ID of the port on the
			 SIU about whom the information is to be retrived."
		::= { starSSUSiuPortLoadInfoEntry 3 }

	starSSUSiuPortTotalConnections	OBJECT-TYPE
		SYNTAX  INTEGER
		ACCESS  read-only
		STATUS  mandatory
		DESCRIPTION
			"This object indicates the total number
			of connections that the SSU handles for
			that port on that SIU."
		::= { starSSUSiuPortLoadInfoEntry 4 }

	starSSUSiuPortNumMcConnections	OBJECT-TYPE
		SYNTAX  INTEGER
		ACCESS  read-only
		STATUS  mandatory
		DESCRIPTION
			"This object indicates the number
			 of multicast connections that the SSU handles for
			 the port on that SIU."
		::= { starSSUSiuPortLoadInfoEntry 5 }
	
	starSSUSiuPortTotalVbrIn	OBJECT-TYPE
		SYNTAX  INTEGER
		ACCESS  read-only
		STATUS  mandatory
		DESCRIPTION
			"This object indicates the total input 
			variable bit rate that the card is currently
			handling per port per SIU." 
		::= { starSSUSiuPortLoadInfoEntry 6 }

	starSSUSiuPortTotalVbrOut   OBJECT-TYPE
		SYNTAX  INTEGER
		ACCESS  read-only
		STATUS  mandatory
		DESCRIPTION
			"This object indicates the total output
			variable bit rate that the card is currently
			handling per port per SIU."
		::= { starSSUSiuPortLoadInfoEntry 7 }

	starSSUSiuPortTotalFbrIn	OBJECT-TYPE
		SYNTAX  INTEGER
		ACCESS  read-only
		STATUS  mandatory
		DESCRIPTION
			"This object indicates the total 
			input fixed bit rate that the card is
			currently handling per port per SIU."
		::= { starSSUSiuPortLoadInfoEntry 8 }

	starSSUSiuPortTotalFbrOut   OBJECT-TYPE
		SYNTAX  INTEGER
		ACCESS  read-only
		STATUS  mandatory
		DESCRIPTION
			"This object indicates the total 
			output fixed bit rate that the card is
			currently handling per port per SIU."
		::= { starSSUSiuPortLoadInfoEntry 9 }

	-----------------------------------------------------------------------
	-- Star System SSU Config Info Table
	-----------------------------------------------------------------------
	starSSUConfigInfoTbl	OBJECT-TYPE
		SYNTAX  SEQUENCE OF  StarSSUConfigInfoEntry
		ACCESS  not-accessible
		STATUS  mandatory
		DESCRIPTION
			"Config Info pertaining to SSU block."
		::= { starSlotSSUInfo 4 }

	starSSUConfigInfoEntry	OBJECT-TYPE
		SYNTAX  StarSSUConfigInfoEntry
		ACCESS  not-accessible
		STATUS  mandatory
		DESCRIPTION
			"An entry in the ssuLoadInfoTbl."
		INDEX { starSSUConfigInfoSlotId }
		::= { starSSUConfigInfoTbl 1 }

	StarSSUConfigInfoEntry ::=
		SEQUENCE {
			starSSUConfigInfoSlotId			INTEGER,
			starSSUSwitchLinkMaxCapacity	INTEGER,
			starSSUSwitchLinkMaxVbr			INTEGER,
			starSSUPercentVbrToLoad			INTEGER,
			starSSUSiuInvalidationTimeout	INTEGER
		}

	starSSUConfigInfoSlotId   OBJECT-TYPE
		SYNTAX  INTEGER
		ACCESS  read-only
		STATUS  mandatory
		DESCRIPTION
			"This object indicates the slot id."
		::= { starSSUConfigInfoEntry 1 }

	starSSUSwitchLinkMaxCapacity   OBJECT-TYPE
		SYNTAX  INTEGER
		ACCESS  read-only
		STATUS  mandatory
		DESCRIPTION
			"This object indicates the maximum capacity
			for each link between switches in Gbps."
		::= { starSSUConfigInfoEntry 2 }

	starSSUSwitchLinkMaxVbr   OBJECT-TYPE
		SYNTAX  INTEGER
		ACCESS  read-only
		STATUS  mandatory
		DESCRIPTION
			"This object indicates the maximum VBR
			for each link between switches in Gbps."
		::= { starSSUConfigInfoEntry 3 }

	starSSUPercentVbrToLoad   OBJECT-TYPE
		SYNTAX  INTEGER
		ACCESS  read-only
		STATUS  mandatory
		DESCRIPTION
			"This object indicates the percentage of
			VBR to deduct to calculate load."
		::= { starSSUConfigInfoEntry 4 }

	starSSUSiuInvalidationTimeout  OBJECT-TYPE
		SYNTAX  INTEGER
		ACCESS  read-only
		STATUS  mandatory
		DESCRIPTION
			"This object indicates the time to wait for
			reconciliation message in minutes."
		::= { starSSUConfigInfoEntry 5 }

	-----------------------------------------------------------------------
	-- Star System SSU Multicast Info Table
	-----------------------------------------------------------------------
	starSSUMulticastInfoTbl   OBJECT-TYPE
		SYNTAX  SEQUENCE OF  StarSSUMulticastInfoEntry
		ACCESS  not-accessible
		STATUS  mandatory
		DESCRIPTION
			"Load information about the SSU Multipoint connections."
		::= { starSlotSSUInfo 5 }

	starSSUMulticastInfoEntry OBJECT-TYPE
		SYNTAX  StarSSUMulticastInfoEntry
		ACCESS  not-accessible
		STATUS  mandatory
		DESCRIPTION
			"An entry in the ssuMulticastInfoTbl."
		INDEX { starSSUMulticastSlotId, starSSUMulticastGroup }
		::= { starSSUMulticastInfoTbl 1 }

	StarSSUMulticastInfoEntry ::=
		SEQUENCE {
			starSSUMulticastSlotId		INTEGER ,
			starSSUMulticastGroup	 	INTEGER ,
			starSSUNumberMcLeaves	 	INTEGER ,
			starSSUMcSourceSiu			INTEGER ,
			starSSUMcSourcePort		 	INTEGER ,
			starSSUMcInputFbr			INTEGER ,
			starSSUMcInputVbr			INTEGER ,
			starSSUMcOutputFbr			INTEGER ,
			starSSUMcOutputVbr			INTEGER
		}

	starSSUMulticastSlotId  OBJECT-TYPE
		SYNTAX  INTEGER
		ACCESS  read-only
		STATUS  mandatory
		DESCRIPTION
			"This object specifies the Slot id of the SSU."
		::= { starSSUMulticastInfoEntry 1 }

	starSSUMulticastGroup  OBJECT-TYPE
		SYNTAX  INTEGER
		ACCESS  read-only
		STATUS  mandatory
		DESCRIPTION
			"This object specifies Multicast Group 
			indicating a particular pt to multi pt conn."
		::= { starSSUMulticastInfoEntry 2 }

	starSSUNumberMcLeaves  OBJECT-TYPE
		SYNTAX  INTEGER
		ACCESS  read-only
		STATUS  mandatory
		DESCRIPTION
			"Indicates the number of pt's to which this
			connection is estabilished."
		::= { starSSUMulticastInfoEntry 3 }

	starSSUMcSourceSiu   OBJECT-TYPE
		SYNTAX  INTEGER
		ACCESS  read-only
		STATUS  mandatory
		DESCRIPTION
			"This object specifies source Siu for 
			this multicast connection."
		::= { starSSUMulticastInfoEntry 4 }

	starSSUMcSourcePort   OBJECT-TYPE
		SYNTAX  INTEGER
		ACCESS  read-only
		STATUS  mandatory
		DESCRIPTION
			"This object specifies the source port 
			for this multicast connection."
		::= { starSSUMulticastInfoEntry 5 }

	starSSUMcInputFbr  OBJECT-TYPE
		SYNTAX  INTEGER
		ACCESS  read-only
		STATUS  mandatory
		DESCRIPTION
			"This object specifies the Input Fixed Bit rate  
			 for this connection."
		::= { starSSUMulticastInfoEntry 6 }

	starSSUMcInputVbr  OBJECT-TYPE
		SYNTAX  INTEGER
		ACCESS  read-only
		STATUS  mandatory
		DESCRIPTION
			"This object specifies the Input Variable Bit rate  
			 for this connection."
		::= { starSSUMulticastInfoEntry 7 }

	starSSUMcOutputFbr  OBJECT-TYPE
		SYNTAX  INTEGER
		ACCESS  read-only
		STATUS  mandatory
		DESCRIPTION
			"This object specifies the Output Fixed Bit rate  
			 for this connection."
		::= { starSSUMulticastInfoEntry 8 }

	starSSUMcOutputVbr  OBJECT-TYPE
		SYNTAX  INTEGER
		ACCESS  read-only
		STATUS  mandatory
		DESCRIPTION
			"This object specifies the Output Variable Bit rate  
			 for this connection."
		::= { starSSUMulticastInfoEntry 9 }

	-----------------------------------------------------------------------
	-- Star System SSU Link Config Info Table
	-----------------------------------------------------------------------
	starSSULinkConfigInfoTbl   OBJECT-TYPE
		SYNTAX  SEQUENCE OF  StarSSULinkConfigInfoEntry
		ACCESS  not-accessible
		STATUS  mandatory
		DESCRIPTION
			"Load information about the SSU Link Configuration."
		::= { starSlotSSUInfo 6 }

	starSSULinkConfigInfoEntry OBJECT-TYPE
		SYNTAX  StarSSULinkConfigInfoEntry
		ACCESS  not-accessible
		STATUS  mandatory
		DESCRIPTION
			"An entry in the ssuLinkConfigInfoTbl."
		INDEX { starSSULinkConfigSlotId, starSSULinkConfigSwitchLevel,
				starSSUConfigSwitchLink }
		::= { starSSULinkConfigInfoTbl 1 }

	StarSSULinkConfigInfoEntry ::=
		SEQUENCE {
			starSSULinkConfigSlotId			INTEGER ,
			starSSULinkConfigSwitchLevel	INTEGER ,
			starSSUConfigSwitchLink		 	INTEGER ,
			starSSULinkMaxCapacity			INTEGER ,
			starSSULinkMaxVbr				INTEGER
		}

	starSSULinkConfigSlotId  OBJECT-TYPE
		SYNTAX  INTEGER
		ACCESS  read-only
		STATUS  mandatory
		DESCRIPTION
			"This object specifies the Slot id of the SSU."
		::= { starSSULinkConfigInfoEntry 1 }

	starSSULinkConfigSwitchLevel  OBJECT-TYPE
		SYNTAX  INTEGER
		ACCESS  read-only
		STATUS  mandatory
		DESCRIPTION
			"This object specifies the Switch level of the
			SSU switch fabric."
		::= { starSSULinkConfigInfoEntry 2 }

	starSSUConfigSwitchLink  OBJECT-TYPE
		SYNTAX  INTEGER
		ACCESS  read-only
		STATUS  mandatory
		DESCRIPTION
			"This object specifies the switch link(1..8)."
		::= { starSSULinkConfigInfoEntry 3 }

	starSSULinkMaxCapacity  OBJECT-TYPE
		SYNTAX  INTEGER
		ACCESS  read-write
		STATUS  mandatory
		DESCRIPTION
			"This object specifies max capacity of the switch
			on that link."
		::= { starSSULinkConfigInfoEntry 4 }

	starSSULinkMaxVbr  OBJECT-TYPE
		SYNTAX  INTEGER
		ACCESS  read-write
		STATUS  mandatory
		DESCRIPTION
			"This object specifies the max Variable bit rate of
			the switch link."
		::= { starSSULinkConfigInfoEntry 5 }

	-----------------------------------------------------------------------
	-- Star System SSU Threshold Info Table
	-----------------------------------------------------------------------
	starSSUPmThresholdInfoTbl   OBJECT-TYPE
		SYNTAX  SEQUENCE OF  StarSSUPmThresholdInfoEntry
		ACCESS  not-accessible
		STATUS  mandatory
		DESCRIPTION
			"Load information about the SSU Performance manager
			 Thresholds ."
		::= { starSlotSSUInfo 7 }

	starSSUPmThresholdInfoEntry OBJECT-TYPE
		SYNTAX  StarSSUPmThresholdInfoEntry
		ACCESS  not-accessible
		STATUS  mandatory
		DESCRIPTION
			"An entry in the ssuPmThresholdInfoTbl."
		INDEX { starSSUPmThresholdSlotId }
		::= { starSSUPmThresholdInfoTbl 1 }

	StarSSUPmThresholdInfoEntry ::=
		SEQUENCE {
			starSSUPmThresholdSlotId					INTEGER,
			starSSUSwitchMcGroupThreshold		 		INTEGER,
			starSSUSwitchMcBitsPerMcgThreshold			INTEGER,
			starSSUSwitchTotalMcBitsThreshold			INTEGER,
			starSSUCrsrReqFailedThreshold				INTEGER,
			starSSUCrsrReqNumThreshold					INTEGER,
			starSSUCrsrReqFailedMcgExceededThreshold	INTEGER,
			starSSUCrsrReconcileFailThreshold			INTEGER,
			starSSUSiuLoadCapacityThreshold				INTEGER
		}

	starSSUPmThresholdSlotId  OBJECT-TYPE
		SYNTAX  INTEGER
		ACCESS  read-only
		STATUS  mandatory
		DESCRIPTION
			"This object specifies the Slot id of the SSU."
		::= { starSSUPmThresholdInfoEntry 1 }

	starSSUSwitchMcGroupThreshold  OBJECT-TYPE
		SYNTAX  INTEGER
		ACCESS  read-write
		STATUS  mandatory
		DESCRIPTION
			"This object specifies threshold for the number
			of multicast groups."
		::= { starSSUPmThresholdInfoEntry 2 }

	starSSUSwitchMcBitsPerMcgThreshold  OBJECT-TYPE
		SYNTAX  INTEGER
		ACCESS  read-write
		STATUS  mandatory
		DESCRIPTION
			"The threshold for multicast bits in a single
			multicast group"
		::= { starSSUPmThresholdInfoEntry 3 }

	starSSUSwitchTotalMcBitsThreshold	OBJECT-TYPE
		SYNTAX  INTEGER
		ACCESS  read-write
		STATUS  mandatory
		DESCRIPTION
			"This object specifies the threshold for the 
			 total num of multicast bits."
		::= { starSSUPmThresholdInfoEntry 4 }

	starSSUCrsrReqFailedThreshold	OBJECT-TYPE
		SYNTAX  INTEGER
		ACCESS  read-write
		STATUS  mandatory
		DESCRIPTION
			"This object specifies the threshold to flag a
			CRSR failure."
		::= { starSSUPmThresholdInfoEntry 5 }

	starSSUCrsrReqNumThreshold   OBJECT-TYPE
		SYNTAX  INTEGER
		ACCESS  read-write
		STATUS  mandatory
		DESCRIPTION
			"This object specifies the threshold for CRSR
			requests beyon which FM is notified."
		::= { starSSUPmThresholdInfoEntry 6 }

	starSSUCrsrReqFailedMcgExceededThreshold   OBJECT-TYPE
		SYNTAX  INTEGER
		ACCESS  read-write
		STATUS  mandatory
		DESCRIPTION
			"This object specifies the threshold at which the
			Multicast group inputs are unavailable and the CRSR 
			has failed to perform its duty."
		::= { starSSUPmThresholdInfoEntry 7 }

	starSSUCrsrReconcileFailThreshold  OBJECT-TYPE
		SYNTAX  INTEGER
		ACCESS  read-write
		STATUS  mandatory
		DESCRIPTION
			"This object specifies the threshold beyond which
			the CRSR reconcile fail is raised."
			::= { starSSUPmThresholdInfoEntry 8 }

	starSSUSiuLoadCapacityThreshold  OBJECT-TYPE
		SYNTAX  INTEGER
		ACCESS  read-write
		STATUS  mandatory
		DESCRIPTION
			"This object specifies the threshold till
			which the SSU accepts the load." 
			::= { starSSUPmThresholdInfoEntry 9 }

	-----------------------------------------------------------------------
	-- Star System Clock Group
	-----------------------------------------------------------------------
	starSysClockInfo		OBJECT IDENTIFIER ::= { starSlot 5 }

	-----------------------------------------------------------------------
	-- Star System Clock Table
	-----------------------------------------------------------------------
	starSysClockTbl	 OBJECT-TYPE
		SYNTAX  SEQUENCE OF SysClockInfoEntry
		ACCESS  not-accessible
		STATUS  mandatory
		DESCRIPTION
			"the table maintains  the clock source of the SCU
			module indexed by Slot #."
		::= { starSysClockInfo 1 }
 
	starSysClockInfoEntry	 OBJECT-TYPE
		SYNTAX  SysClockInfoEntry
		ACCESS  not-accessible
		STATUS  mandatory
		DESCRIPTION
			""
		INDEX { starScuInfoSlotId }
		::= { starSysClockTbl 1 }
 
	SysClockInfoEntry ::=
		SEQUENCE {
			starScuInfoSlotId		INTEGER ,
			starClkSource			INTEGER ,
			starClkPrevSource		INTEGER ,
			starClkSourceLine		INTEGER ,
			starClkPrevSourceLine	INTEGER ,
			starClkStatus			INTEGER ,
			starClkPLLMode			INTEGER ,
			starClkMasterStatus		INTEGER ,
			starClkPriority			INTEGER
		}

	starScuInfoSlotId	 OBJECT-TYPE
		SYNTAX  INTEGER
		ACCESS  read-only
		STATUS  mandatory
		DESCRIPTION
			"This object indicates the slot id."
		::= { starSysClockInfoEntry 1 }
 
	starClkSource   OBJECT-TYPE
		SYNTAX  INTEGER {
			init (0) ,
			bits (1),
			extline (2),
			holdover (3),
			freerun (4)
		}
		ACCESS  read-write
		STATUS  mandatory
		DESCRIPTION
			"This object indicates  the source of the clock."
		::= { starSysClockInfoEntry 2 }
 
	starClkPrevSource   OBJECT-TYPE
		SYNTAX  INTEGER {
			init (0),
			bits (1),
			extline (2),
			holdover (3),
			freerun (4)
		}
		ACCESS  read-only
		STATUS  mandatory
		DESCRIPTION
			"This object indicates  the previous source of 
			the clock."
		::= { starSysClockInfoEntry 3 }
 
	starClkSourceLine   OBJECT-TYPE
		SYNTAX  INTEGER
		ACCESS  read-write
		STATUS  mandatory
		DESCRIPTION
			"This object indicates  the SIU number 1..9
			of the current external clock source."
		::= { starSysClockInfoEntry 4 }
 
	starClkPrevSourceLine   OBJECT-TYPE
		SYNTAX  INTEGER
		ACCESS  read-only
		STATUS  mandatory
		DESCRIPTION
			"This object indicates  the SIU number 1..9
			of the previous external clock source."
		::= { starSysClockInfoEntry 5 }
 
	starClkStatus   OBJECT-TYPE
		SYNTAX  INTEGER {
			normal (1),
			fault (2)
		}
		ACCESS  read-only
		STATUS  mandatory
		DESCRIPTION
			"This object indicates  the status of the 
			current clock source. The clock source
			number must be 1-9: SIU#1-#9 for line
			clock source, or 10: for BITS"
		::= { starSysClockInfoEntry 6 }

	starClkPLLMode   OBJECT-TYPE
		SYNTAX  INTEGER {
			fast (1),
			mid (2),
			normal (3),
			holdover (4),
			freerun (5)
		}
		ACCESS  read-only
		STATUS  mandatory
		DESCRIPTION
			"This object indicates  the port number of the
			current clock source."
		::= { starSysClockInfoEntry 7 }

	starClkMasterStatus   OBJECT-TYPE
		SYNTAX  INTEGER {
			master (1),
			slave (2)
		}
		ACCESS  read-only
		STATUS  mandatory
		DESCRIPTION
			"This object indicates  the master/slave
			status of the current clock source."
		::= { starSysClockInfoEntry 8 }

	starClkPriority   OBJECT-TYPE
		SYNTAX  INTEGER
		ACCESS  read-only
		STATUS  mandatory
		DESCRIPTION
			"This object indicates  the external line
			priority of the current clock source"
		::= { starSysClockInfoEntry 9 }

	-----------------------------------------------------------------------
	-- Star Clock Current Status Table
	-----------------------------------------------------------------------
	starClkCurStatusLineTbl	 OBJECT-TYPE
		SYNTAX  SEQUENCE OF ClkCurStatusLineEntry
		ACCESS  not-accessible
		STATUS  mandatory
		DESCRIPTION
			"the table maintains  the clock source of the SCU
			module indexed by Slot #."
		::= { starSysClockInfo 2 }

	starClkCurStatusLineEntry	 OBJECT-TYPE
		SYNTAX  ClkCurStatusLineEntry 
		ACCESS  not-accessible
		STATUS  mandatory
		DESCRIPTION
			""
		INDEX { starClkStatusSlotId }
		::= { starClkCurStatusLineTbl 1 }
 
	ClkCurStatusLineEntry ::=
		SEQUENCE {
			starClkStatusSlotId			INTEGER ,
			starClkCurStatusSiu1		INTEGER ,
			starClkCurStatusSiu2		INTEGER ,
			starClkCurStatusSiu3		INTEGER ,
			starClkCurStatusSiu4		INTEGER ,
			starClkCurStatusSiu5		INTEGER ,
			starClkCurStatusSiu6		INTEGER ,
			starClkCurStatusSiu7		INTEGER ,
			starClkCurStatusSiu8		INTEGER ,
			starClkCurStatusSiu9		INTEGER
		}
 
	starClkStatusSlotId	 OBJECT-TYPE
		SYNTAX  INTEGER
		ACCESS  read-only
		STATUS  mandatory
		DESCRIPTION
			"This object indicates the slot id."
		::= { starClkCurStatusLineEntry 1 }

	starClkCurStatusSiu1	 OBJECT-TYPE
		SYNTAX  INTEGER {
			normal (1),
			fault (2),
			notready (3)
		}
		ACCESS  read-only
		STATUS  mandatory
		DESCRIPTION
			"It indicates the current status of clock line on slot 5"
		::= { starClkCurStatusLineEntry 2 }

	starClkCurStatusSiu2	 OBJECT-TYPE
		SYNTAX  INTEGER {
			normal (1),
			fault (2),
			notready (3)
		}
		ACCESS  read-only
		STATUS  mandatory
		DESCRIPTION
			"It indicates the current status of clock line"
		::= { starClkCurStatusLineEntry 3 }

	starClkCurStatusSiu3	 OBJECT-TYPE
		SYNTAX  INTEGER {
			normal (1),
			fault (2),
			notready (3)
		}
		ACCESS  read-only
		STATUS  mandatory
		DESCRIPTION
			"It indicates the current status of clock line"
		::= { starClkCurStatusLineEntry 4 }

	starClkCurStatusSiu4	 OBJECT-TYPE
		SYNTAX  INTEGER {
			normal (1),
			fault (2),
			notready (3)
		}
		ACCESS  read-only
		STATUS  mandatory
		DESCRIPTION
			"It indicates the current status of clock line"
		::= { starClkCurStatusLineEntry 5 }

	starClkCurStatusSiu5	 OBJECT-TYPE
		SYNTAX  INTEGER {
			normal (1),
			fault (2),
			notready (3)
		}
		ACCESS  read-only
		STATUS  mandatory
		DESCRIPTION
			"It indicates the current status of clock line"
		::= { starClkCurStatusLineEntry 6 }

	starClkCurStatusSiu6	 OBJECT-TYPE
		SYNTAX  INTEGER {
			normal (1),
			fault (2),
			notready (3)
		}
		ACCESS  read-only
		STATUS  mandatory
		DESCRIPTION
			"It indicates the current status of clock line"
		::= { starClkCurStatusLineEntry 7 }

	starClkCurStatusSiu7	 OBJECT-TYPE
		SYNTAX  INTEGER {
			normal (1),
			fault (2),
			notready (3)
		}
		ACCESS  read-only
		STATUS  mandatory
		DESCRIPTION
			"It indicates the current status of clock line"
		::= { starClkCurStatusLineEntry 8 }

	starClkCurStatusSiu8	 OBJECT-TYPE
		SYNTAX  INTEGER {
			normal (1),
			fault (2),
			notready (3)
		}
		ACCESS  read-only
		STATUS  mandatory
		DESCRIPTION
			"It indicates the current status of clock line slot14"
		::= { starClkCurStatusLineEntry 9 }

	starClkCurStatusSiu9	 OBJECT-TYPE
		SYNTAX  INTEGER {
			normal (1),
			fault (2),
			notready (3)
		}
		ACCESS  read-only
		STATUS  mandatory
		DESCRIPTION
			 "It indicates the current status of clock line on slot 15"
		::= { starClkCurStatusLineEntry 10 }

	-----------------------------------------------------------------------
	-- Star Clock Distributed Current Status Table
	-----------------------------------------------------------------------
	starClkDistribStatusTbl	 OBJECT-TYPE
		SYNTAX  SEQUENCE OF ClkDistribStatusEntry
		ACCESS  not-accessible
		STATUS  mandatory
		DESCRIPTION
			"the table maintains  the clock source of the SCU
			module indexed by Slot #."
		::= { starSysClockInfo 3 }
 
	starClkDistribStatusEntry	OBJECT-TYPE
		SYNTAX  ClkDistribStatusEntry 
		ACCESS  not-accessible
		STATUS  mandatory
		DESCRIPTION
			""
		INDEX { starClkDistribSlotId }
		::= { starClkDistribStatusTbl 1 }
 
	ClkDistribStatusEntry ::=
		SEQUENCE {
			starClkDistribSlotId		 INTEGER ,
			starClkDistribStatusSiu1	 INTEGER ,
			starClkDistribStatusSiu2	 INTEGER ,
			starClkDistribStatusSiu3	 INTEGER ,
			starClkDistribStatusSiu4	 INTEGER ,
			starClkDistribStatusSiu5	 INTEGER ,
			starClkDistribStatusSiu6	 INTEGER ,
			starClkDistribStatusSiu7	 INTEGER ,
			starClkDistribStatusSiu8	 INTEGER ,
			starClkDistribStatusSiu9	 INTEGER
	}

	starClkDistribSlotId	 OBJECT-TYPE
		SYNTAX  INTEGER
		ACCESS  read-only
		STATUS  mandatory
		DESCRIPTION
			"This object indicates the slot id."
		::= { starClkDistribStatusEntry  1 }

	starClkDistribStatusSiu1	 OBJECT-TYPE
		SYNTAX  INTEGER {
			eightKHZ (1),
			nintennMHZ (2)
		}
		ACCESS  read-only
		STATUS  mandatory
		DESCRIPTION
			"It indicates the distribute status of clock on slot 5"
		::= { starClkDistribStatusEntry 2 }

	starClkDistribStatusSiu2	 OBJECT-TYPE
		SYNTAX  INTEGER {
			eightKHZ (1),
			nintennMHZ (2)
		}
		ACCESS  read-only
		STATUS  mandatory
		DESCRIPTION
			"It indicates the distribute status of clock on slot 6"
		::= { starClkDistribStatusEntry 3 }

	starClkDistribStatusSiu3	 OBJECT-TYPE
		SYNTAX  INTEGER {
			eightKHZ (1),
			nintennMHZ (2)
		}
		ACCESS  read-only
		STATUS  mandatory
		DESCRIPTION
			"It indicates the distribute status of clock on slot 7"
		::= { starClkDistribStatusEntry 4 }

	starClkDistribStatusSiu4	 OBJECT-TYPE
		SYNTAX  INTEGER {
			eightKHZ (1),
			nintennMHZ (2)
		}
		ACCESS  read-only
		STATUS  mandatory
		DESCRIPTION
			"It indicates the distribute status of clock on slot 8"
		::= { starClkDistribStatusEntry 5 }

	starClkDistribStatusSiu5	 OBJECT-TYPE
		SYNTAX  INTEGER {
			eightKHZ (1),
			nintennMHZ (2)
		}
		ACCESS  read-only
		STATUS  mandatory
		DESCRIPTION
			"It indicates the distribute status of clock on slot 11"
		::= { starClkDistribStatusEntry 6 }

	starClkDistribStatusSiu6	 OBJECT-TYPE
		SYNTAX  INTEGER {
			eightKHZ (1),
			nintennMHZ (2)
		}
		ACCESS  read-only
		STATUS  mandatory
		DESCRIPTION
			"It indicates the distribute status of clock on slot12"
		::= { starClkDistribStatusEntry 7 }

	starClkDistribStatusSiu7	 OBJECT-TYPE
		SYNTAX  INTEGER {
			eightKHZ (1),
			nintennMHZ (2)
		}
		ACCESS  read-only
		STATUS  mandatory
		DESCRIPTION
			"It indicates the distribute status of clock on slot13"
		::= { starClkDistribStatusEntry 8 }

	starClkDistribStatusSiu8	 OBJECT-TYPE
		SYNTAX  INTEGER {
			eightKHZ (1),
			nintennMHZ (2)
		}
		ACCESS  read-only
		STATUS  mandatory
		DESCRIPTION
			"It indicates the distribute status of clock on slot14"
		::= { starClkDistribStatusEntry 9 }

	starClkDistribStatusSiu9	 OBJECT-TYPE
		SYNTAX  INTEGER {
			eightKHZ (1),
			nintennMHZ (2)
		}
		ACCESS  read-only
		STATUS  mandatory
		DESCRIPTION
			"It indicates the distribute status of clock on slot 15"
		::= { starClkDistribStatusEntry 10 }

	-----------------------------------------------------------------------
	-- Star System Switch88 Group
	-----------------------------------------------------------------------
	starSwitch88Info			OBJECT IDENTIFIER ::={ starSlot 6 }

	-----------------------------------------------------------------------
	-- Star System Switch Info Table
	-----------------------------------------------------------------------
	starSwitchInfoTbl   OBJECT-TYPE
		SYNTAX  SEQUENCE OF  StarSwitchInfoEntry
		ACCESS  not-accessible
		STATUS  mandatory
		DESCRIPTION
			"The table gives register values of the chips found on
			the SSU board."
		::= { starSwitch88Info 1 }

	starSwitchInfoEntry OBJECT-TYPE
		SYNTAX  StarSwitchInfoEntry
		ACCESS  not-accessible
		STATUS  mandatory
		DESCRIPTION
			"An entry in switchInfoTbl."
		INDEX { starSwitchInfoSlotId, starSwitchFabricRow,
				starSwitchFabricColumn }
		::= { starSwitchInfoTbl 1 }

	StarSwitchInfoEntry ::=
		SEQUENCE {
			starSwitchInfoSlotId		INTEGER,
			starSwitchFabricRow			INTEGER,
			starSwitchFabricColumn		INTEGER,
			starSwitchCurrentState		INTEGER,
			starSwitchChipVersion		INTEGER,
			starSwitchFabricLevel		INTEGER,
			starSwitchBckPressureDly	INTEGER,
			starSwitchAggrIp			INTEGER,
			starSwitchAggrOp			INTEGER,
			starSwitchStrictPriority	INTEGER,
			starSwitchInMarkedCellCnt	Counter,
			starSwitchOutMarkedCellCnt	Counter,
			starSwitchRatioAOrder1		INTEGER,
			starSwitchRatioAOrder2		INTEGER,
			starSwitchRatioBOrder1		INTEGER,
			starSwitchRatioBOrder2		INTEGER
		}

	starSwitchInfoSlotId  OBJECT-TYPE
		SYNTAX  INTEGER
		ACCESS  read-only
		STATUS  mandatory
		DESCRIPTION
			"This object indicates the slot id."
		::= { starSwitchInfoEntry 1 }

	starSwitchFabricRow	OBJECT-TYPE
		SYNTAX  INTEGER
		ACCESS  read-only
		STATUS  mandatory
		DESCRIPTION
			"This object indicates the switch chip
			 in the corresponding row."
		::= { starSwitchInfoEntry 2 }

	starSwitchFabricColumn	OBJECT-TYPE
		SYNTAX  INTEGER
		ACCESS  read-only
		STATUS  mandatory
		DESCRIPTION
			"This object indicates the switch chip
			 in the corresponding column." 
		::= { starSwitchInfoEntry 3 }

	starSwitchCurrentState	OBJECT-TYPE
		SYNTAX  INTEGER {
			init (1) ,
			operational (2)
		}
		ACCESS  read-only
		STATUS  mandatory
		DESCRIPTION
			"This object describes the operational
			 state of switch chip."
		::= { starSwitchInfoEntry 4 }

	starSwitchChipVersion	OBJECT-TYPE
		SYNTAX  INTEGER
		ACCESS  read-only
		STATUS  mandatory
		DESCRIPTION
			"This object indicates the version
			 of the switch chip."
		::= { starSwitchInfoEntry 5 }

	starSwitchFabricLevel	OBJECT-TYPE
		SYNTAX  INTEGER
		ACCESS  read-only
		STATUS  mandatory
		DESCRIPTION
			"The stage in which the particular cell is
			 placed in the switch fabric.
			 Value is between 1 and 9."
		::= { starSwitchInfoEntry 6 }

	starSwitchBckPressureDly	OBJECT-TYPE
		SYNTAX  INTEGER {
			noDelay (1),
			clk2Delay (2),
			clk4Delay (3)
		}
		ACCESS  read-only
		STATUS  mandatory
		DESCRIPTION
			"This object indicates that back pressure delay
			 that is to be introduced."
		::= { starSwitchInfoEntry 7 }

	starSwitchAggrIp	OBJECT-TYPE
		SYNTAX  INTEGER
		ACCESS  read-only
		STATUS  mandatory
		DESCRIPTION
			"This object indicates whether inputs are
			 grouped into 4(620 Mbps) or separately(155 Mbps)."
		::= { starSwitchInfoEntry 8 }

	starSwitchAggrOp	OBJECT-TYPE
		SYNTAX  INTEGER
		ACCESS  read-only
		STATUS  mandatory
		DESCRIPTION
			"This object indicates whether outputs are
			 grouped into 4(620 Mbps) or separately(155 Mbps)."
		::= { starSwitchInfoEntry 9 }

	starSwitchStrictPriority OBJECT-TYPE
		SYNTAX  INTEGER
		ACCESS  read-only
		STATUS  mandatory
		DESCRIPTION
			"This var indicates whether back-pressure is inserted
			 on high priority traffic when count of empty cells
			 is 0/8 "
		::= { starSwitchInfoEntry 10 }

	starSwitchInMarkedCellCnt   OBJECT-TYPE
		SYNTAX  Counter
		ACCESS  read-only
		STATUS  mandatory
		DESCRIPTION
			"This object indicates the number of cells
			 modulo 16 on an input which had Tag(9,1) set to 1."
		::= { starSwitchInfoEntry 11 }

	starSwitchOutMarkedCellCnt  OBJECT-TYPE
		SYNTAX  Counter
		ACCESS  read-only
		STATUS  mandatory
		DESCRIPTION
			"This object indicates the number of cells
			 modulo 16 on an output which had Tag(9,1) set to 1."
		::= { starSwitchInfoEntry 12 }

	starSwitchRatioAOrder1	OBJECT-TYPE
		SYNTAX  INTEGER
		ACCESS  read-only
		STATUS  mandatory
		DESCRIPTION
			"This object indicates the number of times
			 queue A is serviced first."
		::= { starSwitchInfoEntry 13 }

	starSwitchRatioAOrder2	OBJECT-TYPE
		SYNTAX  INTEGER
		ACCESS  read-only
		STATUS  mandatory
		DESCRIPTION
			"This object indicates the number of times
			 queue A is serviced second."
		::= { starSwitchInfoEntry  14 }

	starSwitchRatioBOrder1	OBJECT-TYPE
		SYNTAX  INTEGER
		ACCESS  read-only
		STATUS  mandatory
		DESCRIPTION
			"This object indicates the number of times
			 queue B is serviced first."
		::= { starSwitchInfoEntry  15 }

	starSwitchRatioBOrder2	OBJECT-TYPE
		SYNTAX  INTEGER
		ACCESS  read-only
		STATUS  mandatory
		DESCRIPTION
			"This object indicates the number of times
			 queue B is serviced second."
		::= { starSwitchInfoEntry  16 }

	-----------------------------------------------------------------------
	-- Star System Switch Multicast Info Table
	-----------------------------------------------------------------------
	starSwitchMulticastInfoTbl  OBJECT-TYPE
		SYNTAX  SEQUENCE OF  StarSwitchMulticastInfoEntry
		ACCESS  not-accessible
		STATUS  mandatory
		DESCRIPTION
			"Multicast Information about the Switch Chip
			 on the ssu board."
		::= { starSwitch88Info 2 }

	starSwitchMulticastInfoEntry	OBJECT-TYPE
		SYNTAX  StarSwitchMulticastInfoEntry
		ACCESS  not-accessible
		STATUS  mandatory
		DESCRIPTION
			"An entry in Switch multicast info table."
		INDEX { starSlotIdSwitchMcInfo, starMcSwitchFabricRow,
			 starMcSwitchFabricColumn, starSwitchMulticastNo }
		::= { starSwitchMulticastInfoTbl 1 }

	StarSwitchMulticastInfoEntry ::=
		SEQUENCE {
			starSlotIdSwitchMcInfo		INTEGER,
			starMcSwitchFabricRow		INTEGER,
			starMcSwitchFabricColumn	INTEGER,
			starSwitchMulticastNo		INTEGER,
			starSwitchMulticastPorts	INTEGER
		}

	starSlotIdSwitchMcInfo	 OBJECT-TYPE
		SYNTAX  INTEGER
		ACCESS  read-only
		STATUS  mandatory
		DESCRIPTION
			"This object indicates the slot id."
		::= { starSwitchMulticastInfoEntry 1 }

	starMcSwitchFabricRow	OBJECT-TYPE
		SYNTAX  INTEGER
		ACCESS  read-only
		STATUS  mandatory
		DESCRIPTION
			"This object indicates the switch chip
			 in the corresponding row."
		::= { starSwitchMulticastInfoEntry 2 }

	starMcSwitchFabricColumn	OBJECT-TYPE
		SYNTAX  INTEGER			
		ACCESS  read-only
		STATUS  mandatory
		DESCRIPTION
			"This object indicates the switch chip
			 in the corresponding column." 
		::= { starSwitchMulticastInfoEntry 3 }


	starSwitchMulticastNo	OBJECT-TYPE
		SYNTAX  INTEGER
		ACCESS  read-only
		STATUS  mandatory
		DESCRIPTION
			"This object indicates the multicast number
			 for which the value is being requested."
		::= { starSwitchMulticastInfoEntry 4 }


	starSwitchMulticastPorts	OBJECT-TYPE
		SYNTAX  INTEGER
		ACCESS  read-only
		STATUS  mandatory
		DESCRIPTION
			"This object indicates links on the switch
			on which the multicast cells are replicated."
		::= { starSwitchMulticastInfoEntry 5 }

	-----------------------------------------------------------------------
	-- Star System Switch Link Load Table
	-----------------------------------------------------------------------
	starSwitchLinkLoadTbl	 OBJECT-TYPE
		SYNTAX  SEQUENCE OF StarSwitchLinkLoadEntry
		ACCESS  not-accessible
		STATUS  mandatory
		DESCRIPTION
			"Information about the Load on the links between the
			switches in the switch fabric."
		::= { starSwitch88Info 3 }

	starSwitchLinkLoadEntry	 OBJECT-TYPE
		SYNTAX  StarSwitchLinkLoadEntry
		ACCESS  not-accessible
		STATUS  mandatory
		DESCRIPTION
			"An entry in Switch channel load table."
		INDEX { starSlotIdSwitchLoadInfo, starLinkLoadSwitchFabricRow,
				starLinkLoadSwitchFabricColumn, starSwitchLinkId }
		::= { starSwitchLinkLoadTbl 1 }

	StarSwitchLinkLoadEntry ::=
		SEQUENCE {
			starSlotIdSwitchLoadInfo		INTEGER,
			starLinkLoadSwitchFabricRow		INTEGER,
			starLinkLoadSwitchFabricColumn  INTEGER,
			starSwitchLinkId				INTEGER,
			starSwitchLinkVbrIn				INTEGER,
			starSwitchLinkVbrOut			INTEGER,
			starSwitchLinkFbrIn				INTEGER,
			starSwitchLinkFbrOut			INTEGER
		}

	starSlotIdSwitchLoadInfo   OBJECT-TYPE
		SYNTAX  INTEGER
		ACCESS  read-only
		STATUS  mandatory
		DESCRIPTION
			"This object indicates the slot id."
		::= { starSwitchLinkLoadEntry 1 }

	starLinkLoadSwitchFabricRow  OBJECT-TYPE
		SYNTAX  INTEGER
		ACCESS  read-only
		STATUS  mandatory
		DESCRIPTION
			"This object indicates the switch chip
			 in the corresponding row."
		::= { starSwitchLinkLoadEntry 2 }

	starLinkLoadSwitchFabricColumn	OBJECT-TYPE
		SYNTAX  INTEGER
		ACCESS  read-only
		STATUS  mandatory
		DESCRIPTION
			"This object indicates the switch chip
			 in the corresponding column." 
		::= { starSwitchLinkLoadEntry 3 }

	starSwitchLinkId OBJECT-TYPE
		SYNTAX  INTEGER
		ACCESS  read-only
		STATUS  mandatory
		DESCRIPTION
			"This object indicates the channel number
			whose load information is needed."
		::= { starSwitchLinkLoadEntry 4 }

	starSwitchLinkVbrIn  OBJECT-TYPE
		SYNTAX  INTEGER			
		ACCESS  read-only
		STATUS  mandatory
		DESCRIPTION
			"This object indicates the total input 
			variable bit rate that the channel handles."
		::= { starSwitchLinkLoadEntry 5 }

	starSwitchLinkVbrOut   OBJECT-TYPE
		SYNTAX  INTEGER
		ACCESS  read-only
		STATUS  mandatory
		DESCRIPTION
			"This object indicates the total output
			variable bit rate that the channel handles."
		::= { starSwitchLinkLoadEntry 6 }

	starSwitchLinkFbrIn  OBJECT-TYPE
		SYNTAX  INTEGER			
		ACCESS  read-only
		STATUS  mandatory
		DESCRIPTION
			"This object indicates the total input 
			fixed bit rate that the channel handles."
		::= { starSwitchLinkLoadEntry 7 }

	starSwitchLinkFbrOut   OBJECT-TYPE
		SYNTAX  INTEGER
		ACCESS  read-only
		STATUS  mandatory
		DESCRIPTION
			"This object indicates the total output
			fixed bit rate that the channel handles."
		::= { starSwitchLinkLoadEntry 8 }

	-----------------------------------------------------------------------
	-- Star System Cell Mux Table
	-----------------------------------------------------------------------
	starCellMuxInfoTbl	 OBJECT-TYPE
		SYNTAX  SEQUENCE OF StarCellMuxInfoEntry
		ACCESS  not-accessible
		STATUS  mandatory
		DESCRIPTION
			"Gives information about the CellMux(Wac185) chip"
		::= { starSlot 7 }

	starCellMuxInfoEntry   OBJECT-TYPE
		SYNTAX  StarCellMuxInfoEntry
		ACCESS  not-accessible
		STATUS  mandatory
		DESCRIPTION
			"An entry in the CellMuxInfoTbl."
		INDEX { starSlotIdCellMuxInfo, starCellMuxChipId }
		::= { starCellMuxInfoTbl 1 }

	StarCellMuxInfoEntry ::=
		SEQUENCE {
			starSlotIdCellMuxInfo		INTEGER,
			starCellMuxChipId			INTEGER,
			starCellMuxCurrentState		INTEGER,
			starCellMuxChipVersion		INTEGER,
			starCellMuxWatchDogTimer	INTEGER,
			starCellMuxUsedHighBufCnt	Counter,
			starCellMuxUsedMedBufCnt	Counter,
			starCellMuxUsedLowBufCnt	Counter,
			starCellMuxFreeHighBufCnt	Counter,
			starCellMuxFreeMedBufCnt	Counter,
			starCellMuxFreeLowBufCnt	Counter
		}

	starSlotIdCellMuxInfo	OBJECT-TYPE
		SYNTAX  INTEGER
		ACCESS  read-only
		STATUS  mandatory
		DESCRIPTION
			"This object indicates the slot id."
		::= { starCellMuxInfoEntry 1 }

	starCellMuxChipId	OBJECT-TYPE
		SYNTAX  INTEGER
		ACCESS  read-only
		STATUS  mandatory
		DESCRIPTION
			"This object indicates the cell mux chip
			 whose info is needed."
		::= { starCellMuxInfoEntry  2 }

	starCellMuxCurrentState		OBJECT-TYPE
		SYNTAX  INTEGER {
			init (1) ,
			operational (2)
		}
		ACCESS  read-only
		STATUS  mandatory
		DESCRIPTION
			"This object describes the operational
			 state of multiplexer."
		::= { starCellMuxInfoEntry 3 }

	starCellMuxChipVersion		OBJECT-TYPE
		SYNTAX  INTEGER 
		ACCESS  read-only
		STATUS  mandatory
		DESCRIPTION
			"This object describes the version of the 
			 multiplexer chip."
		::= { starCellMuxInfoEntry 4 }

	starCellMuxWatchDogTimer		OBJECT-TYPE
		SYNTAX  INTEGER 
		ACCESS  read-write
		STATUS  mandatory
		DESCRIPTION
			"This object describes the time to wait before
			 the o/p port is checked again for not accepting
			 calls."
		::= { starCellMuxInfoEntry 5 }

	starCellMuxUsedHighBufCnt	 OBJECT-TYPE
		SYNTAX  Counter 
		ACCESS  read-only
		STATUS  mandatory
		DESCRIPTION
			"This object contains the number of high priority
			 buffers allocated."
		::= { starCellMuxInfoEntry 6 }

	starCellMuxUsedMedBufCnt		OBJECT-TYPE
		SYNTAX  Counter 
		ACCESS  read-only
		STATUS  mandatory
		DESCRIPTION
			"This object contains the number of medium priority
			 buffers allocated."
		::= { starCellMuxInfoEntry 7 }

	 starCellMuxUsedLowBufCnt			OBJECT-TYPE
		SYNTAX  Counter
		ACCESS  read-only
		STATUS  mandatory
		DESCRIPTION
			"This object contains the number of low priority
			 buffers allocated."
		::= { starCellMuxInfoEntry 8 }
	 
	starCellMuxFreeHighBufCnt			OBJECT-TYPE
		SYNTAX  Counter 
		ACCESS  read-only
		STATUS  mandatory
		DESCRIPTION
			"This object contains the number of high priority
			 buffers which are free in the mux sram."
		::= { starCellMuxInfoEntry 9 }

	 starCellMuxFreeMedBufCnt			OBJECT-TYPE
		SYNTAX Counter 
		ACCESS  read-only
		STATUS  mandatory
		DESCRIPTION
			"This object contains the number of medium priority
			 buffers which are free in the mux sram."
		::= { starCellMuxInfoEntry 10 }

	starCellMuxFreeLowBufCnt			 OBJECT-TYPE
		SYNTAX  Counter
		ACCESS  read-only
		STATUS  mandatory
		DESCRIPTION
			"This object contains the number of low priority
			 buffers which are free in the mux sram."
		::= { starCellMuxInfoEntry 11 }

	-----------------------------------------------------------------------
	-- Star System Route88 Table
	-----------------------------------------------------------------------
	starSlotRoute88Table	OBJECT-TYPE
		SYNTAX  SEQUENCE OF StarRoute88Entry
		ACCESS  not-accessible
		STATUS  mandatory
		DESCRIPTION
			""
		::= { starSlot 8 }

	starSlotRoute88Entry   OBJECT-TYPE
		SYNTAX  StarRoute88Entry
		ACCESS  not-accessible
		STATUS  mandatory
		DESCRIPTION
			""
		INDEX { starSlotIndex, starSlotRoute88Index }
		::= { starSlotRoute88Table 1 }

	StarRoute88Entry ::=
		SEQUENCE {
			starSlotRoute88Index   				INTEGER,
			starSlotRoute88Revision				INTEGER,
			starSlotRoute88TxParityFailCount	Counter,
			starSlotRoute88BPIgnoredCount		Counter,
			starSlotRoute88BPLiveFailCount		Counter,
			starSlotRoute88WDFailCount			Counter,
			starSlotRoute88TxMarkedCells		Counter,
			starSlotRoute88RxMarkedCells		Counter
		}

	starSlotRoute88Index	OBJECT-TYPE
		SYNTAX  INTEGER 
		ACCESS  read-only
		STATUS  mandatory
		DESCRIPTION
			""
		::= { starSlotRoute88Entry 1 }
 
	starSlotRoute88Revision OBJECT-TYPE
		SYNTAX  INTEGER 
		ACCESS  read-only
		STATUS  mandatory
		DESCRIPTION
			""
		::= { starSlotRoute88Entry 2 }
 
	starSlotRoute88TxParityFailCount	OBJECT-TYPE
		SYNTAX  Counter 
		ACCESS  read-only
		STATUS  mandatory
		DESCRIPTION
			""
		::= { starSlotRoute88Entry 3 }
 
	starSlotRoute88BPIgnoredCount   OBJECT-TYPE
		SYNTAX  Counter 
		ACCESS  read-only
		STATUS  mandatory
		DESCRIPTION
			""
		::= { starSlotRoute88Entry 4 }
 
	starSlotRoute88BPLiveFailCount  OBJECT-TYPE
		SYNTAX  Counter 
		ACCESS  read-only
		STATUS  mandatory
		DESCRIPTION
			""
		::= { starSlotRoute88Entry 5 }
 
	starSlotRoute88WDFailCount  OBJECT-TYPE
		SYNTAX  Counter 
		ACCESS  read-only
		STATUS  mandatory
		DESCRIPTION
			""
		::= { starSlotRoute88Entry 6 }
 
	starSlotRoute88TxMarkedCells	OBJECT-TYPE
		SYNTAX  Counter 
		ACCESS  read-only
		STATUS  mandatory
		DESCRIPTION
			""
		::= { starSlotRoute88Entry 7 }
 
	starSlotRoute88RxMarkedCells	OBJECT-TYPE
		SYNTAX  Counter 
		ACCESS  read-only
		STATUS  mandatory
		DESCRIPTION
			""
		::= { starSlotRoute88Entry 8 }

	-----------------------------------------------------------------------
	-- Star System AAL1 SAR Table
	-----------------------------------------------------------------------
	starSlotAal1SarTable	OBJECT-TYPE
		SYNTAX  SEQUENCE OF StarAal1SarInfoEntry
		ACCESS  not-accessible
		STATUS  mandatory
		DESCRIPTION
			"Gives information about the aal1 sar igt WAC-021 chip"
		::= { starSlot 9 }

	starAal1SarInfoEntry   OBJECT-TYPE
		SYNTAX  StarAal1SarInfoEntry
		ACCESS  not-accessible
		STATUS  mandatory
		DESCRIPTION
			"The Aal1 related parameter table."
		INDEX { starAal1SarSlotId, starAal1SarPortId, starAal1SarChannelId }
		::= { starSlotAal1SarTable 1 }

	StarAal1SarInfoEntry ::=
		SEQUENCE {
			starAal1SarSlotId			INTEGER,
			starAal1SarPortId			INTEGER,
			starAal1SarChannelId		INTEGER,
			starAal1SarInvalidSnCnt	 	INTEGER, 
			starAal1SarIncorrectSnpCnt	INTEGER, 
			starAal1SarRxOAMCellCnt		INTEGER,
			starAal1SarRxCellLossStatus	INTEGER,
			starAal1SarLostCellCnt		INTEGER,
			starAal1SarTxCellCnt		INTEGER,
			starAal1SarRxCellCnt		INTEGER,
			starAal1SarRxUnderrun		INTEGER,
			starAal1SarRxOverrun		INTEGER,
			starAal1SarPtrMismatch		INTEGER
		}

	starAal1SarSlotId	OBJECT-TYPE
		SYNTAX  INTEGER
		ACCESS  read-only
		STATUS  mandatory
		DESCRIPTION
			"This object indicates the slot id."
		::= { starAal1SarInfoEntry 1 }

	 starAal1SarPortId	 OBJECT-TYPE
		SYNTAX  INTEGER
		ACCESS  read-only
		STATUS  mandatory
		DESCRIPTION
			"This object indicates the port number 
			 whose info is needed."
		::= { starAal1SarInfoEntry  2 }

	 starAal1SarChannelId	 OBJECT-TYPE
		SYNTAX  INTEGER
		ACCESS  read-only
		STATUS  mandatory
		DESCRIPTION
			"This object indicates the PCM channel number 
			 whose info is needed."
		::= { starAal1SarInfoEntry  3 }

	 starAal1SarInvalidSnCnt	OBJECT-TYPE
		SYNTAX  INTEGER
		ACCESS  read-only
		STATUS  mandatory
		DESCRIPTION
			"This specifies the number of Invalid sequence numbered cells ."
		::= { starAal1SarInfoEntry  4 }

	starAal1SarIncorrectSnpCnt		OBJECT-TYPE
		SYNTAX  INTEGER
		ACCESS  read-only
		STATUS  mandatory
		DESCRIPTION
			"This specifies the number of cells for which SNP are uncorrected ."
		::= { starAal1SarInfoEntry  5 }

	starAal1SarRxOAMCellCnt	 OBJECT-TYPE
		SYNTAX  INTEGER
		ACCESS  read-only
		STATUS  mandatory
		DESCRIPTION
			" This object has a count of the number of
			OAM Cells Handled."
		::= { starAal1SarInfoEntry 6 }

	starAal1SarRxCellLossStatus	OBJECT-TYPE
		SYNTAX  INTEGER
		ACCESS  read-only
		STATUS  mandatory
		DESCRIPTION
			"This specifies the stataus for Rx cell loss ."
		::= { starAal1SarInfoEntry  7 }

	starAal1SarLostCellCnt	OBJECT-TYPE
		SYNTAX  INTEGER
		ACCESS  read-only
		STATUS  mandatory
		DESCRIPTION
			"This specifies the number of cells with an invalid CRC ."
		::= { starAal1SarInfoEntry  8 }

	starAal1SarTxCellCnt			 OBJECT-TYPE
		SYNTAX  INTEGER
		ACCESS  read-only
		STATUS  mandatory
		DESCRIPTION
			" This object has a count of the number of
			Cells transmitted."
		::= { starAal1SarInfoEntry 9  }

	starAal1SarRxCellCnt		OBJECT-TYPE
		SYNTAX  INTEGER
		ACCESS  read-only
		STATUS  mandatory
		DESCRIPTION
			"This object has a count of the number of
			Cells received."
		::= { starAal1SarInfoEntry  10 }

	 starAal1SarRxUnderrun	 OBJECT-TYPE
		SYNTAX  INTEGER
		ACCESS  read-only
		STATUS  mandatory
		DESCRIPTION
			"This object has a count of the number of
			the receiver underran."
		::= { starAal1SarInfoEntry  11 }

	starAal1SarRxOverrun	 OBJECT-TYPE
		SYNTAX  INTEGER
		ACCESS  read-only
		STATUS  mandatory
		DESCRIPTION
			"This object has a count of the number of
			times the receiver overran."
		::= { starAal1SarInfoEntry  12 }

	starAal1SarPtrMismatch	OBJECT-TYPE
		SYNTAX  INTEGER
		ACCESS  read-only
		STATUS  mandatory
		DESCRIPTION
			"This object has a count of the number of
			Aal1 pointer Mismatches ."
		::= { starAal1SarInfoEntry  13 }

	-----------------------------------------------------------------------
	-- Star System Link State Generation Table
	-----------------------------------------------------------------------
	starSlotLsgnStatusTable		OBJECT-TYPE
		SYNTAX  SEQUENCE OF LsgnEntry
		ACCESS  not-accessible
		STATUS  mandatory
		DESCRIPTION
			"" 
		::= { starSlot 10 }

	starLsgnEntry	OBJECT-TYPE
		SYNTAX	LsgnEntry
		ACCESS	not-accessible
		STATUS	mandatory
		DESCRIPTION
			""
		INDEX	{ starSlotIndex, starPortIndex }
		::= { starSlotLsgnStatusTable 1 }

	LsgnEntry ::=
		SEQUENCE {
			starLsgnDownCt					INTEGER,
			starLsgnUpCt					INTEGER,
			starLsgnTrafficLoadChangedCt	INTEGER,
			starLsgnPeriodMsgCt				INTEGER,
			starLsgnLinkOperStatus			INTEGER
		}

	starLsgnDownCt		OBJECT-TYPE
		SYNTAX	INTEGER
		ACCESS	read-only
		STATUS	mandatory
		DESCRIPTION
			"Number of times a Link Down Message was sent for the
			 link"
		::= { starLsgnEntry 1 }

	starLsgnUpCt		OBJECT-TYPE
		SYNTAX	INTEGER
		ACCESS	read-only
		STATUS	mandatory
		DESCRIPTION
			"Number of times a Link Up Message was sent for the
			 link"
		::= { starLsgnEntry 2 }

	starLsgnTrafficLoadChangedCt	OBJECT-TYPE
		SYNTAX	INTEGER
		ACCESS	read-only
		STATUS	mandatory
		DESCRIPTION
			"Number of times the link's traffic load changed"
		::= { starLsgnEntry 3 }

	starLsgnPeriodMsgCt		OBJECT-TYPE
		SYNTAX	INTEGER
		ACCESS	read-only
		STATUS	mandatory
		DESCRIPTION
			"Number of times a Periodic Link Message was sent"
		::= { starLsgnEntry 4 }

	starLsgnLinkOperStatus		OBJECT-TYPE
		SYNTAX	INTEGER
		ACCESS	read-only
		STATUS	mandatory
		DESCRIPTION
			"Current status of the link"
		::= { starLsgnEntry 5 }

	-----------------------------------------------------------------------
	-- Star System Link Status Update Table in RLSP
	-----------------------------------------------------------------------
	starSlotRlspStatusTable		OBJECT-TYPE
		SYNTAX  SEQUENCE OF RlspEntry
		ACCESS  not-accessible
		STATUS  mandatory
		DESCRIPTION
			"" 
		::= { starSlot 11 }

	starRlspEntry	OBJECT-TYPE
		SYNTAX	RlspEntry
		ACCESS	not-accessible
		STATUS	mandatory
		DESCRIPTION
			""
		INDEX	{ starSlotIndex }
		::= { starSlotRlspStatusTable 1 }

	RlspEntry ::=
		SEQUENCE {
			starRlspForwardedCt		INTEGER,
			starRlspDiscardedCt		INTEGER,
			starRlspInvalidCt		INTEGER,
			starRlspMismatchCt		INTEGER,
			starRlspNoRoutesCt		INTEGER
		}

	starRlspForwardedCt		OBJECT-TYPE
		SYNTAX	INTEGER
		ACCESS	read-only
		STATUS	mandatory
		DESCRIPTION
			"Number of received LSU's (Link Status Updates) that
			 are forwarded"
		::= { starRlspEntry 1 }

	starRlspDiscardedCt		OBJECT-TYPE
		SYNTAX	INTEGER
		ACCESS	read-only
		STATUS	mandatory
		DESCRIPTION
			"Number of received LSU's (Link Status Updates) that
			 are discarded"
		::= { starRlspEntry 2 }

	starRlspInvalidCt		OBJECT-TYPE
		SYNTAX	INTEGER
		ACCESS	read-only
		STATUS	mandatory
		DESCRIPTION
			"Number of messages received that indicate that a route
			 specified by the routing software is incorrect"
		::= { starRlspEntry 3 }

	starRlspMismatchCt		OBJECT-TYPE
		SYNTAX	INTEGER
		ACCESS	read-only
		STATUS	mandatory
		DESCRIPTION
			"Number of received LSU (Link Status Update) messages
			 that did not match locally stored Link State Table 
			 Entries"
		::= { starRlspEntry 4 }

	starRlspNoRoutesCt		OBJECT-TYPE
		SYNTAX	INTEGER
		ACCESS	read-only
		STATUS	mandatory
		DESCRIPTION
			"Number of route requests or route validates for which
			 no route with a valid cost was found"
		::= { starRlspEntry 5 }

	-----------------------------------------------------------------------
	-- Star System Backbone Connection Protocol Table
	-----------------------------------------------------------------------
	starSlotBbcpStatusTable		OBJECT-TYPE
		SYNTAX  SEQUENCE OF BbcpEntry
		ACCESS  not-accessible
		STATUS  mandatory
		DESCRIPTION
			"" 
		::= { starSlot 12 }

	starBbcpEntry	OBJECT-TYPE
		SYNTAX	BbcpEntry
		ACCESS	not-accessible
		STATUS	mandatory
		DESCRIPTION
			""
		INDEX	{ starSlotIndex, starPortIndex }
		::= { starSlotBbcpStatusTable 1 }

	BbcpEntry ::=
		SEQUENCE {
			starBbcpPtoPInConnections					INTEGER,
			starBbcpPtoPOutConnections					INTEGER,
			starBbcpPtoMInConnections					INTEGER,
			starBbcpPtoMOutConnections					INTEGER,
			starBbcpInConnectionLinkFailCt				INTEGER,
			starBbcpInConnectionVcciFailCt				INTEGER,
			starBbcpInConnectionNoSwitchCapacityCt		INTEGER,
			starBbcpInConnectionNoBBCapacityCt			INTEGER,
			starBbcpInConnectionTimeoutCt				INTEGER,
			starBbcpInConnectionChipErrorCt				INTEGER,
			starBbcpInConnectionPreemptFailCt			INTEGER,
			starBbcpInConnectionModuleFailCt			INTEGER,
			starBbcpInConnectionVcciCollisionFailCt		INTEGER,
			starBbcpOutConnectionLinkFailCt				INTEGER,
			starBbcpOutConnectionVcciInvalidCt			INTEGER,
			starBbcpOutConnectionNoSwitchCapacityCt		INTEGER,
			starBbcpOutConnectionNoBBCapacityCt			INTEGER,
			starBbcpOutConnectionTimeoutCt				INTEGER,
			starBbcpOutConnectionChipErrorCt			INTEGER,
			starBbcpOutConnectionPreemptFailCt			INTEGER,
			starBbcpOutConnectionModuleFailCt			INTEGER,
			starBbcpOutConnectionVcciCollisionFailCt	INTEGER,
			starBbcpInConnectionClearLinkFailCt			INTEGER,
			starBbcpInConnectionClearPreemptionCt		INTEGER,
			starBbcpInConnectionClearModuleFailCt		INTEGER,
			starBbcpInConnectionClearNormalCt			INTEGER,
			starBbcpOutConnectionClearLinkFailCt		INTEGER,
			starBbcpOutConnectionClearPreemptionCt		INTEGER,
			starBbcpOutConnectionClearModuleFailCt		INTEGER,
			starBbcpOutConnectionClearNormalCt			INTEGER,
			starBbcpInvalidMsgCt						INTEGER,
			starBbcpTimerExpiredCt						INTEGER,
			starBbcpInvalidEventCt						INTEGER,
			starBbcpAvailableFixedCapacity				INTEGER,
			starBbcpAvailableVariableCapacity			INTEGER
		}

	starBbcpPtoPInConnections	OBJECT-TYPE
		SYNTAX	INTEGER
		ACCESS	read-only
		STATUS	mandatory
		DESCRIPTION
			"Number of active incoming point to point connections"
		::= { starBbcpEntry 1 }

	starBbcpPtoPOutConnections	OBJECT-TYPE
		SYNTAX	INTEGER
		ACCESS	read-only
		STATUS	mandatory
		DESCRIPTION
			"Number of active outgoing point to point connections"
		::= { starBbcpEntry 2 }

	starBbcpPtoMInConnections	OBJECT-TYPE
		SYNTAX	INTEGER
		ACCESS	read-only
		STATUS	mandatory
		DESCRIPTION
			"Number of active incoming point to multi-point 
			 connections"
		::= { starBbcpEntry 3 }

	starBbcpPtoMOutConnections	OBJECT-TYPE
		SYNTAX	INTEGER
		ACCESS	read-only
		STATUS	mandatory
		DESCRIPTION
			"Number of active outgoing point to multi-point 
			 connections"
		::= { starBbcpEntry 4 }

	starBbcpInConnectionLinkFailCt	OBJECT-TYPE
		SYNTAX	INTEGER
		ACCESS	read-only
		STATUS	mandatory
		DESCRIPTION
			"Number of incoming connection requests that were
			 rejected because a backbone link on the module was 
			 down"
		::= { starBbcpEntry 5 }

	starBbcpInConnectionVcciFailCt	OBJECT-TYPE
		SYNTAX	INTEGER
		ACCESS	read-only
		STATUS	mandatory
		DESCRIPTION
			"Number of incoming connection requests that were
			 rejected because Vpi, Vci in the connection is 
			 invalid"
		::= { starBbcpEntry 6 }

	starBbcpInConnectionNoSwitchCapacityCt	OBJECT-TYPE
		SYNTAX	INTEGER
		ACCESS	read-only
		STATUS	mandatory
		DESCRIPTION
			"Number of incoming connection requests that were
			 rejected because the switch did not have the capacity
			 to support the call"
		::= { starBbcpEntry 7 }

	starBbcpInConnectionNoBBCapacityCt	OBJECT-TYPE
		SYNTAX	INTEGER
		ACCESS	read-only
		STATUS	mandatory
		DESCRIPTION
			"Number of incoming connection requests that were
			 rejected because the backbone link did not have the
			 capacity to support the call"
		::= { starBbcpEntry 8 }

	starBbcpInConnectionTimeoutCt	OBJECT-TYPE
		SYNTAX	INTEGER
		ACCESS	read-only
		STATUS	mandatory
		DESCRIPTION
			"Number of incoming connection requests that were
			 rejected because the BBCP did not receive a connection
			 proceeding message within the specified time"
		::= { starBbcpEntry 9 }

	starBbcpInConnectionChipErrorCt	OBJECT-TYPE
		SYNTAX	INTEGER
		ACCESS	read-only
		STATUS	mandatory
		DESCRIPTION
			"Number of incoming connection requests that were
			 rejected because a chip could not be programmed"
		::= { starBbcpEntry 10 }

	starBbcpInConnectionPreemptFailCt	OBJECT-TYPE
		SYNTAX	INTEGER
		ACCESS	read-only
		STATUS	mandatory
		DESCRIPTION
			"Number of incoming connection requests that were
			 rejected because the BBCP did not preempt another
			 connection"
		::= { starBbcpEntry 11 }

	starBbcpInConnectionModuleFailCt	OBJECT-TYPE
		SYNTAX	INTEGER
		ACCESS	read-only
		STATUS	mandatory
		DESCRIPTION
			"Number of incoming connection requests that were
			 rejected because the adjacent module has failed"
		::= { starBbcpEntry 12 }

	starBbcpInConnectionVcciCollisionFailCt	OBJECT-TYPE
		SYNTAX	INTEGER
		ACCESS	read-only
		STATUS	mandatory
		DESCRIPTION
			"Number of incoming connection requests that were
			 rejected because the Vpi/Vci in the connection
			 request has collided with the Vpi/Vci in another
			 connection"
		::= { starBbcpEntry 13 }

	starBbcpOutConnectionLinkFailCt	OBJECT-TYPE
		SYNTAX	INTEGER
		ACCESS	read-only
		STATUS	mandatory
		DESCRIPTION
			"Number of outgoing connection requests that were
			 rejected because a backbone link on the module was 
			 down"
		::= { starBbcpEntry 14 }

	starBbcpOutConnectionVcciInvalidCt	OBJECT-TYPE
		SYNTAX	INTEGER
		ACCESS	read-only
		STATUS	mandatory
		DESCRIPTION
			"Number of outgoing connection requests that were
			 rejected because the Vpi, Vci in the connection is
			 invalid"
		::= { starBbcpEntry 15 }

	starBbcpOutConnectionNoSwitchCapacityCt	OBJECT-TYPE
		SYNTAX	INTEGER
		ACCESS	read-only
		STATUS	mandatory
		DESCRIPTION
			"Number of outgoing connection requests that were
			 rejected because the switch did not have the capacity
			 to support the call"
		::= { starBbcpEntry 16 }

	starBbcpOutConnectionNoBBCapacityCt	OBJECT-TYPE
		SYNTAX	INTEGER
		ACCESS	read-only
		STATUS	mandatory
		DESCRIPTION
			"Number of outgoing connection requests that were
			 rejected because the backbone link did not have
			 the capacity to support the call"
		::= { starBbcpEntry 17 }

	starBbcpOutConnectionTimeoutCt	OBJECT-TYPE
		SYNTAX	INTEGER
		ACCESS	read-only
		STATUS	mandatory
		DESCRIPTION
			"Number of outgoing connection requests that were
			 rejected because the BBCP did not receive a connection
			 proceeding message within the specified time"
		::= { starBbcpEntry 18 }

	starBbcpOutConnectionChipErrorCt	OBJECT-TYPE
		SYNTAX	INTEGER
		ACCESS	read-only
		STATUS	mandatory
		DESCRIPTION
			"Number of outgoing connection requests that were
			 rejected because a chip could not be programmed"
		::= { starBbcpEntry 19 }

	starBbcpOutConnectionPreemptFailCt	OBJECT-TYPE
		SYNTAX	INTEGER
		ACCESS	read-only
		STATUS	mandatory
		DESCRIPTION
			"Number of outgoing connection requests that were
			 rejected because the BBCP did not preempt another
			 connection"
		::= { starBbcpEntry 20 }

	starBbcpOutConnectionModuleFailCt	OBJECT-TYPE
		SYNTAX	INTEGER
		ACCESS	read-only
		STATUS	mandatory
		DESCRIPTION
			"Number of outgoing connection requests that were
			 rejected because the adjacent module has failed"
		::= { starBbcpEntry 21 }

	starBbcpOutConnectionVcciCollisionFailCt	OBJECT-TYPE
		SYNTAX	INTEGER
		ACCESS	read-only
		STATUS	mandatory
		DESCRIPTION
			"Number of outgoing connection requests that were
			 rejected because the Vpi/Vci in the connection
			 request has collided with the Vpi/Vci in another
			 connection"
		::= { starBbcpEntry 22 }

	starBbcpInConnectionClearLinkFailCt	OBJECT-TYPE
		SYNTAX	INTEGER
		ACCESS	read-only
		STATUS	mandatory
		DESCRIPTION
			"Number of incoming connections that were cleared
			 due to failure of a backbone link on the module"
		::= { starBbcpEntry 23 }

	starBbcpInConnectionClearPreemptionCt	OBJECT-TYPE
		SYNTAX	INTEGER
		ACCESS	read-only
		STATUS	mandatory
		DESCRIPTION
			"Number of incoming connections that were cleared
			 due to preemption at the module"
		::= { starBbcpEntry 24 }

	starBbcpInConnectionClearModuleFailCt	OBJECT-TYPE
		SYNTAX	INTEGER
		ACCESS	read-only
		STATUS	mandatory
		DESCRIPTION
			"Number of incoming connections that were cleared
			 due to failure of an adjacent module"
		::= { starBbcpEntry 25 }

	starBbcpInConnectionClearNormalCt	OBJECT-TYPE
		SYNTAX	INTEGER
		ACCESS	read-only
		STATUS	mandatory
		DESCRIPTION
			"Number of incoming connections that were cleared
			 due to a normal clear request"
		::= { starBbcpEntry 26 }

	starBbcpOutConnectionClearLinkFailCt	OBJECT-TYPE
		SYNTAX	INTEGER
		ACCESS	read-only
		STATUS	mandatory
		DESCRIPTION
			"Number of outgoing connections that were cleared
			 due to failure of a backbone link on the module"
		::= { starBbcpEntry 27 }

	starBbcpOutConnectionClearPreemptionCt	OBJECT-TYPE
		SYNTAX	INTEGER
		ACCESS	read-only
		STATUS	mandatory
		DESCRIPTION
			"Number of outgoing connections that were cleared
			 due to preemption at the module"
		::= { starBbcpEntry 28 }

	starBbcpOutConnectionClearModuleFailCt	OBJECT-TYPE
		SYNTAX	INTEGER
		ACCESS	read-only
		STATUS	mandatory
		DESCRIPTION
			"Number of outgoing connections that were cleared
			 due to failure of an adjacent module"
		::= { starBbcpEntry 29 }

	starBbcpOutConnectionClearNormalCt	OBJECT-TYPE
		SYNTAX	INTEGER
		ACCESS	read-only
		STATUS	mandatory
		DESCRIPTION
			"Number of outgoing connections that were cleared
			 due to a noraml clear request"
		::= { starBbcpEntry 30 }

	starBbcpInvalidMsgCt	OBJECT-TYPE
		SYNTAX	INTEGER
		ACCESS	read-only
		STATUS	mandatory
		DESCRIPTION
			"Number of invalid messages received from a peer
			 BBCP"
		::= { starBbcpEntry 31 }

	starBbcpTimerExpiredCt	OBJECT-TYPE
		SYNTAX	INTEGER
		ACCESS	read-only
		STATUS	mandatory
		DESCRIPTION
			"Number of timer expired at signalling"
		::= { starBbcpEntry 32 }

	starBbcpInvalidEventCt	OBJECT-TYPE
		SYNTAX	INTEGER
		ACCESS	read-only
		STATUS	mandatory
		DESCRIPTION
			"Number of times an invalid event occurred in a state"
		::= { starBbcpEntry 33 }

	starBbcpAvailableFixedCapacity	OBJECT-TYPE
		SYNTAX	INTEGER
		ACCESS	read-only
		STATUS	mandatory
		DESCRIPTION
			"Fixed capacity available on a link"
		::= { starBbcpEntry 34 }

	starBbcpAvailableVariableCapacity	OBJECT-TYPE
		SYNTAX	INTEGER
		ACCESS	read-only
		STATUS	mandatory
		DESCRIPTION
			"Variable capacity available on a link"
		::= { starBbcpEntry 35 }

	-----------------------------------------------------------------------
	-- Star System Backbone Cross Connection Table
	-----------------------------------------------------------------------
	starSlotBbcpXConnectTable	OBJECT-TYPE
		SYNTAX  SEQUENCE OF BbcpXConnectEntry
		ACCESS  not-accessible
		STATUS  mandatory
		DESCRIPTION
			"" 
		::= { starSlot 13 }

	starBbcpXConnectEntry	OBJECT-TYPE
		SYNTAX	BbcpXConnectEntry
		ACCESS	not-accessible
		STATUS	mandatory
		DESCRIPTION
			""
		INDEX	{ starBbcpSlotIndex, starBbcpPortIndex, starBbcpGCIDNeId,
				  starBbcpGCIDSlotId, starBbcpGCIDPortId, starBbcpGCIDIfType,
				  starBbcpGCIDConnId, starBbcpGCIDLeafId }
		::= { starSlotBbcpXConnectTable 1 }

	BbcpXConnectEntry ::=
		SEQUENCE {
			starBbcpSlotIndex				INTEGER,
			starBbcpPortIndex				INTEGER,
			starBbcpGCIDNeId				INTEGER,
			starBbcpGCIDSlotId				INTEGER,
			starBbcpGCIDPortId				INTEGER,
			starBbcpGCIDIfType				INTEGER,
			starBbcpGCIDConnId				INTEGER,
			starBbcpGCIDLeafId				INTEGER,
			starBbcpXConnOperStatus			INTEGER,
			starBbcpXConnAdjacentSlotId		INTEGER,
			starBbcpXConnAdjacentPortId		INTEGER,
			starBbcpXConnAdjacentVpi		INTEGER,
			starBbcpXConnAdjacentVci		INTEGER
		}

	starBbcpSlotIndex		OBJECT-TYPE
		SYNTAX	INTEGER
		ACCESS	read-only
		STATUS	mandatory
		DESCRIPTION
			""
		::= { starBbcpXConnectEntry 1 }

	starBbcpPortIndex		OBJECT-TYPE
		SYNTAX	INTEGER
		ACCESS	read-only
		STATUS	mandatory
		DESCRIPTION
			""
		::= { starBbcpXConnectEntry 2 }

	starBbcpGCIDNeId		OBJECT-TYPE
		SYNTAX	INTEGER
		ACCESS	read-only
		STATUS	mandatory
		DESCRIPTION
			""
		::= { starBbcpXConnectEntry 3 }

	starBbcpGCIDSlotId		OBJECT-TYPE
		SYNTAX	INTEGER
		ACCESS	read-only
		STATUS	mandatory
		DESCRIPTION
			""
		::= { starBbcpXConnectEntry 4 }

	starBbcpGCIDPortId		OBJECT-TYPE
		SYNTAX	INTEGER
		ACCESS	read-only
		STATUS	mandatory
		DESCRIPTION
			""
		::= { starBbcpXConnectEntry 5 }

	starBbcpGCIDIfType		OBJECT-TYPE
		SYNTAX	INTEGER
		ACCESS	read-only
		STATUS	mandatory
		DESCRIPTION
			""
		::= { starBbcpXConnectEntry 6 }

	starBbcpGCIDConnId		OBJECT-TYPE
		SYNTAX	INTEGER
		ACCESS	read-only
		STATUS	mandatory
		DESCRIPTION
			""
		::= { starBbcpXConnectEntry 7 }

	starBbcpGCIDLeafId		OBJECT-TYPE
		SYNTAX	INTEGER
		ACCESS	read-only
		STATUS	mandatory
		DESCRIPTION
			""
		::= { starBbcpXConnectEntry 8 }

	starBbcpXConnOperStatus		OBJECT-TYPE
		SYNTAX	INTEGER
		ACCESS	read-only
		STATUS	mandatory
		DESCRIPTION
			"Operational status of specified cross connection in NE"
		::= { starBbcpXConnectEntry 9 }

	starBbcpXConnAdjacentSlotId		OBJECT-TYPE
		SYNTAX	INTEGER
		ACCESS	read-only
		STATUS	mandatory
		DESCRIPTION
			"Adjacent SlotId of specified cross connection"
		::= { starBbcpXConnectEntry 10 }

	starBbcpXConnAdjacentPortId		OBJECT-TYPE
		SYNTAX	INTEGER
		ACCESS	read-only
		STATUS	mandatory
		DESCRIPTION
			"Adjacent PortId of specified cross connection"
		::= { starBbcpXConnectEntry 11 }

	starBbcpXConnAdjacentVpi		OBJECT-TYPE
		SYNTAX	INTEGER
		ACCESS	read-only
		STATUS	mandatory
		DESCRIPTION
			"Adjacent Vpi of specified cross connection"
		::= { starBbcpXConnectEntry 12 }

	starBbcpXConnAdjacentVci		OBJECT-TYPE
		SYNTAX	INTEGER
		ACCESS	read-only
		STATUS	mandatory
		DESCRIPTION
			"Adjacent Vci of specified cross connection"
		::= { starBbcpXConnectEntry 13 }

	-----------------------------------------------------------------------
	-- Star System PVCM Status Table
	-----------------------------------------------------------------------
	starPvcmStatusTable	OBJECT-TYPE
		SYNTAX  SEQUENCE OF PvcmEntry
		ACCESS  not-accessible
		STATUS  mandatory
		DESCRIPTION
			"" 
		::= { starSlot 14 }

	starPvcmEntry	OBJECT-TYPE
		SYNTAX	PvcmEntry
		ACCESS	not-accessible
		STATUS	mandatory
		DESCRIPTION
			""
		INDEX	{ starSlotIndex, starPortIndex }
		::= { starPvcmStatusTable 1 }

	PvcmEntry ::=
		SEQUENCE {
			starPvcmPtoPOrgConnectionNumber			INTEGER,
			starPvcmPtoPTermConnectionNumber		INTEGER,
			starPvcmPtoMOrgConnectionNumber			INTEGER,
			starPvcmPtoMTermConnectionNumber		INTEGER,
			starPvcmOutOfServiceConnectionNumber	INTEGER,
			starPvcmOptimizedConnectionNumber		INTEGER,
			starPvcmRouteFailCt						INTEGER,
			starPvcmConnectReqFailCt				INTEGER,
			starPvcmOrgConnectedFailCt				INTEGER,
			starPvcmTermConnectedFailCt				INTEGER,
			starPvcmActiveConnectionNumber			INTEGER,
			starPvcmDeletedConnectionNumber			INTEGER,
			starPvcmAddedConnectionNumber			INTEGER,
			starPvcmFailedConnectionNumber			INTEGER,
			starPvcmChangedConnectionNumber			INTEGER,
			starPvcmOrgHoldingConnectionNumber		INTEGER,
			starPvcmTermHoldingConnectionNumber		INTEGER,
			starPvcmInvalidMsgNumber				INTEGER,
			starPvcmTimerExpiredCnt					INTEGER
		}

	starPvcmPtoPOrgConnectionNumber		OBJECT-TYPE
		SYNTAX	INTEGER
		ACCESS	read-only
		STATUS	mandatory
		DESCRIPTION
			"Number of point to point connections that originate
			 on this port"
		::= { starPvcmEntry 1 }

	starPvcmPtoPTermConnectionNumber	OBJECT-TYPE
		SYNTAX	INTEGER
		ACCESS	read-only
		STATUS	mandatory
		DESCRIPTION
			"Number of point to point connections that terminate
			 on this port"
		::= { starPvcmEntry 2 }

	starPvcmPtoMOrgConnectionNumber		OBJECT-TYPE
		SYNTAX	INTEGER
		ACCESS	read-only
		STATUS	mandatory
		DESCRIPTION
			"Number of point to multi-point connections that 
		 	 originate on this port"
		::= { starPvcmEntry 3 }

	starPvcmPtoMTermConnectionNumber		OBJECT-TYPE
		SYNTAX	INTEGER
		ACCESS	read-only
		STATUS	mandatory
		DESCRIPTION
			"Number of point to multi-point connections that 
		 	 terminate on this port"
		::= { starPvcmEntry 4 }

	starPvcmOutOfServiceConnectionNumber		OBJECT-TYPE
		SYNTAX	INTEGER
		ACCESS	read-only
		STATUS	mandatory
		DESCRIPTION
			"Number of connections that have been set out of service
			 by the NMS"
		::= { starPvcmEntry 5 }

	starPvcmOptimizedConnectionNumber		OBJECT-TYPE
		SYNTAX	INTEGER
		ACCESS	read-only
		STATUS	mandatory
		DESCRIPTION
			"Number of connections that have had their route
			 optimized"
		::= { starPvcmEntry 6 }

	starPvcmRouteFailCt		OBJECT-TYPE
		SYNTAX	INTEGER
		ACCESS	read-only
		STATUS	mandatory
		DESCRIPTION
			"Number of connections that failed because a route 
			 could not be found"
		::= { starPvcmEntry 7 }

	starPvcmConnectReqFailCt		OBJECT-TYPE
		SYNTAX	INTEGER
		ACCESS	read-only
		STATUS	mandatory
		DESCRIPTION
			"Number of connections that failed during setup"
		::= { starPvcmEntry 8 }

	starPvcmOrgConnectedFailCt		OBJECT-TYPE
		SYNTAX	INTEGER
		ACCESS	read-only
		STATUS	mandatory
		DESCRIPTION
			"Number of connections that failed after being 
			 completely setup"
		::= { starPvcmEntry 9 }

	starPvcmTermConnectedFailCt		OBJECT-TYPE
		SYNTAX	INTEGER
		ACCESS	read-only
		STATUS	mandatory
		DESCRIPTION
			"Number of connections that failed after being setup
			 on the terminating module"
		::= { starPvcmEntry 10 }

	starPvcmActiveConnectionNumber		OBJECT-TYPE
		SYNTAX	INTEGER
		ACCESS	read-only
		STATUS	mandatory
		DESCRIPTION
			"Number of connections currently being processed"
		::= { starPvcmEntry 11 }

	starPvcmDeletedConnectionNumber		OBJECT-TYPE
		SYNTAX	INTEGER
		ACCESS	read-only
		STATUS	mandatory
		DESCRIPTION
			"Number of connections currently being queued for
			 deletion"
		::= { starPvcmEntry 12 }

	starPvcmAddedConnectionNumber		OBJECT-TYPE
		SYNTAX	INTEGER
		ACCESS	read-only
		STATUS	mandatory
		DESCRIPTION
			"Number of connections currently being queued for
			 addition"
		::= { starPvcmEntry 13 }

	starPvcmFailedConnectionNumber		OBJECT-TYPE
		SYNTAX	INTEGER
		ACCESS	read-only
		STATUS	mandatory
		DESCRIPTION
			"Number of connections that have failed, currently
			 queued for processing"
		::= { starPvcmEntry 14 }

	starPvcmChangedConnectionNumber		OBJECT-TYPE
		SYNTAX	INTEGER
		ACCESS	read-only
		STATUS	mandatory
		DESCRIPTION
			"Number of connections that have changed, currently
			 queued for processing"
		::= { starPvcmEntry 15 }

	starPvcmOrgHoldingConnectionNumber		OBJECT-TYPE
		SYNTAX	INTEGER
		ACCESS	read-only
		STATUS	mandatory
		DESCRIPTION
			"Number of connections that have failed repeatedly,
			 now in the holding queue"
		::= { starPvcmEntry 16 }

	starPvcmTermHoldingConnectionNumber		OBJECT-TYPE
		SYNTAX	INTEGER
		ACCESS	read-only
		STATUS	mandatory
		DESCRIPTION
			"Number of terminating connections that are being held,
			 awaiting re-connection, or deletion if re-connection
			 is not forthcoming"
		::= { starPvcmEntry 17 }

	 starPvcmInvalidMsgNumber			OBJECT-TYPE
		SYNTAX	INTEGER
		ACCESS	read-only
		STATUS	mandatory
		DESCRIPTION
			"Number of invalid messages received by PVCM."
		::= { starPvcmEntry 18 }

	 starPvcmTimerExpiredCnt			OBJECT-TYPE
		SYNTAX	INTEGER
		ACCESS	read-only
		STATUS	mandatory
		DESCRIPTION
			"Number of times the timer expired ."
		::= { starPvcmEntry 19 }
	-----------------------------------------------------------------------
	-- Star System PVCM Connection Table
	-----------------------------------------------------------------------
	starPvcConnectionTable OBJECT-TYPE
		SYNTAX  SEQUENCE OF PvcConnectionEntry
		ACCESS  not-accessible
		STATUS  mandatory
		DESCRIPTION
			"" 
		::= { starSlot 15 }

	starPvcConnectionEntry	OBJECT-TYPE
		SYNTAX	PvcConnectionEntry
		ACCESS	not-accessible
		STATUS	mandatory
		DESCRIPTION
			""
		INDEX	{ starPvcSrcSlotId, starPvcSrcPortId, starPvcSrcIfType, 
				  starPvcSrcVpi, starPvcSrcVci, starPvcSrcLeaf, 
				  starPvcSrcDlci, starPvcSrcTimeslot }
		::= { starPvcConnectionTable 1 }

	PvcConnectionEntry ::=
		SEQUENCE {
			starPvcSrcSlotId						INTEGER,
			starPvcSrcPortId						INTEGER,
			starPvcSrcIfType						INTEGER,
			starPvcSrcVpi							INTEGER,
			starPvcSrcVci							INTEGER,
			starPvcSrcLeaf							INTEGER,
			starPvcSrcDlci							INTEGER,
			starPvcSrcTimeslot						INTEGER,
			starPvcDestNodeId						INTEGER,
			starPvcDestSlotId						INTEGER,
			starPvcDestPortId						INTEGER,
			starPvcDestIfType						INTEGER,
			starPvcDestVpi							INTEGER,
			starPvcDestVci							INTEGER,
			starPvcDestDlci							INTEGER,
			starPvcDestTimeslot						INTEGER,
			starPvcConnectionOperStatus				INTEGER,
			starPvcConnectionType					INTEGER,
			starPvcConnectionCOS					INTEGER,
			starPvcConnectionStatusLastChangedDate	INTEGER,
			starPvcConnectionStatusLastChangedTime	INTEGER,
			starPvcConnectionCauseValue				INTEGER
		}

	starPvcSrcSlotId		OBJECT-TYPE
		SYNTAX	INTEGER
		ACCESS	read-only
		STATUS	mandatory
		DESCRIPTION
			""
		::= { starPvcConnectionEntry 1 }
		
	starPvcSrcPortId		OBJECT-TYPE
		SYNTAX	INTEGER
		ACCESS	read-only
		STATUS	mandatory
		DESCRIPTION
			""
		::= { starPvcConnectionEntry 2 }
		
	starPvcSrcIfType		OBJECT-TYPE
		SYNTAX	INTEGER
		ACCESS	read-only
		STATUS	mandatory
		DESCRIPTION
			""
		::= { starPvcConnectionEntry 3 }
		
	starPvcSrcVpi		OBJECT-TYPE
		SYNTAX	INTEGER
		ACCESS	read-only
		STATUS	mandatory
		DESCRIPTION
			""
		::= { starPvcConnectionEntry 4 }
		
	starPvcSrcVci		OBJECT-TYPE
		SYNTAX	INTEGER
		ACCESS	read-only
		STATUS	mandatory
		DESCRIPTION
			""
		::= { starPvcConnectionEntry 5 }
		
	starPvcSrcLeaf		OBJECT-TYPE
		SYNTAX	INTEGER
		ACCESS	read-only
		STATUS	mandatory
		DESCRIPTION
			""
		::= { starPvcConnectionEntry 6 }

	starPvcSrcDlci		OBJECT-TYPE
		SYNTAX	INTEGER
		ACCESS	read-only
		STATUS	mandatory
		DESCRIPTION
			""
		::= { starPvcConnectionEntry 7 }
		
	starPvcSrcTimeslot		OBJECT-TYPE
		SYNTAX	INTEGER
		ACCESS	read-only
		STATUS	mandatory
		DESCRIPTION
			""
		::= { starPvcConnectionEntry 8 }

	starPvcDestNodeId		OBJECT-TYPE
		SYNTAX	INTEGER
		ACCESS	read-only
		STATUS	mandatory
		DESCRIPTION
			""
		::= { starPvcConnectionEntry 9 }
		
	starPvcDestSlotId		OBJECT-TYPE
		SYNTAX	INTEGER
		ACCESS	read-only
		STATUS	mandatory
		DESCRIPTION
			""
		::= { starPvcConnectionEntry 10 }
		
	starPvcDestPortId		OBJECT-TYPE
		SYNTAX	INTEGER
		ACCESS	read-only
		STATUS	mandatory
		DESCRIPTION
			""
		::= { starPvcConnectionEntry 11 }
		
	starPvcDestIfType		OBJECT-TYPE
		SYNTAX	INTEGER
		ACCESS	read-only
		STATUS	mandatory
		DESCRIPTION
			""
		::= { starPvcConnectionEntry 12 }
		
	starPvcDestVpi		OBJECT-TYPE
		SYNTAX	INTEGER
		ACCESS	read-only
		STATUS	mandatory
		DESCRIPTION
			""
		::= { starPvcConnectionEntry 13 }
		
	starPvcDestVci		OBJECT-TYPE
		SYNTAX	INTEGER
		ACCESS	read-only
		STATUS	mandatory
		DESCRIPTION
			""
		::= { starPvcConnectionEntry 14 }
		
	starPvcDestDlci		OBJECT-TYPE
		SYNTAX	INTEGER
		ACCESS	read-only
		STATUS	mandatory
		DESCRIPTION
			""
		::= { starPvcConnectionEntry 15 }
		
	starPvcDestTimeslot		OBJECT-TYPE
		SYNTAX	INTEGER
		ACCESS	read-only
		STATUS	mandatory
		DESCRIPTION
			""
		::= { starPvcConnectionEntry 16 }
		
	starPvcConnectionOperStatus		OBJECT-TYPE
		SYNTAX	INTEGER
		ACCESS	read-only
		STATUS	mandatory
		DESCRIPTION
			"The current state of the connection"
		::= { starPvcConnectionEntry 17 }
		
	starPvcConnectionType		OBJECT-TYPE
		SYNTAX	INTEGER
		ACCESS	read-only
		STATUS	mandatory
		DESCRIPTION
			""
		::= { starPvcConnectionEntry 18 }
		
	starPvcConnectionCOS		OBJECT-TYPE
		SYNTAX	INTEGER
		ACCESS	read-only
		STATUS	mandatory
		DESCRIPTION
			""
		::= { starPvcConnectionEntry 19 }
		
	starPvcConnectionStatusLastChangedDate		OBJECT-TYPE
		SYNTAX	INTEGER
		ACCESS	read-only
		STATUS	mandatory
		DESCRIPTION
			"The time of day the connection last changed"
		::= { starPvcConnectionEntry 20 }
		
	starPvcConnectionStatusLastChangedTime		OBJECT-TYPE
		SYNTAX	INTEGER
		ACCESS	read-only
		STATUS	mandatory
		DESCRIPTION
			"The time of day the connection last changed"
		::= { starPvcConnectionEntry 21 }
		
	starPvcConnectionCauseValue		OBJECT-TYPE
		SYNTAX	INTEGER
		ACCESS	read-only
		STATUS	mandatory
		DESCRIPTION
			""
		::= { starPvcConnectionEntry 22 }
		
	-----------------------------------------------------------------------
	-- Star CES Table ( star proprietary ATM Circuit Emulation  )
	-----------------------------------------------------------------------
	starCesInfo		 OBJECT IDENTIFIER ::= { starSlot 23 }

	-----------------------------------------------------------------------
	-- Star CES Config Table
	-----------------------------------------------------------------------
	starDS1E1CESConfTable 	OBJECT-TYPE
 		SYNTAX  SEQUENCE OF StarDS1E1CESConfEntry
 		ACCESS  not-accessible
 		STATUS  mandatory
 		DESCRIPTION
			"The CES configuration table. This includes mapping channels
	 		 from ATM Port to CBR interfaces. There is one AtmfDS1E1CESConfEntry
	 		 per CES Entity"
 		::= { starCesInfo 1 }

	starDS1E1CESConfEntry	 OBJECT-TYPE
 		SYNTAX  StarDS1E1CESConfEntry
 		ACCESS  not-accessible
 		STATUS  mandatory
 		DESCRIPTION
		"An entry in the CES table. For each entry there is a corresponding
		 entry in the stack table"
 		INDEX   { starDS1E1CESSlotId, starDS1E1CESPortId,
				  starDS1E1CESChannelId }
 		::= { starDS1E1CESConfTable 1 }

	StarDS1E1CESConfEntry ::=
		SEQUENCE {
			starDS1E1CESSlotId				INTEGER,
			starDS1E1CESPortId	 			INTEGER,
			starDS1E1CESChannelId			INTEGER,
			starDS1E1CESMapATMIndex			INTEGER,
			starDS1E1CESMapVPI				INTEGER,
			starDS1E1CESMapVCI				INTEGER,
			starDS1E1CESCBRService			INTEGER,
			starDS1E1CESCBRClockMode		INTEGER,
			starDS1E1CESCas					INTEGER,
			starDS1E1CESPartialFill			INTEGER,
			starDS1E1CESBufMaxSize			INTEGER,
			starDS1E1CESCDVRxT				INTEGER,
			starDS1E1CESCellLossIntegPrd	INTEGER
 		}
	
	starDS1E1CESSlotId	OBJECT-TYPE
		SYNTAX  INTEGER
		ACCESS  read-only
		STATUS  mandatory
		DESCRIPTION
			"This object indicates the slot id."
		::= { starDS1E1CESConfEntry 1 }
 
	 starDS1E1CESPortId		 OBJECT-TYPE
		SYNTAX  INTEGER
		ACCESS  read-only
		STATUS  mandatory
		DESCRIPTION
			"This object indicates the port number
			 whose info is needed."
		::= { starDS1E1CESConfEntry  2 }
 
	starDS1E1CESChannelId	OBJECT-TYPE
		SYNTAX  INTEGER
		ACCESS  read-only
		STATUS  mandatory
		DESCRIPTION
			"This object indicates the channel number
			 whose info is needed."
		::= { starDS1E1CESConfEntry  3 }

 	starDS1E1CESMapATMIndex	 OBJECT-TYPE
	 	SYNTAX  INTEGER
	 	ACCESS  read-only
	 	STATUS  mandatory
	 	DESCRIPTION
		 	"The value of this object is equal to MIB II's ifIndex
			 value of the ATM Port interface mapped through this 
			 CES to a CBR interface."
	 	::= { starDS1E1CESConfEntry   4 }

 	starDS1E1CESMapVPI	OBJECT-TYPE
	 	SYNTAX  INTEGER
	 	ACCESS  read-only
	 	STATUS  mandatory 
	 	DESCRIPTION
		 	"The value of this object is equal to the VPI used 
			for the emulated circuit represented by  this entry
		 	in the ifTable. If there is no connection, this
		 	object is meaningless and will have the value zero."
	 	::= { starDS1E1CESConfEntry 5 }

 	starDS1E1CESMapVCI	OBJECT-TYPE
	 	SYNTAX  INTEGER
	 	ACCESS  read-only
	 	STATUS  mandatory
	 	DESCRIPTION
		 	"The value of this object is equal to the VCI used 
			for the emulated circuit represented by  this entry
			in the ifTable. If there is no connection, this
			object is meaningless and will have the value zero."
	 	::= { starDS1E1CESConfEntry 6 }

	starDS1E1CESCBRService	OBJECT-TYPE
	 	SYNTAX  INTEGER {
			unstructured ( 1),
			structured ( 2)
		}
	 	ACCESS  read-write
	 	STATUS  mandatory
	 	DESCRIPTION
			"Define if DS1/E1 service as structured or not. A
			structured (2) interface is some n * 64kbps. An unstrucutred (1)
			interface is 1.544Mbps or 2.048Mbps. Unstructured(1) passes all
			bits through the ATM network. Structured(2) passes data bits through
			the ATM network, an may also pass signalling bits."
	 	::= { starDS1E1CESConfEntry 7 }

 	starDS1E1CESCBRClockMode	OBJECT-TYPE
	 	SYNTAX  INTEGER {
			synchronous ( 1),
			srts ( 2),
			adaptive ( 3)
		}
	 	ACCESS  read-write
	 	STATUS  mandatory
	 	DESCRIPTION
			"Define if DS1/E1 service clocking mode. This maps into transmit
	 	 	clock source of CBR interface."
	 	::= { starDS1E1CESConfEntry 8 }

 	starDS1E1CESCas	OBJECT-TYPE
	 	SYNTAX  INTEGER {
			basic (1),
			e1Cas (2),
			ds1SfCas (3),
			ds1EsfCas (4)
		}
	 	ACCESS  read-write
	 	STATUS  mandatory
	 	DESCRIPTION
			"This parameter selects which AAL1 format should be used
			:- Basic does not carry CAS bits, and uses a single 125 usec
			frame. e1Cas,ds1SfCas and ds1EsfCas carry CAS bits in a multi
			frame structure for E1,DS1 SF and DS1 ESF respectively. This
			applies to structured interfaces only.Default is basic (1)."
	 	::= { starDS1E1CESConfEntry 9 }

 	starDS1E1CESPartialFill	OBJECT-TYPE
	 	SYNTAX  INTEGER ( 0..47)
	 	ACCESS  read-write
	 	STATUS  mandatory
	 	DESCRIPTION
		""
	 	::= { starDS1E1CESConfEntry  10 }

	starDS1E1CESBufMaxSize	OBJECT-TYPE
	 	SYNTAX  INTEGER ( 1..65536 )
	 	ACCESS  read-write
	 	STATUS  mandatory
	 	DESCRIPTION
		 	""
	 	::= { starDS1E1CESConfEntry  11 }

 	starDS1E1CESCDVRxT	OBJECT-TYPE
	 	SYNTAX  INTEGER ( 1..65535 )
	 	ACCESS  read-write
	 	STATUS  mandatory
	 	DESCRIPTION
		 	""
	 	::= { starDS1E1CESConfEntry  12 }

	starDS1E1CESCellLossIntegPrd	OBJECT-TYPE
	 	SYNTAX  INTEGER ( 1000..65535 )
	 	ACCESS  read-write
	 	STATUS  mandatory
	 	DESCRIPTION
		 	""
	 	::= { starDS1E1CESConfEntry  13 }

	-----------------------------------------------------------------------
	--  Star System CES Statistics Table
	-----------------------------------------------------------------------
	starDS1E1CESStatsTable 	OBJECT-TYPE
 		SYNTAX  SEQUENCE OF StarDS1E1CESStatsEntry
 		ACCESS  not-accessible
 		STATUS  mandatory
 		DESCRIPTION
		"The CES AAL1 statistical data table."
 		::= { starCesInfo 2 }

	starDS1E1CESStatsEntry	 OBJECT-TYPE
 		SYNTAX  StarDS1E1CESStatsEntry
 		ACCESS  not-accessible
 		STATUS  mandatory
 		DESCRIPTION
		"An entry in the CES AAL1 Stats table. "
 		INDEX   { starDS1E1CESStatSlotId, starDS1E1CESStatDeviceId,
				 starDS1E1CESStatPortId, starDS1E1CESStatChannelId }
 		::= { starDS1E1CESStatsTable 1 }

	StarDS1E1CESStatsEntry ::=
  		SEQUENCE {
			starDS1E1CESStatSlotId		INTEGER,	
			starDS1E1CESStatDeviceId	INTEGER,
			starDS1E1CESStatPortId		INTEGER,
			starDS1E1CESStatChannelId	INTEGER,
			starDS1E1CESReassCells		INTEGER,
			starDS1E1CESHdrErrors		INTEGER,
			starDS1E1CESPointerReframes INTEGER,
			starDS1E1CESLostCells		INTEGER,
			starDS1E1CESBufUnderflows	INTEGER,
			starDS1E1CESBufOverflows	INTEGER, 
			starDS1E1CESCellLossStatus 	INTEGER
 		}

	starDS1E1CESStatSlotId	OBJECT-TYPE
		SYNTAX  INTEGER
		ACCESS  read-only
		STATUS  mandatory
		DESCRIPTION
			"This object indicates the slot id."
		::= { starDS1E1CESStatsEntry 1 }
 
	 starDS1E1CESStatDeviceId	 OBJECT-TYPE
		SYNTAX  INTEGER
		ACCESS  read-only
		STATUS  mandatory
		DESCRIPTION
			"This object indicates the device number
			 whose info is needed."
		::= { starDS1E1CESStatsEntry  2 }
 
	 starDS1E1CESStatPortId		 OBJECT-TYPE
		SYNTAX  INTEGER
		ACCESS  read-only
		STATUS  mandatory
		DESCRIPTION
			"This object indicates the port number
			 whose info is needed."
		::= { starDS1E1CESStatsEntry  3 }
 
	 starDS1E1CESStatChannelId	OBJECT-TYPE
		SYNTAX  INTEGER
		ACCESS  read-only
		STATUS  mandatory
		DESCRIPTION
			"This object indicates the channel number
			 whose info is needed."
		::= { starDS1E1CESStatsEntry  4 }

 	starDS1E1CESReassCells 	 OBJECT-TYPE
		SYNTAX  INTEGER
	 	ACCESS  read-only
	 	STATUS  mandatory
	 	DESCRIPTION
		 	""
	 	::= { starDS1E1CESStatsEntry  5 }

 	starDS1E1CESHdrErrors	OBJECT-TYPE
	 	SYNTAX  INTEGER
	 	ACCESS  read-only
	 	STATUS  mandatory
	 	DESCRIPTION
		 	""
	 	::= { starDS1E1CESStatsEntry  6 }

 	starDS1E1CESPointerReframes	OBJECT-TYPE
	 	SYNTAX  INTEGER
	 	ACCESS  read-only
	 	STATUS  mandatory
	 	DESCRIPTION
		 	""
	 	::= { starDS1E1CESStatsEntry  7 }

 	starDS1E1CESLostCells	OBJECT-TYPE
	 	SYNTAX  INTEGER
	 	ACCESS  read-only
	 	STATUS  mandatory
	 	DESCRIPTION
			""
	 	::= { starDS1E1CESStatsEntry  8 }

 	starDS1E1CESBufUnderflows	OBJECT-TYPE
	 	SYNTAX  INTEGER
	 	ACCESS  read-only
	 	STATUS  mandatory
	 	DESCRIPTION
			""
	 	::= { starDS1E1CESStatsEntry  9 }

 	starDS1E1CESBufOverflows	OBJECT-TYPE
	 	SYNTAX  INTEGER
	 	ACCESS  read-only
	 	STATUS  mandatory
	 	DESCRIPTION
			"" 
	 	::= { starDS1E1CESStatsEntry  10 }

 	starDS1E1CESCellLossStatus	OBJECT-TYPE
	 	SYNTAX  INTEGER { 
			noLoss(1),
			loss(2) 
		}
	 	ACCESS  read-only
	 	STATUS  mandatory
	 	DESCRIPTION
			""
	 	::= { starDS1E1CESStatsEntry  11 }

	-----------------------------------------------------------------------
	-- Star System Port Table
	-----------------------------------------------------------------------
	starPortTable		OBJECT-TYPE
		SYNTAX  SEQUENCE OF PortEntry
		ACCESS  not-accessible
		STATUS  mandatory
		DESCRIPTION
			"This table contains port information for all ports
			 in the Star Node and is indexed by Slot number and
			 Port number" 
		::= { starPort 1 }

	starPortEntry	OBJECT-TYPE
		SYNTAX	PortEntry
		ACCESS	not-accessible
		STATUS	mandatory
		DESCRIPTION
			""
		INDEX	{ starSlotIndex, starPortIndex }
		::= { starPortTable 1 }

	PortEntry ::=
		SEQUENCE {
			starPortIndex					INTEGER,
			starPortIfIndex					INTEGER,
			starPortType					INTEGER,
			starPortConfig					INTEGER,
			starPortDescr					DisplayString,
			starPortAdminStatus				INTEGER,
			starPortAtmAddress				OCTET STRING,
			starPortLastChanged				TimeTicks,
			starPortAlarmStatus				INTEGER,
			starPortRemoteAtmAddress		OCTET STRING,
			starPortOperStatus				INTEGER,
			starPortIFType					INTEGER,
			starPortMaxVPINumber			INTEGER,
			starPortUsedVPINumber			INTEGER,
			starPortMaxVCINumber			INTEGER,
			starPortUsedVCINumber			INTEGER,
			starPortMaxFixedCapacity		INTEGER,
			starPortMaxVariableCapacity		INTEGER,
			starPortUsedFwdFixedCapacity	INTEGER,
			starPortUsedFwdVariableCapacity	INTEGER,
			starPortUsedBwdFixedCapacity	INTEGER,
			starPortUsedBwdVariableCapacity	INTEGER,
			starPortAvailableVpi			INTEGER 
		}

	starPortIndex	OBJECT-TYPE
		SYNTAX	INTEGER
		ACCESS	read-only
		STATUS	mandatory
		DESCRIPTION
			"Port number"
		::= { starPortEntry 1 }

	starPortIfIndex	OBJECT-TYPE
		SYNTAX	INTEGER
		ACCESS	read-only
		STATUS	mandatory
		DESCRIPTION
			"This object contains the ifIndex value related to
			 this port.  The formula used to compute is
			 SlotNumber * 100 + PortNumber"
		::= { starPortEntry 2 }

	starPortType	OBJECT-TYPE
		SYNTAX	INTEGER
		ACCESS	read-only
		STATUS	mandatory
		DESCRIPTION
			"Contains the same value as ifType for this port"
		::= { starPortEntry 3 }

	starPortConfig	OBJECT-TYPE
		SYNTAX	INTEGER
		ACCESS	read-only
		STATUS	mandatory
		DESCRIPTION
			"Contains the configuration for this port"
		::= { starPortEntry 4 }

	starPortDescr	OBJECT-TYPE
		SYNTAX	DisplayString
		ACCESS	read-only
		STATUS	mandatory
		DESCRIPTION
			"Character description for this port"
		::= { starPortEntry 5 }

	starPortAdminStatus	OBJECT-TYPE
		SYNTAX	INTEGER
		ACCESS	read-only
		STATUS	mandatory
		DESCRIPTION
			"Administrative status for this port, can only be set
			 by operator doing a configuration file download with
			 a new value for port status"
		::= { starPortEntry 6 }

	starPortAtmAddress	OBJECT-TYPE
		SYNTAX	OCTET STRING
		ACCESS	read-write
		STATUS	mandatory
		DESCRIPTION
			"Atm address used for SVC's only"
		::= { starPortEntry 7 }

	starPortLastChanged	OBJECT-TYPE
		SYNTAX	TimeTicks
		ACCESS	read-only
		STATUS	mandatory
		DESCRIPTION
			"Time this port was last changed or came into service"
		::= { starPortEntry 8 }

	starPortAlarmStatus	OBJECT-TYPE
		SYNTAX	INTEGER
		ACCESS	read-only
		STATUS	mandatory
		DESCRIPTION
			"Last alarm on this port"
		::= { starPortEntry 9 }

	starPortRemoteAtmAddress	OBJECT-TYPE
		SYNTAX	OCTET STRING
		ACCESS	read-write
		STATUS	mandatory
		DESCRIPTION
			"Remote Atm address used for SVC's only"
		::= { starPortEntry 10 }

	starPortOperStatus	OBJECT-TYPE
		SYNTAX	INTEGER {
			in-service(1),
			out-of-service(2)
		}
		ACCESS	read-only
		STATUS	mandatory
		DESCRIPTION
			"Operational status of this port"
		::= { starPortEntry 11 }

	starPortIFType	OBJECT-TYPE
		SYNTAX	INTEGER
		ACCESS	read-only
		STATUS	mandatory
		DESCRIPTION
			"Contains same value as Board type"
		::= { starPortEntry 12 }

	starPortMaxVPINumber	OBJECT-TYPE
		SYNTAX	INTEGER
		ACCESS	read-only
		STATUS	mandatory
		DESCRIPTION
			"Maximum VPI values for this port"
		::= { starPortEntry 13 }

	starPortUsedVPINumber	OBJECT-TYPE
		SYNTAX	INTEGER
		ACCESS	read-only
		STATUS	mandatory
		DESCRIPTION
			"Currently assigned VPI number"
		::= { starPortEntry 14 }

	starPortMaxVCINumber	OBJECT-TYPE
		SYNTAX	INTEGER
		ACCESS	read-only
		STATUS	mandatory
		DESCRIPTION
			"Maximum VCI values for this port"
		::= { starPortEntry 15 }

	starPortUsedVCINumber	OBJECT-TYPE
		SYNTAX	INTEGER
		ACCESS	read-only
		STATUS	mandatory
		DESCRIPTION
			"Currently assigned VCI number"
		::= { starPortEntry 16 }

	starPortMaxFixedCapacity	OBJECT-TYPE
		SYNTAX	INTEGER
		ACCESS	read-only
		STATUS	mandatory
		DESCRIPTION
			""
		::= { starPortEntry 17 }

	starPortMaxVariableCapacity	OBJECT-TYPE
		SYNTAX	INTEGER
		ACCESS	read-only
		STATUS	mandatory
		DESCRIPTION
			""
		::= { starPortEntry 18 }

	starPortUsedFwdFixedCapacity	OBJECT-TYPE
		SYNTAX	INTEGER
		ACCESS	read-only
		STATUS	mandatory
		DESCRIPTION
			""
		::= { starPortEntry 19 }

	starPortUsedFwdVariableCapacity	OBJECT-TYPE
		SYNTAX	INTEGER
		ACCESS	read-only
		STATUS	mandatory
		DESCRIPTION
			""
		::= { starPortEntry 20 }

	starPortUsedBwdFixedCapacity	OBJECT-TYPE
		SYNTAX	INTEGER
		ACCESS	read-only
		STATUS	mandatory
		DESCRIPTION
			""
		::= { starPortEntry 21 }

	starPortUsedBwdVariableCapacity	OBJECT-TYPE
		SYNTAX	INTEGER
		ACCESS	read-only
		STATUS	mandatory
		DESCRIPTION
			""
		::= { starPortEntry 22 }

	starPortAvailableVpi	OBJECT-TYPE
		SYNTAX	INTEGER
		ACCESS	read-only
		STATUS	mandatory
		DESCRIPTION
			"check available VPI value check"
		::= { starPortEntry 23 }

	-----------------------------------------------------------------------
	-- Star System Port DS1 Framer Table
	-----------------------------------------------------------------------
	starPortDS1FramerTable	OBJECT-TYPE
		SYNTAX  SEQUENCE OF PortDS1FramerEntry
		ACCESS  not-accessible
		STATUS  mandatory
		DESCRIPTION
			"This table contains information read from the
			 Brooktree T1 Framer chip and is indexed by Slot number
			 and Device Index" 
		::= { starPort 2 }

	starPortDS1FramerEntry	OBJECT-TYPE
		SYNTAX	PortDS1FramerEntry
		ACCESS	not-accessible
		STATUS	mandatory
		DESCRIPTION
			""
		INDEX	{ starSlotIndex, starPortDS1FramerIndex }
		::= { starPortDS1FramerTable 1 }

	PortDS1FramerEntry ::=
		SEQUENCE {
			starPortDS1FramerIndex				INTEGER,
			starPortDS1FramerRevision			INTEGER,
			starPortDS1FramerFrameMode			INTEGER,
			starPortDS1FramerLineCoding			INTEGER,
			starPortDS1FramerBPVCounter			INTEGER,
			starPortDS1FramerFBErrorCounter		INTEGER,
			starPortDS1FramerCRCErrorCounter	INTEGER,
			starPortDS1FramerCOFACounter		INTEGER
		}

	starPortDS1FramerIndex	OBJECT-TYPE
		SYNTAX	INTEGER
		ACCESS	read-only
		STATUS	mandatory
		DESCRIPTION
			"Device index of DS1 Framer chip"
		::= { starPortDS1FramerEntry 1 }

	starPortDS1FramerRevision	OBJECT-TYPE
		SYNTAX	INTEGER
		ACCESS	read-only
		STATUS	mandatory
		DESCRIPTION
			"Device revision number"
		::= { starPortDS1FramerEntry 2 }

	starPortDS1FramerFrameMode	OBJECT-TYPE
		SYNTAX	INTEGER {
			sfnormal(1),
			sft1dm(2),
			esfnormal(3),
			esfzbtis(4)
		}
		ACCESS	read-only
		STATUS	mandatory
		DESCRIPTION
			"DS1 Framer frame mode"
		::= { starPortDS1FramerEntry 3 }

	starPortDS1FramerLineCoding	OBJECT-TYPE
		SYNTAX	INTEGER {
			ami(1),
			mbzs(2),
			b8zstxrx(3)
		}
		ACCESS	read-only
		STATUS	mandatory
		DESCRIPTION
			"DS1 Framer line coding type"
		::= { starPortDS1FramerEntry 4 }

	starPortDS1FramerBPVCounter	OBJECT-TYPE
		SYNTAX	INTEGER
		ACCESS	read-only
		STATUS	mandatory
		DESCRIPTION
			"Number of bipolar violations"
		::= { starPortDS1FramerEntry 5 }

	starPortDS1FramerFBErrorCounter	OBJECT-TYPE
		SYNTAX	INTEGER
		ACCESS	read-only
		STATUS	mandatory
		DESCRIPTION
			"Number of frame bit errors"
		::= { starPortDS1FramerEntry 6 }

	starPortDS1FramerCRCErrorCounter	OBJECT-TYPE
		SYNTAX	INTEGER
		ACCESS	read-only
		STATUS	mandatory
		DESCRIPTION
			"Number of CRC errors"
		::= { starPortDS1FramerEntry 7 }

	starPortDS1FramerCOFACounter	OBJECT-TYPE
		SYNTAX	INTEGER
		ACCESS	read-only
		STATUS	mandatory
		DESCRIPTION
			"Number of change-of-frame-alignments"
		::= { starPortDS1FramerEntry 8 }

	-----------------------------------------------------------------------
	-- Star System Port E1 Framer Table
	-----------------------------------------------------------------------
	starPortE1FramerTable	OBJECT-TYPE
		SYNTAX  SEQUENCE OF PortE1FramerEntry
		ACCESS  not-accessible
		STATUS  mandatory
		DESCRIPTION
			"This table contains information read from the
			 E1 Framer chip and is indexed by Slot number
			 and Device Index" 
		::= { starPort 3 }

	starPortE1FramerEntry	OBJECT-TYPE
		SYNTAX	PortE1FramerEntry
		ACCESS	not-accessible
		STATUS	mandatory
		DESCRIPTION
			""
		INDEX	{ starSlotIndex, starPortE1FramerIndex }
		::= { starPortE1FramerTable 1 }

	PortE1FramerEntry ::=
		SEQUENCE {
			starPortE1FramerIndex				INTEGER,
			starPortE1FramerRevision			INTEGER,
			starPortE1FramerLineCoding			INTEGER,
			starPortE1FramerSignalMode			INTEGER,
			starPortE1FramerCRCErrorCounter		INTEGER,
			starPortE1FramerLCVErrorCounter		INTEGER,
			starPortE1FramerFASErrorCounter		INTEGER
		}

	starPortE1FramerIndex	OBJECT-TYPE
		SYNTAX	INTEGER
		ACCESS	read-only
		STATUS	mandatory
		DESCRIPTION
			"Device index of E1 Framer chip"
		::= { starPortE1FramerEntry 1 }

	starPortE1FramerRevision	OBJECT-TYPE
		SYNTAX	INTEGER
		ACCESS	read-only
		STATUS	mandatory
		DESCRIPTION
			"Device revision number"
		::= { starPortE1FramerEntry 2 }

	starPortE1FramerLineCoding	OBJECT-TYPE
		SYNTAX	INTEGER {
			ami(1),
			hdb3(2)
		}
		ACCESS	read-only
		STATUS	mandatory
		DESCRIPTION
			"E1 Framer line coding mode"
		::= { starPortE1FramerEntry 3 }

	starPortE1FramerSignalMode	OBJECT-TYPE
		SYNTAX	INTEGER {
			ccs(1),
			cas(2),
			lapd(3)
		}
		ACCESS	read-only
		STATUS	mandatory
		DESCRIPTION
			"E1 Framer signalling mode"
		::= { starPortE1FramerEntry 4 }

	starPortE1FramerCRCErrorCounter	OBJECT-TYPE
		SYNTAX	INTEGER
		ACCESS	read-only
		STATUS	mandatory
		DESCRIPTION
			"Number of CRC errors"
		::= { starPortE1FramerEntry 5 }

	starPortE1FramerLCVErrorCounter	OBJECT-TYPE
		SYNTAX	INTEGER
		ACCESS	read-only
		STATUS	mandatory
		DESCRIPTION
			"Number of frame bit errors"
		::= { starPortE1FramerEntry 6 }

	starPortE1FramerFASErrorCounter	OBJECT-TYPE
		SYNTAX	INTEGER
		ACCESS	read-only
		STATUS	mandatory
		DESCRIPTION
			"Number of change-of-frame-alignments"
		::= { starPortE1FramerEntry 7 }

	-----------------------------------------------------------------------
	-- Star System Port DS3 Framer Table
	-----------------------------------------------------------------------
	starPortDS3FramerTable	OBJECT-TYPE
			SYNTAX  SEQUENCE OF PortDS3FramerEntry
			ACCESS  not-accessible
			STATUS  mandatory
			DESCRIPTION
			"This table contains information read from the
			 DS3 Framer chip and is indexed by Slot number
			 and Device Index" 
		::= { starPort 4 }

	starPortDS3FramerEntry	OBJECT-TYPE
		SYNTAX	PortDS3FramerEntry
		ACCESS	not-accessible
		STATUS	mandatory
		DESCRIPTION
			""
		INDEX	{ starSlotIndex, starPortDS3FramerIndex }
		::= { starPortDS3FramerTable 1 }

	PortDS3FramerEntry ::=
		SEQUENCE {
			starPortDS3FramerIndex			INTEGER,
			starPortDS3FramerRevision		INTEGER,
			starPortDS3FramerFramingMode	INTEGER
		}

	starPortDS3FramerIndex	OBJECT-TYPE
		SYNTAX	INTEGER
		ACCESS	read-only
		STATUS	mandatory
		DESCRIPTION
			"Device index of DS3 Framer chip"
		::= { starPortDS3FramerEntry 1 }

	starPortDS3FramerRevision	OBJECT-TYPE
		SYNTAX	INTEGER
		ACCESS	read-only
		STATUS	mandatory
		DESCRIPTION
			"Device revision number"
		::= { starPortDS3FramerEntry 2 }

	starPortDS3FramerFramingMode	OBJECT-TYPE
		SYNTAX	INTEGER {
			m13(1),
			c-bit(2)
		}
		ACCESS	read-only
		STATUS	mandatory
		DESCRIPTION
			"DS3 Framer framing mode"
		::= { starPortDS3FramerEntry 3 }

	-----------------------------------------------------------------------
	-- Star System Port Sonet Uni Table
	-----------------------------------------------------------------------
	starPortSonetUniTable	OBJECT-TYPE
			SYNTAX  SEQUENCE OF PortSonetUniEntry
			ACCESS  not-accessible
			STATUS  mandatory
			DESCRIPTION
			"This table contains information read from the
			 Sonet Uni Device and is indexed by Slot number
			 and Device Index" 
		::= { starPort 5 }

	starPortSonetUniEntry	OBJECT-TYPE
		SYNTAX	PortSonetUniEntry
		ACCESS	not-accessible
		STATUS	mandatory
		DESCRIPTION
			""
		INDEX	{ starSlotIndex, starPortSonetUniIndex }
		::= { starPortSonetUniTable 1 }

	PortSonetUniEntry ::=
		SEQUENCE {
			starPortSonetUniIndex		INTEGER,
			starPortSonetUniMsgTxCt		INTEGER,
			starPortSonetUniMsgRxCt		INTEGER,
			starPortSonetUniHECErrorCt	INTEGER
		}

	starPortSonetUniIndex	OBJECT-TYPE
		SYNTAX	INTEGER
		ACCESS	read-only
		STATUS	mandatory
		DESCRIPTION
			"Device index of Sonet Uni chip"
		::= { starPortSonetUniEntry 1 }

	starPortSonetUniMsgTxCt	OBJECT-TYPE
		SYNTAX	INTEGER
		ACCESS	read-only
		STATUS	mandatory
		DESCRIPTION
			"Transmitted message counter"
		::= { starPortSonetUniEntry 2 }

	starPortSonetUniMsgRxCt	OBJECT-TYPE
		SYNTAX	INTEGER
		ACCESS	read-only
		STATUS	mandatory
		DESCRIPTION
			"Received message counter"
		::= { starPortSonetUniEntry 3 }

	starPortSonetUniHECErrorCt	OBJECT-TYPE
		SYNTAX	INTEGER
		ACCESS	read-only
		STATUS	mandatory
		DESCRIPTION
			"HEC error counter"
		::= { starPortSonetUniEntry 4 }
	-----------------------------------------------------------------------
	-- Star System Port DS3 Uni Table 
	-----------------------------------------------------------------------

	starPortDs3UniTable	OBJECT-TYPE
		SYNTAX	SEQUENCE OF PortDs3UniEntry
		ACCESS	not-accessible
		STATUS	mandatory
		DESCRIPTION
			"This Table contains information read from the
			 DS3 Uni Device and is indexed by dsx3CurrentIndex
			 ans is referenced RFC 1407 & 1695"
		::= { starPort 6 }

	starPortDs3UniEntry OBJECT-TYPE
		SYNTAX  PortDs3UniEntry
		ACCESS  not-accessible
		STATUS  mandatory
		DESCRIPTION
			""
		INDEX   { starDsx3CurrentIndex }
		::= { starPortDs3UniTable 1 }
 
	PortDs3UniEntry ::=
		SEQUENCE {
			starDsx3CurrentIndex	INTEGER,
			starPortDs3TxFEBEcount  Gauge,
			starPortDs3RxFEBEcount  Gauge,
			starPortPlcpTxFEBEcount Gauge,
			starPortPlcpRxFEBEcount Gauge,
			starPortRAIstatus	   INTEGER,
			starPortPlcpCVcount	 Gauge,
			starPortPlcpEScount	 Gauge,
			starPortPlcpSEScount	Gauge,
			starPortPlcpEFScount	Gauge,
			starPortPlcpSEFScount   Gauge,
			starPortPlcpUAScount	Gauge,
			starPortDs3LSEScount	Gauge,
			starPortDs3AISScount	Gauge,
			starPortDs3EFScount	 Gauge
		}

	starDsx3CurrentIndex OBJECT-TYPE
		SYNTAX  INTEGER (1..65535)
		ACCESS  read-only
		STATUS  mandatory
		DESCRIPTION
			"The index value which uniquely identifies the
			DS3/E3 interface to which this entry is
			applicable.  The interface identified by a
			particular value of this index is the same
			interface as identified by the same value an
			dsx3LineIndex object instance."
		::= { starPortDs3UniEntry 1 }
 
	starPortDs3TxFEBEcount  OBJECT-TYPE
		SYNTAX  Gauge
		ACCESS  read-only
		STATUS  mandatory
		DESCRIPTION
			"The counter associated with the number of
			non-111 FEBE code when F,M,Cp bit error occur
			in transfer mode. Ref: RFC1407"
		::= { starPortDs3UniEntry 2 }
 
	starPortDs3RxFEBEcount  OBJECT-TYPE
		SYNTAX  Gauge
		ACCESS  read-only
		STATUS  mandatory
		DESCRIPTION
			"The counter associated with the number of
			non-111 FEBE code when F,M,Cp bit error occur
			in receive mode. Ref: RFC1407"
		::= { starPortDs3UniEntry 3 }
 
	starPortPlcpTxFEBEcount OBJECT-TYPE
		SYNTAX  Gauge
		ACCESS  read-only
		STATUS  mandatory
		DESCRIPTION
			"The counter associated with the number of
			BI/BIP-8 error when transfer mode. Ref: RFC1407"
		::= { starPortDs3UniEntry 4 }

	starPortPlcpRxFEBEcount OBJECT-TYPE
		SYNTAX  Gauge
		ACCESS  read-only
		STATUS  mandatory
		DESCRIPTION
			"The counter associated with the number of
			FEBE count when receive mode. Ref: RFC1407"
		::= { starPortDs3UniEntry 5 }

	starPortRAIstatus	   OBJECT-TYPE
		SYNTAX  INTEGER
		ACCESS  read-only
		STATUS  mandatory
		DESCRIPTION
			"The status of RAI bit in GI byte. Ref: RFC1407"
		::= { starPortDs3UniEntry 6 }

	starPortPlcpCVcount	 OBJECT-TYPE
		SYNTAX  Gauge
		ACCESS  read-only
		STATUS  mandatory
		DESCRIPTION
			"The counter associated with the number of
			BI/BIP-8 error. Ref: RFC1407"
		::= { starPortDs3UniEntry 7 }

	starPortPlcpEScount	 OBJECT-TYPE
		SYNTAX  Gauge
		ACCESS  read-only
		STATUS  mandatory
		DESCRIPTION
			"The counter associated with the count second of
			more than single CV. Ref: RFC1407"
		::= { starPortDs3UniEntry 8 }
 
	starPortPlcpSEScount	OBJECT-TYPE
		SYNTAX  Gauge
		ACCESS  read-only
		STATUS  mandatory
		DESCRIPTION
			"The counter associated with the count second of
			more than 15 CVs. Ref: RFC1407"
		::= { starPortDs3UniEntry 9 }
 
	starPortPlcpEFScount	OBJECT-TYPE
		SYNTAX  Gauge
		ACCESS  read-only
		STATUS  mandatory
		DESCRIPTION
			"The counter associated with the count second of
			more than single PLCP FERR. Ref: RFC1407"
		::= { starPortDs3UniEntry 10 }
 
	starPortPlcpSEFScount   OBJECT-TYPE
		SYNTAX  Gauge
		ACCESS  read-only
		STATUS  mandatory
		DESCRIPTION
			"The counter associated with the count second of
			more than single SEF. Ref: RFC1407"
		::= { starPortDs3UniEntry 11 }

	starPortPlcpUAScount	OBJECT-TYPE
		SYNTAX  Gauge
		ACCESS  read-only
		STATUS  mandatory
		DESCRIPTION
			"The counter associated with the count second of
			DS3 LOS, AIS, LOF or PLCP LOF. Ref: RFC1407"
		::= { starPortDs3UniEntry 12 }
 
	starPortDs3LSEScount	OBJECT-TYPE
		SYNTAX  Gauge
		ACCESS  read-only
		STATUS  mandatory
		DESCRIPTION
			"The counter associated with the count second of
			at least 45 LCVs. Ref: RFC1407"
		::= { starPortDs3UniEntry 13 }
 
	starPortDs3AISScount		OBJECT-TYPE
		SYNTAX  Gauge
		ACCESS  read-only
		STATUS  mandatory
		DESCRIPTION
			"The counter associated with the count second of
			AIS detection. Ref: RFC1407"
		::= { starPortDs3UniEntry 14 }
 
	starPortDs3EFScount	 OBJECT-TYPE
		SYNTAX  Gauge
		ACCESS  read-only
		STATUS  mandatory
		DESCRIPTION
			"The counter associated with the count second of
			any errored frame bit. Ref: RFC1407"
		::= { starPortDs3UniEntry 15 }

	-----------------------------------------------------------------------
	-- Star System Port PDH Uni Table
	-----------------------------------------------------------------------
	starPortPdhUniTable	OBJECT-TYPE
		SYNTAX  SEQUENCE OF PortPdhUniEntry
		ACCESS  not-accessible
		STATUS  mandatory
		DESCRIPTION
			"This table contains information read from the
			 Pdh Uni Device and is indexed by Slot number
			 and Device Index" 
		::= { starPort 7 }

	starPortPdhUniEntry	OBJECT-TYPE
		SYNTAX	PortPdhUniEntry
		ACCESS	not-accessible
		STATUS	mandatory
		DESCRIPTION
			""
		INDEX	{ starSlotIndex, starPortPdhUniIndex }
		::= { starPortPdhUniTable 1 }

	PortPdhUniEntry ::=
		SEQUENCE {
			starPortPdhUniIndex		INTEGER,
			starPortPdhUniMsgTxCt	INTEGER,
			starPortPdhUniMsgRxCt	INTEGER,
			starPortPdhUniHECErrCt	INTEGER
		}

	starPortPdhUniIndex	OBJECT-TYPE
		SYNTAX	INTEGER
		ACCESS	read-only
		STATUS	mandatory
		DESCRIPTION
			"Device index of Pdh Uni chip"
		::= { starPortPdhUniEntry 1 }

	starPortPdhUniMsgTxCt	OBJECT-TYPE
		SYNTAX	INTEGER
		ACCESS	read-only
		STATUS	mandatory
		DESCRIPTION
			"Transmitted message counter"
		::= { starPortPdhUniEntry 2 }

	starPortPdhUniMsgRxCt	OBJECT-TYPE
		SYNTAX	INTEGER
		ACCESS	read-only
		STATUS	mandatory
		DESCRIPTION
			"Received message counter"
		::= { starPortPdhUniEntry 3 }

	starPortPdhUniHECErrCt	OBJECT-TYPE
		SYNTAX	INTEGER
		ACCESS	read-only
		STATUS	mandatory
		DESCRIPTION
			"HEC error counter"
		::= { starPortPdhUniEntry 4 }
	
	-----------------------------------------------------------------------
	-- Star Port DS1ATM CDB chip Table
	-----------------------------------------------------------------------
	starPortDS1ATMTable	OBJECT-TYPE
		SYNTAX SEQUENCE OF PortDS1ATMEntry
		ACCESS not-accessible
		STATUS mandatory
		DESCRIPTION
			"This table contains DS1 ATM chip  peformance data 
			 read from ATM chip of AIU T1, AIU E1 interface"
		::= { starPort 9 }

	starPortDS1ATMEntry	OBJECT-TYPE
		SYNTAX  PortDS1ATMEntry
		ACCESS  not-accessible
		STATUS  mandatory
		DESCRIPTION  "	"
		INDEX { starSlotIndex, starPortDS1ATMIndex }
		::= { starPortDS1ATMTable 1 }

	PortDS1ATMEntry ::=
		SEQUENCE {
			starPortDS1ATMIndex					INTEGER,
			starPortDS1ATMHecCnt				INTEGER,
			starPortDS1ATMDiscardCellCnt		INTEGER,
			starPortDS1ATMErrCorrectCellCnt		INTEGER,
			starPortDS1ATMRxBusyCellCnt			INTEGER,
			starPortDS1ATMTxBusyCellCnt			INTEGER
		}

	starPortDS1ATMIndex   OBJECT-TYPE
		SYNTAX	INTEGER
		ACCESS  read-only
		STATUS  mandatory
		DESCRIPTION  "The chip number for CDB chips. Each interface
				 has one CDB chip."
		::= { starPortDS1ATMEntry 1 }

	starPortDS1ATMHecCnt   OBJECT-TYPE
		SYNTAX	INTEGER
		ACCESS  read-only
		STATUS  mandatory
		DESCRIPTION
				 "Header Error Check(HEC) counter is incremented
				when thereis an error in the HEC value indicate
				either single or multiple errors in ATM cell
				heaer"
		::= { starPortDS1ATMEntry 2 }

	starPortDS1ATMDiscardCellCnt  OBJECT-TYPE
		SYNTAX	INTEGER
		ACCESS  read-only
		STATUS  mandatory
		DESCRIPTION  " This counter is incremented when the 3-cell
			output FIFO of the CDB is forced to overflow."
		::= { starPortDS1ATMEntry 3 }

	starPortDS1ATMErrCorrectCellCnt  OBJECT-TYPE
		SYNTAX	INTEGER
		ACCESS  read-only
		STATUS  mandatory
		DESCRIPTION  "This counter is incremented for every ATM cell 
			header this is corrected for a singel bit error"
		::= { starPortDS1ATMEntry 4 }

	starPortDS1ATMRxBusyCellCnt OBJECT-TYPE
		SYNTAX	INTEGER
		ACCESS  read-only
		STATUS  mandatory
		DESCRIPTION  "The counter is increment for each complete
			received busy cell."
		::= { starPortDS1ATMEntry 5 }

	starPortDS1ATMTxBusyCellCnt  OBJECT-TYPE
		SYNTAX	INTEGER
		ACCESS  read-only
		STATUS  mandatory
		DESCRIPTION  "The counter is inceremented for each complete
			 tranmitted busy cell."
		::= { starPortDS1ATMEntry 6 }

	-----------------------------------------------------------------------
	-- Star Port Munich32 chip Table
	-----------------------------------------------------------------------
	starPortM32Table 	OBJECT-TYPE
		SYNTAX	SEQUENCE OF PortM32Entry
		ACCESS	not-accessible
		STATUS	mandatory
		DESCRIPTION "This table contains the performance monitoring
			data for Siemens Munich32 chip (Multichannel
			Network Interface Controlloer for HDLC) for channelized 
			FIU board."
		::= { starPort 10 }

	starPortM32Entry	OBJECT-TYPE
		SYNTAX	PortM32Entry
		ACCESS  not-accessible
		STATUS	mandatory
		INDEX 	{ starPortM32SlotId, starPortM32ChipId }
		::= { starPortM32Table 1 }

	PortM32Entry ::=
		SEQUENCE {
			starPortM32SlotId					INTEGER,
			starPortM32ChipId					INTEGER,
			starPortM32RxCrcErrorCount			INTEGER,
			starPortM32RxNobErrorCount			INTEGER,
			starPortM32RxLfdErrorCount			INTEGER,
			starPortM32RxIntBufOverFlwCount		INTEGER,
			starPortM32RxAbortCount				INTEGER,
			starPortM32RxShortFrameCount		INTEGER,
			starPortM32RxDiscardFrameCount		INTEGER,
			starPortM32RxPduCount				INTEGER,
			starPortM32RxByteCount				INTEGER,
			starPortM32TxErrorCount				INTEGER,
			starPortM32TxPduCount				INTEGER,
			starPortM32TxByteCount				INTEGER
		}

	starPortM32SlotId	OBJECT-TYPE
		SYNTAX	INTEGER
		ACCESS  read-only
		STATUS 	mandatory
		DESCRIPTION 
			"This object indicates the slot number on the FIU module"
		::= { starPortM32Entry 1 }

	starPortM32ChipId	OBJECT-TYPE
		SYNTAX	INTEGER
		ACCESS  read-only
		STATUS 	mandatory
		DESCRIPTION 
			"This is the device Munich32 number (port no.) on the FIU module"
		::= { starPortM32Entry 2 }

	starPortM32RxCrcErrorCount	OBJECT-TYPE
		SYNTAX	INTEGER
		ACCESS  read-only
		STATUS 	mandatory
		DESCRIPTION 
			"Receive CRC Error counter"
		::= { starPortM32Entry 3 }

	starPortM32RxNobErrorCount	OBJECT-TYPE
		SYNTAX	INTEGER
		ACCESS  read-only
		STATUS 	mandatory
		DESCRIPTION 
			"Receive NOB bit Error counter"
		::= { starPortM32Entry 4 }

	starPortM32RxLfdErrorCount	OBJECT-TYPE
		SYNTAX	INTEGER
		ACCESS  read-only
		STATUS 	mandatory
		DESCRIPTION 
			"Receive LFD bit Error counter"
		::= { starPortM32Entry 5 }

	starPortM32RxIntBufOverFlwCount	OBJECT-TYPE
		SYNTAX	INTEGER
		ACCESS  read-only
		STATUS 	mandatory
		DESCRIPTION 
			"Receive buffer overvlow counter"
		::= { starPortM32Entry 6 }

	starPortM32RxAbortCount	OBJECT-TYPE
		SYNTAX	INTEGER
		ACCESS  read-only
		STATUS 	mandatory
		DESCRIPTION 
			"Receive abort frame counter"
		::= { starPortM32Entry 7 }

	starPortM32RxShortFrameCount	OBJECT-TYPE
		SYNTAX	INTEGER
		ACCESS  read-only
		STATUS 	mandatory
		DESCRIPTION 
			"Receive short frame counter"
		::= { starPortM32Entry 8 }

	starPortM32RxDiscardFrameCount	OBJECT-TYPE
		SYNTAX	INTEGER
		ACCESS  read-only
		STATUS 	mandatory
		DESCRIPTION 
			"Receive discarded frame counter"
		::= { starPortM32Entry 9 }

	starPortM32RxPduCount	OBJECT-TYPE
		SYNTAX	INTEGER
		ACCESS  read-only
		STATUS 	mandatory
		DESCRIPTION 
			"Receive PDU counter"
		::= { starPortM32Entry 10 }

	starPortM32RxByteCount	OBJECT-TYPE
		SYNTAX	INTEGER
		ACCESS  read-only
		STATUS 	mandatory
		DESCRIPTION 
			"Receive byte counter"
		::= { starPortM32Entry 11 }

	starPortM32TxErrorCount	OBJECT-TYPE
		SYNTAX	INTEGER
		ACCESS  read-only
		STATUS 	mandatory
		DESCRIPTION 
			"Transmit Error counter"
		::= { starPortM32Entry 12 }

	starPortM32TxPduCount	OBJECT-TYPE
		SYNTAX	INTEGER
		ACCESS  read-only
		STATUS 	mandatory
		DESCRIPTION 
			"Transmit PDU counter"
		::= { starPortM32Entry 13 }

	starPortM32TxByteCount	OBJECT-TYPE
		SYNTAX	INTEGER
		ACCESS  read-only
		STATUS 	mandatory
		DESCRIPTION 
			"Transmit byte counter"
		::= { starPortM32Entry 14 }

	-----------------------------------------------------------------------
	-- Star Port HDLC Configuration Information Table
	-----------------------------------------------------------------------
	starPortHdlcConfigTable	OBJECT-TYPE
		SYNTAX  SEQUENCE OF PortHdlcConfigEntry
		ACCESS  not-accessible
		STATUS  mandatory
		DESCRIPTION
			"This table contains information read from the
			Hdlc Device and is indexed by Slot number
			and Device Index" 
		::= { starPort 11 }

	starPortHdlcConfigEntry	OBJECT-TYPE
		SYNTAX	PortHdlcConfigEntry
		ACCESS	not-accessible
		STATUS	mandatory
		DESCRIPTION
			""
		INDEX	{ starSlotIndex, starPortHdlcIndex }
		::= { starPortHdlcConfigTable 1 }

	PortHdlcConfigEntry ::=
		SEQUENCE {
			starPortHdlcIndex			INTEGER,
			starPortHdlcLineSpeed		INTEGER,
			starPortHdlcLineEncoding	INTEGER,
			starPortHdlcCrcMode			INTEGER,
			starPortHdlcDteDce			INTEGER,
			starPortHdlcClockMode		INTEGER
		}

	starPortHdlcIndex	OBJECT-TYPE
		SYNTAX	INTEGER
		ACCESS	read-only
		STATUS	mandatory
		DESCRIPTION
			"Device index of Hdlc chip"
		::= { starPortHdlcConfigEntry 1 }

	starPortHdlcLineSpeed	OBJECT-TYPE
		SYNTAX	INTEGER {
			t1(1)
		}
		ACCESS	read-only
		STATUS	mandatory
		DESCRIPTION
			"Hdlc chip line speed"
		::= { starPortHdlcConfigEntry 2 }

	starPortHdlcLineEncoding	OBJECT-TYPE
		SYNTAX	INTEGER {
			nrz(1),
			nrzi(2)
		}
		ACCESS	read-only
		STATUS	mandatory
		DESCRIPTION
			"Hdlc line encoding mode"
		::= { starPortHdlcConfigEntry 3 }

	starPortHdlcCrcMode	OBJECT-TYPE
		SYNTAX	INTEGER {
			crc16(1),
			crcccitt(2)
		}
		ACCESS	read-only
		STATUS	mandatory
		DESCRIPTION
			"Hdlc CRC mode"
		::= { starPortHdlcConfigEntry 4 }

	starPortHdlcDteDce	OBJECT-TYPE
		SYNTAX	INTEGER {
			dte(1),
			dce(2)
		}
		ACCESS	read-only
		STATUS	mandatory
		DESCRIPTION
			"Hdlc Dte/Dce type"
		::= { starPortHdlcConfigEntry 5 }

	starPortHdlcClockMode	OBJECT-TYPE
		SYNTAX	INTEGER {
			internal(1),
			external(2)
		}
		ACCESS	read-only
		STATUS	mandatory
		DESCRIPTION
			"Clock mode"
		::= { starPortHdlcConfigEntry 6 }

	-----------------------------------------------------------------------
	-- Star System SVC Port Status Table
	-----------------------------------------------------------------------
	starSvcmStatusTable	 OBJECT-TYPE
		SYNTAX  SEQUENCE OF SvcmStatusEntry
		ACCESS  not-accessible
		STATUS  mandatory
		DESCRIPTION
			""
		::= { starPort 12 }
 
	starSvcmStatusEntry OBJECT-TYPE
		SYNTAX  SvcmStatusEntry
		ACCESS  not-accessible
		STATUS  mandatory
		DESCRIPTION
			""
		INDEX   { starSlotIndex, starPortIndex }
		::= { starSvcmStatusTable 1 }
 
	SvcmStatusEntry ::=
		SEQUENCE {
			starSvcmActiveCallCnt				   INTEGER,
			starSvcmLastTxCause					 INTEGER,
			starSvcmPtoPOrgActiveConnectionCnt	  INTEGER,
			starSvcmPtoPTermActiveConnectionCnt	 INTEGER,
			starSvcmPtoMPOrgActiveConnectionCnt	 INTEGER,
			starSvcmPtoMPTermActiveConnectionCnt	INTEGER,
			starSvcmConnectionSetupFailCnt		  INTEGER,
			starSvcmTxCallProceedingMsgCnt		  INTEGER,
			starSvcmRxCallProceedingMsgCnt		  INTEGER,
			starSvcmTxConnectMsgCnt				 INTEGER,
			starSvcmRxConnectMsgCnt				 INTEGER,
			starSvcmTxSetupMsgCnt				   INTEGER,
			starSvcmRxSetupMsgCnt				   INTEGER,
			starSvcmTxReleaseMsgCnt				 INTEGER,
			starSvcmRxReleaseMsgCnt				 INTEGER,
			starSvcmTxReleaseCompleteMsgCnt		 INTEGER,
			starSvcmRxReleaseCompleteMsgCnt		 INTEGER,
			starSvcmTxRestartMsgCnt				 INTEGER,
			starSvcmRxRestartMsgCnt				 INTEGER,
			starSvcmTxRestartAckMsgCnt			  INTEGER,
			starSvcmRxRestartAckMsgCnt			  INTEGER,
			starSvcmTxStatusMsgCnt				  INTEGER,
			starSvcmRxStatusMsgCnt				  INTEGER,
			starSvcmTxStatusEnquiryMsgCnt		   INTEGER,
			starSvcmRxStatusEnquiryMsgCnt		   INTEGER
		}
 
	starSvcmActiveCallCnt				   OBJECT-TYPE
		SYNTAX  INTEGER
		ACCESS  read-only
		STATUS  mandatory
		DESCRIPTION
			""
		::= { starSvcmStatusEntry 1 }
 
	starSvcmLastTxCause					 OBJECT-TYPE
		SYNTAX  INTEGER
		ACCESS  read-only
		STATUS  mandatory
		DESCRIPTION
			""
		::= { starSvcmStatusEntry 2 }
 
	starSvcmPtoPOrgActiveConnectionCnt	  OBJECT-TYPE
		SYNTAX  INTEGER
		ACCESS  read-only
		STATUS  mandatory
		DESCRIPTION
			""
		::= { starSvcmStatusEntry 3 }
 
	starSvcmPtoPTermActiveConnectionCnt	 OBJECT-TYPE
		SYNTAX  INTEGER
		ACCESS  read-only
		STATUS  mandatory
		DESCRIPTION
			""
		::= { starSvcmStatusEntry 4 }
 
	starSvcmPtoMPOrgActiveConnectionCnt	 OBJECT-TYPE
		SYNTAX  INTEGER
		ACCESS  read-only
		STATUS  mandatory
		DESCRIPTION
			""
		::= { starSvcmStatusEntry 5 }
 
	starSvcmPtoMPTermActiveConnectionCnt	OBJECT-TYPE
		SYNTAX  INTEGER
		ACCESS  read-only
		STATUS  mandatory
		DESCRIPTION
			""
		::= { starSvcmStatusEntry 6 }
 
	starSvcmConnectionSetupFailCnt		  OBJECT-TYPE
		SYNTAX  INTEGER
		ACCESS  read-only
		STATUS  mandatory
		DESCRIPTION
			""
		::= { starSvcmStatusEntry 7 }
 
	starSvcmTxCallProceedingMsgCnt		  OBJECT-TYPE
		SYNTAX  INTEGER
		ACCESS  read-only
		STATUS  mandatory
		DESCRIPTION
			""
		::= { starSvcmStatusEntry 8 }
 
	starSvcmRxCallProceedingMsgCnt		  OBJECT-TYPE
		SYNTAX  INTEGER
		ACCESS  read-only
		STATUS  mandatory
		DESCRIPTION
			""
		::= { starSvcmStatusEntry 9 }
 
	starSvcmTxConnectMsgCnt				 OBJECT-TYPE
		SYNTAX  INTEGER
		ACCESS  read-only
		STATUS  mandatory
		DESCRIPTION
			""
		::= { starSvcmStatusEntry 10 }
 
	starSvcmRxConnectMsgCnt				 OBJECT-TYPE
		SYNTAX  INTEGER
		ACCESS  read-only
		STATUS  mandatory
		DESCRIPTION
			""
		::= { starSvcmStatusEntry 11 }
 
	starSvcmTxSetupMsgCnt				   OBJECT-TYPE
		SYNTAX  INTEGER
		ACCESS  read-only
		STATUS  mandatory
		DESCRIPTION
			""
		::= { starSvcmStatusEntry 12 }
 
	starSvcmRxSetupMsgCnt				   OBJECT-TYPE
		SYNTAX  INTEGER
		ACCESS  read-only
		STATUS  mandatory
		DESCRIPTION
			""
		::= { starSvcmStatusEntry 13 }
 
	starSvcmTxReleaseMsgCnt				 OBJECT-TYPE
		SYNTAX  INTEGER
		ACCESS  read-only
		STATUS  mandatory
		DESCRIPTION
			""
		::= { starSvcmStatusEntry 14 }
 
	starSvcmRxReleaseMsgCnt				 OBJECT-TYPE
		SYNTAX  INTEGER
		ACCESS  read-only
		STATUS  mandatory
		DESCRIPTION
			""
		::= { starSvcmStatusEntry 15 }
 
	starSvcmTxReleaseCompleteMsgCnt		 OBJECT-TYPE
		SYNTAX  INTEGER
		ACCESS  read-only
		STATUS  mandatory
		DESCRIPTION
			""
		::= { starSvcmStatusEntry 16 }
 
	starSvcmRxReleaseCompleteMsgCnt		 OBJECT-TYPE
		SYNTAX  INTEGER
		ACCESS  read-only
		STATUS  mandatory
		DESCRIPTION
			""
		::= { starSvcmStatusEntry 17 }
 
	starSvcmTxRestartMsgCnt				 OBJECT-TYPE
		SYNTAX  INTEGER
		ACCESS  read-only
		STATUS  mandatory
		DESCRIPTION
			""
		::= { starSvcmStatusEntry 18 }
 
	starSvcmRxRestartMsgCnt				 OBJECT-TYPE
		SYNTAX  INTEGER
		ACCESS  read-only
		STATUS  mandatory
		DESCRIPTION
			""
		::= { starSvcmStatusEntry 19 }
 
	starSvcmTxRestartAckMsgCnt			  OBJECT-TYPE
		SYNTAX  INTEGER
		ACCESS  read-only
		STATUS  mandatory
		DESCRIPTION
			""
		::= { starSvcmStatusEntry 20 }
 
	starSvcmRxRestartAckMsgCnt			  OBJECT-TYPE
		SYNTAX  INTEGER
		ACCESS  read-only
		STATUS  mandatory
		DESCRIPTION
			""
		::= { starSvcmStatusEntry 21 }
 
	starSvcmTxStatusMsgCnt				  OBJECT-TYPE
		SYNTAX  INTEGER
		ACCESS  read-only
		STATUS  mandatory
		DESCRIPTION
			""
		::= { starSvcmStatusEntry 22 }
 
	starSvcmRxStatusMsgCnt				  OBJECT-TYPE
		SYNTAX  INTEGER
		ACCESS  read-only
		STATUS  mandatory
		DESCRIPTION
			""
		::= { starSvcmStatusEntry 23 }
 
	starSvcmTxStatusEnquiryMsgCnt		   OBJECT-TYPE
		SYNTAX  INTEGER
		ACCESS  read-only
		STATUS  mandatory
		DESCRIPTION
			""
		::= { starSvcmStatusEntry 24 }
 
	starSvcmRxStatusEnquiryMsgCnt		   OBJECT-TYPE
		SYNTAX  INTEGER
		ACCESS  read-only
		STATUS  mandatory
		DESCRIPTION
			""
		::= { starSvcmStatusEntry 25 }

	-----------------------------------------------------------------------
	-- Star System SVC AIU Stats Table
	-----------------------------------------------------------------------
	starSvcmAiuStatsTable   OBJECT-TYPE
		SYNTAX  SEQUENCE OF SvcmAiuStatsEntry
		ACCESS  not-accessible
		STATUS  mandatory
		DESCRIPTION
			""
		::= { starPort 13 }
 
	starSvcmAiuStatsEntry   OBJECT-TYPE
		SYNTAX  SvcmAiuStatsEntry
		ACCESS  not-accessible
		STATUS  mandatory
		DESCRIPTION
			""
		INDEX   { starSlotIndex, starPortIndex }
		::= { starSvcmAiuStatsTable 1 }
 
	SvcmAiuStatsEntry ::=
		SEQUENCE {
			starSvcmAiuTxSSCOPDiscardedCells			INTEGER,
			starSvcmAiuRxBGNCells					   INTEGER,
			starSvcmAiuRxBGAKCells					  INTEGER,
			starSvcmAiuRxENDCells					   INTEGER,
			starSvcmAiuRxRSCells						INTEGER,
			starSvcmAiuRxRSAKCells					  INTEGER,
			starSvcmAiuRxSDCells						INTEGER,
			starSvcmAiuRxSDPCCells					  INTEGER,
			starSvcmAiuRxPOLLCells					  INTEGER,
			starSvcmAiuRxSTATCells					  INTEGER,
			starSvcmAiuRxUSTATCells					 INTEGER,
			starSvcmAiuRxUDCells						INTEGER,
			starSvcmAiuRxMDCells						INTEGER,
			starSvcmAiuTxAddPartyMsgCnt				 INTEGER,
			starSvcmAiuRxAddPartyMsgCnt				 INTEGER,
			starSvcmAiuTxAddPartyRejMsgCnt			  INTEGER,
			starSvcmAiuRxAddPartyRejMsgCnt			  INTEGER,
			starSvcmAiuTxAddPartyAckMsgCnt			  INTEGER,
			starSvcmAiuRxAddPartyAckMsgCnt			  INTEGER,
			starSvcmAiuTxDropPartyMsgCnt				INTEGER,
			starSvcmAiuRxDropPartyMsgCnt				INTEGER,
			starSvcmAiuTxDropPartyAckMsgCnt			 INTEGER,
			starSvcmAiuRxDropPartyAckMsgCnt			 INTEGER
		}
 
	starSvcmAiuTxSSCOPDiscardedCells			OBJECT-TYPE
		SYNTAX  INTEGER
		ACCESS  read-only
		STATUS  mandatory
		DESCRIPTION
			""
		::= { starSvcmAiuStatsEntry 1 }
 
	starSvcmAiuRxBGNCells					   OBJECT-TYPE
		SYNTAX  INTEGER
		ACCESS  read-only
		STATUS  mandatory
		DESCRIPTION
			""
		::= { starSvcmAiuStatsEntry 2 }
 
	starSvcmAiuRxBGAKCells					  OBJECT-TYPE
		SYNTAX  INTEGER
		ACCESS  read-only
		STATUS  mandatory
		DESCRIPTION
			""
		::= { starSvcmAiuStatsEntry 3 }
 
	starSvcmAiuRxENDCells					   OBJECT-TYPE
		SYNTAX  INTEGER
		ACCESS  read-only
		STATUS  mandatory
		DESCRIPTION
			""
		::= { starSvcmAiuStatsEntry 4 }
 
	starSvcmAiuRxRSCells						OBJECT-TYPE
		SYNTAX  INTEGER
		ACCESS  read-only
		STATUS  mandatory
		DESCRIPTION
			""
		::= { starSvcmAiuStatsEntry 5 }
 
	starSvcmAiuRxRSAKCells					  OBJECT-TYPE
		SYNTAX  INTEGER
		ACCESS  read-only
		STATUS  mandatory
		DESCRIPTION
			""
		::= { starSvcmAiuStatsEntry 6 }
 
	starSvcmAiuRxSDCells						OBJECT-TYPE
		SYNTAX  INTEGER
		ACCESS  read-only
		STATUS  mandatory
		DESCRIPTION
			""
		::= { starSvcmAiuStatsEntry 7 }
 
	starSvcmAiuRxSDPCCells					  OBJECT-TYPE
		SYNTAX  INTEGER
		ACCESS  read-only
		STATUS  mandatory
		DESCRIPTION
			""
		::= { starSvcmAiuStatsEntry 8 }
 
	starSvcmAiuRxPOLLCells					  OBJECT-TYPE
		SYNTAX  INTEGER
		ACCESS  read-only
		STATUS  mandatory
		DESCRIPTION
			""
		::= { starSvcmAiuStatsEntry 9 }
 
	starSvcmAiuRxSTATCells					  OBJECT-TYPE
		SYNTAX  INTEGER
		ACCESS  read-only
		STATUS  mandatory
		DESCRIPTION
			""
		::= { starSvcmAiuStatsEntry 10 }

	starSvcmAiuRxUSTATCells					 OBJECT-TYPE
		SYNTAX  INTEGER
		ACCESS  read-only
		STATUS  mandatory
		DESCRIPTION
			""
		::= { starSvcmAiuStatsEntry 11 }

	starSvcmAiuRxUDCells						OBJECT-TYPE
		SYNTAX  INTEGER
		ACCESS  read-only
		STATUS  mandatory
		DESCRIPTION
			""
		::= { starSvcmAiuStatsEntry 12 }

	starSvcmAiuRxMDCells						OBJECT-TYPE
		SYNTAX  INTEGER
		ACCESS  read-only
		STATUS  mandatory
		DESCRIPTION
			""
		::= { starSvcmAiuStatsEntry 13 }

	starSvcmAiuTxAddPartyMsgCnt				 OBJECT-TYPE
		SYNTAX  INTEGER
		ACCESS  read-only
		STATUS  mandatory
		DESCRIPTION
			""
		::= { starSvcmAiuStatsEntry 14 }

		starSvcmAiuRxAddPartyMsgCnt			 OBJECT-TYPE
		SYNTAX  INTEGER
		ACCESS  read-only
		STATUS  mandatory
		DESCRIPTION
		""
		::= { starSvcmAiuStatsEntry 15 }

	starSvcmAiuTxAddPartyRejMsgCnt			  OBJECT-TYPE
		SYNTAX  INTEGER
		ACCESS  read-only
		STATUS  mandatory
		DESCRIPTION
			""
		::= { starSvcmAiuStatsEntry 16 }

	starSvcmAiuRxAddPartyRejMsgCnt			  OBJECT-TYPE
		SYNTAX  INTEGER
		ACCESS  read-only
		STATUS  mandatory
		DESCRIPTION
			""
		::= { starSvcmAiuStatsEntry 17 }
 
	starSvcmAiuTxAddPartyAckMsgCnt			  OBJECT-TYPE
		SYNTAX  INTEGER
		ACCESS  read-only
		STATUS  mandatory
		DESCRIPTION
			""
		::= { starSvcmAiuStatsEntry 18 }
 
	starSvcmAiuRxAddPartyAckMsgCnt			  OBJECT-TYPE
		SYNTAX  INTEGER
		ACCESS  read-only
		STATUS  mandatory
		DESCRIPTION
			""
		::= { starSvcmAiuStatsEntry 19 }
 
	starSvcmAiuTxDropPartyMsgCnt				OBJECT-TYPE
		SYNTAX  INTEGER
		ACCESS  read-only
		STATUS  mandatory
		DESCRIPTION
			""
		::= { starSvcmAiuStatsEntry 20 }
 
	starSvcmAiuRxDropPartyMsgCnt				OBJECT-TYPE
		SYNTAX  INTEGER
		ACCESS  read-only
		STATUS  mandatory
		DESCRIPTION
			""
		::= { starSvcmAiuStatsEntry 21 }
 
	starSvcmAiuTxDropPartyAckMsgCnt			 OBJECT-TYPE
		SYNTAX  INTEGER
		ACCESS  read-only
		STATUS  mandatory
		DESCRIPTION
			""
		::= { starSvcmAiuStatsEntry 22 }

	starSvcmAiuRxDropPartyAckMsgCnt			 OBJECT-TYPE
	SYNTAX  INTEGER
	ACCESS  read-only
	STATUS  mandatory
	DESCRIPTION
			""
	::= { starSvcmAiuStatsEntry 23 }
 
	-----------------------------------------------------------------------
	-- Star System SVC FIU Stats Table
	-----------------------------------------------------------------------
	starSvcmFiuStatsTable   OBJECT-TYPE
		SYNTAX  SEQUENCE OF SvcmFiuStatsEntry
		ACCESS  not-accessible
		STATUS  mandatory
		DESCRIPTION
			""
		::= { starPort 14 }
 
	starSvcmFiuStatsEntry   OBJECT-TYPE
		SYNTAX  SvcmFiuStatsEntry
		ACCESS  not-accessible
		STATUS  mandatory
		DESCRIPTION
			""
		INDEX   { starSlotIndex, starPortIndex }
		::= { starSvcmFiuStatsTable 1 }
 
	SvcmFiuStatsEntry ::=
		SEQUENCE {
			starSvcmFiuQ933TimerExpiryCnt		   INTEGER,
			starSvcmFiuQ933IllegalMsgCnt			INTEGER,
			starSvcmFiuQ922TimerExpiryCnt		   INTEGER,
			starSvcmFiuQ922LinkFailIndicationCnt	INTEGER,
			starSvcmFiuQ922UnackedMsgCnt			INTEGER
		}
 
	starSvcmFiuQ933TimerExpiryCnt		   OBJECT-TYPE
		SYNTAX  INTEGER
		ACCESS  read-only
		STATUS  mandatory
		DESCRIPTION
			""
		::= { starSvcmFiuStatsEntry 1 }
 
	starSvcmFiuQ933IllegalMsgCnt			OBJECT-TYPE
		SYNTAX  INTEGER
		ACCESS  read-only
		STATUS  mandatory
		DESCRIPTION
			""
		::= { starSvcmFiuStatsEntry 2 }
 
	starSvcmFiuQ922TimerExpiryCnt		   OBJECT-TYPE
		SYNTAX  INTEGER
		ACCESS  read-only
		STATUS  mandatory
		DESCRIPTION
			""
		::= { starSvcmFiuStatsEntry 3 }
 
	starSvcmFiuQ922LinkFailIndicationCnt	OBJECT-TYPE
		SYNTAX  INTEGER
		ACCESS  read-only
		STATUS  mandatory
		DESCRIPTION
			""
		::= { starSvcmFiuStatsEntry 4 }
 
	starSvcmFiuQ922UnackedMsgCnt			OBJECT-TYPE
		SYNTAX  INTEGER
		ACCESS  read-only
		STATUS  mandatory
		DESCRIPTION
			""
		::= { starSvcmFiuStatsEntry 5 }

	-----------------------------------------------------------------------
	-- Star System Port Trunk Table Added on (3/27/98)
	-----------------------------------------------------------------------
	starPortTrunkTable		OBJECT-TYPE
		SYNTAX  SEQUENCE OF PortTrunkEntry
		ACCESS  not-accessible
		STATUS  mandatory
		DESCRIPTION
			""
		::= { starPort 15 }

	starPortTrunkEntry	OBJECT-TYPE
		SYNTAX	PortTrunkEntry
		ACCESS	not-accessible
		STATUS	mandatory
		DESCRIPTION
			""
		INDEX	{ starSlotIndex, starPortIndex }
		::= { starPortTrunkTable 1 }

	PortTrunkEntry ::=
		SEQUENCE {
			starTotalInFixedCapa		INTEGER,
			starTotalOutFixedCapa		INTEGER,
			starTotalInVariableCapa		INTEGER,
			starTotalOutVariableCapa	INTEGER,
			starPvcInFixedCapa			INTEGER,
			starPvcOutFixedCapa			INTEGER,
			starPvcInVariableCapa		INTEGER,
			starPvcOutVariableCapa		INTEGER,
			starSvcInFixedCapa			INTEGER,
			starSvcOutFixedCapa			INTEGER,
			starSvcInVariableCapa		INTEGER,
			starSvcOutVariableCapa		INTEGER 
		}

	starTotalInFixedCapa	OBJECT-TYPE
		SYNTAX	INTEGER
		ACCESS	read-only
		STATUS	mandatory
		DESCRIPTION
			""
		::= { starPortTrunkEntry 1 }

	starTotalOutFixedCapa	OBJECT-TYPE
		SYNTAX	INTEGER
		ACCESS	read-only
		STATUS	mandatory
		DESCRIPTION
			""
		::= { starPortTrunkEntry 2 }

	starTotalInVariableCapa	OBJECT-TYPE
		SYNTAX	INTEGER
		ACCESS	read-only
		STATUS	mandatory
		DESCRIPTION
			""
		::= { starPortTrunkEntry 3 }

	starTotalOutVariableCapa	OBJECT-TYPE
		SYNTAX	INTEGER
		ACCESS	read-only
		STATUS	mandatory
		DESCRIPTION
			""
		::= { starPortTrunkEntry 4 }

	starPvcInFixedCapa	OBJECT-TYPE
		SYNTAX	INTEGER
		ACCESS	read-only
		STATUS	mandatory
		DESCRIPTION
			""
		::= { starPortTrunkEntry 5 }

	starPvcOutFixedCapa	OBJECT-TYPE
		SYNTAX	INTEGER
		ACCESS	read-only
		STATUS	mandatory
		DESCRIPTION
			""
		::= { starPortTrunkEntry 6 }

	starPvcInVariableCapa	OBJECT-TYPE
		SYNTAX	INTEGER
		ACCESS	read-only
		STATUS	mandatory
		DESCRIPTION
			""
		::= { starPortTrunkEntry 7 }

	starPvcOutVariableCapa	OBJECT-TYPE
		SYNTAX	INTEGER
		ACCESS	read-only
		STATUS	mandatory
		DESCRIPTION
			""
		::= { starPortTrunkEntry 8 }

	starSvcInFixedCapa	OBJECT-TYPE
		SYNTAX	INTEGER
		ACCESS	read-only
		STATUS	mandatory
		DESCRIPTION
			""
		::= { starPortTrunkEntry 9 }

	starSvcOutFixedCapa	OBJECT-TYPE
		SYNTAX	INTEGER
		ACCESS	read-only
		STATUS	mandatory
		DESCRIPTION
			""
		::= { starPortTrunkEntry 10 }

	starSvcInVariableCapa	OBJECT-TYPE
		SYNTAX	INTEGER
		ACCESS	read-only
		STATUS	mandatory
		DESCRIPTION
			""
		::= { starPortTrunkEntry 11 }

	starSvcOutVariableCapa	OBJECT-TYPE
		SYNTAX	INTEGER
		ACCESS	read-only
		STATUS	mandatory
		DESCRIPTION
			""
		::= { starPortTrunkEntry 12 }

	-----------------------------------------------------------------------
	-- Star System Real Status Table Added on (4/4/98)
	-----------------------------------------------------------------------
	starPortRealStatusTable		OBJECT-TYPE
		SYNTAX  SEQUENCE OF PortRealStatusEntry
		ACCESS  not-accessible
		STATUS  mandatory
		DESCRIPTION
			""
		::= { starPort 16 }

	starPortRealStatusEntry	OBJECT-TYPE
		SYNTAX	PortRealStatusEntry
		ACCESS	not-accessible
		STATUS	mandatory
		DESCRIPTION
			""
		INDEX	{ starSlotIndex }
		::= { starPortRealStatusTable 1 }

	PortRealStatusEntry ::=
		SEQUENCE {
			starPortConfigRealStatus	INTEGER,
			starPortAlarmRealStatus		INTEGER,
			starPortOperRealStatus		INTEGER,
			starPortRealStatusDescr		OCTET STRING
		}

	starPortConfigRealStatus	OBJECT-TYPE
		SYNTAX	INTEGER
		ACCESS	read-only
		STATUS	mandatory
		DESCRIPTION
			""
		::= { starPortRealStatusEntry 1 }

	starPortAlarmRealStatus	OBJECT-TYPE
		SYNTAX	INTEGER
		ACCESS	read-only
		STATUS	mandatory
		DESCRIPTION
			""
		::= { starPortRealStatusEntry 2 }

	starPortOperRealStatus	OBJECT-TYPE
		SYNTAX	INTEGER
		ACCESS	read-only
		STATUS	mandatory
		DESCRIPTION
			""
		::= { starPortRealStatusEntry 3 }

	starPortRealStatusDescr	OBJECT-TYPE
		SYNTAX	OCTET STRING
		ACCESS	read-only
		STATUS	mandatory
		DESCRIPTION
			""
		::= { starPortRealStatusEntry 4 }

	-----------------------------------------------------------------------
	-- Star Port PM Threshold Table by Hyoung 07/13/98
	-----------------------------------------------------------------------
	starPortPmThresholdTable	OBJECT-TYPE
		SYNTAX  SEQUENCE OF  PortPmThresholdTable
		ACCESS  not-accessible
		STATUS  mandatory
		DESCRIPTION
			"PM threshold information for history monitoring"
		::= { starPort 17 }
 
	starPortPmThresholdEntry		OBJECT-TYPE
		SYNTAX  PortPmThresholdTable
		ACCESS  not-accessible
		STATUS  mandatory
		DESCRIPTION
			""
		INDEX { starSlotIndex, starPortIndex, starPortPmThreshIdx }
		::= { starPortPmThresholdTable 1 }
 
	PortPmThresholdTable ::=
		SEQUENCE {
			starPortPmThreshIdx		INTEGER,
			starPortPmTrigger		INTEGER,
			starPortPmFlag			INTEGER,
			starPortPmThreshValue	INTEGER,
			starPortPmRearmValue	INTEGER,
			starPortPmPriority		INTEGER,
			starPortPmInterval		INTEGER,
			starPortPmCnt			INTEGER
	}

	starPortPmThreshIdx OBJECT-TYPE
		SYNTAX  INTEGER
		ACCESS  read-write
		STATUS  mandatory
		DESCRIPTION
			""
		::= { starPortPmThresholdEntry 1 }
 
	starPortPmTrigger   OBJECT-TYPE
		SYNTAX  INTEGER
		ACCESS  read-write
		STATUS  mandatory
		DESCRIPTION
			""
		::= { starPortPmThresholdEntry 2 }

	starPortPmFlag  OBJECT-TYPE
		SYNTAX  INTEGER
		ACCESS  read-write
		STATUS  mandatory
		DESCRIPTION
			""
		::= { starPortPmThresholdEntry 3 }
 
	starPortPmThreshValue   OBJECT-TYPE
		SYNTAX  INTEGER
		ACCESS  read-write
		STATUS  mandatory
		DESCRIPTION
			""
		::= { starPortPmThresholdEntry 4 }
 
	starPortPmRearmValue	OBJECT-TYPE
		SYNTAX  INTEGER
		ACCESS  read-write
		STATUS  mandatory
		DESCRIPTION
			""
		::= { starPortPmThresholdEntry 5 }
 
	starPortPmPriority  OBJECT-TYPE
		SYNTAX  INTEGER
		ACCESS  read-write
		STATUS  mandatory
		DESCRIPTION
			""
		::= { starPortPmThresholdEntry 6 }
 
	starPortPmInterval  OBJECT-TYPE
		SYNTAX  INTEGER
		ACCESS  read-write
		STATUS  mandatory
		DESCRIPTION
			""
		::= { starPortPmThresholdEntry 7 }

	starPortPmCnt	  OBJECT-TYPE
		SYNTAX  INTEGER
		ACCESS  read-write
		STATUS  mandatory
		DESCRIPTION
			""
		::= { starPortPmThresholdEntry 8 }

	-----------------------------------------------------------------------
	-- Star Port Frame Relay LMI Link Status by Hyoung 30/09/98
	-----------------------------------------------------------------------
	starPortLMIStatsTable	OBJECT-TYPE
		SYNTAX  SEQUENCE OF  PortLMIStatsTable
		ACCESS  not-accessible
		STATUS  mandatory
		DESCRIPTION
			"Frame Relay LMI link information"
		::= { starPort 18 }

	starPortLMIStatsEntry	OBJECT-TYPE
		SYNTAX	PortLMIStatsTable
		ACCESS	not-accessible
		STATUS	mandatory
		DESCRIPTION
			""
		INDEX   { starSlotIndex, starPortIndex }
		::= { starPortLMIStatsTable 1 }
 
	PortLMIStatsTable ::=
		SEQUENCE {
			starPortLMILinkStats		INTEGER
		}

	starPortLMILinkStats	OBJECT-TYPE
		SYNTAX  INTEGER
		ACCESS  read-only
		STATUS  mandatory
		DESCRIPTION
			""
		::= { starPortLMIStatsEntry 1 }
	
    -----------------------------------------------------------------------
    -- Star Port FIU12 Physical PM added by Hyoung 06/01/99
    -----------------------------------------------------------------------
    starPortFiu12Ds1Table   OBJECT-TYPE
        SYNTAX  SEQUENCE OF  PortFiu12Ds1Table
        ACCESS  not-accessible
        STATUS  mandatory
        DESCRIPTION
            ""
        ::= { starPort 19 }
 
    starPortFiu12Ds1Entry   OBJECT-TYPE
        SYNTAX  PortFiu12Ds1Table
        ACCESS  not-accessible
        STATUS  mandatory
        DESCRIPTION
            ""
        INDEX   { starPortFiu12Index }
        ::= { starPortFiu12Ds1Table 1 }
 
    PortFiu12Ds1Table ::=
        SEQUENCE {
            starPortFiu12Index      INTEGER,
            starPortFiu12Ds1LCV     INTEGER,
            starPortFiu12Ds1BEE     INTEGER,
            starPortFiu12Ds1FER     INTEGER,
            starPortFiu12Ds1OOF     INTEGER,
            starPortFiu12E1FER      INTEGER,
            starPortFiu12E1FEBE     INTEGER,
            starPortFiu12E1CRC      INTEGER,
            starPortFiu12E1LCV      INTEGER
        }
 
    starPortFiu12Index    OBJECT-TYPE
        SYNTAX  INTEGER
        ACCESS  read-only
        STATUS  mandatory
        DESCRIPTION
            ""
        ::= { starPortFiu12Ds1Entry 1 }
 
    starPortFiu12Ds1LCV    OBJECT-TYPE
        SYNTAX  INTEGER
        ACCESS  read-only
        STATUS  mandatory
        DESCRIPTION
            ""
        ::= { starPortFiu12Ds1Entry 2 }
 
    starPortFiu12Ds1BEE    OBJECT-TYPE
        SYNTAX  INTEGER
        ACCESS  read-only
        STATUS  mandatory
        DESCRIPTION
            ""
        ::= { starPortFiu12Ds1Entry 3 }
 
    starPortFiu12Ds1FER    OBJECT-TYPE
        SYNTAX  INTEGER
        ACCESS  read-only
        STATUS  mandatory
        DESCRIPTION
            ""
        ::= { starPortFiu12Ds1Entry 4 }
 
    starPortFiu12Ds1OOF    OBJECT-TYPE
        SYNTAX  INTEGER
        ACCESS  read-only
        STATUS  mandatory
        DESCRIPTION
            ""
        ::= { starPortFiu12Ds1Entry 5 }
 
    starPortFiu12E1FER    OBJECT-TYPE
        SYNTAX  INTEGER
        ACCESS  read-only
        STATUS  mandatory
        DESCRIPTION
            ""
        ::= { starPortFiu12Ds1Entry 6 }
 
    starPortFiu12E1FEBE    OBJECT-TYPE
        SYNTAX  INTEGER
        ACCESS  read-only
        STATUS  mandatory
        DESCRIPTION
            ""
        ::= { starPortFiu12Ds1Entry 7 }
 
    starPortFiu12E1CRC    OBJECT-TYPE
        SYNTAX  INTEGER
        ACCESS  read-only
        STATUS  mandatory
        DESCRIPTION
            ""
        ::= { starPortFiu12Ds1Entry 8 }
 
    starPortFiu12E1LCV    OBJECT-TYPE
        SYNTAX  INTEGER
        ACCESS  read-only
        STATUS  mandatory
        DESCRIPTION
            ""
        ::= { starPortFiu12Ds1Entry 9 }

	-----------------------------------------------------------------------
	-- Star Port FIU12_T3 Framer PM   added by Sunah 08/10/99 
	-----------------------------------------------------------------------
	starPortFiu12Ds3FramerTable	OBJECT-TYPE
  		SYNTAX  SEQUENCE OF  PortFiu12Ds3FramerTable
        ACCESS  not-accessible
        STATUS  mandatory
        DESCRIPTION
            ""
        ::= { starPort 20 }

	starPortFiu12Ds3FramerEntry   OBJECT-TYPE
        SYNTAX  PortFiu12Ds3FramerTable
        ACCESS  not-accessible
        STATUS  mandatory
        DESCRIPTION
            ""
        INDEX   { starSlotIndex, starPortFiu12Ds3FramerIndex }
        ::= { starPortFiu12Ds3FramerTable 1 }
 
    PortFiu12Ds3FramerTable ::=
        SEQUENCE {
            starPortFiu12Ds3FramerIndex   INTEGER,
            starPortFiu12Ds3FramerLCV     INTEGER,
            starPortFiu12Ds3FramerFERR    INTEGER,
            starPortFiu12Ds3FramerDXZS    INTEGER,
            starPortFiu12Ds3FramerPERR    INTEGER,
            starPortFiu12Ds3FramerCPERR   INTEGER,
            starPortFiu12Ds3FramerFEBE    INTEGER
        }


	starPortFiu12Ds3FramerIndex    OBJECT-TYPE
        SYNTAX  INTEGER
        ACCESS  read-only
        STATUS  mandatory
        DESCRIPTION
            ""
        ::= { starPortFiu12Ds3FramerEntry 1 }

	starPortFiu12Ds3FramerLCV    OBJECT-TYPE
        SYNTAX  INTEGER
        ACCESS  read-only
        STATUS  mandatory
        DESCRIPTION
            ""
        ::= { starPortFiu12Ds3FramerEntry 2 }
 
    starPortFiu12Ds3FramerFERR    OBJECT-TYPE
        SYNTAX  INTEGER
        ACCESS  read-only
        STATUS  mandatory
        DESCRIPTION
            ""
        ::= { starPortFiu12Ds3FramerEntry 3 }
 
    starPortFiu12Ds3FramerDXZS    OBJECT-TYPE
        SYNTAX  INTEGER
        ACCESS  read-only
        STATUS  mandatory
        DESCRIPTION
            ""
        ::= { starPortFiu12Ds3FramerEntry 4 }
 
    starPortFiu12Ds3FramerPERR    OBJECT-TYPE
        SYNTAX  INTEGER
        ACCESS  read-only
        STATUS  mandatory
        DESCRIPTION
            ""
        ::= { starPortFiu12Ds3FramerEntry 5 }
 
    starPortFiu12Ds3FramerCPERR    OBJECT-TYPE
        SYNTAX  INTEGER
        ACCESS  read-only
        STATUS  mandatory
        DESCRIPTION
            ""
        ::= { starPortFiu12Ds3FramerEntry 6 }
 
    starPortFiu12Ds3FramerFEBE    OBJECT-TYPE
        SYNTAX  INTEGER
        ACCESS  read-only
        STATUS  mandatory
        DESCRIPTION
            ""
        ::= { starPortFiu12Ds3FramerEntry 7 }
	
	-----------------------------------------------------------------------
	-- Physical Loopback for FIU_T3(DS1) by sunah 99.9.14
	-----------------------------------------------------------------------
	starPhysicalLoopbackTable OBJECT-TYPE
		SYNTAX  SEQUENCE OF PhysicalLoopbackTable 
		ACCESS  not-accessible
		STATUS  mandatory
		DESCRIPTION
			" Set and Get Physical Loopback for FIU_T3(DS1)"
		::= { starPort 21 }

	 starPhysicalLoopbackEntry   OBJECT-TYPE
        SYNTAX  PhysicalLoopbackTable
        ACCESS  not-accessible
        STATUS  mandatory
        DESCRIPTION
            ""
        INDEX   { starSlotIndex, starPortIndex,
                  starPhysicalLoopbackDs1Port, starPhysicalLoopbackMethod,
                  starPhysicalLoopbackCtrl }
        ::= { starPhysicalLoopbackTable 1 }
 
    PhysicalLoopbackTable ::=
		SEQUENCE {
			starPhysicalLoopbackDs1Port    INTEGER,
			starPhysicalLoopbackMethod     INTEGER,
			starPhysicalLoopbackCtrl       INTEGER,
			starPhysicalLoopbackStatus     INTEGER,
			starPhysicalLoopbackDescr      OCTET STRING
		}
	
	starPhysicalLoopbackDs1Port    OBJECT-TYPE
        SYNTAX  INTEGER
        ACCESS  read-only
        STATUS  mandatory
        DESCRIPTION
            "FIU_T3(Ds1) Port "
        ::= { starPhysicalLoopbackEntry 1 }

	starPhysicalLoopbackMethod    OBJECT-TYPE
		SYNTAX  INTEGER
        ACCESS  read-only
        STATUS  mandatory
        DESCRIPTION
			"19 : External Loopback 
			 20 : Internal Loopback"
		::= { starPhysicalLoopbackEntry 2 }


	starPhysicalLoopbackCtrl    OBJECT-TYPE
		SYNTAX  INTEGER{
			set(1),
			release(2)
		}
        ACCESS  read-only
        STATUS  mandatory
        DESCRIPTION
			"1 : Set Loopback 
			 2 : Release Loopback"
		::= { starPhysicalLoopbackEntry 3 }

	starPhysicalLoopbackStatus    OBJECT-TYPE
		SYNTAX  INTEGER
        ACCESS  read-write
        STATUS  mandatory
        DESCRIPTION
			" Get or Set a physical Loopback for each port"	
		::= { starPhysicalLoopbackEntry 4 }

	starPhysicalLoopbackDescr    OBJECT-TYPE
		SYNTAX  OCTET STRING
		ACCESS  read-only
		STATUS  mandatory
		DESCRIPTION
			" Get a physical Loopback status for all ports "
		::= { starPhysicalLoopbackEntry 5 }
 
    ----------------------------------------------------------------------
    -- starPPP Group
    ----------------------------------------------------------------------
    starPPP      OBJECT IDENTIFIER ::= { starPort 22 }

    starPPPLinkStatusTable   OBJECT-TYPE
           SYNTAX    SEQUENCE OF StarPPPLinkStatusEntry
           ACCESS    not-accessible
           STATUS    mandatory
           DESCRIPTION
                     "A table containing PPP-link specific variables
                     for this PPP implementation."
           ::= { starPPP 1 }

    starPPPLinkStatusEntry   OBJECT-TYPE
           SYNTAX    StarPPPLinkStatusEntry
           ACCESS    not-accessible
           STATUS    mandatory
           DESCRIPTION
                     "Management information about a particular PPP
                     Link."
	       INDEX     { starSlotIndex, starPortIndex }
           ::= { starPPPLinkStatusTable 1 }


    StarPPPLinkStatusEntry ::= SEQUENCE {
           starPPPLinkStatusPhysicalIndex
                INTEGER,
           starPPPLinkStatusBadAddresses
                Counter,
           starPPPLinkStatusBadControls
                Counter,
           starPPPLinkStatusPacketTooLongs
                Counter,
           starPPPLinkStatusBadFCSs
                Counter,
           starPPPLinkStatusLocalMRU
                INTEGER,
           starPPPLinkStatusRemoteMRU
                INTEGER,
           starPPPLinkStatusLocalToPeerACCMap
                OCTET STRING,
           starPPPLinkStatusPeerToLocalACCMap
                OCTET STRING,
           starPPPLinkStatusLocalToRemotePC
                INTEGER,
           starPPPLinkStatusRemoteToLocalPC
                INTEGER,
           starPPPLinkStatusLocalToRemoteACFC
                INTEGER,
           starPPPLinkStatusRemoteToLocalACFC
                INTEGER,
           starPPPLinkStatusTransmitFcsSize
                INTEGER,
           starPPPLinkStatusReceiveFcsSize
                INTEGER
           }

    starPPPLinkStatusPhysicalIndex   OBJECT-TYPE
           SYNTAX    INTEGER(0..2147483647)
           ACCESS    read-only
           STATUS    mandatory
           DESCRIPTION
                     "The value of ifIndex that identifies the
                     lower-level interface over which this PPP Link
                     is operating. This interface would usually be
                     an HDLC or RS-232 type of interface. If there
                     is no lower-layer interface element, or there
                     is no ifEntry for the element, or the element
                     can not be identified, then the value of this
                     object is 0.  For example, suppose that PPP is
                     operating over a serial port. This would use
                     two entries in the ifTable. The PPP could be
                     running over `interface' number 123 and the
                     serial port could be running over `interface'
                     number 987.  Therefore, ifSpecific.123 would
                     contain the OBJECT IDENTIFIER ppp
                     starPPPLinkStatusPhysicalIndex.123 would contain
                     987, and ifSpecific.987 would contain the
                     OBJECT IDENTIFIER for the serial-port's media-
                     specific MIB."
           ::= { starPPPLinkStatusEntry 1 }


    starPPPLinkStatusBadAddresses   OBJECT-TYPE
           SYNTAX    Counter
           ACCESS    read-only
           STATUS    mandatory
           DESCRIPTION
                     "The number of packets received with an
                     incorrect Address Field. This counter is a
                     component of the ifInErrors variable that is
                     associated with the interface that represents
                     this PPP Link."
           REFERENCE
                     "Section 3.1, Address Field, of RFC1331."
           ::= { starPPPLinkStatusEntry 2 }


    starPPPLinkStatusBadControls   OBJECT-TYPE
           SYNTAX    Counter
           ACCESS    read-only
           STATUS    mandatory
           DESCRIPTION
                     "The number of packets received on this link
                     with an incorrect Control Field. This counter
                     is a component of the ifInErrors variable that
                     is associated with the interface that
                     represents this PPP Link."
           REFERENCE
                     "Section 3.1, Control Field, of RFC1331."
           ::= { starPPPLinkStatusEntry 3 }


    starPPPLinkStatusPacketTooLongs   OBJECT-TYPE
           SYNTAX    Counter
           ACCESS    read-only
           STATUS    mandatory
           DESCRIPTION
                     "The number of received packets that have been
                     discarded because their length exceeded the
                     MRU. This counter is a component of the
                     ifInErrors variable that is associated with the
                     interface that represents this PPP Link. NOTE,
                     packets which are longer than the MRU but which
                     are successfully received and processed are NOT
                     included in this count."
           ::= { starPPPLinkStatusEntry 4 }


    starPPPLinkStatusBadFCSs   OBJECT-TYPE
           SYNTAX    Counter
           ACCESS    read-only
           STATUS    mandatory
           DESCRIPTION
                     "The number of received packets that have been
                     discarded due to having an incorrect FCS. This
                     counter is a component of the ifInErrors
                     variable that is associated with the interface
                     that represents this PPP Link."
           ::= { starPPPLinkStatusEntry 5 }


      starPPPLinkStatusLocalMRU   OBJECT-TYPE
           SYNTAX    INTEGER(1..2147483647)
           ACCESS    read-only
           STATUS    mandatory
           DESCRIPTION
                     "The current value of the MRU for the local PPP
                     Entity. This value is the MRU that the remote
                     entity is using when sending packets to the
                     local PPP entity. The value of this object is
                     meaningful only when the link has reached the
                     open state (ifOperStatus is up)."
           ::= { starPPPLinkStatusEntry 6 }


    starPPPLinkStatusRemoteMRU   OBJECT-TYPE
           SYNTAX    INTEGER(1..2147483647)
           ACCESS    read-only
           STATUS    mandatory
           DESCRIPTION
                     "The current value of the MRU for the remote
                     PPP Entity. This value is the MRU that the
                     local entity is using when sending packets to
                     the remote PPP entity. The value of this object
                     is meaningful only when the link has reached
                     the open state (ifOperStatus is up)."
           ::= { starPPPLinkStatusEntry 7 }

      
    starPPPLinkStatusLocalToPeerACCMap   OBJECT-TYPE
           SYNTAX    OCTET STRING (SIZE (0..4))
           ACCESS    read-only
           STATUS    mandatory
           DESCRIPTION
                     "The current value of the ACC Map used for
                     sending packets from the local PPP entity to
                     the remote PPP entity. The value of this object
                     is meaningful only when the link has reached
                     the open state (ifOperStatus is up)."
           ::= { starPPPLinkStatusEntry 8 }


    starPPPLinkStatusPeerToLocalACCMap   OBJECT-TYPE
           SYNTAX    OCTET STRING (SIZE (0..4))
           ACCESS    read-only
           STATUS    mandatory
           DESCRIPTION
                     "The ACC Map used by the remote PPP entity when
                     transmitting packets to the local PPP entity.
                     The value of this object is meaningful only
                     when the link has reached the open state
                     (ifOperStatus is up)."
           ::= { starPPPLinkStatusEntry 9 }

     
    starPPPLinkStatusLocalToRemotePC OBJECT-TYPE
           SYNTAX    INTEGER {
                     enabled(1),
                     disabled(2)
                }
           ACCESS    read-only
           STATUS    mandatory
           DESCRIPTION
                     "Indicates whether the local PPP entity will
                     use Protocol Compression when transmitting
                     packets to the remote PPP entity. The value of
                     this object is meaningful only when the link
                     has reached the open state (ifOperStatus is
                     up)."
           ::= { starPPPLinkStatusEntry 10 }

 
    starPPPLinkStatusRemoteToLocalPC OBJECT-TYPE
           SYNTAX    INTEGER {
                     enabled(1),
                     disabled(2)
                }
           ACCESS    read-only
           STATUS    mandatory
           DESCRIPTION
                     "Indicates whether the remote PPP entity will
                     use Protocol Compression when transmitting
                     packets to the local PPP entity. The value of
                     this object is meaningful only when the link
                     has reached the open state (ifOperStatus is
                     up)."
           ::= { starPPPLinkStatusEntry 11 }


    starPPPLinkStatusLocalToRemoteACFC   OBJECT-TYPE
           SYNTAX    INTEGER {
                     enabled(1),
                     disabled(2)
                }
           ACCESS    read-only
           STATUS    mandatory
           DESCRIPTION
                     "Indicates whether the local PPP entity will
                     use Address and Control Compression when
                     transmitting packets to the remote PPP entity.
                     The value of this object is meaningful only
                     when the link has reached the open state
                     (ifOperStatus is up)."
           ::= { starPPPLinkStatusEntry 12 }


    starPPPLinkStatusRemoteToLocalACFC   OBJECT-TYPE
           SYNTAX    INTEGER {
                     enabled(1),
                     disabled(2)
                }
           ACCESS    read-only
           STATUS    mandatory
           DESCRIPTION
                     "Indicates whether the remote PPP entity will
                     use Address and Control Compression when
                     transmitting packets to the local PPP entity.
                     The value of this object is meaningful only
                     when the link has reached the open state
                     (ifOperStatus is up)."
           ::= { starPPPLinkStatusEntry 13 }


    starPPPLinkStatusTransmitFcsSize   OBJECT-TYPE
           SYNTAX    INTEGER (0..128)
           ACCESS    read-only
           STATUS    mandatory
           DESCRIPTION
                     "The size of the Frame Check Sequence (FCS) in
                     bits that the local node will generate when
                     sending packets to the remote node. The value
                     of this object is meaningful only when the link
                     has reached the open state (ifOperStatus is
                     up)."
           ::= { starPPPLinkStatusEntry 14 }


    starPPPLinkStatusReceiveFcsSize   OBJECT-TYPE
           SYNTAX    INTEGER (0..128)
           ACCESS    read-only
           STATUS    mandatory
           DESCRIPTION
                     "The size of the Frame Check Sequence (FCS) in
                     bits that the remote node will generate when
                     sending packets to the local node. The value of
                     this object is meaningful only when the link
                     has reached the open state (ifOperStatus is
                     up)."
           ::= { starPPPLinkStatusEntry 15 }


    starPPPLqrTable   OBJECT-TYPE
           SYNTAX    SEQUENCE OF StarPPPLqrEntry
           ACCESS    not-accessible
           STATUS    mandatory
           DESCRIPTION
                     "Table containing the LQR parameters and
                     statistics for the local PPP entity."
           ::= { starPPP 2 }


    starPPPLqrEntry   OBJECT-TYPE
           SYNTAX    StarPPPLqrEntry
           ACCESS    not-accessible
           STATUS    mandatory
           DESCRIPTION
                     "LQR information for a particular PPP link. A
                     PPP link will have an entry in this table if
                     and only if LQR Quality Monitoring has been
                     successfully negotiated for said link."
           INDEX     { starSlotIndex, starPortIndex }
           ::= { starPPPLqrTable 1 }


    StarPPPLqrEntry ::= SEQUENCE {
           starPPPLqrQuality
                INTEGER,
           starPPPLqrInGoodOctets
                Counter,
           starPPPLqrLocalPeriod
                INTEGER,
           starPPPLqrRemotePeriod
                INTEGER,
           starPPPLqrOutLQRs
                Counter,
           starPPPLqrInLQRs
                Counter
      }

    starPPPLqrQuality   OBJECT-TYPE
           SYNTAX    INTEGER {
                     good(1),
                     bad(2),
                     not-determined(3)
                }
           ACCESS    read-only
           STATUS    mandatory
           DESCRIPTION
                     "The current quality of the link as declared by
                     the local PPP entity's Link-Quality Management
                     modules. No effort is made to define good or
                     bad, nor the policy used to determine it. The
                     not-determined value indicates that the entity
                     does not actually evaluate the link's quality.
                     This value is used to disambiguate the
                     `determined to be good' case from the `no
                     determination made and presumed to be good'
                     case."
           ::= { starPPPLqrEntry 1 }


    starPPPLqrInGoodOctets   OBJECT-TYPE
           SYNTAX    Counter
           ACCESS    read-only
           STATUS    mandatory
           DESCRIPTION
                     "The LQR InGoodOctets counter for this link."
           REFERENCE
                     "Section 2.2, Counters, of RFC1333."
           ::= { starPPPLqrEntry 2 }


    starPPPLqrLocalPeriod   OBJECT-TYPE
           SYNTAX    INTEGER(1..2147483647)
           ACCESS    read-only
           STATUS    mandatory
           DESCRIPTION
                     "The LQR reporting period, in hundredths of a
                     second that is in effect for the local PPP
                     entity."
           REFERENCE
                     "Section 2.5, Configuration Option Format, of
                     RFC1333."
           ::= { starPPPLqrEntry 3 }


    starPPPLqrRemotePeriod   OBJECT-TYPE
           SYNTAX    INTEGER(1..2147483647)
           ACCESS    read-only
           STATUS    mandatory
           DESCRIPTION
                     "The LQR reporting period, in hundredths of a
                     second, that is in effect for the remote PPP
                     entity."
           REFERENCE
                     "Section 2.5, Configuration Option Format, of
                     RFC1333."
           ::= { starPPPLqrEntry 4 }

    starPPPLqrOutLQRs   OBJECT-TYPE
           SYNTAX    Counter
           ACCESS    read-only
           STATUS    mandatory
           DESCRIPTION
                     "The value of the OutLQRs counter on the local
                     node for the link identified by ifIndex."
           REFERENCE
                     "Section 2.2, Counters, of RFC1333."
           ::= { starPPPLqrEntry 5 }


    starPPPLqrInLQRs   OBJECT-TYPE
           SYNTAX    Counter
           ACCESS    read-only
           STATUS    mandatory
           DESCRIPTION
                     "The value of the InLQRs counter on the local
                     node for the link identified by ifIndex."
           REFERENCE
                     "Section 2.2, Counters, of RFC1333."
           ::= { starPPPLqrEntry 6 }



    starPPPIpTable   OBJECT-TYPE
           SYNTAX    SEQUENCE OF StarPPPIpEntry
           ACCESS    not-accessible
           STATUS    mandatory
           DESCRIPTION
                     "Table containing the IP parameters and
                     statistics for the local PPP entity."
           ::= { starPPP 3 }


    starPPPIpEntry   OBJECT-TYPE
           SYNTAX    StarPPPIpEntry
           ACCESS    not-accessible
           STATUS    mandatory
           DESCRIPTION
                     "IPCP status information for a particular PPP
                     link."
           INDEX     { starSlotIndex, starPortIndex }
           ::= { starPPPIpTable 1 }


    StarPPPIpEntry ::= SEQUENCE {
           starPPPIpOperStatus
                INTEGER,
           starPPPIpLocalToRemoteCP
                INTEGER,
           starPPPIpRemoteToLocalCP
                INTEGER,
           starPPPIpRemoteMaxSlotId
                INTEGER,
           starPPPIpLocalMaxSlotId
                INTEGER
      }

	starPPPIpOperStatus   OBJECT-TYPE
           SYNTAX    INTEGER {opened(1), not-opened(2)}
           ACCESS    read-only
           STATUS    mandatory
           DESCRIPTION
                     "The operational status of the IP network
                     protocol. If the value of this object is up
                     then the finite state machine for the IP
                     network protocol has reached the Opened state."
           ::= { starPPPIpEntry 1 }


    starPPPIpLocalToRemoteCP   OBJECT-TYPE
           SYNTAX    INTEGER {
                     none(1),
                     vj-tcp(2)
                }
           ACCESS    read-only
           STATUS    mandatory
           DESCRIPTION
                     "The IP compression protocol that the local
                     PPP-IP entity uses when sending packets to the
                     remote PPP-IP entity. The value of this object
                     is meaningful only when the link has reached
                     the open state (starPPPIpOperStatus is opened)."
           ::= { starPPPIpEntry 2 }


    starPPPIpRemoteToLocalCP   OBJECT-TYPE
           SYNTAX    INTEGER {
                     none(1),
                     vj-tcp(2)
                }
           ACCESS    read-only
           STATUS    mandatory
           DESCRIPTION
                     "The IP compression protocol that the remote
                     PPP-IP entity uses when sending packets to the
                     local PPP-IP entity. The value of this object
                     is meaningful only when the link has reached
                     the open state (starPPPIpOperStatus is opened)."
           ::= { starPPPIpEntry 3 }

    starPPPIpRemoteMaxSlotId   OBJECT-TYPE
           SYNTAX    INTEGER(0..255)
           ACCESS    read-only
           STATUS    mandatory
           DESCRIPTION
                     "The Max-Slot-Id parameter that the remote node
                     has advertised and that is in use on the link.
                     If vj-tcp header compression is not in use on
                     the link then the value of this object shall be
                     0. The value of this object is meaningful only
                     when the link has reached the open state
                     (starPPPIpOperStatus is opened)."
           ::= { starPPPIpEntry 4 }


    starPPPIpLocalMaxSlotId   OBJECT-TYPE
           SYNTAX    INTEGER(0..255)
           ACCESS    read-only
           STATUS    mandatory
           DESCRIPTION
                     "The Max-Slot-Id parameter that the local node
                     has advertised and that is in use on the link.
                     If vj-tcp header compression is not in use on
                     the link then the value of this object shall be
                     0. The value of this object is meaningful only
                     when the link has reached the open state
                     (starPPPIpOperStatus is opened)."
           ::= { starPPPIpEntry 5 }

	-----------------------------------------------------------------------
	-- Star System Vpl Statistics Table
	-----------------------------------------------------------------------
	starVplStatsTable		OBJECT-TYPE
		SYNTAX  SEQUENCE OF VplStatsEntry
		ACCESS  not-accessible
		STATUS  mandatory
		DESCRIPTION
			"This table contains statistics gathered on a specific
			port and is indexed by Slot number, Port number and
			VPI" 
		::= { starConn 1 }

	starVplStatsEntry	OBJECT-TYPE
		SYNTAX	VplStatsEntry
		ACCESS	not-accessible
		STATUS	mandatory
		DESCRIPTION
			""
		INDEX   { starVplSlotIndex,  starVplPortIndex,  starVplConnRole,
				  starVplSourceNode, starVplSourceSlot, starVplSourcePort, 
				  starVplSourceVpi,  starVplSourceVci }
		::= { starVplStatsTable 1 }
 
	VplStatsEntry ::=
		SEQUENCE {
			starVplSlotIndex			INTEGER,
			starVplPortIndex			INTEGER,
			starVplSourceNode			INTEGER,
			starVplSourceSlot			INTEGER,
			starVplSourcePort			INTEGER,
			starVplSourceVpi			INTEGER,
			starVplSourceVci			INTEGER,
			starVplConnRole				INTEGER,
			starVplStatsTimeStamp		Counter,
			starVplNumOAMInvalidCRC		Counter,
			starVplRtCongestedState		INTEGER,
			starVplRtNewVpi				Counter,
			starVplRtCellsRxCount		Counter,
			starVplRtCellsDroppedCount  Counter,
			starVplRtCellsCongCount		Counter,
			starVplUpcGcra0ViolCount	Counter,
			starVplUpcGcra1ViolCount	Counter,
			starVplUpcCellsCLP0			Counter,
			starVplUpcTotalCells		Counter,
			starVplUpcTotalOAMCells		Counter
		}
 
	starVplSlotIndex	OBJECT-TYPE
		SYNTAX  INTEGER
		ACCESS  read-only
		STATUS  mandatory
		DESCRIPTION
			""
		::= { starVplStatsEntry 1 }
 
	starVplPortIndex	OBJECT-TYPE
		SYNTAX  INTEGER
		ACCESS  read-only
		STATUS  mandatory
		DESCRIPTION
			""
		::= { starVplStatsEntry 2 }
 
	starVplSourceNode   OBJECT-TYPE
		SYNTAX  INTEGER
		ACCESS  read-only
		STATUS  mandatory
		DESCRIPTION
			""
		::= { starVplStatsEntry 3 }
 
	starVplSourceSlot   OBJECT-TYPE
		SYNTAX  INTEGER
		ACCESS  read-only
		STATUS  mandatory
		DESCRIPTION
			""
		::= { starVplStatsEntry 4 }
 
	starVplSourcePort   OBJECT-TYPE
		SYNTAX  INTEGER
		ACCESS  read-only
		STATUS  mandatory
		DESCRIPTION
			""
		::= { starVplStatsEntry 5 }
 
	starVplSourceVpi	OBJECT-TYPE
		SYNTAX  INTEGER
		ACCESS  read-only
		STATUS  mandatory
		DESCRIPTION
			""
		::= { starVplStatsEntry 6 }
 
	starVplSourceVci	OBJECT-TYPE
		SYNTAX  INTEGER
		ACCESS  read-only
		STATUS  mandatory
		DESCRIPTION
			""
		::= { starVplStatsEntry 7 }
 
	starVplConnRole	OBJECT-TYPE
		SYNTAX  INTEGER
		ACCESS  read-only
		STATUS  mandatory
		DESCRIPTION
			""
		::= { starVplStatsEntry 8 }
 
	starVplStatsTimeStamp   OBJECT-TYPE
		SYNTAX  Counter
		ACCESS  read-only
		STATUS  mandatory
		DESCRIPTION
			""
		::= { starVplStatsEntry 9 }
 
	starVplNumOAMInvalidCRC OBJECT-TYPE
		SYNTAX  Counter
		ACCESS  read-only
		STATUS  mandatory
		DESCRIPTION
			"Invalid CRC OAM cell count"
		::= { starVplStatsEntry 10 }
 
	starVplRtCongestedState OBJECT-TYPE
		SYNTAX  INTEGER {
			congested(1),
			notcongested(2)
		}
		ACCESS  read-only
		STATUS  mandatory
		DESCRIPTION
			"Congested state for this VP"
		::= { starVplStatsEntry 11 }
 
	starVplRtNewVpi OBJECT-TYPE
		SYNTAX  Counter
		ACCESS  read-only
		STATUS  mandatory
		DESCRIPTION
			"VPI value to be used when translation is enabled"
		::= { starVplStatsEntry 12 }
 
	starVplRtCellsRxCount   OBJECT-TYPE
		SYNTAX  Counter
		ACCESS  read-only
		STATUS  mandatory
		DESCRIPTION
			"Number of cells received in RT level for this VP"
		::= { starVplStatsEntry 13 }
 
	starVplRtCellsDroppedCount  OBJECT-TYPE
		SYNTAX  Counter
		ACCESS  read-only
		STATUS  mandatory
		DESCRIPTION
			"Number of cells dropped in RT level for this VP"
		::= { starVplStatsEntry 14 }
 
	starVplRtCellsCongCount OBJECT-TYPE
		SYNTAX  Counter
		ACCESS  read-only
		STATUS  mandatory
		DESCRIPTION
			"Number of cells congested in RT level for this VP"
		::= { starVplStatsEntry 15 }
 
	starVplUpcGcra0ViolCount	OBJECT-TYPE
		SYNTAX  Counter
		ACCESS  read-only
		STATUS  mandatory
		DESCRIPTION
			"Number of cells tagged or dropped by Gcra0 algorithm"
		::= { starVplStatsEntry 16 }
 
	starVplUpcGcra1ViolCount	OBJECT-TYPE
		SYNTAX  Counter
		ACCESS  read-only
		STATUS  mandatory
		DESCRIPTION
			"Number of cells tagged or dropped by Gcra1 algorithm"
		::= { starVplStatsEntry 17 }
 
	starVplUpcCellsCLP0 OBJECT-TYPE
		SYNTAX  Counter
		ACCESS  read-only
		STATUS  mandatory
		DESCRIPTION
			"Number of cells received with CLP0 in UPC level for
			 this VP"
		::= { starVplStatsEntry 18 }
 
	starVplUpcTotalCells	OBJECT-TYPE
		SYNTAX  Counter
		ACCESS  read-only
		STATUS  mandatory
		DESCRIPTION
			"Total cells received by this VP"
		::= { starVplStatsEntry 19 }
 
	starVplUpcTotalOAMCells OBJECT-TYPE
		SYNTAX  Counter
		ACCESS  read-only
		STATUS  mandatory
		DESCRIPTION
			"Total OAM cells passed through by this VP"
		::= { starVplStatsEntry 20 }

	-----------------------------------------------------------------------
	-- Star System Vcl Statistics Table
	-----------------------------------------------------------------------
	starVclStatsTable	   OBJECT-TYPE
		SYNTAX  SEQUENCE OF VclStatsEntry
		ACCESS  not-accessible
		STATUS  mandatory
		DESCRIPTION
			"This table contains statistics gathered on a specific
			 port and is indexed by Slot number, Port number,
			 VPI and VCI,DLCI,Timeslot,Leafno"
		::= { starConn 2 }
 
	starVclStatsEntry   OBJECT-TYPE
		SYNTAX  VclStatsEntry
		ACCESS  not-accessible
		STATUS  mandatory
		DESCRIPTION
			""
		INDEX   { starVclSlotIndex,  starVclPortIndex,  starVclConnRole,
                  starVclSourceNode, starVclSourceSlot, starVclSourcePort,
                  starVclSourceVpi,  starVclSourceVci,  starVclSourceDlci,
                  starVclSourceTimeslot, starVclSourceIftype, starVclSourceLeafno }
		::= { starVclStatsTable 1 }
 
	VclStatsEntry ::=
		SEQUENCE {
			starVclSlotIndex			INTEGER,
			starVclPortIndex			INTEGER,
			starVclSourceNode			INTEGER,
			starVclSourceSlot			INTEGER,
			starVclSourcePort			INTEGER,
			starVclSourceVpi			INTEGER,
			starVclSourceVci			INTEGER,
			starVclConnRole				INTEGER,
-- STAda02930 HYOUNG 2000.9.22
--			starVclSourceDlci			INTEGER,
--			starVclSourceTimeslot		INTEGER,
--			starVclSourceIftype			INTEGER,
--			starVclSourceLeafno			INTEGER,
			starVclStatsTimeStamp		Counter,
			starVclNumOAMInvalidCRC		Counter,
			starVclRtCongestedState		INTEGER,
			starVclRtLastAal5State		Counter,
			starVclRtNewVpi				Counter,
			starVclRtNewVci				Counter,
			starVclRtCellsRxCount	   Counter,
			starVclRtCellsDroppedCount	Counter,
			starVclRtCellsCongCount		Counter,
			starVclUpcGcra0ViolCount	Counter,
			starVclUpcGcra1ViolCount	Counter,
			starVclUpcCellsCLP0			Counter,
			starVclUpcTotalCells		Counter,
			starVclUpcTotalOAMCells		Counter,
-- STAda02930 HYOUNG 2000.9.22
			starVclSourceDlci			INTEGER,
			starVclSourceTimeslot		INTEGER,
			starVclSourceIftype			INTEGER,
			starVclSourceLeafno			INTEGER
		}
 
	starVclSlotIndex			OBJECT-TYPE
		SYNTAX  INTEGER
		ACCESS  read-only
		STATUS  mandatory
		DESCRIPTION
			""
		::= { starVclStatsEntry 1 }
 
	starVclPortIndex			OBJECT-TYPE
		SYNTAX  INTEGER
		ACCESS  read-only
		STATUS  mandatory
		DESCRIPTION
			""
		::= { starVclStatsEntry 2 }
 
	starVclSourceNode		   OBJECT-TYPE
		SYNTAX  INTEGER
		ACCESS  read-only
		STATUS  mandatory
		DESCRIPTION
			""
		::= { starVclStatsEntry 3 }
 
	starVclSourceSlot		   OBJECT-TYPE
		SYNTAX  INTEGER
		ACCESS  read-only
		STATUS  mandatory
		DESCRIPTION
			""
		::= { starVclStatsEntry 4 }
 
	starVclSourcePort		   OBJECT-TYPE
		SYNTAX  INTEGER
		ACCESS  read-only
		STATUS  mandatory
		DESCRIPTION
			""
		::= { starVclStatsEntry 5 }
 
	starVclSourceVpi			OBJECT-TYPE
		SYNTAX  INTEGER
		ACCESS  read-only
		STATUS  mandatory
		DESCRIPTION
			""
		::= { starVclStatsEntry 6 }
 
	starVclSourceVci			OBJECT-TYPE
		SYNTAX  INTEGER
		ACCESS  read-only
		STATUS  mandatory
		DESCRIPTION
			""
		::= { starVclStatsEntry 7 }
 
	starVclConnRole			OBJECT-TYPE
		SYNTAX  INTEGER
		ACCESS  read-only
		STATUS  mandatory
		DESCRIPTION
			""
		::= { starVclStatsEntry 8 }

	starVclStatsTimeStamp		   OBJECT-TYPE
		SYNTAX  Counter
		ACCESS  read-only
		STATUS  mandatory
		DESCRIPTION
			"This object indicates the time stamp"
		::= { starVclStatsEntry 9 }
 
	starVclNumOAMInvalidCRC OBJECT-TYPE
		SYNTAX  Counter
		ACCESS  read-only
		STATUS  mandatory
		DESCRIPTION
			"Invalid CRC OAM cell count"
		::= { starVclStatsEntry 10 }
 
	starVclRtCongestedState OBJECT-TYPE
		SYNTAX  INTEGER {
			notcongested(1),
			congested(2)
		}
		ACCESS  read-only
		STATUS  mandatory
		DESCRIPTION
			"Congested state for this VP"
		::= { starVclStatsEntry 11 }
 
	starVclRtLastAal5State  OBJECT-TYPE
		SYNTAX  Counter
		ACCESS  read-only
		STATUS  mandatory
		DESCRIPTION
			"Current Aal5 state for last cell"
		::= { starVclStatsEntry 12 }
 
	starVclRtNewVpi OBJECT-TYPE
		SYNTAX  Counter
		ACCESS  read-only
		STATUS  mandatory
		DESCRIPTION
			"VPI value to be used when translation is enabled"
		::= { starVclStatsEntry 13 }
 
	starVclRtNewVci OBJECT-TYPE
		SYNTAX  Counter
		ACCESS  read-only
		STATUS  mandatory
		DESCRIPTION
			"VCI value to be used when translation is enabled"
		::= { starVclStatsEntry 14 }
 
	starVclRtCellsRxCount   OBJECT-TYPE
		SYNTAX  Counter
		ACCESS  read-only
		STATUS  mandatory
		DESCRIPTION
			"Number of cells received in RT level for this VP/VC"
		::= { starVclStatsEntry 15 }
 
	starVclRtCellsDroppedCount  OBJECT-TYPE
		SYNTAX  Counter
		ACCESS  read-only
		STATUS  mandatory
		DESCRIPTION
			"Number of cells dropped in RT level for this VP/VC"
		::= { starVclStatsEntry 16 }
 
	starVclRtCellsCongCount OBJECT-TYPE
		SYNTAX  Counter
		ACCESS  read-only
		STATUS  mandatory
		DESCRIPTION
			"Number of cells congested in RT level for this VP/VC"
		::= { starVclStatsEntry 17 }
 
	starVclUpcGcra0ViolCount	OBJECT-TYPE
		SYNTAX  Counter
		ACCESS  read-only
		STATUS  mandatory
		DESCRIPTION
			"Number of cells tagged or dropped by Gcra0 algorithm"
		::= { starVclStatsEntry 18 }
 
	starVclUpcGcra1ViolCount	OBJECT-TYPE
		SYNTAX  Counter
		ACCESS  read-only
		STATUS  mandatory
		DESCRIPTION
			"Number of cells tagged or dropped by Gcra1 algorithm"
		::= { starVclStatsEntry 19 }
 
	starVclUpcCellsCLP0 OBJECT-TYPE
		SYNTAX  Counter
		ACCESS  read-only
		STATUS  mandatory
		DESCRIPTION
			"Number of cells received with CLP0 in UPC level for
			 this VP/VC"
		::= { starVclStatsEntry 20 }
 
	starVclUpcTotalCells	OBJECT-TYPE
		SYNTAX  Counter
		ACCESS  read-only
		STATUS  mandatory
		DESCRIPTION
			"Total cells received by this VP/VC"
		::= { starVclStatsEntry 21 }
 
	starVclUpcTotalOAMCells OBJECT-TYPE
		SYNTAX  Counter
		ACCESS  read-only
		STATUS  mandatory
		DESCRIPTION
			"Total OAM cells passed through by this VP/VC"
		::= { starVclStatsEntry 22 }

--	STAda02930
--	HYOUNG 2000.9.22
--	For Index matching with NMS

    starVclSourceDlci          OBJECT-TYPE
        SYNTAX  INTEGER
        ACCESS  read-only
        STATUS  mandatory
        DESCRIPTION
            ""
        ::= { starVclStatsEntry 23 }
 
    starVclSourceTimeslot          OBJECT-TYPE
        SYNTAX  INTEGER
        ACCESS  read-only
        STATUS  mandatory
        DESCRIPTION
            ""
        ::= { starVclStatsEntry 24 }
 
    starVclSourceIftype          OBJECT-TYPE
        SYNTAX  INTEGER
        ACCESS  read-only
        STATUS  mandatory
        DESCRIPTION
            ""
        ::= { starVclStatsEntry 25 }
 
    starVclSourceLeafno          OBJECT-TYPE
        SYNTAX  INTEGER
        ACCESS  read-only
        STATUS  mandatory
        DESCRIPTION
            ""
        ::= { starVclStatsEntry 26 }
 
	-----------------------------------------------------------------------
	-- Star System Vpi Vci Range Change - HYOUNG 99.4.12
	-----------------------------------------------------------------------
	starVpiRangeTable	  OBJECT-TYPE
		SYNTAX  SEQUENCE OF VpiRangeEntry
		ACCESS  not-accessible
		STATUS  mandatory
		DESCRIPTION
			""
		::= { starConn 3 }
 
	starVpiRangeEntry  OBJECT-TYPE
		SYNTAX  VpiRangeEntry
		ACCESS  not-accessible
		STATUS  mandatory
		DESCRIPTION
			""
		INDEX   { starSlotIndex, starPortIndex, starVpiIndex }
		::= { starVpiRangeTable 1 }
 
	VpiRangeEntry ::=
		SEQUENCE {
			starVpiIndex				INTEGER,
			starVpiVciBitRangeClass		INTEGER,
			starVpiBitRangeValue		INTEGER,
			starVciBitRangeValue		INTEGER,
			starAvailableVpiValue		INTEGER
		}

	starVpiIndex	OBJECT-TYPE
		SYNTAX  INTEGER 
		ACCESS  read-only
		STATUS  mandatory
		DESCRIPTION
			""
		::= { starVpiRangeEntry 1 }

	starVpiVciBitRangeClass	OBJECT-TYPE
		SYNTAX  INTEGER 
		ACCESS  read-write
		STATUS  mandatory
		DESCRIPTION
			""
		::= { starVpiRangeEntry 2 }

	starVpiBitRangeValue	OBJECT-TYPE
		SYNTAX  INTEGER 
		ACCESS  read-only
		STATUS  mandatory
		DESCRIPTION
			""
		::= { starVpiRangeEntry 3 }

	starVciBitRangeValue	OBJECT-TYPE
		SYNTAX  INTEGER 
		ACCESS  read-only
		STATUS  mandatory
		DESCRIPTION
			""
		::= { starVpiRangeEntry 4 }

	starAvailableVpiValue	OBJECT-TYPE
		SYNTAX  INTEGER 
		ACCESS  read-only
		STATUS  mandatory
		DESCRIPTION
			""
		::= { starVpiRangeEntry 5 }

	-----------------------------------------------------------------------
	-- Star System Loopback Control Table
	-----------------------------------------------------------------------
	starLoopbackCtrTable		OBJECT-TYPE
		SYNTAX  SEQUENCE OF LoopbackCtrEntry
		ACCESS  not-accessible
		STATUS  mandatory
		DESCRIPTION
			"This table contains objects that allow an NMS
			 operator to setup and start a loopback test" 
		::= { starConn 5 }

	starLoopbackCtrEntry	OBJECT-TYPE
		SYNTAX	LoopbackCtrEntry
		ACCESS	not-accessible
		STATUS	mandatory
		DESCRIPTION
			""
		INDEX	{ starSlotIndex }
		::= { starLoopbackCtrTable 1 }

	LoopbackCtrEntry ::=
		SEQUENCE {
			starLoopbackCtrPortIndex			INTEGER,
			starLoopbackCtrVpi					INTEGER,
			starLoopbackCtrVci					INTEGER,
			starLoopbackCtrDeviceId				INTEGER,
			starLoopbackCtrType					INTEGER,
			starLoopbackCtrEndType				INTEGER,
			starLoopbackCtrTxCellNo				INTEGER,
			starLoopbackCtrTimetoWait			INTEGER,
			starLoopbackCtrSetup				INTEGER,
			starLoopbackCtrMethod				INTEGER,
			starLoopbackCtrGeneration			INTEGER,
			starLoopbackCtrInputType			INTEGER,
			starLoopbackCtrPdhNum				INTEGER,
			starLoopbackCtrCellSpeed			INTEGER,
			starLoopbackCtrGCIDNeId				INTEGER,
			starLoopbackCtrGCIDSlotIndex		INTEGER,
			starLoopbackCtrGCIDPortIndex		INTEGER,
			starLoopbackCtrGCIDModuleIfType		INTEGER,
			starLoopbackCtrGCIDVpi				INTEGER,
			starLoopbackCtrGCIDVci				INTEGER,
			starLoopbackCtrGCIDDlci				INTEGER,
			starLoopbackCtrGCIDTimeSlot			INTEGER,
			starLoopbackCtrGCIDLeafNum			INTEGER,
			starLoopbackCtrAssignedSessionNo	INTEGER,
			starLoopbackCtrArea					INTEGER,
			starLoopbackCtrChannelType			INTEGER,
			starLoopbackCtrLastSetupResult		INTEGER,
			starLoopbackCtrPortNum				INTEGER,
			starLoopbackCtrGenCellType			INTEGER
		}

	starLoopbackCtrPortIndex	OBJECT-TYPE
		SYNTAX	INTEGER
		ACCESS	read-write
		STATUS	mandatory
		DESCRIPTION
			"Port number for this loopback request"
		::= { starLoopbackCtrEntry 1 }

	starLoopbackCtrVpi	OBJECT-TYPE
		SYNTAX	INTEGER
		ACCESS	read-write
		STATUS	mandatory
		DESCRIPTION
			"VPI for this loopback request"
		::= { starLoopbackCtrEntry 2 }

	starLoopbackCtrVci	OBJECT-TYPE
		SYNTAX	INTEGER
		ACCESS	read-write
		STATUS	mandatory
		DESCRIPTION
			"VCI for this loopback request"
		::= { starLoopbackCtrEntry 3 }

	starLoopbackCtrDeviceId	OBJECT-TYPE
		SYNTAX	INTEGER
		ACCESS	read-write
		STATUS	mandatory
		DESCRIPTION
			"Device Id for the specified chip type"
		::= { starLoopbackCtrEntry 4 }

	starLoopbackCtrType	OBJECT-TYPE
		SYNTAX	INTEGER {
			oam-f4(1),
			oam-f5(2),
			phyline(3),
			physsu(4)
		}
		ACCESS	read-write
		STATUS	mandatory
		DESCRIPTION
			"Type of loopback, OAM loopback F4, F5 or physical
			 level loopback"
		::= { starLoopbackCtrEntry 5 }

	starLoopbackCtrEndType	OBJECT-TYPE
		SYNTAX	INTEGER {
			segment(1),
			connection-end(2),
			intermediate(3)
		}
		ACCESS	read-write
		STATUS	mandatory
		DESCRIPTION
			"Loopback end type"
		::= { starLoopbackCtrEntry 6 }

	starLoopbackCtrTxCellNo	OBJECT-TYPE
		SYNTAX	INTEGER 
		ACCESS	read-write
		STATUS	mandatory
		DESCRIPTION
			"Cell numbers to send request for loopback test"
		::= { starLoopbackCtrEntry 7 }

	starLoopbackCtrTimetoWait	OBJECT-TYPE
		SYNTAX	INTEGER 
		ACCESS	read-write
		STATUS	mandatory
		DESCRIPTION
			"Interval in seconds to wait for the loopbacked cell
			 to arrive after sending"
		::= { starLoopbackCtrEntry 8 }

	starLoopbackCtrSetup	OBJECT-TYPE
		SYNTAX	INTEGER { 
			initrcvphy(1),
			initrcvatm(2),
			initsender(3),
			finishreceiver(4),
			finishsender(5)
		}
		ACCESS	read-write
		STATUS	mandatory
		DESCRIPTION
			"Setup request for specified command.  All parameters
			 related to each command should be preset before 
			 initiating this action"
		::= { starLoopbackCtrEntry 9 }

	starLoopbackCtrMethod 			OBJECT-TYPE
		SYNTAX	INTEGER 
		ACCESS	read-write
		STATUS	mandatory
		DESCRIPTION
			"Defines how cell is to be loopbacked.  This field is
			 only used for the receiver of the loopback"
		::= { starLoopbackCtrEntry 10 }

	starLoopbackCtrGeneration 		OBJECT-TYPE
		SYNTAX	INTEGER 
		ACCESS	read-write
		STATUS	mandatory
		DESCRIPTION
			"Defines how loopback cell is generated.  This field
			 is only used by the sender of the loopback"
		::= { starLoopbackCtrEntry 11 }

	starLoopbackCtrInputType 		OBJECT-TYPE
		SYNTAX	INTEGER {
			gcid(1),
			vcci(2)
		}
		ACCESS	read-write
		STATUS	mandatory
		DESCRIPTION
			"Describes what information will be used to setup the
			 loopback, either all of GCID or Vpi/Vci values"
		::= { starLoopbackCtrEntry 12 }

	starLoopbackCtrPdhNum 			OBJECT-TYPE
		SYNTAX	INTEGER 
		ACCESS	read-write
		STATUS	mandatory
		DESCRIPTION
			"Channel # used for PDH loopbacks"
		::= { starLoopbackCtrEntry 13 }

	starLoopbackCtrCellSpeed 		OBJECT-TYPE
		SYNTAX	INTEGER 
		ACCESS	read-write
		STATUS	mandatory
		DESCRIPTION
			"Future entry for how many cells to be generated per
			 second"
		::= { starLoopbackCtrEntry 14 }

	starLoopbackCtrGCIDNeId 		OBJECT-TYPE
		SYNTAX	INTEGER 
		ACCESS	read-write
		STATUS	mandatory
		DESCRIPTION
			"Node Id from GCID when GCID Input type is selected"
		::= { starLoopbackCtrEntry 15 }

	starLoopbackCtrGCIDSlotIndex 		OBJECT-TYPE
		SYNTAX	INTEGER 
		ACCESS	read-write
		STATUS	mandatory
		DESCRIPTION
			"Slot Id from GCID when GCID Input type is selected"
		::= { starLoopbackCtrEntry 16 }

	starLoopbackCtrGCIDPortIndex 		OBJECT-TYPE
		SYNTAX	INTEGER 
		ACCESS	read-write
		STATUS	mandatory
		DESCRIPTION
			"Port Id from GCID when GCID Input type is selected"
		::= { starLoopbackCtrEntry 17 }

	starLoopbackCtrGCIDModuleIfType 	OBJECT-TYPE
		SYNTAX	INTEGER 
		ACCESS	read-write
		STATUS	mandatory
		DESCRIPTION
			"Module Interface type from GCID when GCID Input type 
			 is selected"
		::= { starLoopbackCtrEntry 18 }

	starLoopbackCtrGCIDVpi 			OBJECT-TYPE
		SYNTAX	INTEGER 
		ACCESS	read-write
		STATUS	mandatory
		DESCRIPTION
			"VPI from GCID when GCID Input type is selected"
		::= { starLoopbackCtrEntry 19 }

	starLoopbackCtrGCIDVci 			OBJECT-TYPE
		SYNTAX	INTEGER 
		ACCESS	read-write
		STATUS	mandatory
		DESCRIPTION
			"VCI from GCID when GCID Input type is selected"
		::= { starLoopbackCtrEntry 20 }

	starLoopbackCtrGCIDDlci 		OBJECT-TYPE
		SYNTAX	INTEGER 
		ACCESS	read-write
		STATUS	mandatory
		DESCRIPTION
			"DLCI from GCID when GCID Input type is selected and
			 board is Frame Relay type"
		::= { starLoopbackCtrEntry 21 }

	starLoopbackCtrGCIDTimeSlot 		OBJECT-TYPE
		SYNTAX	INTEGER 
		ACCESS	read-write
		STATUS	mandatory
		DESCRIPTION
			"Timeslot from GCID when GCID Input type is selected"
		::= { starLoopbackCtrEntry 22 }

	starLoopbackCtrGCIDLeafNum 		OBJECT-TYPE
		SYNTAX	INTEGER 
		ACCESS	read-write
		STATUS	mandatory
		DESCRIPTION
			"Lear number from GCID when GCID Input type is selected"
		::= { starLoopbackCtrEntry 23 }

	starLoopbackCtrAssignedSessionNo	OBJECT-TYPE
		SYNTAX	INTEGER 
		ACCESS	read-write
		STATUS	mandatory
		DESCRIPTION
			"NMS Assigned session number for this loopback request"
		::= { starLoopbackCtrEntry 24 }

	starLoopbackCtrArea 		OBJECT-TYPE
		SYNTAX	INTEGER {
			intraloop(1),
			interloop(2),
			remoteloop(3)
		}
		ACCESS	read-write
		STATUS	mandatory
		DESCRIPTION
			"Method for loopback test"
		::= { starLoopbackCtrEntry 25 }

	starLoopbackCtrChannelType 		OBJECT-TYPE
		SYNTAX	INTEGER {
			userchan(1),
			looptestchan(2)
		}
		ACCESS	read-write
		STATUS	mandatory
		DESCRIPTION
			"Defines the channel to be used for loopback test, 
			 either a User channel or a predefined test channel"
		::= { starLoopbackCtrEntry 26 }

	starLoopbackCtrLastSetupResult	OBJECT-TYPE
		SYNTAX	INTEGER {
			success(1),
			fail(2)
		}
		ACCESS	read-only
		STATUS	mandatory
		DESCRIPTION
			"Success or failure of last setup request"
		::= { starLoopbackCtrEntry 27 }

	starLoopbackCtrPortNum 		OBJECT-TYPE
		SYNTAX	INTEGER 
		ACCESS	read-write
		STATUS	mandatory
		DESCRIPTION
			"port number of loopback test"
		::= { starLoopbackCtrEntry 28 }

	starLoopbackCtrGenCellType	OBJECT-TYPE
		SYNTAX	INTEGER {
			segment(1),
			connection-end(2)
		}
		ACCESS	read-write
		STATUS	mandatory
		DESCRIPTION
			"type of cell to be generated"
		::= { starLoopbackCtrEntry 29 }

	-----------------------------------------------------------------------
	-- Star System Loopback Result Table
	-----------------------------------------------------------------------
	starLoopbackResultTable		OBJECT-TYPE
		SYNTAX  SEQUENCE OF LoopbackResultEntry
		ACCESS  not-accessible
		STATUS  mandatory
		DESCRIPTION
			"This table contains loopback result information and
			 is indexed by Slot number, Device Index and Session
			 number" 
		::= { starConn 6 }

	starLoopbackResultEntry	OBJECT-TYPE
		SYNTAX	LoopbackResultEntry
		ACCESS	not-accessible
		STATUS	mandatory
		DESCRIPTION
			""
		INDEX	{ starSlotIndex }
		::= { starLoopbackResultTable 1 }

	LoopbackResultEntry ::=
		SEQUENCE {
			starLoopbackResultGeneratedCells	INTEGER,
			starLoopbackResultReturnedCells		INTEGER
		}

	starLoopbackResultGeneratedCells	OBJECT-TYPE
		SYNTAX	INTEGER
		ACCESS	read-only
		STATUS	mandatory
		DESCRIPTION
			"Number of generated cells for loopback test at this
			 session"
		::= { starLoopbackResultEntry 1 }

	starLoopbackResultReturnedCells	OBJECT-TYPE
		SYNTAX	INTEGER
		ACCESS	read-only
		STATUS	mandatory
		DESCRIPTION
			"Number of returned cells for loopback test at this
			 session"
		::= { starLoopbackResultEntry 2 }

	-----------------------------------------------------------------------
	-- Star System Performance Monitor Control Table
	-----------------------------------------------------------------------
	starPmCtrTable		OBJECT-TYPE
		SYNTAX  SEQUENCE OF PmCtrEntry
		ACCESS  not-accessible
		STATUS  mandatory
		DESCRIPTION
			"This table allows an NMS operator to setup a 
			 Performance Monitoring session for a specific device
			 and is indexed by Slot number" 
		::= { starConn 7 }

	starPmCtrEntry	OBJECT-TYPE
		SYNTAX	PmCtrEntry
		ACCESS	not-accessible
		STATUS	mandatory
		DESCRIPTION
			""
		INDEX	{ starSlotIndex }
		::= { starPmCtrTable 1 }

	PmCtrEntry ::=
		SEQUENCE {
			starPmCtrUpcId					INTEGER,
			starPmCtrVpi					INTEGER,
			starPmCtrVci					INTEGER,
			starPmCtrSegmentType			INTEGER,
			starPmCtrNodeType				INTEGER,
			starPmCtrBlockSize				INTEGER,
			starPmCtrPmCellClp				INTEGER,
			starPmCtrBackRptGen				INTEGER,
			starPmCtrActivate				INTEGER,
			starPmCtrStart					INTEGER,
			starPmCtrLastAssignedSession	INTEGER
		}

	starPmCtrUpcId	OBJECT-TYPE
		SYNTAX	INTEGER
		ACCESS	read-write
		STATUS	mandatory
		DESCRIPTION
			"UPC Device id for Performance Monitor control"
		::= { starPmCtrEntry 1 }

	starPmCtrVpi	OBJECT-TYPE
		SYNTAX	INTEGER
		ACCESS	read-write
		STATUS	mandatory
		DESCRIPTION
			"VPI for Performance Monitor control"
		::= { starPmCtrEntry 2 }

	starPmCtrVci	OBJECT-TYPE
		SYNTAX	INTEGER
		ACCESS	read-write
		STATUS	mandatory
		DESCRIPTION
			"VCI for Performance Monitor control"
		::= { starPmCtrEntry 3 }

	starPmCtrSegmentType	OBJECT-TYPE
		SYNTAX	INTEGER {
			segmentvpc(1),
			end-to-endvpc(2),
			segmentvcc(3),
			end-to-endvcc(4)
		}
		ACCESS	read-write
		STATUS	mandatory
		DESCRIPTION
			"Segment type for Performance Monitor control"
		::= { starPmCtrEntry 4 }

	starPmCtrNodeType	OBJECT-TYPE
		SYNTAX	INTEGER {
			orignode(1),
			termnode(2)
		}
		ACCESS	read-write
		STATUS	mandatory
		DESCRIPTION
			"Node type (Origin or Termination) for Performance 
			 Monitor control"
		::= { starPmCtrEntry 5 }

	starPmCtrBlockSize	OBJECT-TYPE
		SYNTAX	INTEGER
		ACCESS	read-write
		STATUS	mandatory
		DESCRIPTION
			"Block size of Performance Monitoring"
		::= { starPmCtrEntry 6 }

	starPmCtrPmCellClp	OBJECT-TYPE
		SYNTAX	INTEGER {
			clp0(0),
			clp1(1)
		}
		ACCESS	read-write
		STATUS	mandatory
		DESCRIPTION
			"value of Clp in Performance Monitoring"
		::= { starPmCtrEntry 7 }

	starPmCtrBackRptGen	OBJECT-TYPE
		SYNTAX	INTEGER {
			nobwgr(0),
 			bwgrGen(1)
		}
		ACCESS	read-write
		STATUS	mandatory
		DESCRIPTION
			""
		::= { starPmCtrEntry 8 }

	starPmCtrActivate	OBJECT-TYPE
		SYNTAX	INTEGER {
			activate(1),
			deactivate(2)
		}
		ACCESS	read-write
		STATUS	mandatory
		DESCRIPTION
			"Status of activate Performance Monitor.  Used by NMS
			 operator to activate/deactivate a Performance
			 Monitoring session"
		::= { starPmCtrEntry 9 }

	starPmCtrStart	OBJECT-TYPE
		SYNTAX	INTEGER {
			start(1),
			stop(2)
		}
		ACCESS	read-write
		STATUS	mandatory
		DESCRIPTION
			"Starts/Stops a Performance Monitoring session"
		::= { starPmCtrEntry 10 }

	starPmCtrLastAssignedSession	OBJECT-TYPE
		SYNTAX	INTEGER
		ACCESS	read-only
		STATUS	mandatory
		DESCRIPTION
			"Performance Monitoring session number assigned by
			 the last PM activate request"
		::= { starPmCtrEntry 11 }

	-----------------------------------------------------------------------
	-- Star System Performance Monitor Table
	-----------------------------------------------------------------------
	starPmTable		OBJECT-TYPE
		SYNTAX  SEQUENCE OF PmEntry
		ACCESS  not-accessible
		STATUS  mandatory
		DESCRIPTION
			"This table contains Performance Monitoring result
			 information and is indexed by Slot number, Device
			 index and Session number" 
		::= { starConn 8 }

	starPmEntry	OBJECT-TYPE
		SYNTAX	PmEntry
		ACCESS	not-accessible
		STATUS	mandatory
		DESCRIPTION
			""
		INDEX	{ starSlotIndex, starPmCtrUpcId, starPmCtrLastAssignedSession}
		::= { starPmTable 1 }

	PmEntry ::=
		SEQUENCE {
			starPmTotalCellClp0Count		INTEGER,
			starPmTotalCellClp01Count		INTEGER,
			starPmLostCellClp0Count			INTEGER,
			starPmLostCellClp01Count		INTEGER,
			starPmErroredCellCount			INTEGER,
			starPmMisinsertedCellCount		INTEGER,
			starPmSeverelyErroredBlockCount	INTEGER
		}

	starPmTotalCellClp0Count OBJECT-TYPE
		SYNTAX	INTEGER
		ACCESS	read-only
		STATUS	mandatory
		DESCRIPTION
			"Total number of CLPO cell count for this PM Session"
		::= { starPmEntry 1 }

	starPmTotalCellClp01Count OBJECT-TYPE
		SYNTAX	INTEGER
		ACCESS	read-only
		STATUS	mandatory
		DESCRIPTION
			"Total number of CLPO1 cell count for this PM Session"
		::= { starPmEntry 2 }

	starPmLostCellClp0Count	OBJECT-TYPE
		SYNTAX	INTEGER
		ACCESS	read-only
		STATUS	mandatory
		DESCRIPTION
			"Number of CLP0 lost cells for this PM session"
		::= { starPmEntry 3 }

	starPmLostCellClp01Count	OBJECT-TYPE
		SYNTAX	INTEGER
		ACCESS	read-only
		STATUS	mandatory
		DESCRIPTION
			"Number of CLP1 lost cells for this PM session"
		::= { starPmEntry 4 }

	starPmErroredCellCount	OBJECT-TYPE
		SYNTAX	INTEGER
		ACCESS	read-only
		STATUS	mandatory
		DESCRIPTION
			"Number of errored cells for this PM session"
		::= { starPmEntry 5 }

	starPmMisinsertedCellCount	OBJECT-TYPE
		SYNTAX	INTEGER
		ACCESS	read-only
		STATUS	mandatory
		DESCRIPTION
			"Number of misinserted cells for this PM session"
		::= { starPmEntry 6 }

	starPmSeverelyErroredBlockCount	OBJECT-TYPE
		SYNTAX	INTEGER
		ACCESS	read-only
		STATUS	mandatory
		DESCRIPTION
			"Number of severely errored blocks for this PM session"
		::= { starPmEntry 7 }

	-----------------------------------------------------------------------
	-- Star System Pvc Route Table
	-----------------------------------------------------------------------
	starPvcRouteTable	OBJECT-TYPE
		SYNTAX  SEQUENCE OF PvcRouteEntry
		ACCESS  not-accessible
		STATUS  mandatory
		DESCRIPTION
			"" 
		::= { starConn 9 }

	starPvcRouteEntry	OBJECT-TYPE
		SYNTAX	PvcRouteEntry
		ACCESS	not-accessible
		STATUS	mandatory
		DESCRIPTION
			""
		INDEX	{ starPvcRouteGCIDSlotId, starPvcRouteGCIDPortId,
				  starPvcRouteGCIDIfType, starPvcRouteGCIDConnId,
				  starPvcRouteGCIDLeafId, starPvcRouteHopIndex }
		::= { starPvcRouteTable 1 }

	PvcRouteEntry ::=
		SEQUENCE {
			starPvcRouteGCIDSlotId			INTEGER,
			starPvcRouteGCIDPortId			INTEGER,
			starPvcRouteGCIDIfType			INTEGER,
			starPvcRouteGCIDConnId			INTEGER,
			starPvcRouteGCIDLeafId			INTEGER,
			starPvcRouteHopIndex			INTEGER,
			starPvcRouteOutgoingNeId		INTEGER,
			starPvcRouteOutgoingNodeType	INTEGER,
			starPvcRouteOutgoingModuleId	INTEGER,
			starPvcRouteOutgoingPortId		INTEGER
		}

	starPvcRouteGCIDSlotId	OBJECT-TYPE
		SYNTAX	INTEGER
		ACCESS	read-only
		STATUS	mandatory
		DESCRIPTION
			"Slot # of GCID for pvcm"
		::= { starPvcRouteEntry 1 }

	starPvcRouteGCIDPortId	OBJECT-TYPE
		SYNTAX	INTEGER
		ACCESS	read-only
		STATUS	mandatory
		DESCRIPTION
			"Port # of GCID for pvcm"
		::= { starPvcRouteEntry 2 }

	starPvcRouteGCIDIfType	OBJECT-TYPE
		SYNTAX	INTEGER
		ACCESS	read-only
		STATUS	mandatory
		DESCRIPTION
			"Interface type of GCID for pvcm"
		::= { starPvcRouteEntry 3 }

	starPvcRouteGCIDConnId	OBJECT-TYPE
		SYNTAX	INTEGER
		ACCESS	read-only
		STATUS	mandatory
		DESCRIPTION
			"connection # of GCID for pvcm
			VPI = 16bits & VCI = 16bits for ATM,
			DLCI = 32bits for FRAME RELAY or,
			TIMESLOT = 32bits for PDH"
		::= { starPvcRouteEntry 4 }

	starPvcRouteGCIDLeafId	OBJECT-TYPE
		SYNTAX	INTEGER
		ACCESS	read-only
		STATUS	mandatory
		DESCRIPTION
			""
		::= { starPvcRouteEntry 5 }

	starPvcRouteHopIndex	OBJECT-TYPE
		SYNTAX	INTEGER
		ACCESS	read-only
		STATUS	mandatory
		DESCRIPTION
			"Sequential index into this table, 0=First Hop, 
			 1=Next Hop, etc."
		::= { starPvcRouteEntry 6 }

	starPvcRouteOutgoingNeId	OBJECT-TYPE
		SYNTAX	INTEGER
		ACCESS	read-only
		STATUS	mandatory
		DESCRIPTION
			"Current Star Node Id"
		::= { starPvcRouteEntry 7 }

	starPvcRouteOutgoingNodeType	OBJECT-TYPE
		SYNTAX	INTEGER {
			source(1),
			transit(2),
			dest(3)
		}
		ACCESS	read-only
		STATUS	mandatory
		DESCRIPTION
			"Identifier of Star Node in route path"
		::= { starPvcRouteEntry 8 }

	starPvcRouteOutgoingModuleId	OBJECT-TYPE
		SYNTAX	INTEGER
		ACCESS	read-only
		STATUS	mandatory
		DESCRIPTION
			"Slot number of outgoing board for this route"
		::= { starPvcRouteEntry 9 }

	starPvcRouteOutgoingPortId	OBJECT-TYPE
		SYNTAX	INTEGER
		ACCESS	read-only
		STATUS	mandatory
		DESCRIPTION
			"Port number of outgoing port for this route"
		::= { starPvcRouteEntry 10 }

	-----------------------------------------------------------------------
	-- Star System Continuity Check Control Table
	-----------------------------------------------------------------------
	starCcCtrTable		OBJECT-TYPE
		SYNTAX  SEQUENCE OF CcCtrEntry
		ACCESS  not-accessible
		STATUS  mandatory
		DESCRIPTION
			"This table contains objects that allow an NMS
			 operator to setup and start a Continuity Check test" 
		::= { starConn 10 }

	starCcCtrEntry	OBJECT-TYPE
		SYNTAX	CcCtrEntry
		ACCESS	not-accessible
		STATUS	mandatory
		DESCRIPTION
			""
		INDEX	{ starSlotIndex }
		::= { starCcCtrTable 1 }

	CcCtrEntry ::=
		SEQUENCE {
			starCcCtrPortIndex			INTEGER,
			starCcCtrVpi				INTEGER,
			starCcCtrVci				INTEGER,
			starCcCtrType				INTEGER,
			starCcCtrEndType			INTEGER,
			starCcCtrSetup				INTEGER,
			starCcCtrInputType			INTEGER,
			starCcCtrGCIDNeId			INTEGER,
			starCcCtrGCIDSlotIndex		INTEGER,
			starCcCtrGCIDPortIndex		INTEGER,
			starCcCtrGCIDModuleIfType	INTEGER,
			starCcCtrGCIDVpi			INTEGER,
			starCcCtrGCIDVci			INTEGER,
			starCcCtrGCIDDlci			INTEGER,
			starCcCtrGCIDTimeSlot		INTEGER,
			starCcCtrGCIDLeafNum		INTEGER
		}

	starCcCtrPortIndex	OBJECT-TYPE
		SYNTAX	INTEGER
		ACCESS	read-write
		STATUS	mandatory
		DESCRIPTION
			"Port number for this continuity check request"
		::= { starCcCtrEntry 1 }

	starCcCtrVpi	OBJECT-TYPE
		SYNTAX	INTEGER
		ACCESS	read-write
		STATUS	mandatory
		DESCRIPTION
			"VPI for this continuity check request"
		::= { starCcCtrEntry 2 }

	starCcCtrVci	OBJECT-TYPE
		SYNTAX	INTEGER
		ACCESS	read-write
		STATUS	mandatory
		DESCRIPTION
			"VCI for this continuity check request"
		::= { starCcCtrEntry 3 }

	starCcCtrType	OBJECT-TYPE
		SYNTAX	INTEGER {
			oam-f4(1),
			oam-f5(2)
		}
		ACCESS	read-write
		STATUS	mandatory
		DESCRIPTION
			"Type of continuity check, OAM F4, F5 or physical
			 level continuity check, currently only F5"
		::= { starCcCtrEntry 4 }

	starCcCtrEndType	OBJECT-TYPE
		SYNTAX	INTEGER {
			segment(1),
			connection-end(2)
		}
		ACCESS	read-write
		STATUS	mandatory
		DESCRIPTION
			"Continuity check end type"
		::= { starCcCtrEntry 5 }

	starCcCtrSetup	OBJECT-TYPE
		SYNTAX	INTEGER {
			initccsender(1),
			initccreceiver(2),
			finishccreceiver(3),
			finishccsender(4)
		}
		ACCESS	read-write
		STATUS	mandatory
		DESCRIPTION
			"Setup request for specified command.  All parameters
			 related to each command should be preset before 
			 initiating this action"
		::= { starCcCtrEntry 6 }

	starCcCtrInputType	OBJECT-TYPE
		SYNTAX	INTEGER {
			gcid(1),
			vcci(2)
		}
		ACCESS	read-write
		STATUS	mandatory
		DESCRIPTION
			"Describes what information will be used to setup the
			 continuity check, either all of GCID or Vpi/Vci values"
		::= { starCcCtrEntry 7 }

	starCcCtrGCIDNeId	OBJECT-TYPE
		SYNTAX	INTEGER
		ACCESS	read-write
		STATUS	mandatory
		DESCRIPTION
			"Node Id from GCID when GCID Input type is selected"
		::= { starCcCtrEntry 8 }

	starCcCtrGCIDSlotIndex	OBJECT-TYPE
		SYNTAX	INTEGER
		ACCESS	read-write
		STATUS	mandatory
		DESCRIPTION
			"Slot Id from GCID when GCID Input type is selected"
		::= { starCcCtrEntry 9 }

	starCcCtrGCIDPortIndex	OBJECT-TYPE
		SYNTAX	INTEGER
		ACCESS	read-write
		STATUS	mandatory
		DESCRIPTION
			"Port Id from GCID when GCID Input type is selected"
		::= { starCcCtrEntry 10 }

	starCcCtrGCIDModuleIfType	OBJECT-TYPE
		SYNTAX	INTEGER
		ACCESS	read-write
		STATUS	mandatory
		DESCRIPTION
			"Module Interface type from GCID when GCID Input type 
			 is selected"
		::= { starCcCtrEntry 11 }

	starCcCtrGCIDVpi	OBJECT-TYPE
		SYNTAX	INTEGER
		ACCESS	read-write
		STATUS	mandatory
		DESCRIPTION
			"VPI from GCID when GCID Input type is selected"
		::= { starCcCtrEntry 12 }

	starCcCtrGCIDVci	OBJECT-TYPE
		SYNTAX	INTEGER
		ACCESS	read-write
		STATUS	mandatory
		DESCRIPTION
			"VCI from GCID when GCID Input type is selected"
		::= { starCcCtrEntry 13 }

	starCcCtrGCIDDlci	OBJECT-TYPE
		SYNTAX	INTEGER
		ACCESS	read-write
		STATUS	mandatory
		DESCRIPTION
			"DLCI from GCID when GCID Input type is selected and
			 board is Frame Relay type"
		::= { starCcCtrEntry 14 }

	starCcCtrGCIDTimeSlot	OBJECT-TYPE
		SYNTAX	INTEGER
		ACCESS	read-write
		STATUS	mandatory
		DESCRIPTION
			"TimeSlot from GCID when board is PIU"
		::= { starCcCtrEntry 15 }

	starCcCtrGCIDLeafNum	OBJECT-TYPE
		SYNTAX	INTEGER
		ACCESS	read-write
		STATUS	mandatory
		DESCRIPTION
					 "Lear number from GCID when GCID Input type is selected"
		::= { starCcCtrEntry 16 }

	----------------------------------------------------------------------
	-- Star System Port Statistics Table
	----------------------------------------------------------------------
	starPortCellStatsTable	OBJECT-TYPE
		SYNTAX  SEQUENCE OF PortCellStatsEntry
		ACCESS  not-accessible
		STATUS  mandatory
		DESCRIPTION
			"This table contains statistics gathered on a specific
			 port and is indexed by Slot number, Port number "
		::= { starConn 11 }
 
	starPortCellStatsEntry  OBJECT-TYPE
		SYNTAX  PortCellStatsEntry
		ACCESS  not-accessible
		STATUS  mandatory
		DESCRIPTION
			""
		INDEX   { starSlotIndex, starPortIndex }
		::= { starPortCellStatsTable 1 }
 
	PortCellStatsEntry ::=
		SEQUENCE {
			starPortTimeStamp			Counter,
			starPortRtCellsRxCount		Counter,
			starPortRtCellsDroppedCount	Counter,
			starPortRtCellsCongCount	Counter,
			starPortUpcCellsCLP0		Counter,
			starPortUpcTotalCells		Counter,
			starPortUpcGcra0ViolCount	Counter,
			starPortUpcGcra1ViolCount	Counter,
			starPortUpcTotalOAMCells	Counter
		}

	starPortTimeStamp OBJECT-TYPE
		SYNTAX  Counter
		ACCESS  read-only
		STATUS  mandatory
		DESCRIPTION
			"Time Stamp in Seconds"
		::= { starPortCellStatsEntry 1 }
 
	starPortRtCellsRxCount  OBJECT-TYPE
		SYNTAX  Counter
		ACCESS  read-only
		STATUS  mandatory
		DESCRIPTION
			"Number of cells received in RT level for this port"
		::= { starPortCellStatsEntry 2 }
 
	starPortRtCellsDroppedCount OBJECT-TYPE
		SYNTAX  Counter
		ACCESS  read-only
		STATUS  mandatory
		DESCRIPTION
			"Number of cells dropped in RT level for this VP/VC"
		::= { starPortCellStatsEntry 3 }
 
	starPortRtCellsCongCount OBJECT-TYPE
		SYNTAX  Counter
		ACCESS  read-only
		STATUS  mandatory
		DESCRIPTION
			"Number of cells congestion in RT level for this VP/VC"
		::= { starPortCellStatsEntry 4 }
 
	starPortUpcCellsCLP0 OBJECT-TYPE
		SYNTAX  Counter
		ACCESS  read-only
		STATUS  mandatory
		DESCRIPTION
			"Number of cells with CLP0 in UPC level for this VP/VC"
		::= { starPortCellStatsEntry 5 }
 
	starPortUpcTotalCells OBJECT-TYPE
		SYNTAX  Counter
		ACCESS  read-only
		STATUS  mandatory
		DESCRIPTION
			"Number of total cells in UPC level for this VP/VC"
		::= { starPortCellStatsEntry 6 }
 
	starPortUpcGcra0ViolCount OBJECT-TYPE
		SYNTAX  Counter
		ACCESS  read-only
		STATUS  mandatory
		DESCRIPTION
			"Number of total GCRA0 violation cells in UPC level for this VP/VC"
		::= { starPortCellStatsEntry 7 }
 
	starPortUpcGcra1ViolCount OBJECT-TYPE
		SYNTAX  Counter
		ACCESS  read-only
		STATUS  mandatory
		DESCRIPTION
			"Number of total GCRA0 violation cells in UPC level for this VP/VC"
		::= { starPortCellStatsEntry 8 }
 
 
	starPortUpcTotalOAMCells OBJECT-TYPE
		SYNTAX  Counter
		ACCESS  read-only
		STATUS  mandatory
		DESCRIPTION
			"Number of total OAM cells in UPC level for this VP/VC"
		::= { starPortCellStatsEntry 9 }

	-----------------------------------------------------------------------
	-- Star System ATM Loopback Point Check Table
	-----------------------------------------------------------------------
	starAtmPointTable	  OBJECT-TYPE
		SYNTAX  SEQUENCE OF AtmPointEntry
		ACCESS  not-accessible
		STATUS  mandatory
		DESCRIPTION
			""
		::= { starConn 13 }
 
	starAtmPointEntry  OBJECT-TYPE
		SYNTAX  AtmPointEntry
		ACCESS  not-accessible
		STATUS  mandatory
		DESCRIPTION
			""
		INDEX   { starSlotIndex, starPortIndex, starLoopbackCtrGCIDNeId,
				  starLoopbackCtrGCIDSlotIndex, starLoopbackCtrGCIDPortIndex,
				  starLoopbackCtrGCIDModuleIfType, starLoopbackCtrGCIDVpi,
				  starLoopbackCtrGCIDVci, starLoopbackCtrGCIDDlci,
				  starLoopbackCtrGCIDTimeSlot, starLoopbackCtrGCIDLeafNum }
		::= { starAtmPointTable 1 }
 
	AtmPointEntry ::=
		SEQUENCE {
			starAtmPointPointType
				INTEGER
		}

	starAtmPointPointType	OBJECT-TYPE
		SYNTAX  INTEGER {
			segmentend(1),
			connectionend(2),
			intermediate(3)
		}
		ACCESS  read-write
		STATUS  mandatory
		DESCRIPTION
			""
		::= { starAtmPointEntry 1 }

	-----------------------------------------------------------------------
	-- Star System SVC Route Table
	-----------------------------------------------------------------------
	starSvcRouteTable   OBJECT-TYPE
		SYNTAX  SEQUENCE OF SvcRouteEntry
		ACCESS  not-accessible
		STATUS  mandatory
		DESCRIPTION
			""
		::= { starConn 14 }
 
	starSvcRouteEntry   OBJECT-TYPE
		SYNTAX  SvcRouteEntry
		ACCESS  not-accessible
		STATUS  mandatory
		DESCRIPTION
			""
		INDEX   { starSvcRouteGCIDSlotId, starSvcRouteGCIDPortId,
				  starSvcRouteGCIDIfType, starSvcRouteGCIDConnId,
				  starSvcRouteGCIDLeafId, starSvcRouteHopIndex }
		::= { starSvcRouteTable 1 }
 
	SvcRouteEntry ::=
		SEQUENCE {
			starSvcRouteGCIDSlotId			INTEGER,
			starSvcRouteGCIDPortId			INTEGER,
			starSvcRouteGCIDIfType			INTEGER,
			starSvcRouteGCIDConnId			INTEGER,
			starSvcRouteGCIDLeafId			INTEGER,
			starSvcRouteHopIndex			INTEGER,
			starSvcRouteOutgoingNeId		INTEGER,
			starSvcRouteOutgoingNodeType	INTEGER,
			starSvcRouteOutgoingModuleId	INTEGER,
			starSvcRouteOutgoingPortId		INTEGER
		}
 
	starSvcRouteGCIDSlotId  OBJECT-TYPE
		SYNTAX  INTEGER
		ACCESS  read-only
		STATUS  mandatory
		DESCRIPTION
			"slot # of GCID for svcm"
		::= { starSvcRouteEntry 1 }
 
	starSvcRouteGCIDPortId  OBJECT-TYPE
		SYNTAX  INTEGER
		ACCESS  read-only
		STATUS  mandatory
		DESCRIPTION
			"port # of GCID for svcm"
		::= { starSvcRouteEntry 2 }
 
	starSvcRouteGCIDIfType  OBJECT-TYPE
		SYNTAX  INTEGER
		ACCESS  read-only
		STATUS  mandatory
		DESCRIPTION
			"interface type of GCID for svcm"
		::= { starSvcRouteEntry 3 }
 
	starSvcRouteGCIDConnId  OBJECT-TYPE
		SYNTAX  INTEGER
		ACCESS  read-only
		STATUS  mandatory
		DESCRIPTION
			"connection # of GCID for svcm
			 VPI = 16bits & VCI = 16bits for ATM,
			 DLCI = 32bits for FRAME RELAY or,
			 TIMESLOT = 32bits for PDH"
		::= { starSvcRouteEntry 4 }
 
	starSvcRouteGCIDLeafId  OBJECT-TYPE
		SYNTAX  INTEGER
		ACCESS  read-only
		STATUS  mandatory
		DESCRIPTION
			""
		::= { starSvcRouteEntry 5 }
 
	starSvcRouteHopIndex	OBJECT-TYPE
		SYNTAX  INTEGER
		ACCESS  read-only
		STATUS  mandatory
		DESCRIPTION
			"Sequential index into this table, 0=First Hop,
			 1=Next Hop, etc."
		::= { starSvcRouteEntry 6 }
 
	starSvcRouteOutgoingNeId	OBJECT-TYPE
		SYNTAX  INTEGER
		ACCESS  read-only
		STATUS  mandatory
		DESCRIPTION
			"Current Star Node Id"
		::= { starSvcRouteEntry 7 }
 
	starSvcRouteOutgoingNodeType	OBJECT-TYPE
		SYNTAX  INTEGER {
			source(1),
			transit(2),
			dest(3)
		}
		ACCESS  read-only
		STATUS  mandatory
		DESCRIPTION
			"Identifier of Star Node in route path"
		::= { starSvcRouteEntry 8 }
 
	starSvcRouteOutgoingModuleId	OBJECT-TYPE
		SYNTAX  INTEGER
		ACCESS  read-only
		STATUS  mandatory
		DESCRIPTION
			"Slot number of outgoing board for this route"
		::= { starSvcRouteEntry 9 }
 
	starSvcRouteOutgoingPortId  OBJECT-TYPE
		SYNTAX  INTEGER
		ACCESS  read-only
		STATUS  mandatory
		DESCRIPTION
			"Port number of outgoing port for this route"
		::= { starSvcRouteEntry 10 }
 
	-----------------------------------------------------------------------
	-- Star System PVC Route Table for Route Query (Added on 3/27/98)
	-----------------------------------------------------------------------
	starPVCRouteTable   OBJECT-TYPE
		SYNTAX  SEQUENCE OF PVCRouteEntry
		ACCESS  not-accessible
		STATUS  mandatory
		DESCRIPTION
			"Route table for route query by BBCP"
		::= { starConn 15 }

	starPVCRouteEntry   OBJECT-TYPE
		SYNTAX  PVCRouteEntry
		ACCESS  not-accessible
		STATUS  mandatory
		DESCRIPTION
			""
		INDEX   { starSlotIndex, starPortIndex, starPvcRouteAdjacentNodeType,
				  starPvcRouteSrcGCIDNeId,   starPvcRouteSrcGCIDSlotId,
				  starPvcRouteSrcGCIDPortId, starPvcRouteSrcGCIDIfType, 
				  starPvcRouteSrcGCIDConnId, starPvcRouteSrcGCIDLeafId }
		::= { starPVCRouteTable 1 }
 
	PVCRouteEntry ::=
		SEQUENCE {
			starPvcRouteSrcGCIDNeId			INTEGER,
			starPvcRouteSrcGCIDSlotId		INTEGER,
			starPvcRouteSrcGCIDPortId		INTEGER,
			starPvcRouteSrcGCIDIfType		INTEGER,
			starPvcRouteSrcGCIDConnId		INTEGER,
			starPvcRouteSrcGCIDLeafId		INTEGER,
			starPvcRouteAdjacentNeId		INTEGER,
			starPvcRouteAdjacentSlotId		INTEGER,
			starPvcRouteAdjacentPortId		INTEGER,
			starPvcRouteAdjacentNodeType	INTEGER,
			starPvcRouteLocalNodeType		INTEGER,
			starPvcRouteLocalIfType			INTEGER,
			starPvcRouteLocalConnId			INTEGER,
			starPvcRouteLocalLeafId			INTEGER,
			starPvcRouteQueryDescr			OCTET STRING
		}

	starPvcRouteSrcGCIDNeId  OBJECT-TYPE
		SYNTAX  INTEGER
		ACCESS  read-only
		STATUS  mandatory
		DESCRIPTION
			"NE # of GCID for route query (BBCP)"
		::= { starPVCRouteEntry 1 }

	starPvcRouteSrcGCIDSlotId  OBJECT-TYPE
		SYNTAX  INTEGER
		ACCESS  read-only
		STATUS  mandatory
		DESCRIPTION
			"slot # of GCID for route query (BBCP)"
		::= { starPVCRouteEntry 2 }
 
	starPvcRouteSrcGCIDPortId  OBJECT-TYPE
		SYNTAX  INTEGER
		ACCESS  read-only
		STATUS  mandatory
		DESCRIPTION
			"port # of GCID for route query (BBCP)"
		::= { starPVCRouteEntry 3 }
 
	starPvcRouteSrcGCIDIfType  OBJECT-TYPE
		SYNTAX  INTEGER
		ACCESS  read-only
		STATUS  mandatory
		DESCRIPTION
			"interface type of GCID for route query (BBCP)"
		::= { starPVCRouteEntry 4 }
 
	starPvcRouteSrcGCIDConnId  OBJECT-TYPE
		SYNTAX  INTEGER
		ACCESS  read-only
		STATUS  mandatory
		DESCRIPTION
			"connection # of GCID for route query (BBCP)
			 VPI = 16bits & VCI = 16bits for ATM,
			 DLCI = 32bits for FRAME RELAY or,
			 TIMESLOT = 32bits for PDH"
		::= { starPVCRouteEntry 5 }
 
	starPvcRouteSrcGCIDLeafId  OBJECT-TYPE
		SYNTAX  INTEGER
		ACCESS  read-only
		STATUS  mandatory
		DESCRIPTION
			""
		::= { starPVCRouteEntry 6 }
 
	starPvcRouteAdjacentNeId	OBJECT-TYPE
		SYNTAX  INTEGER
		ACCESS  read-only
		STATUS  mandatory
		DESCRIPTION
			"Current Star Node Id"
		::= { starPVCRouteEntry 7 }
 
	starPvcRouteAdjacentSlotId	OBJECT-TYPE
		SYNTAX  INTEGER
		ACCESS  read-only
		STATUS  mandatory
		DESCRIPTION
			"Slot number of outgoing board for this route"
		::= { starPVCRouteEntry 8 }
 
	starPvcRouteAdjacentPortId	OBJECT-TYPE
		SYNTAX  INTEGER
		ACCESS  read-only
		STATUS  mandatory
		DESCRIPTION
			"Slot number of outgoing board for this route"
		::= { starPVCRouteEntry 9 }
 
	starPvcRouteAdjacentNodeType	OBJECT-TYPE
		SYNTAX  INTEGER {
			source(1),
			incoming(2),
			outgoing(3),
			dest(4)
		}
		ACCESS  read-only
		STATUS  mandatory
		DESCRIPTION
			"Identifier of Star Node in adjacent route path (role)"
		::= { starPVCRouteEntry 10 }

	starPvcRouteLocalNodeType	OBJECT-TYPE
		SYNTAX  INTEGER {
			source(1),
			incoming(2),
			outgoing(3),
			dest(4)
		}
		ACCESS  read-only
		STATUS  mandatory
		DESCRIPTION
			"Identifier of Star Node in local route path (role)"
		::= { starPVCRouteEntry 11 }
 
	starPvcRouteLocalIfType	OBJECT-TYPE
		SYNTAX  INTEGER
		ACCESS  read-only
		STATUS  mandatory
		DESCRIPTION
			"Slot number of outgoing board for this route"
		::= { starPVCRouteEntry 12 }
 
	starPvcRouteLocalConnId	OBJECT-TYPE
		SYNTAX  INTEGER
		ACCESS  read-only
		STATUS  mandatory
		DESCRIPTION
			"Slot number of outgoing board for this route"
		::= { starPVCRouteEntry 13 }
 
	starPvcRouteLocalLeafId	OBJECT-TYPE
		SYNTAX  INTEGER
		ACCESS  read-only
		STATUS  mandatory
		DESCRIPTION
			"Slot number of outgoing board for this route"
		::= { starPVCRouteEntry 14 }
 
	starPvcRouteQueryDescr	OBJECT-TYPE
		SYNTAX  OCTET STRING
		ACCESS  read-only
		STATUS  mandatory
		DESCRIPTION
			"Slot number of outgoing board for this route"
		::= { starPVCRouteEntry 15 }
 
	-----------------------------------------------------------------------
	-- Star System Backbone Link Table (Added on 5/6/96)
	-----------------------------------------------------------------------
	starBackboneLinkTable	OBJECT-TYPE
		SYNTAX  SEQUENCE OF BackboneLinkEntry
		ACCESS  not-accessible
		STATUS  mandatory
		DESCRIPTION
			"This table contains information for BackBone links and
			 is indexed by a Backbone Link Id" 
		::= { starBackbone 1 }

	starBackboneLinkEntry	OBJECT-TYPE
		SYNTAX	BackboneLinkEntry
		ACCESS	not-accessible
		STATUS	mandatory
		DESCRIPTION
			""
		INDEX	{ starSlotIndex, starPortIndex }
		::= { starBackboneLinkTable 1 }

	BackboneLinkEntry ::=
		SEQUENCE {
			starBackboneLinkStatus		INTEGER,
			starBackboneLinkDestNodeId	INTEGER,
			starBackboneLinkDestSlotId	INTEGER,
			starBackboneLinkDestPortId	INTEGER,
			starBackboneLinkIfType		INTEGER,
			starBackboneLinkConnStatus	INTEGER
		}

	starBackboneLinkStatus	OBJECT-TYPE
		SYNTAX	INTEGER
		ACCESS	read-only
		STATUS	mandatory
		DESCRIPTION
			"Status of this Backbone Link"
		::= { starBackboneLinkEntry 1 }

	starBackboneLinkDestNodeId	OBJECT-TYPE
		SYNTAX	INTEGER
		ACCESS	read-only
		STATUS	mandatory
		DESCRIPTION
			"Destination Node for this Backbone Link"
		::= { starBackboneLinkEntry 2 }

	starBackboneLinkDestSlotId	OBJECT-TYPE
		SYNTAX	INTEGER
		ACCESS	read-only
		STATUS	mandatory
		DESCRIPTION
			"Destination Slot number of this Backbone Link Link"
		::= { starBackboneLinkEntry 3 }

	starBackboneLinkDestPortId	OBJECT-TYPE
		SYNTAX	INTEGER
		ACCESS	read-only
		STATUS	mandatory
		DESCRIPTION
			"Destination Port number of this Backbone Link Link"
		::= { starBackboneLinkEntry 4 }

	starBackboneLinkIfType	OBJECT-TYPE
		SYNTAX	INTEGER
		ACCESS	read-only
		STATUS	mandatory
		DESCRIPTION
			"Interface port type of this Backbone Link Link"
		::= { starBackboneLinkEntry 5 }

 	starBackboneLinkConnStatus  OBJECT-TYPE
 		SYNTAX  INTEGER
		ACCESS  read-only
		STATUS  mandatory
		DESCRIPTION
			"Status of this Backbone Link Connection for Warning"
		::= { starBackboneLinkEntry 6 }

	-----------------------------------------------------------------------
	-- Star FIU Info Group (from FutureSoft - 12/7/95)
	-----------------------------------------------------------------------
	starFiuModuleInfo		 OBJECT IDENTIFIER ::= { starSlot 16 }

	-----------------------------------------------------------------------
	-- Star RFC1604 Extended F/R Info Subgroup (from FutureSoft - 12/7/95)
	-----------------------------------------------------------------------
	starFrlExtnModuleInfo		 OBJECT IDENTIFIER ::= { starFiuModuleInfo 1 }

	-----------------------------------------------------------------------
	-- Star RFC1604 Extended F/R Port Table
	-----------------------------------------------------------------------
	frlPortInfoTbl	OBJECT-TYPE
		SYNTAX  SEQUENCE OF FrlPortInfoEntry
		ACCESS  not-accessible
		STATUS  mandatory
		DESCRIPTION
			"This table is an extension to the Port table 
			in RFC1604, viz the frame relay mib."
		::= { starFrlExtnModuleInfo 1 }

	frlPortInfoEntry	 OBJECT-TYPE
		SYNTAX  FrlPortInfoEntry
		ACCESS  not-accessible
		STATUS  mandatory
		DESCRIPTION
			"An entry into FrlPortInfoTbl."
		INDEX { frlPortInfoSlotId, frlPortInfoPortId }
		::= { frlPortInfoTbl 1 }

	FrlPortInfoEntry ::=
		SEQUENCE {
			frlPortInfoSlotId	INTEGER ,
			frlPortInfoPortId	INTEGER ,
			frlPortSigMode		INTEGER ,
			frlPortActiveDlci	INTEGER 
		}

	frlPortInfoSlotId		 OBJECT-TYPE
		SYNTAX  INTEGER
		ACCESS  read-only
		STATUS  mandatory
		DESCRIPTION
			"This object indicates the slot id."
		::= { frlPortInfoEntry 1 }

	frlPortInfoPortId		 OBJECT-TYPE
		SYNTAX  INTEGER
		ACCESS  read-only
		STATUS  mandatory
		DESCRIPTION
			"This object indicates the port id."
		::= { frlPortInfoEntry 2 }

	frlPortSigMode			OBJECT-TYPE
		SYNTAX  INTEGER (1..4)
		ACCESS  read-only
		STATUS  mandatory
		DESCRIPTION
			"This object indicates if the port is emulating
				user,network,bi-directional,bidir with sync."

		::= { frlPortInfoEntry 3 }

	frlPortActiveDlci		OBJECT-TYPE
		SYNTAX  INTEGER
		ACCESS  read-only
		STATUS  mandatory
		DESCRIPTION
			"This object indicates  the num of active DLCi's
				on the port."
		::= { frlPortInfoEntry 4 }

	-----------------------------------------------------------------------
	-- Star RFC1604 Extended F/R Endpoint Info Table
	-----------------------------------------------------------------------
	frlPvcEndptInfoTbl	OBJECT-TYPE
		SYNTAX  SEQUENCE OF FrlPvcEndptInfoEntry
		ACCESS  not-accessible
		STATUS  mandatory
		DESCRIPTION
			"This table ia an extension for the Frame relay 
				PVC endpt table of Rfc1604, viz the
				Frame relay mib."
		::= { starFrlExtnModuleInfo 2 }

	 frlPvcEndptInfoEntry		OBJECT-TYPE
		SYNTAX  FrlPvcEndptInfoEntry
		ACCESS  not-accessible
		STATUS  mandatory
		DESCRIPTION
			"An entry into FrlPvcEndptTbl."
		INDEX { frlPvcEndptInfoSlotId, frlPvcEndptInfoPortId,
				frlPvcEndptInfoDlci }
		::= { frlPvcEndptInfoTbl 1 }

	FrlPvcEndptInfoEntry ::=
		SEQUENCE {
			frlPvcEndptInfoSlotId		INTEGER,
			frlPvcEndptInfoPortId		INTEGER,
			frlPvcEndptInfoDlci			INTEGER,
			frPvcEndptInfoTimeStamp 	INTEGER,
			frPvcMarkedDe				INTEGER,
			frPvcEndptOperStatus		INTEGER,
			frPvcEndptNoRecvFECN		INTEGER,
			frPvcEndptNoTxFECN			INTEGER,
			frPvcEndptNoRecvBECN		INTEGER,
			frPvcEndptNoTxBECN			INTEGER,
			frPvcEndptNoTxDE			INTEGER,
			frPvcEndptNoDiscardWithDE	INTEGER,
			frPvcEndptNoDiscardWoutDE	INTEGER, 
			frPvcEndptInDEFrames		INTEGER
		}

	 frlPvcEndptInfoSlotId		 OBJECT-TYPE
		SYNTAX  INTEGER
		ACCESS  read-only
		STATUS  mandatory
		DESCRIPTION
			"This object indicates the slot id."
		::= { frlPvcEndptInfoEntry 1 }

	 frlPvcEndptInfoPortId		 OBJECT-TYPE
		SYNTAX  INTEGER
		ACCESS  read-only
		STATUS  mandatory
		DESCRIPTION
			"This object indicates the port id." 
		::= {  frlPvcEndptInfoEntry  2 }

	 frlPvcEndptInfoDlci			OBJECT-TYPE
		SYNTAX  INTEGER
		ACCESS  read-only
		STATUS  mandatory
		DESCRIPTION
			"This object indicates the Dlci ."
		::= {  frlPvcEndptInfoEntry  3 }

	 frPvcEndptInfoTimeStamp	OBJECT-TYPE
		SYNTAX  INTEGER
		ACCESS  read-only
		STATUS  mandatory
		DESCRIPTION
			"This object indicates time slot ."
		::= {  frlPvcEndptInfoEntry  4 }

	frPvcMarkedDe				OBJECT-TYPE
		SYNTAX  INTEGER
		ACCESS  read-only
		STATUS  mandatory
		DESCRIPTION
			"This object indicates the num of frames received
				with the DE bit set ."
		::= {  frlPvcEndptInfoEntry  5 }

	frPvcEndptOperStatus			OBJECT-TYPE
		SYNTAX  INTEGER
		ACCESS  read-only
		STATUS  mandatory
		DESCRIPTION
			"This object indicates if the PVC is active or not."
		::= {  frlPvcEndptInfoEntry  6 }

	frPvcEndptNoRecvFECN			OBJECT-TYPE
		SYNTAX  INTEGER
		ACCESS  read-only
		STATUS  mandatory
		DESCRIPTION
			"This object indicates number of received 
			 frames with FECN bit set for this dlci."
		::= {  frlPvcEndptInfoEntry  7 }

	frPvcEndptNoTxFECN			OBJECT-TYPE
		SYNTAX  INTEGER
		ACCESS  read-only
		STATUS  mandatory
		DESCRIPTION
			"This object indicates number of transmitted 
			 frames with FECN bit set for this dlci."
		::= {  frlPvcEndptInfoEntry  8 }

	frPvcEndptNoRecvBECN			OBJECT-TYPE
		SYNTAX  INTEGER
		ACCESS  read-only
		STATUS  mandatory
		DESCRIPTION
			"This object indicates number of received 
			 frames with BECN bit set for this dlci."
		::= {  frlPvcEndptInfoEntry  9 }

	frPvcEndptNoTxBECN			OBJECT-TYPE
		SYNTAX  INTEGER
		ACCESS  read-only
		STATUS  mandatory
		DESCRIPTION
			"This object indicates number of transmitted 
			 frames with BECN bit set for this dlci."
		::= {  frlPvcEndptInfoEntry  10 }

	frPvcEndptNoTxDE			OBJECT-TYPE
		SYNTAX  INTEGER
		ACCESS  read-only
		STATUS  mandatory
		DESCRIPTION
			"This object indicates number of transmitted 
			 frames with DE bit set for this dlci."
		::= {  frlPvcEndptInfoEntry  11 }

	frPvcEndptNoDiscardWithDE			OBJECT-TYPE
		SYNTAX  INTEGER
		ACCESS  read-only
		STATUS  mandatory
		DESCRIPTION
			"This object indicates number of frames 
			 discarded with DE bit set for this dlci."
		::= {  frlPvcEndptInfoEntry  12 }

	frPvcEndptNoDiscardWoutDE			OBJECT-TYPE
		SYNTAX  INTEGER
		ACCESS  read-only
		STATUS  mandatory
		DESCRIPTION
			"This object indicates number of frames 
			 discarded with out DE bit set for this dlci."
		::= {  frlPvcEndptInfoEntry  13 }

	frPvcEndptInDEFrames			OBJECT-TYPE
		SYNTAX  INTEGER
		ACCESS  read-only
		STATUS  mandatory
		DESCRIPTION
			"From RFC1604"
		::= {  frlPvcEndptInfoEntry  14 }

	-----------------------------------------------------------------------
	-- Star FIU SSCS Info Subgroup
	-----------------------------------------------------------------------
	starFiuSscsInfo		 OBJECT IDENTIFIER
		::= { starFiuModuleInfo 2 }

	-----------------------------------------------------------------------
	-- Star FIU SSCS Interface Info Table
	-----------------------------------------------------------------------
	starFiuSscsIfInfoTbl	OBJECT-TYPE
		SYNTAX  SEQUENCE OF StarFiuSscsIfInfoEntry
		ACCESS  not-accessible
		STATUS  mandatory
		DESCRIPTION
			"This table provides information pertaining to the
			Interface of frame relay service specific convergence
			subfunction."
		::= { starFiuSscsInfo 1 }

	starFiuSscsIfInfoEntry	 OBJECT-TYPE
		SYNTAX  StarFiuSscsIfInfoEntry
		ACCESS  not-accessible
		STATUS  mandatory
		DESCRIPTION
			"An entry into FiuSscsIfInfoTbl."
		INDEX { starFiuIfInfoSlotId, starFiuIfInfoPortId }
		::= { starFiuSscsIfInfoTbl 1 }

	StarFiuSscsIfInfoEntry ::=
		SEQUENCE {
			starFiuIfInfoSlotId			INTEGER ,
			starFiuIfInfoPortId			INTEGER ,
			starFiuFrcsIfAdminStatus	INTEGER ,
			starFiuFrcsIfOperStatus		INTEGER ,
			starFiuFrcsIfLastChange		INTEGER ,
			starFiuFrcsIfInOctets		INTEGER ,
			starFiuFrcsIfInUcastPkts	INTEGER ,
			starFiuFrcsIfInDiscards		INTEGER ,
			starFiuFrcsIfInErrors		INTEGER ,
			starFiuFrcsIfOutOctets		INTEGER ,
			starFiuFrcsIfOutUcastPkts	INTEGER ,
			starFiuFrcsIfOutDiscards	INTEGER ,
			starFiuFrcsIfOutErrors		INTEGER 
		}

	starFiuIfInfoSlotId	 OBJECT-TYPE
		SYNTAX  INTEGER
		ACCESS  read-only
		STATUS  mandatory
		DESCRIPTION
			"This object indicates the slot id."
		::= { starFiuSscsIfInfoEntry 1 }

	starFiuIfInfoPortId	 OBJECT-TYPE
		SYNTAX  INTEGER
		ACCESS  read-only
		STATUS  mandatory
		DESCRIPTION
			"This object indicates the port id."
		::= { starFiuSscsIfInfoEntry 2 }

	starFiuFrcsIfAdminStatus  OBJECT-TYPE
		SYNTAX  INTEGER {
			defined (1),
			undefined (2),
			out-of-service (3)
		}
		ACCESS  read-only
		STATUS  mandatory
		DESCRIPTION
			"This object describes the administrative
			 status of Fiu card."
		::= { starFiuSscsIfInfoEntry 3 }

	starFiuFrcsIfOperStatus	 OBJECT-TYPE
		SYNTAX  INTEGER {
			up   (1),
			down (2)
		}
		ACCESS  read-only
		STATUS  mandatory
		DESCRIPTION
		"Indicates the operational status of the active Fiu card."
		::= { starFiuSscsIfInfoEntry 4 }

	starFiuFrcsIfLastChange	OBJECT-TYPE
		SYNTAX  INTEGER
		ACCESS  read-only
		STATUS  mandatory
		DESCRIPTION
			"Indicates the elapsed  time since 
			last oper_status change in timeticks ." 
		::= { starFiuSscsIfInfoEntry 5 }

	starFiuFrcsIfInOctets	OBJECT-TYPE
		SYNTAX  INTEGER
		ACCESS  read-only
		STATUS  mandatory
		DESCRIPTION
			"Indicates the number of received octets." 
		::= { starFiuSscsIfInfoEntry 6 }

	starFiuFrcsIfInUcastPkts	OBJECT-TYPE
		SYNTAX  INTEGER
		ACCESS  read-only
		STATUS  mandatory
		DESCRIPTION
			"Indicates the number of successfully received frames."
		::= { starFiuSscsIfInfoEntry 7 }

	starFiuFrcsIfInDiscards	OBJECT-TYPE
		SYNTAX  INTEGER 
		ACCESS  read-only
		STATUS  mandatory
		DESCRIPTION
			" Indicates the number of 
			discarded frames due to congestion or policing."
		::= { starFiuSscsIfInfoEntry 8 }

	starFiuFrcsIfInErrors	OBJECT-TYPE
		SYNTAX  INTEGER 
		ACCESS  read-only
		STATUS  mandatory
		DESCRIPTION
			"Indicates the number of received frames discarded 
			due to the following errors - invalid DLCI."
		::= { starFiuSscsIfInfoEntry 9 }

	starFiuFrcsIfOutOctets	OBJECT-TYPE
		SYNTAX  INTEGER 
		ACCESS  read-only
		STATUS  mandatory
		DESCRIPTION
			"Indicates the number of transmitted octets."
		::= { starFiuSscsIfInfoEntry 10 }

	starFiuFrcsIfOutUcastPkts	OBJECT-TYPE
		SYNTAX  INTEGER 
		ACCESS  read-only
		STATUS  mandatory
		DESCRIPTION
		"Indicates the number of successfully transmitted frames."
		::= { starFiuSscsIfInfoEntry 11 }

	starFiuFrcsIfOutDiscards	OBJECT-TYPE
		SYNTAX  INTEGER 
		ACCESS  read-only
		STATUS  mandatory
		DESCRIPTION
		"Indicates the number of discarded frames due to congestion."
		::= { starFiuSscsIfInfoEntry 12 }

	starFiuFrcsIfOutErrors	OBJECT-TYPE
		SYNTAX  INTEGER 
		ACCESS  read-only
		STATUS  mandatory
		DESCRIPTION
			"Indicates the number of transmit frames 
			discarded due to the following errors-invalid 
			DLCI,incorrect ATM header."
		::= { starFiuSscsIfInfoEntry 13 }

	-----------------------------------------------------------------------
	-- Star FIU SSCS PVC Info Table
	-----------------------------------------------------------------------
	starFiuSscsPvcInfoTbl		 OBJECT-TYPE
		SYNTAX  SEQUENCE OF StarFiuSscsPvcInfoEntry
		ACCESS  not-accessible
		STATUS  mandatory
		DESCRIPTION
			"This table provides the information about the
			Fr-SSCS pvc, ie., on a per DLCI basis."
		::= { starFiuSscsInfo  2 }

	starFiuSscsPvcInfoEntry	 OBJECT-TYPE
		SYNTAX  StarFiuSscsPvcInfoEntry
		ACCESS  not-accessible
		STATUS  mandatory
		DESCRIPTION
			"An entry into Fiu PVC table for SSCS."
		INDEX { starFiuPvcInfoSlotId, starFiuPvcInfoPortId ,
				starFiuPvcInfoDlci }
		::= { starFiuSscsPvcInfoTbl 1 }

	StarFiuSscsPvcInfoEntry ::=
		SEQUENCE {
			starFiuPvcInfoSlotId				INTEGER, 
			starFiuPvcInfoPortId				INTEGER,
			starFiuPvcInfoDlci					INTEGER,
			starFiuFrcsPvcEndptInFrames 		INTEGER,
			starFiuFrcsPvcEndptOutFrames		INTEGER,
			starFiuFrcsPvcEndptInOctets			INTEGER,
			starFiuFrcsPvcEndptOutOctets		INTEGER,
			starFiuFrcsPvcConnectAdminStatus 	INTEGER,
			starFiuFrcsPvcEndptOperStatus		INTEGER,
			starFiuFrcsPvcEndptLastChange		INTEGER,
			starFiuFrcsPvcTxVp					INTEGER,
			starFiuFrcsPvcTxVc					INTEGER,
			starFiuFrcsPvcRxVp					INTEGER,
			starFiuFrcsPvcRxVc					INTEGER,
			starFiuFrcsPvcEndptOutOamCells		INTEGER,	
			starFiuFrcsPvcEndptInOamCells		INTEGER,	
			starFiuFrcsPvcEndptOutRawCells		INTEGER,	
			starFiuFrcsPvcEndptInRawCells		INTEGER		

		}

	starFiuPvcInfoSlotId	OBJECT-TYPE
		SYNTAX  INTEGER
		ACCESS  read-only
		STATUS  mandatory
		DESCRIPTION
			"This object indicates the slot id."
		::= { starFiuSscsPvcInfoEntry 1 }

	starFiuPvcInfoPortId	OBJECT-TYPE
		SYNTAX  INTEGER
		ACCESS  read-only
		STATUS  mandatory
		DESCRIPTION
			"This object indicates the port id."
		::= { starFiuSscsPvcInfoEntry 2 }

	starFiuPvcInfoDlci			OBJECT-TYPE
		SYNTAX  INTEGER
		ACCESS  read-only
		STATUS  mandatory
		DESCRIPTION
			"This object indicates the Dlci value."
		::= { starFiuSscsPvcInfoEntry 3 }

	starFiuFrcsPvcEndptInFrames  OBJECT-TYPE
		SYNTAX  INTEGER 
		ACCESS  read-only
		STATUS  mandatory
		DESCRIPTION
			" Indicates the number of received frames."
		::= { starFiuSscsPvcInfoEntry 4 }

	starFiuFrcsPvcEndptOutFrames	 OBJECT-TYPE
		SYNTAX  INTEGER 
		ACCESS  read-only
		STATUS  mandatory
		DESCRIPTION
			"Indicates the number of frames successfully sent out."
		::= { starFiuSscsPvcInfoEntry 5 }

	starFiuFrcsPvcEndptInOctets	OBJECT-TYPE
		SYNTAX  INTEGER
		ACCESS  read-only
		STATUS  mandatory
		DESCRIPTION
			"Indicates the number of received octets."
		::= { starFiuSscsPvcInfoEntry 6 }

	starFiuFrcsPvcEndptOutOctets	OBJECT-TYPE
		SYNTAX  INTEGER
		ACCESS  read-only
		STATUS  mandatory
		DESCRIPTION
			"Indicates the number of octets successfully sent out."
		::= { starFiuSscsPvcInfoEntry 7 }

	starFiuFrcsPvcConnectAdminStatus	OBJECT-TYPE
		SYNTAX  INTEGER {
			defined (1),
			undefined (2),
			out-of-service (3)
		}
		ACCESS  read-only
		STATUS  mandatory
		DESCRIPTION
			"Indicates the number of octets successfully sent out ."
		::= { starFiuSscsPvcInfoEntry 8 }

	starFiuFrcsPvcEndptOperStatus	OBJECT-TYPE
		SYNTAX  INTEGER	{
			up (1),
			down (2)
		}
		ACCESS  read-only
		STATUS  mandatory
		DESCRIPTION
			" Indicates the operational status of this port."
		::= { starFiuSscsPvcInfoEntry 9 }

	starFiuFrcsPvcEndptLastChange	OBJECT-TYPE
		SYNTAX  INTEGER 
		ACCESS  read-only
		STATUS  mandatory
		DESCRIPTION
			"Indicates the elapsed time since last 
			 oper_status change in timeticks."
		::= { starFiuSscsPvcInfoEntry 10 }

	 starFiuFrcsPvcTxVp	 		OBJECT-TYPE
		SYNTAX  INTEGER 
		ACCESS  read-only
		STATUS  mandatory
		DESCRIPTION
			"Indicates the VPI that the Dlci is mapped for Tx."
		::= { starFiuSscsPvcInfoEntry 11 }

	 starFiuFrcsPvcTxVc	 		OBJECT-TYPE
		SYNTAX  INTEGER 
		ACCESS  read-only
		STATUS  mandatory
		DESCRIPTION
			"Indicates the VCI that the Dlci is mapped for Tx."
		::= { starFiuSscsPvcInfoEntry 12 }

	 starFiuFrcsPvcRxVp	 		OBJECT-TYPE
		SYNTAX  INTEGER 
		ACCESS  read-only
		STATUS  mandatory
		DESCRIPTION
			"Indicates the VPI that the Dlci is mapped for Rx."
		::= { starFiuSscsPvcInfoEntry 13 }

	 starFiuFrcsPvcRxVc	 		OBJECT-TYPE
		SYNTAX  INTEGER 
		ACCESS  read-only
		STATUS  mandatory
		DESCRIPTION
			"Indicates the VCI that the Dlci is mapped for Rx."
		::= { starFiuSscsPvcInfoEntry 14 }

	 starFiuFrcsPvcEndptOutOamCells	 	OBJECT-TYPE
		SYNTAX  INTEGER 
		ACCESS  read-only
		STATUS  mandatory
		DESCRIPTION
			"Indicates the number of oam cells transmitted."
		::= { starFiuSscsPvcInfoEntry 15 }

	starFiuFrcsPvcEndptInOamCells	 		OBJECT-TYPE
		SYNTAX  INTEGER 
		ACCESS  read-only
		STATUS  mandatory
		DESCRIPTION
			"Indicates the number of oam cells received."
		::= { starFiuSscsPvcInfoEntry 16 }

	starFiuFrcsPvcEndptOutRawCells	 		OBJECT-TYPE
		SYNTAX  INTEGER 
		ACCESS  read-only
		STATUS  mandatory
		DESCRIPTION
			"Indicates the number of raw cells transmitted."
		::= { starFiuSscsPvcInfoEntry 17 }

	starFiuFrcsPvcEndptInRawCells	 		OBJECT-TYPE
		SYNTAX  INTEGER 
		ACCESS  read-only
		STATUS  mandatory
		DESCRIPTION
			"Indicates the number of raw cells received."
		::= { starFiuSscsPvcInfoEntry 18 }

	-----------------------------------------------------------------------
	-- Star FIU Mgmt Statistics Info Table
	-----------------------------------------------------------------------
	starFrMgmtStatisticInfoTbl		OBJECT-TYPE
		SYNTAX  SEQUENCE OF StarFrMgmtStatisticInfoEntry
		ACCESS  not-accessible
		STATUS  mandatory
		DESCRIPTION
			"An entry into Frame relay management table-
				it provides statistics info."
		::= { starFiuModuleInfo 3 }

	starFrMgmtStatisticInfoEntry	 OBJECT-TYPE
		SYNTAX  StarFrMgmtStatisticInfoEntry
		ACCESS  not-accessible
		STATUS  mandatory
		DESCRIPTION
			"An entry into Fiu's Frame relay management table."
		INDEX { starFrMgmtStatisticSlotId, starFrMgmtStatisticPortId }
		::= { starFrMgmtStatisticInfoTbl 1 }

	StarFrMgmtStatisticInfoEntry ::=
		SEQUENCE {
			starFrMgmtStatisticSlotId		INTEGER ,
			starFrMgmtStatisticPortId		INTEGER ,
			starFrlMgtInKeepalive			INTEGER ,
			starFrlMgtOutKeepalive			INTEGER ,
			starFrlMgtInStatus				INTEGER ,
			starFrlMgtOutStatus				INTEGER ,
			starFrlMgtInStatusReply			INTEGER ,
			starFrlMgtOutStatusReply		INTEGER ,
			starFrlMgtInAsyncUpdates		INTEGER ,
			starFrlMgtOutAsyncUpdates		INTEGER ,
			starFrlMgtNoMismatchSeqNo		INTEGER ,
			starFrlMgtNoT392TimeOut			INTEGER ,
			starFrlMgtNoRecvErDlci			INTEGER ,
			starFrlMgtLastRecvErDlci		INTEGER 
		}

	starFrMgmtStatisticSlotId		 	OBJECT-TYPE
		SYNTAX  INTEGER
		ACCESS  read-only
		STATUS  mandatory
		DESCRIPTION
			"This object indicates the slot id."
		::= { starFrMgmtStatisticInfoEntry  1 }

	 starFrMgmtStatisticPortId		 	OBJECT-TYPE
		SYNTAX  INTEGER
		ACCESS  read-only
		STATUS  mandatory
		DESCRIPTION
			"This object indicates the Port id."
		::= { starFrMgmtStatisticInfoEntry  2 }

	 starFrlMgtInKeepalive		OBJECT-TYPE
		SYNTAX  INTEGER
		ACCESS  read-only
		STATUS  mandatory
		DESCRIPTION
			"Incoming keep alives."
		::= { starFrMgmtStatisticInfoEntry  3 }

	 starFrlMgtOutKeepalive			OBJECT-TYPE
		SYNTAX  INTEGER
		ACCESS  read-only
		STATUS  mandatory
		DESCRIPTION
			"Outgoing keep alives."
		::= { starFrMgmtStatisticInfoEntry 4 }

	 starFrlMgtInStatus			OBJECT-TYPE
		SYNTAX  INTEGER
		ACCESS  read-only
		STATUS  mandatory
		DESCRIPTION
			"Incoming Status messages."
		::= { starFrMgmtStatisticInfoEntry  5 }

	 starFrlMgtOutStatus			OBJECT-TYPE
		SYNTAX  INTEGER
		ACCESS  read-only
		STATUS  mandatory
		DESCRIPTION
			"Outgoing Status Messages."
		::= { starFrMgmtStatisticInfoEntry  6 }

	 starFrlMgtInStatusReply		OBJECT-TYPE
		SYNTAX  INTEGER
		ACCESS  read-only
		STATUS  mandatory
		DESCRIPTION
			"Status of the reply for an incoming status message."
		::= { starFrMgmtStatisticInfoEntry  7 }

	 starFrlMgtOutStatusReply		OBJECT-TYPE
		SYNTAX  INTEGER
		ACCESS  read-only
		STATUS  mandatory
		DESCRIPTION
			"Status of the reply for an outgoing status message."
		::= { starFrMgmtStatisticInfoEntry  8 }

	starFrlMgtInAsyncUpdates	 OBJECT-TYPE
		SYNTAX  INTEGER
		ACCESS  read-only
		STATUS  mandatory
		DESCRIPTION
			"Info about the incoming asynchronous updates."
		::= { starFrMgmtStatisticInfoEntry  9 }

	 starFrlMgtOutAsyncUpdates	 OBJECT-TYPE
		SYNTAX  INTEGER
		ACCESS  read-only
		STATUS  mandatory
		DESCRIPTION
			"Info about the outgoing asynchronous updates."
		::= { starFrMgmtStatisticInfoEntry  10 }

	 starFrlMgtNoMismatchSeqNo	 OBJECT-TYPE
		SYNTAX  INTEGER
		ACCESS  read-only
		STATUS  mandatory
		DESCRIPTION
			"Info about number of mismatched sequence number
			 in the LMI message."
		::= { starFrMgmtStatisticInfoEntry  11 }

	 starFrlMgtNoT392TimeOut		 OBJECT-TYPE
		SYNTAX  INTEGER
		ACCESS  read-only
		STATUS  mandatory
		DESCRIPTION
			"Info about number of T392 time-out."
		::= { starFrMgmtStatisticInfoEntry  12 }

	 starFrlMgtNoRecvErDlci		OBJECT-TYPE
		SYNTAX  INTEGER
		ACCESS  read-only
		STATUS  mandatory
		DESCRIPTION
			"Info about number of received error DLCI."
		::= { starFrMgmtStatisticInfoEntry  13 }

	 starFrlMgtLastRecvErDlci		OBJECT-TYPE
		SYNTAX  INTEGER
		ACCESS  read-only
		STATUS  mandatory
		DESCRIPTION
			"Info about last received errored DLCI value."
		::= { starFrMgmtStatisticInfoEntry  14 }

	-----------------------------------------------------------------------
	-- Star FIU PM Info Subgroup
	-----------------------------------------------------------------------
	starFiuPmInfo			OBJECT IDENTIFIER ::= { starFiuModuleInfo  4 }

	-----------------------------------------------------------------------
	-- Star FIU HDLC PM Info Table
	-----------------------------------------------------------------------
	starFrHdlcPmInfoTbl		OBJECT-TYPE
		SYNTAX  SEQUENCE OF StarFrHdlcPmInfoEntry
		ACCESS  not-accessible
		STATUS  mandatory
		DESCRIPTION
			"An entry into Frame relay Performance management 
			table- Hdlc Tx & RX on a port basis."
		::= { starFiuPmInfo 1 }

	starFrHdlcPmInfoEntry	 OBJECT-TYPE
		SYNTAX  StarFrHdlcPmInfoEntry
		ACCESS  not-accessible
		STATUS  mandatory
		DESCRIPTION
			"An entry into Fiu's Frame relay performance 
			management table."
		INDEX { starFrHdlcPmSlotId, starFrHdlcPmPortId }
		::= { starFrHdlcPmInfoTbl 1 }

	StarFrHdlcPmInfoEntry ::=
		SEQUENCE {
			starFrHdlcPmSlotId		 	INTEGER,
			starFrHdlcPmPortId		 	INTEGER,
			starFrHdlcRxOverrunCount	INTEGER,
			starFrHdlcTxUnderrunCount	INTEGER 
		}

	starFrHdlcPmSlotId		 	OBJECT-TYPE
		SYNTAX  INTEGER
		ACCESS  read-only
		STATUS  mandatory
		DESCRIPTION
			"This object indicates the slot id."
		::= { starFrHdlcPmInfoEntry 1 }

	starFrHdlcPmPortId		 	OBJECT-TYPE
		SYNTAX  INTEGER
		ACCESS  read-only
		STATUS  mandatory
		DESCRIPTION
			"This object indicates the Port id."
		::= { starFrHdlcPmInfoEntry 2 }

	starFrHdlcRxOverrunCount		OBJECT-TYPE
		SYNTAX  INTEGER
		ACCESS  read-only
		STATUS  mandatory
		DESCRIPTION
			"This object indicates the number of times the 
				Rx overran - Performance Manager specific."
		::= { starFrHdlcPmInfoEntry 3 }

	starFrHdlcTxUnderrunCount		OBJECT-TYPE
		SYNTAX  INTEGER
		ACCESS  read-only
		STATUS  mandatory
		DESCRIPTION
			"This object indicates the number of times the 
				Tx underran - Performance Manager specific."
		::= { starFrHdlcPmInfoEntry 4 }

	-----------------------------------------------------------------------
	-- Star FIU Frame relay Congestion Control Statistics Table 	
	-----------------------------------------------------------------------
	starFrCongStatInfoTbl		OBJECT-TYPE
		SYNTAX  SEQUENCE OF StarFrCongStatInfoEntry
		ACCESS  not-accessible
		STATUS  mandatory
		DESCRIPTION
			"An entry into Frame relay Congestion Control 
			Statistics Table based on slot, port, DLCI 
			and Time Stamp"
		::= { starFiuModuleInfo 5 }

	starFrCongStatInfoEntry	 OBJECT-TYPE
		SYNTAX StarFrCongStatInfoEntry 
		ACCESS  not-accessible
		STATUS  mandatory
		DESCRIPTION
			"An entry into Fiu's Frame relay Congestion 
			 Control Statistics table."
		INDEX { starFrCongStatSlotId, starFrCongStatPortId }
		::= { starFrCongStatInfoTbl 1 }

	StarFrCongStatInfoEntry ::=
		SEQUENCE {
			starFrCongStatSlotId			INTEGER,
			starFrCongStatPortId			INTEGER,
			starFrCongStatTimeStamp			INTEGER,
			starFrCongNoRecvFECN 			INTEGER,
			starFrCongNoTxFECN				INTEGER,
			starFrCongNoRecvBECN 			INTEGER,
			starFrCongNoTxBECN				INTEGER,
			starFrCongNoRecvDE	 			INTEGER,
			starFrCongNoTxDE				INTEGER,
			starFrCongNoMarkDE				INTEGER,
			starFrCongNoDiscardWithDE		INTEGER,
			starFrCongNoDiscardWoutDE		INTEGER
		}

	starFrCongStatSlotId		 	OBJECT-TYPE
		SYNTAX  INTEGER
		ACCESS  read-only
		STATUS  mandatory
		DESCRIPTION
			"This object indicates the slot id."
		::= { starFrCongStatInfoEntry 1 }

	starFrCongStatPortId		 	OBJECT-TYPE
		SYNTAX  INTEGER
		ACCESS  read-only
		STATUS  mandatory
		DESCRIPTION
			"This object indicates the Port id."
		::= { starFrCongStatInfoEntry 2 }

	starFrCongStatTimeStamp		OBJECT-TYPE
		SYNTAX  INTEGER
		ACCESS  read-only
		STATUS  mandatory
		DESCRIPTION
			"This object indicates Time Stamp. "
		::= { starFrCongStatInfoEntry 3 }

	starFrCongNoRecvFECN		OBJECT-TYPE
		SYNTAX  INTEGER
		ACCESS  read-only
		STATUS  mandatory
		DESCRIPTION
			"Number of received frames with FECN bit set. "
		::= { starFrCongStatInfoEntry 4 }

	starFrCongNoTxFECN		OBJECT-TYPE
		SYNTAX  INTEGER
		ACCESS  read-only
		STATUS  mandatory
		DESCRIPTION
			"Number of transmitted frames with FECN bit set. "
		::= { starFrCongStatInfoEntry 5 }

	starFrCongNoRecvBECN		OBJECT-TYPE
		SYNTAX  INTEGER
		ACCESS  read-only
		STATUS  mandatory
		DESCRIPTION
			"Number of received  frames with BECN bit set. "
		::= { starFrCongStatInfoEntry 6 }

	starFrCongNoTxBECN		OBJECT-TYPE
		SYNTAX  INTEGER
		ACCESS  read-only
		STATUS  mandatory
		DESCRIPTION
			"Number of transmitted frames with BECN bit set. "
		::= { starFrCongStatInfoEntry 7 }

	starFrCongNoRecvDE		OBJECT-TYPE
		SYNTAX  INTEGER
		ACCESS  read-only
		STATUS  mandatory
		DESCRIPTION
			"Number of frames received with DE bit set."
		::= { starFrCongStatInfoEntry 8 }

	starFrCongNoTxDE		OBJECT-TYPE
		SYNTAX  INTEGER
		ACCESS  read-only
		STATUS  mandatory
		DESCRIPTION
			"Number of frames transmitted with DE bit set. "
		::= { starFrCongStatInfoEntry 9 }

	starFrCongNoMarkDE		OBJECT-TYPE
		SYNTAX  INTEGER
		ACCESS  read-only
		STATUS  mandatory
		DESCRIPTION
			"Number of frames marked with DE bit in the 
			 Network."
		::= { starFrCongStatInfoEntry 10 }

	starFrCongNoDiscardWithDE		OBJECT-TYPE
		SYNTAX  INTEGER
		ACCESS  read-only
		STATUS  mandatory
		DESCRIPTION
			"Number of frames discarded with DE bit set. "
		::= { starFrCongStatInfoEntry 11 }

	starFrCongNoDiscardWoutDE		OBJECT-TYPE
		SYNTAX  INTEGER
		ACCESS  read-only
		STATUS  mandatory
		DESCRIPTION
			"Number of frames discarded without DE bit set."
		::= { starFrCongStatInfoEntry 12 }

	-----------------------------------------------------------------------
	-- Star FIU SSCS Interface Performance Table 	
	-----------------------------------------------------------------------
	starFiuSscsIfPerfTbl		OBJECT-TYPE
		SYNTAX  SEQUENCE OF StarFiuSscsIfPerfTblEntry
		ACCESS  not-accessible
		STATUS  mandatory
		DESCRIPTION
			"An entry into Frame relay transmit receive traffic
			statistics  table based on portId."
		::= { starFiuSscsInfo 3 }

	starFiuSscsIfPerfTblEntry	 OBJECT-TYPE
		SYNTAX  StarFiuSscsIfPerfTblEntry 
		ACCESS  not-accessible
		STATUS  mandatory
		DESCRIPTION
			"An entry into Fiu's Frame relay Tx/Rx permormance table."
		INDEX { starFiuSscsIfPerfSlotId, starFiuSscsIfPerfPortId }
		::= { starFiuSscsIfPerfTbl 1 }

	StarFiuSscsIfPerfTblEntry ::=
		SEQUENCE {
			starFiuSscsIfPerfSlotId		INTEGER ,
			starFiuSscsIfPerfPortId		INTEGER ,
			starFiuSscsIfPerfTmStp		INTEGER ,
			starFiuSscsIfPerfRxPktSz	INTEGER ,
			starFiuSscsIfPerfTxpktSz	INTEGER ,
			starFiuSscsIfPerfRxFrPs		INTEGER ,
			starFiuSscsIfPerfTxFrPs		INTEGER ,
			starFiuSscsIfPerfRxKbps		INTEGER ,
			starFiuSscsIfPerfTxKbps		INTEGER ,
			starFiuSscsIfPerfRxUt		INTEGER ,
			starFiuSscsIfPerfTxUt		INTEGER 
		}

	starFiuSscsIfPerfSlotId		 	OBJECT-TYPE
		SYNTAX  INTEGER
		ACCESS  read-only
		STATUS  mandatory
		DESCRIPTION
			"This object indicates the slot id."
		::= { starFiuSscsIfPerfTblEntry  1 }

	 starFiuSscsIfPerfPortId		 	OBJECT-TYPE
		SYNTAX  INTEGER
		ACCESS  read-only
		STATUS  mandatory
		DESCRIPTION
			"This object indicates the Port id."
		::= { starFiuSscsIfPerfTblEntry  2 }

	 starFiuSscsIfPerfTmStp				OBJECT-TYPE
		SYNTAX  INTEGER
		ACCESS  read-only
		STATUS  mandatory
		DESCRIPTION
			"This object indicates the time stamp"
		::= { starFiuSscsIfPerfTblEntry 3 }

	starFiuSscsIfPerfRxPktSz	 	 OBJECT-TYPE
		SYNTAX  INTEGER
		ACCESS  read-only
		STATUS  mandatory
		DESCRIPTION
			"Average receive frame size."
		::= { starFiuSscsIfPerfTblEntry  4 }

	 starFiuSscsIfPerfTxpktSz			OBJECT-TYPE
		SYNTAX  INTEGER
		ACCESS  read-only
		STATUS  mandatory
		DESCRIPTION
			"Average transmitted frame size."
		::= { starFiuSscsIfPerfTblEntry  5 }

	 starFiuSscsIfPerfRxFrPs		OBJECT-TYPE
		SYNTAX  INTEGER
		ACCESS  read-only
		STATUS  mandatory
		DESCRIPTION
			"Average received number of frames per second."
		::= { starFiuSscsIfPerfTblEntry  6 }

	 starFiuSscsIfPerfTxFrPs		OBJECT-TYPE
		SYNTAX  INTEGER
		ACCESS  read-only
		STATUS  mandatory
		DESCRIPTION
			"Average transmitted number of frames per second."
		::= { starFiuSscsIfPerfTblEntry  7 }

	starFiuSscsIfPerfRxKbps	 OBJECT-TYPE
		SYNTAX  INTEGER
		ACCESS  read-only
		STATUS  mandatory
		DESCRIPTION
			"Average received number of Kbps ."
		::= { starFiuSscsIfPerfTblEntry  8 }

	 starFiuSscsIfPerfTxKbps	 OBJECT-TYPE
		SYNTAX  INTEGER
		ACCESS  read-only
		STATUS  mandatory
		DESCRIPTION
			"Average transmitted number of Kbps."
		::= { starFiuSscsIfPerfTblEntry  9 }

	 starFiuSscsIfPerfRxUt	 OBJECT-TYPE
		SYNTAX  INTEGER
		ACCESS  read-only
		STATUS  mandatory
		DESCRIPTION
			"Received line utilization."
		::= { starFiuSscsIfPerfTblEntry  10 }

	 starFiuSscsIfPerfTxUt	 OBJECT-TYPE
		SYNTAX  INTEGER
		ACCESS  read-only
		STATUS  mandatory
		DESCRIPTION
			"Transmitted line utilization ."
		::= { starFiuSscsIfPerfTblEntry  11 }

	-----------------------------------------------------------------------
	-- Star FIU PVC Endpoint Performance Table 	
	-----------------------------------------------------------------------
	starfrPVCEndptPerfTbl		OBJECT-TYPE
		SYNTAX  SEQUENCE OF StarfrPVCEndptPerfTblEntry
		ACCESS  not-accessible
		STATUS  mandatory
		DESCRIPTION
			"An entry into Frame relay transmit receive traffic statistics
			 table based on portId and DLCI."
		::= { starFrlExtnModuleInfo 3 }

	starfrPVCEndptPerfTblEntry	 OBJECT-TYPE
		SYNTAX  StarfrPVCEndptPerfTblEntry 
		ACCESS  not-accessible
		STATUS  mandatory
		DESCRIPTION
			"An entry into Fiu's Frame relay Tx/Rx permormance table."
		INDEX { starfrPVCEndptPerfSlotId, starfrPVCEndptPerfPortId,
				starfrPVCEndptPerfDLCIIndex }
		::= { starfrPVCEndptPerfTbl 1 }

	StarfrPVCEndptPerfTblEntry ::=
		SEQUENCE {
			starfrPVCEndptPerfSlotId		INTEGER ,
			starfrPVCEndptPerfPortId		INTEGER ,
			starfrPVCEndptPerfDLCIIndex		INTEGER ,
			starfrPVCEndptPerfTmStp			INTEGER ,
			starfrPVCEndptPerfRxPktSz		INTEGER ,
			starfrPVCEndptPerfTxpktSz		INTEGER ,
			starfrPVCEndptPerfRxFrPs		INTEGER ,
			starfrPVCEndptPerfTxFrPs		INTEGER ,
			starfrPVCEndptPerfRxKbps		INTEGER ,
			starfrPVCEndptPerfTxKbps		INTEGER ,
			starfrPVCEndptPerfRxUt			INTEGER ,
			starfrPVCEndptPerfTxUt			INTEGER 
		}

	starfrPVCEndptPerfSlotId		 	OBJECT-TYPE
		SYNTAX  INTEGER
		ACCESS  read-only
		STATUS  mandatory
		DESCRIPTION
			"This object indicates the slot id."
		::= { starfrPVCEndptPerfTblEntry  1 }

	 starfrPVCEndptPerfPortId		 	OBJECT-TYPE
		SYNTAX  INTEGER
		ACCESS  read-only
		STATUS  mandatory
		DESCRIPTION
			"This object indicates the Port id."
		::= { starfrPVCEndptPerfTblEntry  2 }

	 starfrPVCEndptPerfDLCIIndex		OBJECT-TYPE
		SYNTAX  INTEGER
		ACCESS  read-only
		STATUS  mandatory
		DESCRIPTION
			"This object indicates the Dlci value."
		::= { starfrPVCEndptPerfTblEntry  3 }

	 starfrPVCEndptPerfTmStp			OBJECT-TYPE
		SYNTAX  INTEGER
		ACCESS  read-only
		STATUS  mandatory
		DESCRIPTION
			"This object indicates the time stamp"
		::= { starfrPVCEndptPerfTblEntry 4 }

	 starfrPVCEndptPerfRxPktSz			OBJECT-TYPE
		SYNTAX  INTEGER
		ACCESS  read-only
		STATUS  mandatory
		DESCRIPTION
			"Average receive frame size."
		::= { starfrPVCEndptPerfTblEntry  5 }

	 starfrPVCEndptPerfTxpktSz			OBJECT-TYPE
		SYNTAX  INTEGER
		ACCESS  read-only
		STATUS  mandatory
		DESCRIPTION
			"Average transmitted frame size."
		::= { starfrPVCEndptPerfTblEntry  6 }

	 starfrPVCEndptPerfRxFrPs		OBJECT-TYPE
		SYNTAX  INTEGER
		ACCESS  read-only
		STATUS  mandatory
		DESCRIPTION
			"Average received number of frames per second."
		::= { starfrPVCEndptPerfTblEntry  7 }

	 starfrPVCEndptPerfTxFrPs		OBJECT-TYPE
		SYNTAX  INTEGER
		ACCESS  read-only
		STATUS  mandatory
		DESCRIPTION
			"Average transmitted number of frames per second."
		::= { starfrPVCEndptPerfTblEntry  8 }

	starfrPVCEndptPerfRxKbps	 OBJECT-TYPE
		SYNTAX  INTEGER
		ACCESS  read-only
		STATUS  mandatory
		DESCRIPTION
			"Average received number of Kbps ."
		::= { starfrPVCEndptPerfTblEntry  9 }

	 starfrPVCEndptPerfTxKbps	 OBJECT-TYPE
		SYNTAX  INTEGER
		ACCESS  read-only
		STATUS  mandatory
		DESCRIPTION
			"Average transmitted number of Kbps."
		::= { starfrPVCEndptPerfTblEntry  10 }

	 starfrPVCEndptPerfRxUt	 OBJECT-TYPE
		SYNTAX  INTEGER
		ACCESS  read-only
		STATUS  mandatory
		DESCRIPTION
			"Received line utilization."
		::= { starfrPVCEndptPerfTblEntry  11 }

	 starfrPVCEndptPerfTxUt	 OBJECT-TYPE
		SYNTAX  INTEGER
		ACCESS  read-only
		STATUS  mandatory
		DESCRIPTION
			"Transmitted line utilization ."
		::= { starfrPVCEndptPerfTblEntry  12 }

	------------------------------------------------------------------------
	-- Star System Aal5 Info Subgroup
	------------------------------------------------------------------------
	starAal5Info			OBJECT IDENTIFIER ::={ starSlot 17 }

	------------------------------------------------------------------------
	-- Star System Aal5 Channel Statistics Table
	------------------------------------------------------------------------
	starAal5ChannelStatisticsTbl	 OBJECT-TYPE
		SYNTAX  SEQUENCE OF StarAal5ChannelStatisticsInfoEntry
		ACCESS  not-accessible
		STATUS  mandatory
		DESCRIPTION
			"This table specifies info about the Aal5
			channel statistics on VCC basis."
		::= { starAal5Info 1 }

	starAal5ChannelStatisticsInfoEntry   OBJECT-TYPE
		SYNTAX  StarAal5ChannelStatisticsInfoEntry
		ACCESS  not-accessible
		STATUS  mandatory
		DESCRIPTION
			"Gives information about the statistics pertaining to Aal5." 
		INDEX { starAal5ChannelStatisticsSlotIdInfo,
				starAal5ChannelStatisticsChipId }
		::= { starAal5ChannelStatisticsTbl 1 }

	StarAal5ChannelStatisticsInfoEntry ::=
		SEQUENCE {
			starAal5ChannelStatisticsSlotIdInfo		INTEGER,
			starAal5ChannelStatisticsChipId			INTEGER,
			starAal5NumPktsTransmitted				INTEGER,
			starAal5NumPktsReceived					INTEGER,
			starAal5NumTimesTxQueUnderrun			INTEGER,
			starAal5NumTimesRxQueUnderrun			INTEGER,
			starAal5NumTimesPktDropped			  INTEGER,
			starAal5NumTimesInvalidCPI			  INTEGER,
			starAal5NumTimesLengthViolation		 INTEGER,
			starAal5NumTimesOverRxDataUnit		  INTEGER,
			starAal5NumTimesCRCViolation			INTEGER,
			starAal5NumTimesTimerExpire			 INTEGER
		}

	starAal5ChannelStatisticsSlotIdInfo	OBJECT-TYPE
		SYNTAX  INTEGER
		ACCESS  read-only
		STATUS  mandatory
		DESCRIPTION
			"This object indicates the slot id."
		::= { starAal5ChannelStatisticsInfoEntry 1 }

	starAal5ChannelStatisticsChipId	OBJECT-TYPE
		SYNTAX  INTEGER
		ACCESS  read-only
		STATUS  mandatory
		DESCRIPTION
			"This object indicates the chip id."
		::= { starAal5ChannelStatisticsInfoEntry 2 }

	starAal5NumPktsTransmitted		 OBJECT-TYPE
		SYNTAX  INTEGER
		ACCESS  read-only
		STATUS  mandatory
		DESCRIPTION
			"This object indicates the num pkts transmitted."
		::= { starAal5ChannelStatisticsInfoEntry 3 }

	starAal5NumPktsReceived			OBJECT-TYPE
		SYNTAX  INTEGER
		ACCESS  read-only
		STATUS  mandatory
		DESCRIPTION
			"This object indicates the num of pkts received."
		::= { starAal5ChannelStatisticsInfoEntry 4 }

	starAal5NumTimesTxQueUnderrun		OBJECT-TYPE
		SYNTAX  INTEGER
		ACCESS  read-only
		STATUS  mandatory
		DESCRIPTION
			"This object indicates the num of times the transmit
			queue underran."
		::= { starAal5ChannelStatisticsInfoEntry 5 }

	starAal5NumTimesRxQueUnderrun		OBJECT-TYPE
		SYNTAX  INTEGER
		ACCESS  read-only
		STATUS  mandatory
		DESCRIPTION
			"This object indicates the num of times the receive
			queue underran."
		::= { starAal5ChannelStatisticsInfoEntry 6 }

	starAal5NumTimesPktDropped	  OBJECT-TYPE
		SYNTAX	INTEGER
		ACCESS	read-only
		STATUS	mandatory
		DESCRIPTION
			"This object indicates the num of Packets the receive
			queue dropped."
		::= { starAal5ChannelStatisticsInfoEntry 7 }

   starAal5NumTimesInvalidCPI	OBJECT-TYPE
		SYNTAX	INTEGER
		ACCESS	read-only
		STATUS	mandatory
		DESCRIPTION
			"This object indicates Invalid CPI field."
		::= { starAal5ChannelStatisticsInfoEntry 8 }

	starAal5NumTimesLengthViolation	 OBJECT-TYPE
		SYNTAX  INTEGER
		ACCESS  read-only
		STATUS  mandatory
		DESCRIPTION
			"This object indicates the Length Violation."
		::= { starAal5ChannelStatisticsInfoEntry 9 }

	starAal5NumTimesOverRxDataUnit	  OBJECT-TYPE
		SYNTAX  INTEGER
		ACCESS  read-only
		STATUS  mandatory
		DESCRIPTION
			"This object indicates the num of Oversized received
			Data unit."
		::= { starAal5ChannelStatisticsInfoEntry 10 }
 
	starAal5NumTimesCRCViolation		OBJECT-TYPE
		SYNTAX  INTEGER
		ACCESS  read-only
		STATUS  mandatory
		DESCRIPTION
			"This object indicates the CRC Violation."
		::= { starAal5ChannelStatisticsInfoEntry 11 }
 
	starAal5NumTimesTimerExpire		 OBJECT-TYPE
		SYNTAX  INTEGER
		ACCESS  read-only
		STATUS  mandatory
		DESCRIPTION
			"This object indicates the Timer expiration."
		::= { starAal5ChannelStatisticsInfoEntry 12 }

	------------------------------------------------------------------------
	-- Star System Aal5 Status Table
	------------------------------------------------------------------------
	starAal5StatusTbl	 OBJECT-TYPE
		SYNTAX  SEQUENCE OF StarAal5StatusInfoEntry
		ACCESS  not-accessible
		STATUS  mandatory
		DESCRIPTION
			"Gives information about the Aal5 channel status." 
		::= { starAal5Info 2 }

	starAal5StatusInfoEntry   OBJECT-TYPE
		SYNTAX  StarAal5StatusInfoEntry
		ACCESS  not-accessible
		STATUS  mandatory
		DESCRIPTION
			"An entry in the Aal5InfoTbl."
		INDEX { starAal5ChannelStatusSlotIdInfo, 
				starAal5ChannelStatusChipId }
		::= { starAal5StatusTbl 1 }

	StarAal5StatusInfoEntry ::=
		SEQUENCE {
			starAal5ChannelStatusSlotIdInfo		INTEGER,
			starAal5ChannelStatusChipId			INTEGER,
			starAal5NumPktsQuedToTransmit		INTEGER,
			starAal5NumTxChannelsOpened			INTEGER,
			starAal5NumRxChannelsOpened			INTEGER
		}

	starAal5ChannelStatusSlotIdInfo	OBJECT-TYPE
		SYNTAX  INTEGER
		ACCESS  read-only
		STATUS  mandatory
		DESCRIPTION
			"This object indicates the slot id."
		::= { starAal5StatusInfoEntry 1 }

	starAal5ChannelStatusChipId	OBJECT-TYPE
		SYNTAX  INTEGER
		ACCESS  read-only
		STATUS  mandatory
		DESCRIPTION
			"This object indicates the chip id."
		::= { starAal5StatusInfoEntry 2 }

		starAal5NumPktsQuedToTransmit		OBJECT-TYPE
		SYNTAX  INTEGER
		ACCESS  read-only
		STATUS  mandatory
		DESCRIPTION
			"This object indicates the num of packets that 
				have been queued for transmission."
		::= { starAal5StatusInfoEntry 3 }

		starAal5NumTxChannelsOpened	OBJECT-TYPE
		SYNTAX  INTEGER
		ACCESS  read-only
		STATUS  mandatory
		DESCRIPTION
			"This object indicates the num of Transmit channels
			 that have been opened."
		::= { starAal5StatusInfoEntry 4 }

		starAal5NumRxChannelsOpened		OBJECT-TYPE
		SYNTAX  INTEGER
		ACCESS  read-only
		STATUS  mandatory
		DESCRIPTION
			"This object indicates the num of Receive channels
			that have been opened."
		::= { starAal5StatusInfoEntry 5 }

	------------------------------------------------------------------------
	-- Star System Aal5 Config TX Table
	------------------------------------------------------------------------
	starAal5ConfigTxVCTbl	 OBJECT-TYPE
		SYNTAX  SEQUENCE OF StarAal5ConfigTxVCInfoEntry
		ACCESS  not-accessible
		STATUS  mandatory
		DESCRIPTION
			"Gives information about the Aal5 transmit VC table
			 configuration." 
		::= { starAal5Info 3 }

	starAal5ConfigTxVCInfoEntry   OBJECT-TYPE
		SYNTAX  StarAal5ConfigTxVCInfoEntry
		ACCESS  not-accessible
		STATUS  mandatory
		DESCRIPTION
			"An entry in the Aal5ConfigTxVCTbl."
		INDEX { starAal5ConfigTxVCSlotIdInfo, starAal5ConfigTxVCChipId,
				starAal5ConfigTxVPIndex, starAal5ConfigTxVCIndex }
		::= { starAal5ConfigTxVCTbl 1 }

	StarAal5ConfigTxVCInfoEntry ::=
		SEQUENCE {
			starAal5ConfigTxVCSlotIdInfo		INTEGER,
			starAal5ConfigTxVCChipId			INTEGER,
			starAal5ConfigTxVPIndex				INTEGER,
			starAal5ConfigTxVCIndex				INTEGER,
			starAal5TxVCChannelType				INTEGER,
			starAal5CpcsUU						INTEGER,
			starAal5AvgI						INTEGER,
			starAal5AvgM						INTEGER,
			starAal5PeakRate					INTEGER,
			starAal5MaxBurst					INTEGER,
			starAal5Priority					INTEGER
		}

	starAal5ConfigTxVCSlotIdInfo	OBJECT-TYPE
		SYNTAX  INTEGER
		ACCESS  read-only
		STATUS  mandatory
		DESCRIPTION
			"This object indicates the slot id."
		::= { starAal5ConfigTxVCInfoEntry 1 }

	starAal5ConfigTxVCChipId	OBJECT-TYPE
		SYNTAX  INTEGER
		ACCESS  read-only
		STATUS  mandatory
		DESCRIPTION
			"This object indicates the chip id."
		::= { starAal5ConfigTxVCInfoEntry 2 }

	starAal5ConfigTxVPIndex			OBJECT-TYPE
		SYNTAX  INTEGER
		ACCESS  read-only
		STATUS  mandatory
		DESCRIPTION
			"This object indicates the Vp index."
		::= { starAal5ConfigTxVCInfoEntry 3 }

	starAal5ConfigTxVCIndex			OBJECT-TYPE
		SYNTAX  INTEGER
		ACCESS  read-only
		STATUS  mandatory
		DESCRIPTION
			"This object indicates the Vc index."
		::= { starAal5ConfigTxVCInfoEntry 4 }

	starAal5TxVCChannelType			OBJECT-TYPE
		SYNTAX  INTEGER
		ACCESS  read-only
		STATUS  mandatory
		DESCRIPTION
			"This object indicates the channel type."
		::= { starAal5ConfigTxVCInfoEntry 5 }

	starAal5CpcsUU				OBJECT-TYPE
		SYNTAX  INTEGER
		ACCESS  read-only
		STATUS  mandatory
		DESCRIPTION
			"This object indicates the CPCS-UU type."
		::= { starAal5ConfigTxVCInfoEntry 6 }

	starAal5AvgI				OBJECT-TYPE
		SYNTAX  INTEGER
		ACCESS  read-only
		STATUS  mandatory
		DESCRIPTION
			"This object is a traffic shaper parameter."
		::= { starAal5ConfigTxVCInfoEntry 7 }

	starAal5AvgM				OBJECT-TYPE
		SYNTAX  INTEGER
		ACCESS  read-only
		STATUS  mandatory
		DESCRIPTION
			"This object is a traffic shaper parameter."
		::= { starAal5ConfigTxVCInfoEntry 8 }

	starAal5PeakRate			OBJECT-TYPE
		SYNTAX  INTEGER
		ACCESS  read-only
		STATUS  mandatory
		DESCRIPTION
			"This object indicates the peak data transfer rate."
		::= { starAal5ConfigTxVCInfoEntry 9 }

	starAal5MaxBurst			OBJECT-TYPE
		SYNTAX  INTEGER
		ACCESS  read-only
		STATUS  mandatory
		DESCRIPTION
		"This object indicates the max burst data transfer rate."
		::= { starAal5ConfigTxVCInfoEntry 10 }

	starAal5Priority			OBJECT-TYPE
		SYNTAX  INTEGER
		ACCESS  read-only
		STATUS  mandatory
		DESCRIPTION
			"This object indicates the priority."
		::= { starAal5ConfigTxVCInfoEntry 11 }

	------------------------------------------------------------------------
	-- Star System Aal5 Config RX Table
	------------------------------------------------------------------------
	starAal5ConfigRxVCTbl	 OBJECT-TYPE
		SYNTAX  SEQUENCE OF StarAal5ConfigRxVCInfoEntry
		ACCESS  not-accessible
		STATUS  mandatory
		DESCRIPTION
			"Gives information about the Receive VC table." 
		::= { starAal5Info 4 }

	starAal5ConfigRxVCInfoEntry   OBJECT-TYPE
		SYNTAX  StarAal5ConfigRxVCInfoEntry
		ACCESS  not-accessible
		STATUS  mandatory
		DESCRIPTION
			"This table provides info about the Aal5 Rx an a VCC."
		INDEX { starAal5ConfigRxVCSlotIdInfo, starAal5ConfigRxVCChipId,
				starAal5ConfigRxVPIndex, starAal5ConfigRxVCIndex }
		::= { starAal5ConfigRxVCTbl 1 }

	StarAal5ConfigRxVCInfoEntry ::=
		SEQUENCE {
			starAal5ConfigRxVCSlotIdInfo	INTEGER,
			starAal5ConfigRxVCChipId		INTEGER,
			starAal5ConfigRxVPIndex			INTEGER,
			starAal5ConfigRxVCIndex			INTEGER,
			starAal5PoolNum					INTEGER,
			starAal5NumOAMDrops				INTEGER,
			starAal5RxVCChannelType			INTEGER,
			starAal5MaxNumSegments			INTEGER
		}

	starAal5ConfigRxVCSlotIdInfo	OBJECT-TYPE
		SYNTAX  INTEGER
		ACCESS  read-only
		STATUS  mandatory
		DESCRIPTION
			"This object indicates the slot id."
		::= { starAal5ConfigRxVCInfoEntry 1 }

	starAal5ConfigRxVCChipId	OBJECT-TYPE
		SYNTAX  INTEGER
		ACCESS  read-only
		STATUS  mandatory
		DESCRIPTION
			"This object indicates the chip id."
		::= { starAal5ConfigRxVCInfoEntry 2 }

	starAal5ConfigRxVPIndex			OBJECT-TYPE
		SYNTAX  INTEGER
		ACCESS  read-only
		STATUS  mandatory
		DESCRIPTION
			"This object indicates the Vp index."
		::= { starAal5ConfigRxVCInfoEntry 3 }

	starAal5ConfigRxVCIndex			OBJECT-TYPE
		SYNTAX  INTEGER
		ACCESS  read-only
		STATUS  mandatory
		DESCRIPTION
			"This object indicates the Vc index."
		::= { starAal5ConfigRxVCInfoEntry 4 }

	starAal5PoolNum				OBJECT-TYPE
		SYNTAX  INTEGER
		ACCESS  read-only
		STATUS  mandatory
		DESCRIPTION
			"This object indicates the Pool number."
		::= { starAal5ConfigRxVCInfoEntry 5 }

	starAal5NumOAMDrops			OBJECT-TYPE
		SYNTAX  INTEGER
		ACCESS  read-only
		STATUS  mandatory
		DESCRIPTION
			"This object indicates the num of cell drops by OAM."
		::= { starAal5ConfigRxVCInfoEntry 6 }

	starAal5RxVCChannelType			OBJECT-TYPE
		SYNTAX  INTEGER
		ACCESS  read-only
		STATUS  mandatory
		DESCRIPTION
			"This object indicates the VC channel type."
		::= { starAal5ConfigRxVCInfoEntry 7 }

	starAal5MaxNumSegments			OBJECT-TYPE
		SYNTAX  INTEGER
		ACCESS  read-only
		STATUS  mandatory
		DESCRIPTION
			"This object indicates the max num of segments."
		::= { starAal5ConfigRxVCInfoEntry 8 }

	------------------------------------------------------------------------
	-- Star System Route88 Chip Subgroup
	------------------------------------------------------------------------
	starRout88Info			OBJECT IDENTIFIER ::={ starSlot 18 }

	------------------------------------------------------------------------
	-- Star System Route88 Chip Info Table
	------------------------------------------------------------------------
	starRoutInfoTbl	 OBJECT-TYPE
		SYNTAX  SEQUENCE OF StarRoutInfoEntry
		ACCESS  not-accessible
		STATUS  mandatory
		DESCRIPTION
			"Gives information about the registers in 
				the rout chip." 
		::= { starRout88Info 1 }

	starRoutInfoEntry   OBJECT-TYPE
		SYNTAX  StarRoutInfoEntry
		ACCESS  not-accessible
		STATUS  mandatory
		DESCRIPTION
			"An entry in the RoutInfoTbl."
		INDEX { starSlotIdRoutInfo, starRoutChipId }
		::= { starRoutInfoTbl 1 }

	StarRoutInfoEntry ::=
		SEQUENCE {
			starSlotIdRoutInfo			INTEGER,
			starRoutChipId				INTEGER,
			starRoutCurrentState		INTEGER,
			starRoutChipVersion			INTEGER,
			starRoutSramConfig			INTEGER,
			starRoutBckPressureDly		INTEGER,
			starRoutNumVpi				INTEGER,
			starRoutConnectToSar		INTEGER,
			starRoutWatchDogConfig		INTEGER,
			starRoutEmptyQstate			INTEGER,
			starRoutTxMarkedCellCnt		Counter,
			starRoutRxMarkedCellCnt		Counter,
			starRoutTxParityFailCnt		Counter,
			starRoutBpIgnoredCnt		Counter,
			starRoutLiveFailCnt			Counter,
			starRoutWdFailCnt			Counter,
			starRoutEmptyQCongQd		INTEGER,
			starRoutEmptyQCurQd			INTEGER,
			starRoutRatioAOrder1		INTEGER,
			starRoutRatioBOrder1		INTEGER,
			starRoutRatioAOrder2		INTEGER,
			starRoutRatioBOrder2		INTEGER
		}

	starSlotIdRoutInfo	OBJECT-TYPE
		SYNTAX  INTEGER
		ACCESS  read-only
		STATUS  mandatory
		DESCRIPTION
			"This object indicates the slot id."
		::= { starRoutInfoEntry 1 }

	starRoutChipId	OBJECT-TYPE
		SYNTAX  INTEGER
		ACCESS  read-only
		STATUS  mandatory
		DESCRIPTION
			"This object indicates the rout chip
			 whose info is needed."
		::= { starRoutInfoEntry  2 }

	starRoutCurrentState		OBJECT-TYPE
		SYNTAX  INTEGER {
			init (1) ,
			operational (2)
		}
		ACCESS  read-only
		STATUS  mandatory
		DESCRIPTION
			"This object describes the operational
			 state of rout chip."
		::= { starRoutInfoEntry 3 }

	starRoutChipVersion OBJECT-TYPE
		SYNTAX  INTEGER
		ACCESS  read-only
		STATUS  mandatory
		DESCRIPTION
			"This object indicates the version 
			number of the rout chip." 
		::= { starRoutInfoEntry 4 }

	starRoutSramConfig  OBJECT-TYPE
		SYNTAX  INTEGER {
			ram2x32x8 (1) ,
			ram2x128x8 (2) ,
			ram4x128x8 (3)
		}
		ACCESS  read-only
		STATUS  mandatory
		DESCRIPTION
			"Indicates how the SRAM is configured for the
			 rout chip: it can be two 32K * 8 SRAM,
			 two 128K * 8 SRAM or four 128 * 8 SRAM." 
		::= { starRoutInfoEntry 5 }

	starRoutBckPressureDly	OBJECT-TYPE
		SYNTAX  INTEGER  {
			noDelay (1) ,
			clk2Delay (2) ,
			clk4Delay (3)
		}
		ACCESS  read-only
		STATUS  mandatory
		DESCRIPTION
			"This object indicates whether there is no
			 back pressure delay, two SE_CLK back pressure
			 delay or four SE_CLK back pressure delay."
		::= { starRoutInfoEntry 6 }

	starRoutNumVpi	OBJECT-TYPE
		SYNTAX  INTEGER
		ACCESS  read-only
		STATUS  mandatory
		DESCRIPTION
			"This object indicates the no of VPI, VCI bits
			 that will be used in the index to the
			 channel control block." 
		::= { starRoutInfoEntry 7 }

	starRoutConnectToSar		OBJECT-TYPE
		SYNTAX  INTEGER {
			connectPHY (1) ,
			connectSAR (2)
		}
		ACCESS  read-only
		STATUS  mandatory
		DESCRIPTION
			"This object indicates whether the connection
			 is to the PHY layer or SAR layer."
		::= { starRoutInfoEntry 8 }

	starRoutWatchDogConfig	OBJECT-TYPE
		SYNTAX  INTEGER
		ACCESS  read-only
		STATUS  mandatory
		DESCRIPTION
			"This object indicates the number of cells times
			 into(*) 32 which the UTOPIA TX_FULL
			 must be deasserted at least once."
		::= { starRoutInfoEntry 9 }

	starRoutEmptyQstate		 OBJECT-TYPE
		SYNTAX  INTEGER {
			inCongestion (1),
			notInCongestion (2)
		}
		ACCESS  read-only
		STATUS  mandatory
		DESCRIPTION
			"This object indicates whether the empty queue
			 in the rout device is congested or not."
		::= { starRoutInfoEntry 10 }

	starRoutTxMarkedCellCnt	 OBJECT-TYPE
		SYNTAX  Counter
		ACCESS  read-only
		STATUS  mandatory
		DESCRIPTION
			"This object indicates the number of cells
			 modulo 16 from the switch fabric which had
			 Tag(9,1) set to 1."
		::= { starRoutInfoEntry 11 }

	starRoutRxMarkedCellCnt	 OBJECT-TYPE
		SYNTAX  Counter
		ACCESS  read-only
		STATUS  mandatory
		DESCRIPTION
			"This object indicates the number of cells
			 modulo 16 to the switch fabric which had
			 Tag(9,1) set to 1."
		::= { starRoutInfoEntry  12 }

	starRoutTxParityFailCnt	 OBJECT-TYPE
		SYNTAX  Counter
		ACCESS  read-only
		STATUS  mandatory
		DESCRIPTION
			"This object indicates the number of times
			the transmit parity was bad."
		::= { starRoutInfoEntry  13 }

	starRoutBpIgnoredCnt	 OBJECT-TYPE
		SYNTAX  Counter
		ACCESS  read-only
		STATUS  mandatory
		DESCRIPTION
			"This object indicates the number of times
			the back pressure was ignored."
		::= { starRoutInfoEntry  14 }

	starRoutLiveFailCnt	 OBJECT-TYPE
		SYNTAX  Counter
		ACCESS  read-only
		STATUS  mandatory
		DESCRIPTION
			"This object indicates the
			back pressure live fail count."
		::= { starRoutInfoEntry  15 }

	starRoutWdFailCnt	 OBJECT-TYPE
		SYNTAX  Counter
		ACCESS  read-only
		STATUS  mandatory
		DESCRIPTION
			"This object indicates the number of times
			the output watchdog timer expired."
		::= { starRoutInfoEntry  16 }

	starRoutEmptyQCongQd		OBJECT-TYPE
		SYNTAX   INTEGER
		ACCESS  read-only
		STATUS  mandatory
		DESCRIPTION
			"This object indicates the number of cell
			 buffers below which the device 
			 will enter the empty congestion state."
		::= { starRoutInfoEntry  17 }

	starRoutEmptyQCurQd		 OBJECT-TYPE
		SYNTAX  INTEGER
		ACCESS  read-only
		STATUS  mandatory
		DESCRIPTION
			"This object indicates the current empty
			 queue depth in the rout."
		::= { starRoutInfoEntry  18 }

	starRoutRatioAOrder1		 OBJECT-TYPE
		SYNTAX  INTEGER
		ACCESS  read-only
		STATUS  mandatory
		DESCRIPTION
			" This object specifies the num of eighths
			of the priority Queue in which Queue A is 
			served first."
		::= { starRoutInfoEntry  19 }

	starRoutRatioBOrder1		 OBJECT-TYPE
		SYNTAX  INTEGER
		ACCESS  read-only
		STATUS  mandatory
		DESCRIPTION
			" This object specifies the num of eighths
			of the priority Queue in which Queue B is 
			served first."
		::= { starRoutInfoEntry  20 }

	starRoutRatioAOrder2		 OBJECT-TYPE
		SYNTAX  INTEGER
		ACCESS  read-only
		STATUS  mandatory
		DESCRIPTION
			" This object specifies the num of eighths
			of the priority Queue in which Queue A is 
			served second."
		::= { starRoutInfoEntry  21 }

	starRoutRatioBOrder2		 OBJECT-TYPE
		SYNTAX  INTEGER
		ACCESS  read-only
		STATUS  mandatory
		DESCRIPTION
			" This object specifies the num of eighths
			of the priority Queue in which Queue B is 
			served second."
		::= { starRoutInfoEntry 22 }

	------------------------------------------------------------------------
	-- Star System Route88 Priority Queue Info Table
	------------------------------------------------------------------------
	starRoutPrioQInfoTbl		OBJECT-TYPE
		SYNTAX  SEQUENCE OF  StarRoutPrioQInfoEntry
		ACCESS  not-accessible
		STATUS  mandatory
		DESCRIPTION
			"Gives information about the seven priority queues."
		::= { starRout88Info 2 }

	starRoutPrioQInfoEntry	OBJECT-TYPE
		SYNTAX  StarRoutPrioQInfoEntry
		ACCESS  not-accessible
		STATUS  mandatory
		DESCRIPTION
			"An entry in the RoutPrioQInfoTbl." 
		INDEX { starSlotIdPrioQInfo, starPrioQRoutChipId, starRoutPrioQType }
		::= { starRoutPrioQInfoTbl 1 }

	StarRoutPrioQInfoEntry ::=
		SEQUENCE {
			starSlotIdPrioQInfo			INTEGER,
			starPrioQRoutChipId			INTEGER,
			starRoutPrioQType			INTEGER,
			starRoutPerPrioMaximumQd	INTEGER,
			starRoutPerPrioCongestionQd INTEGER,
			starRoutPerPrioCurrentQd	INTEGER,
			starRoutIsQCongested		INTEGER,
			starRoutIsCellInQueue		INTEGER
		}

	starSlotIdPrioQInfo	OBJECT-TYPE
		SYNTAX  INTEGER
		ACCESS  read-only
		STATUS  mandatory
		DESCRIPTION
			"This object indicates the slot id."
		::= { starRoutPrioQInfoEntry 1 }

	starPrioQRoutChipId	OBJECT-TYPE
		SYNTAX  INTEGER
		ACCESS  read-only
		STATUS  mandatory
		DESCRIPTION
			"This object indicates the rout chip whose
			 info is needed." 
		::= { starRoutPrioQInfoEntry  2 }

	starRoutPrioQType   OBJECT-TYPE
		SYNTAX  INTEGER{
			highPriorityA (1),
			multicastQueue (2),
			pba (3),
			pbb (4),
			pbc (5),
			highPriorityB (6),
			oamReceiveQ (7)
		}
		ACCESS  read-only
		STATUS		mandatory
		DESCRIPTION
			"The value indicates the queue type whose info
			 is to be retrived." 
		::= { starRoutPrioQInfoEntry  3 }

	starRoutPerPrioMaximumQd	OBJECT-TYPE
		SYNTAX  INTEGER
		ACCESS  read-only
		STATUS  mandatory
		DESCRIPTION
			"Maximum per priority queue depth."
		::= { starRoutPrioQInfoEntry  4 }

	starRoutPerPrioCongestionQd	 OBJECT-TYPE
		SYNTAX  INTEGER
		ACCESS  read-only
		STATUS  mandatory
		DESCRIPTION
			"Congestion per priority queue depth."
		::= { starRoutPrioQInfoEntry  5 }

	starRoutPerPrioCurrentQd		OBJECT-TYPE
		SYNTAX  INTEGER
		ACCESS  read-only
		STATUS  mandatory
		DESCRIPTION
			"Current per priority queue depth."
		::= { starRoutPrioQInfoEntry  6 }

	starRoutIsQCongested		OBJECT-TYPE
		SYNTAX  INTEGER{
			qCongested (1),
			qNotCongested (2)
		}
		ACCESS  read-only
		STATUS  mandatory
		DESCRIPTION
			"Maximum per priority queue depth."
		::= { starRoutPrioQInfoEntry  7 }

	starRoutIsCellInQueue	 OBJECT-TYPE
		SYNTAX  INTEGER{
			cellPresent (1),
			cellNotPresent (2)
		}
		ACCESS  read-only
		STATUS  mandatory
		DESCRIPTION
			"Maximum per priority queue depth."
		::= { starRoutPrioQInfoEntry  8 }

	------------------------------------------------------------------------
	-- Star System Route CCB Info Table
	------------------------------------------------------------------------
	starRoutCcbInfoTbl  OBJECT-TYPE
		SYNTAX  SEQUENCE OF  StarRoutCcbInfoEntry
		ACCESS  not-accessible
		STATUS  mandatory
		DESCRIPTION
			"Gives information about Channel control block
			 maintained for each VP, VC." 
		::= { starRout88Info 3 }

	starRoutCcbInfoEntry		OBJECT-TYPE
		SYNTAX  StarRoutCcbInfoEntry
		ACCESS  not-accessible
		STATUS  mandatory
		DESCRIPTION
			"An entry in the routCcbInfoTbl." 
		INDEX { starCcbInfoSlotId, starCcbRoutChipId, starRoutVp, starRoutVc }
		::= { starRoutCcbInfoTbl 1 }

	StarRoutCcbInfoEntry ::=
		SEQUENCE {
			starCcbInfoSlotId		INTEGER,
			starCcbRoutChipId		INTEGER,
			starRoutVp				INTEGER,
			starRoutVc				INTEGER,
			starRoutEnClpDrop		INTEGER,
			starRoutEnAal5Epd		INTEGER,
			starRoutEnEfciMark		INTEGER,
			starRoutEnExtDrop		INTEGER,
			starRoutPti7			INTEGER,
			starRoutPti6			INTEGER,
			starRoutPti5			INTEGER,
			starRoutPti4			INTEGER,
			starRoutCcbQueue		INTEGER,
			starRoutMaxPerVcQd		INTEGER,
			starRoutCongPerVcQd		INTEGER,
			starRoutCurPerVcQd		INTEGER,
			starRoutTags			OCTET STRING ,
			starRoutIsVpTranslated  INTEGER,
			starRoutIsVcTranslated  INTEGER,
			starRoutNewVp			INTEGER,
			starRoutNewVc			INTEGER,
			starRoutCellRxCnt		Counter,
			starRoutCellsDrpdCnt	Counter,
			starRoutCongCellCnt	Counter
		}

	starCcbInfoSlotId	OBJECT-TYPE
		SYNTAX  INTEGER
		ACCESS  read-only
		STATUS  mandatory
		DESCRIPTION
			"This object indicates the slot id."
		::= { starRoutCcbInfoEntry 1 }

	starCcbRoutChipId   OBJECT-TYPE
		SYNTAX  INTEGER
		ACCESS  read-only
		STATUS  mandatory
		DESCRIPTION
			"This object indicates the rout chip
			 whose info is needed."
		::= { starRoutCcbInfoEntry  2 }

	starRoutVp  OBJECT-TYPE
		SYNTAX  INTEGER
		ACCESS  read-only
		STATUS  mandatory
		DESCRIPTION
			" The virtual path of the call."
		::= { starRoutCcbInfoEntry  3 }

	starRoutVc  OBJECT-TYPE
		SYNTAX  INTEGER
		ACCESS  read-only
		STATUS  mandatory
		DESCRIPTION
			" The virtual channel of the call."
		::= { starRoutCcbInfoEntry  4 }

	starRoutEnClpDrop   OBJECT-TYPE
		SYNTAX  INTEGER{
			enablesClpDrop (1),
			disablesClpDrop (2)
		}
		ACCESS  read-write
		STATUS  mandatory
		DESCRIPTION
			"Indicates wheter CLP dropping when either the VC,
			 the priority, or the device is in the congested
			 state is Enable or Disabled."
		::= { starRoutCcbInfoEntry  5 }

	starRoutEnAal5Epd   OBJECT-TYPE
		SYNTAX  INTEGER{
			enablesAal5Discard (1),
			disablesAal5Discard (2)
		}
		ACCESS  read-write
		STATUS  mandatory
		DESCRIPTION
			"Indicates whether the device Enables/Disables
			AAL5 early packed discard when either VC, the
			priority, or the device is in the congested state."
		::= { starRoutCcbInfoEntry  6 }

	starRoutEnEfciMark  OBJECT-TYPE
		SYNTAX  INTEGER{
			enablesEfciMarking (1),
			disablesEfciMarking (2)
		}
		ACCESS  read-write
		STATUS  mandatory
		DESCRIPTION
			"Indicates whether the device Enables/Disables
			EFCI cell marking  when either VC, the
			priority, or the device is in the congested
			state as the cells are dequeued."
		::= { starRoutCcbInfoEntry  7 }

	starRoutEnExtDrop   OBJECT-TYPE
		SYNTAX  INTEGER{
			enablesExtDrop (1),
			disablesExtDrop (2)
		}
		ACCESS  read-write
		STATUS  mandatory
		DESCRIPTION
			"Indicates whether the device enables/disables
			dropping of cells if EXT_DROP pin is asserted."
		::= { starRoutCcbInfoEntry  8 }

	starRoutPti7		OBJECT-TYPE
		SYNTAX  INTEGER{
			putPti (1),
			passPti (2)
		}
		ACCESS  read-write
		STATUS  mandatory
		DESCRIPTION
			"Indicates whether the device puts/passes
			received cells of PTI7 into OAM receive queue."
		::= { starRoutCcbInfoEntry  9 }

	starRoutPti6		OBJECT-TYPE
		SYNTAX  INTEGER{
			putPti (1),
			passPti (2)
		}
		ACCESS  read-write
		STATUS  mandatory
		DESCRIPTION
			"Indicates whether the device puts/passes
			received cells of PTI6 into OAM receive queue."
		::= { starRoutCcbInfoEntry  10 }
 
	starRoutPti5		OBJECT-TYPE
		SYNTAX  INTEGER{
			putPti (1),
			passPti (2)
		}
		ACCESS  read-write
		STATUS  mandatory
		DESCRIPTION
			"Indicates whether the device puts/passes
			received cells of PTI5 into OAM receive queue."
		::= { starRoutCcbInfoEntry  11 }

	starRoutPti4		OBJECT-TYPE
		SYNTAX  INTEGER{
			putPti (1),
			passPti (2)
		}
		ACCESS  read-write
		STATUS  mandatory
		DESCRIPTION
			"Indicates whether the device puts/passes
			received cells of PTI4 into OAM receive queue."
		::= { starRoutCcbInfoEntry  12 }

	starRoutCcbQueue	OBJECT-TYPE
		SYNTAX  INTEGER{
			highPriorityA (1),
			multicastQueue (2),
			pbA (3),
			pbB (4),
			pbC (5),
			highPriorityB (6),
			oamReceiveQ (7)
		}
		ACCESS  read-only
		STATUS  mandatory
		DESCRIPTION
			"Indicates the queue type in which the cells of
			the given VP, VC will be placed."
		::= { starRoutCcbInfoEntry  13 }

	starRoutMaxPerVcQd  OBJECT-TYPE
		SYNTAX  INTEGER
		ACCESS  read-only
		STATUS  mandatory
		DESCRIPTION
			"This object gives the per VC upper limit to
			the depth of the queue."
		::= { starRoutCcbInfoEntry  14 }

	starRoutCongPerVcQd OBJECT-TYPE
		SYNTAX  INTEGER
		ACCESS  read-only
		STATUS  mandatory
		DESCRIPTION
			"This object indicates the per VC queue depth
			above which the enabled congestion management
			actions are taken."
		::= { starRoutCcbInfoEntry  15 }

	starRoutCurPerVcQd  OBJECT-TYPE
		SYNTAX  INTEGER
		ACCESS  read-only
		STATUS  mandatory
		DESCRIPTION
			"current per VC queue depth."
		::= { starRoutCcbInfoEntry 16 }

	starRoutTags	OBJECT-TYPE
		SYNTAX  OCTET STRING ( SIZE (0..4 ) )
		ACCESS  read-only
		STATUS  mandatory
		DESCRIPTION
			"Tag information inserted into SE_D_OUT immediately
			after the QUEUE field."
		::= { starRoutCcbInfoEntry 17 }

	starRoutIsVpTranslated	OBJECT-TYPE
		SYNTAX  INTEGER {
			translateVP (1) ,
			doNotTranslateVP (2)
		}
		ACCESS  read-only
		STATUS  mandatory
		DESCRIPTION
			"Indicates whether VP will be translated
				1 implies VP-is-translated
				2 implies VP-is-not-translated."
		::= { starRoutCcbInfoEntry 18 }

	starRoutIsVcTranslated	OBJECT-TYPE
		SYNTAX  INTEGER  {
			translateVC (1) ,
			doNotTranslateVC (2)
		}
		ACCESS  read-only
		STATUS  mandatory
		DESCRIPTION
			"Indicates whether VC will be translated
				1 implies VC-is-translated
				2 implies VC-is-not-translated."
		::= { starRoutCcbInfoEntry 19 }

	starRoutNewVp   OBJECT-TYPE
		SYNTAX  INTEGER
		ACCESS  read-only
		STATUS  mandatory
		DESCRIPTION
			"The New VPI value to which the cells
			 are translated."
		::= { starRoutCcbInfoEntry 20 }

	starRoutNewVc   OBJECT-TYPE
		SYNTAX  INTEGER
		ACCESS  read-only
		STATUS  mandatory
		DESCRIPTION
			"The New VCI value to which the cells
			 are translated."
		::= { starRoutCcbInfoEntry 21 }

	starRoutCellRxCnt   OBJECT-TYPE
		SYNTAX  Counter
		ACCESS  read-only
		STATUS  mandatory
		DESCRIPTION
			"Count of the cells received."
		::= { starRoutCcbInfoEntry 22 }

	starRoutCellsDrpdCnt   OBJECT-TYPE
		SYNTAX  Counter
		ACCESS  read-only
		STATUS  mandatory
		DESCRIPTION
			"The count of the cells dropped."
		::= { starRoutCcbInfoEntry 23 }

	starRoutCongCellCnt OBJECT-TYPE
		SYNTAX  Counter
		ACCESS  read-only
		STATUS  mandatory
		DESCRIPTION
			"Count of the EFCI bits newly marked."
		::= { starRoutCcbInfoEntry 24 }

	------------------------------------------------------------------------
	-- Star System HDLC Controller Subgroup
	------------------------------------------------------------------------
	starHdlcControllerInfo		 OBJECT IDENTIFIER ::={ starSlot 19 }

	------------------------------------------------------------------------
	-- Star System FIU HDLC Status Table
	------------------------------------------------------------------------
	starFiuHdlcStatusTbl  OBJECT-TYPE
		SYNTAX  SEQUENCE OF  StarFiuHdlcStatusInfoEntry
		ACCESS  not-accessible
		STATUS  mandatory
		DESCRIPTION
			"Gives information about HDLC driver parameters." 
		::= { starHdlcControllerInfo 1 }

	starFiuHdlcStatusInfoEntry		OBJECT-TYPE
		SYNTAX  StarFiuHdlcStatusInfoEntry
		ACCESS  not-accessible
		STATUS  mandatory
		DESCRIPTION
			"An entry in the Hdlc status table." 
		INDEX { starFiuHdlcStatusSlotId, starFiuHdlcStatusChipId }
		::= { starFiuHdlcStatusTbl 1 }

	StarFiuHdlcStatusInfoEntry ::=
		SEQUENCE {
			starFiuHdlcStatusSlotId		INTEGER,
			starFiuHdlcStatusChipId		INTEGER,
			starFiuHdlcRxBuffOverFlow	INTEGER,
			starFiuHdlcRxCountOverflow	INTEGER,
			starFiuHdlcRxShort			INTEGER,
			starFiuHdlcRxAbort			INTEGER,
			starFiuHdlcRxOverrun		INTEGER,
			starFiuHdlcRxCrc			INTEGER,
			starFiuHdlcRxPduCount		INTEGER,
			starFiuHdlcRxByteCount		INTEGER,
			starFiuHdlcTxUnderrun		INTEGER,
			starFiuHdlcTxPduCount		INTEGER,
			starFiuHdlcTxByteCount		INTEGER,
			starFiuHdlcLinkstatus		INTEGER,
			starFiuHdlcTxBuffOverFlow	INTEGER,
			starFiuHdlcTxCountOverflow	INTEGER
		}

	starFiuHdlcStatusSlotId		OBJECT-TYPE
		SYNTAX  INTEGER
		ACCESS  read-only
		STATUS  mandatory
		DESCRIPTION
			"This object indicates the slot id."
		::= { starFiuHdlcStatusInfoEntry 1 }

	starFiuHdlcStatusChipId	OBJECT-TYPE
		SYNTAX  INTEGER
		ACCESS  read-only
		STATUS  mandatory
		DESCRIPTION
			"This object indicates the Hdlc chip
			 whose info is needed."
		::= { starFiuHdlcStatusInfoEntry  2 }

	starFiuHdlcRxBuffOverFlow	 OBJECT-TYPE
		SYNTAX  INTEGER
		ACCESS  read-only
		STATUS  mandatory
		DESCRIPTION
			"This object indicates the receive buffer 
			overflow."
		::= { starFiuHdlcStatusInfoEntry  3 }

	starFiuHdlcRxCountOverflow		OBJECT-TYPE
		SYNTAX  INTEGER
		ACCESS  read-only
		STATUS  mandatory
		DESCRIPTION
			"This object indicates the receive count 
			overflow."
		::= { starFiuHdlcStatusInfoEntry  4 }

	 starFiuHdlcRxShort		OBJECT-TYPE
		SYNTAX  INTEGER
		ACCESS  read-only
		STATUS  mandatory
		DESCRIPTION
			"This object indicates the receive buffer is
			short of what is required."
		::= { starFiuHdlcStatusInfoEntry  5 }

	 starFiuHdlcRxAbort		OBJECT-TYPE
		SYNTAX  INTEGER
		ACCESS  read-only
		STATUS  mandatory
		DESCRIPTION
			"This object indicates a receive abort ."
		::= { starFiuHdlcStatusInfoEntry  6 }

	starFiuHdlcRxOverrun	 OBJECT-TYPE
		SYNTAX  INTEGER
		ACCESS  read-only
		STATUS  mandatory
		DESCRIPTION
			"This object indicates that the receive buffer
			data was overwritten by new incoming data."
		::= { starFiuHdlcStatusInfoEntry  7 }

	starFiuHdlcRxCrc	 OBJECT-TYPE
		SYNTAX  INTEGER
		ACCESS  read-only
		STATUS  mandatory
		DESCRIPTION
			"This object indicates the receive crc."
		::= { starFiuHdlcStatusInfoEntry  8 }

	 starFiuHdlcRxPduCount	 OBJECT-TYPE
		SYNTAX  INTEGER
		ACCESS  read-only
		STATUS  mandatory
		DESCRIPTION
			"This object indicates the num of PDU's
			received."
		::= { starFiuHdlcStatusInfoEntry  9 }

	 starFiuHdlcRxByteCount		OBJECT-TYPE
		SYNTAX  INTEGER
		ACCESS  read-only
		STATUS  mandatory
		DESCRIPTION
			"This object indicates the received byte count."
		::= { starFiuHdlcStatusInfoEntry  10 }

	starFiuHdlcTxUnderrun		OBJECT-TYPE
		SYNTAX  INTEGER
		ACCESS  read-only
		STATUS  mandatory
		DESCRIPTION
			"This object indicates that the transmitter has
			 run out of data to transmit."  
		::= { starFiuHdlcStatusInfoEntry  11 }

	 starFiuHdlcTxPduCount		OBJECT-TYPE
		SYNTAX  INTEGER
		ACCESS  read-only
		STATUS  mandatory
		DESCRIPTION
			"This object indicates the num of PDU's in the
			transmit buffer ."
		::= { starFiuHdlcStatusInfoEntry  12 }

	 starFiuHdlcTxByteCount		OBJECT-TYPE
		SYNTAX  INTEGER
		ACCESS  read-only
		STATUS  mandatory
		DESCRIPTION
			"This object indicates the num of bytes in the
			transmit buffer."
		::= { starFiuHdlcStatusInfoEntry  13 }

	starFiuHdlcLinkstatus		OBJECT-TYPE
		SYNTAX  INTEGER
		ACCESS  read-only
		STATUS  mandatory
		DESCRIPTION
			"This object indicates the Link Status."
		::= { starFiuHdlcStatusInfoEntry  14 }

	 starFiuHdlcTxBuffOverFlow	 OBJECT-TYPE
		SYNTAX  INTEGER
		ACCESS  read-only
		STATUS  mandatory
		DESCRIPTION
			"This object indicates the transmit buffer
			overflow."
		::= { starFiuHdlcStatusInfoEntry  15 }

	starFiuHdlcTxCountOverflow	OBJECT-TYPE
		SYNTAX  INTEGER
		ACCESS  read-only
		STATUS  mandatory
		DESCRIPTION
			"This object indicates the transmit count
			overflow."
		::= { starFiuHdlcStatusInfoEntry  16 }

	-----------------------------------------------------------------------
	-- Star Rcl Info Subgroup (from FutureSoft - 12/12/95)
	-----------------------------------------------------------------------
	starRclInfo		OBJECT IDENTIFIER ::= { starSlot 20 }

	-----------------------------------------------------------------------
	-- Star Rcl Info Table
	-----------------------------------------------------------------------
	starRclInfoTbl	 OBJECT-TYPE
		SYNTAX  SEQUENCE OF StarRclInfoEntry
		ACCESS  not-accessible
		STATUS  mandatory
		DESCRIPTION
			"This table contains duplication related objects."
		::= { starRclInfo 1 }

	starRclInfoEntry	 OBJECT-TYPE
		SYNTAX  StarRclInfoEntry
		ACCESS  not-accessible
		STATUS  mandatory
		DESCRIPTION
			"An entry into RclInfoTbl."
		INDEX { starRclInfoSlotId }
		::= { starRclInfoTbl 1 }

	StarRclInfoEntry ::=
		SEQUENCE {
			starRclInfoSlotId			INTEGER ,
			starRclNumRegAppl			INTEGER ,
			starRclNumSwitchovers		INTEGER ,
			starRclSwitchoverThreshold	INTEGER ,
			starRclSwitchoverTimeLimit	INTEGER ,
			starRclSwitchoverResetTime	INTEGER ,
			starRclLockoutFlag			INTEGER ,
			starRclHmcTestStatus		INTEGER ,
			starRclHmcTestResult		INTEGER ,
			starRclModuleStatus		INTEGER ,
			starRclSwitchoverReason	INTEGER ,
			starRclSwitchoverTime	INTEGER
		}

	starRclInfoSlotId	OBJECT-TYPE
		SYNTAX  INTEGER
		ACCESS  read-only
		STATUS  mandatory
		DESCRIPTION
			"This object indicates the slot id."
		::= { starRclInfoEntry 1 }

	starRclNumRegAppl  OBJECT-TYPE
		SYNTAX  INTEGER
		ACCESS  read-only
		STATUS  mandatory
		DESCRIPTION
			"This object indicates the number of
			 applications registered with the RCL for
			 data shadowing."
		::= { starRclInfoEntry 2 }

	starRclNumSwitchovers	 OBJECT-TYPE
		SYNTAX  INTEGER 
		ACCESS  read-only
		STATUS  mandatory
		DESCRIPTION
			"Indicates the number of times switchover has occurred
			since the time the system had come up."
		::= { starRclInfoEntry 3 }

	starRclSwitchoverThreshold	OBJECT-TYPE
		SYNTAX  INTEGER 
		ACCESS  read-write
		STATUS  mandatory
		DESCRIPTION
			"Indicates the threshold of the number of times
			 switchover can occur within the specified time."
		::= { starRclInfoEntry 4 }

	starRclSwitchoverTimeLimit	OBJECT-TYPE
		SYNTAX  INTEGER 
		ACCESS  read-write
		STATUS  mandatory
		DESCRIPTION
			"Indicates the time within which number of switchovers
			 should not exceed the maximum."
		::= { starRclInfoEntry 5 }

	starRclSwitchoverResetTime	OBJECT-TYPE
		SYNTAX  INTEGER 
		ACCESS  read-write
		STATUS  mandatory
		DESCRIPTION
			"Indicates the time for which there should be no 
			 switchover before the module can come out of lockout state."
		::= { starRclInfoEntry 6 }

	starRclLockoutFlag		 OBJECT-TYPE
		SYNTAX  INTEGER {
			lock (1),
			unlock (2)
		}
		ACCESS  read-write
		STATUS  mandatory
		DESCRIPTION
			"If this object is set(lock) then a switchover of
			 active to standby or standby to active cannot take place."
		::= { starRclInfoEntry 7 }
	
	starRclHmcTestStatus	OBJECT-TYPE
		SYNTAX  INTEGER {
			idle (1),
			testInProgress (2),
			testInitiatedByOtherModule (3),
			initiateTest (4)
		}
		ACCESS  read-write
		STATUS  mandatory
		DESCRIPTION
			"Indicates the status of the HMC test.
			 A set(write) to 'initiatetest' is performed
			 to initiate the diagnostic."
		::= { starRclInfoEntry 8 }

	starRclHmcTestResult	OBJECT-TYPE
		SYNTAX  INTEGER {
			testSuccess (1),
			testCancelDueToStateChange (2),
			testCancelDueToTimeout (3),
			testFail (4)
		}
		ACCESS  read-only
		STATUS  mandatory
		DESCRIPTION
			"Indicates the result of the last HMC test carried out."
		::= { starRclInfoEntry 9 }

	starRclModuleStatus		OBJECT-TYPE
		SYNTAX  INTEGER {
			init (1),
			active (2),
			standby (3),
			standalone (4)
		}
		ACCESS  read-write
		STATUS  mandatory
		DESCRIPTION
			"Indicates the status of the board .
			 A set(write) to 'standby' is done
			 to make the module to switch to standby mode."
		::= { starRclInfoEntry 10 }

	starRclSwitchoverReason	OBJECT-TYPE
		SYNTAX  INTEGER {
			eject (1),
			powerFail (2),
			cpuFail (3),
			reset (4),
			redundantModuleUp (5),
			requestFromRednModule (6),
			requestFromNms (7),
			rcldHealthCheckFail (8),
			hmcdTestFail (9),
			hmcRegisterFail (10)
		}
		ACCESS  read-only
		STATUS  mandatory
		DESCRIPTION
			"Indicates the reason for the last switchover"
		::= { starRclInfoEntry 11 }

	starRclSwitchoverTime	OBJECT-TYPE
		SYNTAX  INTEGER
		ACCESS  read-only
		STATUS  mandatory
		DESCRIPTION
			"Indicates the time when the last switchover occurred"
		::= { starRclInfoEntry 12 }

	-----------------------------------------------------------------------
	-- Star Rcl Reg Info Table
	-----------------------------------------------------------------------
	starRclRegInfoTbl			OBJECT-TYPE
		SYNTAX  SEQUENCE OF StarRclRegInfoEntry
		ACCESS  not-accessible
		STATUS  mandatory
		DESCRIPTION
			"This table contains duplication related variables."
		::= { starRclInfo  2 }

	starRclRegInfoEntry	 OBJECT-TYPE
		SYNTAX  StarRclRegInfoEntry
		ACCESS  not-accessible
		STATUS  mandatory
		DESCRIPTION
			"An entry into spuRclRegInfoTbl."
		INDEX { starRclRegInfoSlotId, starRclRegKey }
		::= { starRclRegInfoTbl 1 }

	StarRclRegInfoEntry ::=
		SEQUENCE {
			starRclRegInfoSlotId	INTEGER ,
			starRclRegKey			INTEGER ,
			starRclRegTaskName		OCTET STRING ,
			starRclRegQueueName		OCTET STRING
		}

	starRclRegInfoSlotId OBJECT-TYPE
		SYNTAX  INTEGER
		ACCESS  read-only
		STATUS  mandatory
		DESCRIPTION
			"This object indicates the slot id."
		::= { starRclRegInfoEntry 1 }

	starRclRegKey		OBJECT-TYPE
		SYNTAX  INTEGER
		ACCESS  read-only
		STATUS  mandatory
		DESCRIPTION
			"This object indicates the key name with which
			 the application was registered."
		::= { starRclRegInfoEntry 2 }

	starRclRegTaskName   OBJECT-TYPE
		SYNTAX  OCTET STRING ( SIZE (0..3 ) )
		ACCESS  read-only
		STATUS  mandatory
		DESCRIPTION
			"This object indicates the task name for the
			 corresponding key."
		::= { starRclRegInfoEntry 3 }

	starRclRegQueueName  OBJECT-TYPE
		SYNTAX  OCTET STRING ( SIZE (0..3 ) )
		ACCESS  read-only
		STATUS  mandatory
		DESCRIPTION
			"This object indicates the queue name for the
			 corresponding key."
		::= { starRclRegInfoEntry 4 }

	-----------------------------------------------------------------------
	-- Star CAS Info Subgroup
	-----------------------------------------------------------------------
	starCasInfo			OBJECT IDENTIFIER ::= { starSlot 21 }

	-----------------------------------------------------------------------
	-- Star CAS Status Info Subgroup
	-----------------------------------------------------------------------
	starCasStatusInfoTbl	OBJECT-TYPE
		SYNTAX	SEQUENCE OF StarCasStatusInfoEntry
		ACCESS	not-accessible
		STATUS	mandatory
		DESCRIPTION
			"This Table has info about the CAS status."
		::={ starCasInfo 1 }

	starCasStatusInfoEntry	OBJECT-TYPE
		SYNTAX	StarCasStatusInfoEntry
		ACCESS  not-accessible
		STATUS  mandatory
		DESCRIPTION	
			"Specifies the Cas status ."
		INDEX { starCasStatusSlotId, starCasStatusPortId, 
				starCasStatusChannelId }
		::= { starCasStatusInfoTbl 1 }

	StarCasStatusInfoEntry ::=
		SEQUENCE {
			starCasStatusSlotId					INTEGER,
			starCasStatusPortId					INTEGER,
			starCasStatusChannelId				INTEGER,
			starCasStatusConfigured				INTEGER,	
			starCasStatusCurrentStatus			INTEGER,
			starCasStatusStatusChange	 		INTEGER,
			starCasStatusNewStatusSampleNum		INTEGER
		}

	starCasStatusSlotId	OBJECT-TYPE
		SYNTAX  INTEGER
		ACCESS  read-only
		STATUS  mandatory
		DESCRIPTION
			"This object indicates the slot id."
		::= { starCasStatusInfoEntry 1 }

	starCasStatusPortId	OBJECT-TYPE
		SYNTAX  INTEGER
		ACCESS  read-only
		STATUS  mandatory
		DESCRIPTION
			"This object indicates the port id."
		::= { starCasStatusInfoEntry 2 }

	starCasStatusChannelId	OBJECT-TYPE
		SYNTAX  INTEGER
		ACCESS  read-only
		STATUS  mandatory
		DESCRIPTION
			"This object indicates the channel id."
		::= { starCasStatusInfoEntry 3 }

	starCasStatusConfigured	 OBJECT-TYPE
		SYNTAX  INTEGER
		ACCESS  read-only
		STATUS  mandatory
		DESCRIPTION
			"This object indicates if the channel is configured."
		::= { starCasStatusInfoEntry 4 }

	starCasStatusCurrentStatus	OBJECT-TYPE
		SYNTAX  INTEGER
		ACCESS  read-only
		STATUS  mandatory
		DESCRIPTION
			"This object indicates the ON-Hook or OFF-Hook status."
		::= { starCasStatusInfoEntry 5 }

	starCasStatusStatusChange	 OBJECT-TYPE
		SYNTAX  INTEGER
		ACCESS  read-only
		STATUS  mandatory
		DESCRIPTION
			"This object indicates the state change of a channel."
		::= { starCasStatusInfoEntry 6 }

	 starCasStatusNewStatusSampleNum	 OBJECT-TYPE
		SYNTAX  INTEGER
		ACCESS  read-only
		STATUS  mandatory
		DESCRIPTION
			"This object indicates the number of times the
			 the CAS polling routine should see this channel in
			 a certain state to flag a change in state."
		::= { starCasStatusInfoEntry 7 }

	-----------------------------------------------------------------------
	-- Star CAS Status Port Info Subgroup
	-----------------------------------------------------------------------
	starCasStatusPortInfoTbl	OBJECT-TYPE
		SYNTAX	SEQUENCE OF StarCasStatusPortInfoEntry
		ACCESS	not-accessible
		STATUS	mandatory
		DESCRIPTION
			"This Table has info about the CAS status."
		::={ starCasInfo 2 }

	starCasStatusPortInfoEntry	OBJECT-TYPE
		SYNTAX	StarCasStatusPortInfoEntry
		ACCESS  not-accessible
		STATUS  mandatory
		DESCRIPTION	
			"Specifies the Cas status ."
		INDEX { starCasStatusPortSlotId, starCasStatusPortPortId }
		::= { starCasStatusPortInfoTbl 1 }

	StarCasStatusPortInfoEntry ::=
		SEQUENCE {
			starCasStatusPortSlotId				INTEGER,
			starCasStatusPortPortId				INTEGER,
			starCasStatusPortConfigured			INTEGER,
			starCasStatusPortCasSamplePeriod	INTEGER,
			starCasStatusPortCasSampleNum		INTEGER
		}

	starCasStatusPortSlotId	OBJECT-TYPE
		SYNTAX  INTEGER
		ACCESS  read-only
		STATUS  mandatory
		DESCRIPTION
			"This object indicates the slot id."
		::= { starCasStatusPortInfoEntry 1 }

	starCasStatusPortPortId	OBJECT-TYPE
		SYNTAX  INTEGER
		ACCESS  read-only
		STATUS  mandatory
		DESCRIPTION
			"This object indicates the port id."
		::= { starCasStatusPortInfoEntry 2 }

	starCasStatusPortConfigured		 OBJECT-TYPE
		SYNTAX  INTEGER
		ACCESS  read-only
		STATUS  mandatory
		DESCRIPTION
			"This object indicates if the port is configured."
		::= { starCasStatusPortInfoEntry 3 }

	starCasStatusPortCasSamplePeriod	OBJECT-TYPE
		SYNTAX  INTEGER
		ACCESS  read-only
		STATUS  mandatory
		DESCRIPTION
			"This object indicates the Cas Sample Period."
		::= { starCasStatusPortInfoEntry 4 }

	starCasStatusPortCasSampleNum	 OBJECT-TYPE
		SYNTAX  INTEGER
		ACCESS  read-only
		STATUS  mandatory
		DESCRIPTION
			"This object indicates the num of 10 millisec
			samples to be done within the sample period."
		::= { starCasStatusPortInfoEntry 5 }

	-----------------------------------------------------------------------
	-- Star Trap Objects
	-----------------------------------------------------------------------
	starTrapPriority  OBJECT-TYPE
		SYNTAX	INTEGER
		ACCESS	read-only
		STATUS	mandatory
		DESCRIPTION
			"Trap severity, associated with all traps"
		::= { starTrap 1 }

	starReturnedErrorCode  OBJECT-TYPE
		SYNTAX	INTEGER
		ACCESS	read-only
		STATUS	mandatory
		DESCRIPTION
			"Error status value used by various traps"
		::= { starTrap 2 }

	starCfPSUNum  OBJECT-TYPE
		SYNTAX	INTEGER
		ACCESS	read-only
		STATUS	mandatory
		DESCRIPTION
			"Power Supply failure indicator of which PSU # failed"
		::= { starTrap 3 }

	starCfFANNum  OBJECT-TYPE
		SYNTAX	INTEGER
		ACCESS	read-only
		STATUS	mandatory
		DESCRIPTION
			"Fan failure indicator of which Fan # failed"
		::= { starTrap 4 }

	starCfSlotActualBoardType  OBJECT-TYPE
		SYNTAX	INTEGER
		ACCESS	read-only
		STATUS	mandatory
		DESCRIPTION
			"Slot mismatch failure trap indicator of which slot
			 has a configured board type that does not match the
			 actual board type"
		::= { starTrap 5 }

	starCfConfiguredBoardType  OBJECT-TYPE
		SYNTAX	INTEGER
		ACCESS	read-only
		STATUS	mandatory
		DESCRIPTION
			"Board type from configuration data"
		::= { starTrap 6 }

	starCfActualFileVersion  OBJECT-TYPE
		SYNTAX	INTEGER
		ACCESS	read-only
		STATUS	mandatory
		DESCRIPTION
			"Current file version number"
		::= { starTrap 7 }

	starCfConfiguredFileVersion  OBJECT-TYPE
		SYNTAX	INTEGER
		ACCESS	read-only
		STATUS	mandatory
		DESCRIPTION
			"Configured file version number"
		::= { starTrap 8 }

	starTaskName  OBJECT-TYPE
		SYNTAX	DisplayString
		ACCESS	read-only
		STATUS	mandatory
		DESCRIPTION
			"Task name of task that caused trap"
		::= { starTrap 9 }

	starQueueName  OBJECT-TYPE
		SYNTAX	DisplayString
		ACCESS	read-only
		STATUS	mandatory
		DESCRIPTION
			"Queue name of destination messgae queue"
		::= { starTrap 10 }

	starMsgSize  OBJECT-TYPE
		SYNTAX	INTEGER
		ACCESS	read-only
		STATUS	mandatory
		DESCRIPTION
			"Message size requested that was unavailable"
		::= { starTrap 11 }

	starFileName  OBJECT-TYPE
		SYNTAX	DisplayString
		ACCESS	read-only
		STATUS	mandatory
		DESCRIPTION
			"Filename that was in error"
		::= { starTrap 12 }

	starDeviceType  OBJECT-TYPE
		SYNTAX	INTEGER
		ACCESS	read-only
		STATUS	mandatory
		DESCRIPTION
			"Device type that has an alarm"
		::= { starTrap 13 }

	starModuleIfType  OBJECT-TYPE
		SYNTAX	INTEGER
		ACCESS	read-only
		STATUS	mandatory
		DESCRIPTION
			"Module Interface type that has an alarm"
		::= { starTrap 14 }

	starRefClkIndex  OBJECT-TYPE
		SYNTAX	INTEGER
		ACCESS	read-only
		STATUS	mandatory
		DESCRIPTION
			"Clock reference number for clock alarm"
		::= { starTrap 15 }

	starEthernetType  OBJECT-TYPE
		SYNTAX	INTEGER {
			nms(1),
			ipc1(2),
			ipc2(3)
		}
		ACCESS	read-only
		STATUS	mandatory
		DESCRIPTION
			"Ethernet alarm"
		::= { starTrap 16 }

	starDS1ChanIndex  OBJECT-TYPE
		SYNTAX	INTEGER
		ACCESS	read-only
		STATUS	mandatory
		DESCRIPTION
			"DS1 Channel alarm"
		::= { starTrap 17 }

	starDS2ChanIndex  OBJECT-TYPE
		SYNTAX	INTEGER
		ACCESS	read-only
		STATUS	mandatory
		DESCRIPTION
			"DS2 Channel alarm"
		::= { starTrap 18 }

	starDeviceId  OBJECT-TYPE
		SYNTAX	INTEGER
		ACCESS	read-only
		STATUS	mandatory
		DESCRIPTION
			"Device Id of device that has an alarm"
		::= { starTrap 19 }

	starRcvdMsgType  OBJECT-TYPE
		SYNTAX	INTEGER
		ACCESS	read-only
		STATUS	mandatory
		DESCRIPTION
			"Received Message type that was in error"
		::= { starTrap 20 }

	starReturnedSlotIndex  OBJECT-TYPE
		SYNTAX	INTEGER
		ACCESS	read-only
		STATUS	mandatory
		DESCRIPTION
			"Slot Id of board in error"
		::= { starTrap 21 }

	starRcvdSrcSlotIndex  OBJECT-TYPE
		SYNTAX	INTEGER
		ACCESS	read-only
		STATUS	mandatory
		DESCRIPTION
			"Slot Id of msg from unknown slot #"
		::= { starTrap 22 }

	starRcvdModuleIfType  OBJECT-TYPE
		SYNTAX	INTEGER
		ACCESS	read-only
		STATUS	mandatory
		DESCRIPTION
			""
		::= { starTrap 23 }

	starFileId  OBJECT-TYPE
		SYNTAX	INTEGER
		ACCESS	read-only
		STATUS	mandatory
		DESCRIPTION
			"Configuration File Id of file in error"
		::= { starTrap 24 }

	starCOSId  OBJECT-TYPE
		SYNTAX	INTEGER
		ACCESS	read-only
		STATUS	mandatory
		DESCRIPTION
			"Class of Service that is out of bounds"
		::= { starTrap 25 }

	starRcvdModuleType  OBJECT-TYPE
		SYNTAX	INTEGER
		ACCESS	read-only
		STATUS	mandatory
		DESCRIPTION
			"Module type received that is in error"
		::= { starTrap 26 }

	starRcvdGroupId  OBJECT-TYPE
		SYNTAX	INTEGER
		ACCESS	read-only
		STATUS	mandatory
		DESCRIPTION
			"Unknown fault group Id"
		::= { starTrap 27 }

	starRcvdSubId  OBJECT-TYPE
		SYNTAX	INTEGER
		ACCESS	read-only
		STATUS	mandatory
		DESCRIPTION
			"Unknown fault sub Id"
		::= { starTrap 28 }

	starGcidNeId  OBJECT-TYPE
		SYNTAX	INTEGER
		ACCESS	read-only
		STATUS	mandatory
		DESCRIPTION
			"GCID Node Id"
		::= { starTrap 29 }

	starGcidSlotIndex  OBJECT-TYPE
		SYNTAX	INTEGER
		ACCESS	read-only
		STATUS	mandatory
		DESCRIPTION
			"GCID Slot Index"
		::= { starTrap 30 }

	starGcidPortIndex  OBJECT-TYPE
		SYNTAX	INTEGER
		ACCESS	read-only
		STATUS	mandatory
		DESCRIPTION
			"GCID Port Index"
		::= { starTrap 31 }

	starGcidModuleIfType  OBJECT-TYPE
		SYNTAX	INTEGER
		ACCESS	read-only
		STATUS	mandatory
		DESCRIPTION
			"GCID Module Interface type"
		::= { starTrap 32 }

	starGcidLeafNum  OBJECT-TYPE
		SYNTAX	INTEGER
		ACCESS	read-only
		STATUS	mandatory
		DESCRIPTION
			"GCID Leaf number"
		::= { starTrap 33 }

	starGcidConnectionNum  OBJECT-TYPE
		SYNTAX	INTEGER
		ACCESS	read-only
		STATUS	mandatory
		DESCRIPTION
			"GCID Connection number"
		::= { starTrap 34 }

	starCRSRResultedErrorCode  OBJECT-TYPE
		SYNTAX	INTEGER
		ACCESS	read-only
		STATUS	mandatory
		DESCRIPTION
			"CRSR error code"
		::= { starTrap 35 }

	starCRSRFailedSlotIndex  OBJECT-TYPE
		SYNTAX	INTEGER
		ACCESS	read-only
		STATUS	mandatory
		DESCRIPTION
			"CRSR slot index of failed slot"
		::= { starTrap 36 }

	starCRSRFailedPortIndex  OBJECT-TYPE
		SYNTAX	INTEGER
		ACCESS	read-only
		STATUS	mandatory
		DESCRIPTION
			"CRSR port index of failed port"
		::= { starTrap 37 }

	starCRSRDescriptionCode  OBJECT-TYPE
		SYNTAX	INTEGER
		ACCESS	read-only
		STATUS	mandatory
		DESCRIPTION
			"CRSR description code"
		::= { starTrap 38 }

	starSwitchReason  OBJECT-TYPE
		SYNTAX	INTEGER
		ACCESS	read-only
		STATUS	mandatory
		DESCRIPTION
			"Reason for a redundancy switchover"
		::= { starTrap 39 }

	starBoardFailReason  OBJECT-TYPE
		SYNTAX	INTEGER
		ACCESS	read-only
		STATUS	mandatory
		DESCRIPTION
			"Board Failure reason for redundant board"
		::= { starTrap 40 }

	starCDRGetReason  OBJECT-TYPE
		SYNTAX	INTEGER
		ACCESS	read-only
		STATUS	mandatory
		DESCRIPTION
			"CDR file get reasone"
		::= { starTrap 41 }

	starCDRFileSplitNum  OBJECT-TYPE
		SYNTAX	INTEGER
		ACCESS	read-only
		STATUS	mandatory
		DESCRIPTION
			"number of CDR file split"
		::= { starTrap 42 }

	starPvcmConfFaultCause  OBJECT-TYPE
		SYNTAX	INTEGER
		ACCESS	read-only
		STATUS	mandatory
		DESCRIPTION
			""
		::= { starTrap 43 }

	starConnClearCause  OBJECT-TYPE
		SYNTAX	INTEGER
		ACCESS	read-only
		STATUS	mandatory
		DESCRIPTION
			""
		::= { starTrap 44 }

	starRemoteNeId  OBJECT-TYPE
		SYNTAX	INTEGER
		ACCESS	read-only
		STATUS	mandatory
		DESCRIPTION
			""
		::= { starTrap 45 }

	starRemoteModuleNum  OBJECT-TYPE
		SYNTAX	INTEGER
		ACCESS	read-only
		STATUS	mandatory
		DESCRIPTION
			""
		::= { starTrap 46 }

	starRemotePortIndex  OBJECT-TYPE
		SYNTAX	INTEGER
		ACCESS	read-only
		STATUS	mandatory
		DESCRIPTION
			""
		::= { starTrap 47 }

	starFrLmiPortIndex  OBJECT-TYPE
		SYNTAX	INTEGER
		ACCESS	read-only
		STATUS	mandatory
		DESCRIPTION
			""
		::= { starTrap 48 }

	starQueuePoolId  OBJECT-TYPE
		SYNTAX	INTEGER
		ACCESS	read-only
		STATUS	mandatory
		DESCRIPTION
			""
		::= { starTrap 49 }

	starRipAddress0  OBJECT-TYPE
		SYNTAX	INTEGER
		ACCESS	read-only
		STATUS	mandatory
		DESCRIPTION
			""
		::= { starTrap 50 }

	starRipAddress1  OBJECT-TYPE
		SYNTAX	INTEGER
		ACCESS	read-only
		STATUS	mandatory
		DESCRIPTION
			""
		::= { starTrap 51 }

	starRipAddress2  OBJECT-TYPE
		SYNTAX	INTEGER
		ACCESS	read-only
		STATUS	mandatory
		DESCRIPTION
			""
		::= { starTrap 52 }

	starRipAddress3  OBJECT-TYPE
		SYNTAX	INTEGER
		ACCESS	read-only
		STATUS	mandatory
		DESCRIPTION
			""
		::= { starTrap 53 }

	starRipAddress4  OBJECT-TYPE
		SYNTAX	INTEGER
		ACCESS	read-only
		STATUS	mandatory
		DESCRIPTION
			""
		::= { starTrap 54 }

	starFatalErrorCode  OBJECT-TYPE
		SYNTAX	INTEGER
		ACCESS	read-only
		STATUS	mandatory
		DESCRIPTION
			""
		::= { starTrap 55 }

	starSvcmCacThreshold  OBJECT-TYPE
		SYNTAX	INTEGER
		ACCESS	read-only
		STATUS	mandatory
		DESCRIPTION
			""
		::= { starTrap 56 }
END
