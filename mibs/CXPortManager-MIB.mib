CXPortManager-MIB DEFINITIONS ::= BEGIN

IMPORTS
   OBJECT-TYPE    FROM RFC-1212

--  Proprietary Imports

     cxPortManager   FROM CXProduct-SMI;

cxPrtMPlannedCfgTable OBJECT-TYPE
   SYNTAX  SEQUENCE OF CxPrtMPlannedCfgEntry
   ACCESS  not-accessible
   STATUS  mandatory
   DESCRIPTION
"A table that defines planned port configuration."
   REFERENCE
      " "
   ::= { cxPortManager 1 }


cxPrtMPlannedCfgEntry OBJECT-TYPE
   SYNTAX CxPrtMPlannedCfgEntry
   ACCESS  not-accessible
   STATUS  mandatory
   DESCRIPTION
      ""
   INDEX { cxPrtMPrtNum }
   ::= { cxPrtMPlannedCfgTable 1 }

 CxPrtMPlannedCfgEntry::=
   SEQUENCE {
      cxPrtMPrtNum                    INTEGER,
      cxPrtMPrtType                   INTEGER
      }

cxPrtMPrtNum    OBJECT-TYPE
   SYNTAX  INTEGER
   ACCESS read-only
   STATUS mandatory
   DESCRIPTION
"Displays the port number.

You cannot modify this object. It is a display
that the software provides.

Options:
- CX900: 11, 21, 31, 41, 51, 61 or 71. The first digit identifies the 
slot number the I/O board resides in, the second digit identifies 
the port number on the I/O board.


- CX1000: a single digit from 1 to 4. The port numbers available vary 
depending on the type of module. For example, the LAN module supports 
only one port per I/O board and the Voice module supports only two 
ports per I/O board, but the Frame Relay module supports 4 ports per 
I/O board. You distinguish between module port numbers by 
specifying the slot number of the I/O board using a different object.

Default Value: none"

   ::= { cxPrtMPlannedCfgEntry 1 }

cxPrtMPrtType   OBJECT-TYPE
   SYNTAX  INTEGER (1..255)
   ACCESS read-write
   STATUS mandatory
   DESCRIPTION
"Determines the data link layer type for the port.

The setting of this object is dynamic. The port immediately implements 
the setting that you enter.

Options:

other (1): removes the link layer configuration for the associated port
ethernet (6)
token_ring (9)
lapb (16)
sdlc (17)
T1  (18)
E1	(19)
basic_isdn (20)
async (22)
frame_relay (32)
bop (33)
bisync (83)
voice (100)

Default Value: none

Configuration Changed: operative"

   ::= { cxPrtMPlannedCfgEntry 2 }

cxPrtMAdminTable OBJECT-TYPE
   SYNTAX  SEQUENCE OF CxPrtMAdminEntry
   ACCESS  not-accessible
   STATUS  mandatory
   DESCRIPTION
      "A table that controls ports."
   REFERENCE
      " "
   ::= { cxPortManager 2 }


cxPrtMAdminEntry OBJECT-TYPE
   SYNTAX CxPrtMAdminEntry
   ACCESS  not-accessible
   STATUS  mandatory
   DESCRIPTION
"The index of the table is a port number which is in either the IF table 
or the planned CFG table."
   INDEX { cxPrtMPrtNum }
   ::= { cxPrtMAdminTable 1 }

 CxPrtMAdminEntry::=
   SEQUENCE {
      cxPrtMAdminPortControl        INTEGER
      }

cxPrtMAdminPortControl  OBJECT-TYPE
   SYNTAX   INTEGER
            {
               activate(1),
               deactivate(2),
               reinitialize(3)
            }
   ACCESS write-only
   STATUS mandatory
   DESCRIPTION
"Determines the state of the administrative configuration associated
with the port.

The setting of this object is dynamic. The port immediately implements 
the option you enter.

Options:
activate (1): activates the administrative
configuration for a port which does not have
any configuration.

deactivate (2): puts a running port into a no
configuration state.

reintialize (3): activates a new administrative
configuration for a port currently running an
operative configuration.

Default Value: none

Configuration Changed: operative"

   ::= { cxPrtMAdminEntry 1 }


END
