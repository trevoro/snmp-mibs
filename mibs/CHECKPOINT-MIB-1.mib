CHECKPOINT-MIB-1 DEFINITIONS ::= BEGIN

	  -- SUBTREE: 1.3.6.1.4.1.1919.1.1
	  -- iso.org.dod.internet.private.enterprises.checkpoint.products.fw

          IMPORTS
                  enterprises, NetworkAddress, IpAddress, Counter, Gauge,
                          TimeTicks
                      FROM RFC1155-SMI
                  OBJECT-TYPE
                          FROM RFC-1212;

          -- textual conventions

          DisplayString ::=
              OCTET STRING
          -- This data type is used to model textual information taken
          -- from the NVT ASCII character set.  By convention, objects
          -- with this syntax are declared as having


          --
          --      SIZE (0..255)

          PhysAddress ::=
              OCTET STRING
          -- This data type is used to model media addresses.  For many
          -- types of media, this will be in a binary representation.
          -- For example, an ethernet address would be represented as
          -- a string of 6 octets.

	checkpoint		OBJECT IDENTIFIER ::= { enterprises 1919 }
	products		OBJECT IDENTIFIER ::= { checkpoint 1 }
	fw			OBJECT IDENTIFIER ::= { products 1 }

	  -- the FW group
	  -- Overall statistics and state
	  -- To be added a table of statistics by interfaces.

	  fwModuleState OBJECT-TYPE
              SYNTAX  DisplayString (SIZE (0..255))
              ACCESS  read-only
              STATUS  mandatory
              DESCRIPTION
                      "The state of the fw module."
              ::= { fw 1 }

	  fwFilterName OBJECT-TYPE
              SYNTAX  DisplayString (SIZE (0..255))
              ACCESS  read-only
              STATUS  mandatory
              DESCRIPTION
                      "The name of the loaded filter."
              ::= { fw 2 }

	  fwFilterDate OBJECT-TYPE
              SYNTAX  DisplayString (SIZE (0..255))
              ACCESS  read-only
              STATUS  mandatory
              DESCRIPTION
                      "When was the filter installed (STRING!)"
              ::= { fw 3 }

	  fwAccepted OBJECT-TYPE
              SYNTAX  INTEGER
              ACCESS  read-only
              STATUS  mandatory
              DESCRIPTION
                      "The number of accepted packets."
              ::= { fw 4 }

	  fwRejected OBJECT-TYPE
              SYNTAX  INTEGER
              ACCESS  read-only
              STATUS  mandatory
              DESCRIPTION
                      "The number of rejected  packets."
              ::= { fw 5 }

	  fwDropped OBJECT-TYPE
              SYNTAX  INTEGER
              ACCESS  read-only
              STATUS  mandatory
              DESCRIPTION
                      "The number of dropped packets."
              ::= { fw 6 }

	  fwLogged OBJECT-TYPE
              SYNTAX  INTEGER
              ACCESS  read-only
              STATUS  mandatory
              DESCRIPTION
                      "The number of logged packets."
              ::= { fw 7 }

	  fwMajor OBJECT-TYPE
              SYNTAX  INTEGER
              ACCESS  read-only
              STATUS  mandatory
              DESCRIPTION
                      "FireWall-1 Major Version."
              ::= { fw 8 }

	  fwMinor OBJECT-TYPE
              SYNTAX  INTEGER
              ACCESS  read-only
              STATUS  mandatory
              DESCRIPTION
                      "FireWall-1 Minor Version."
              ::= { fw 9 }

	  fwProduct OBJECT-TYPE
              SYNTAX  INTEGER
              ACCESS  read-only
              STATUS  mandatory
              DESCRIPTION
                      "FireWall-1 Product."
              ::= { fw 10 }

	  fwEvent OBJECT-TYPE
              SYNTAX  DisplayString (SIZE (0..255))
              ACCESS  read-only
              STATUS  mandatory
              DESCRIPTION
                      "A string containing the last snmp trap sent via fw"
              ::= { fw 11 }
END
