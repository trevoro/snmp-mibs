-- *********************************************************************
-- Copyright 1993-2000 VERITAS Software - All Rights Reserved.
-- *********************************************************************
-- VRTS-SNMP-MIB.txt
-- MIB for VERITAS NetBackup, VxVM, VxFS, VCS and Common Managed Objects
-- 
-- Release version = 1.2
-- Patch level     = 0
--
-- We authorized the use of this document provided that this
-- copyright notice is included, and the user has obtained official 
-- authorization from VERITAS Enterprise Consulting Services under a service
-- contract.
--
-- This VERITAS SNMP MIB Specification embodies intellectual property.  
-- The copyright retains all title and ownership in the specification, 
-- including any revisions. 
--
-- This specification is supplied "AS IS," and no
-- warranty, either express or implied, as to the use, operation,
-- condition, or performance of the specification, is made.
--
-- The right to change this MIB without notification is retained.
--
-- *********************************************************************

VRTS-SNMP-MIBv1 DEFINITIONS ::= BEGIN

IMPORTS
		enterprises
               FROM RFC1155-SMI
      OBJECT-TYPE
               FROM RFC-1212
      TRAP-TYPE
               FROM RFC-1215
      DisplayString
               FROM RFC1213-MIB
		Integer32
					FROM SNMPv2-SMI
;

veritas OBJECT IDENTIFIER ::= { enterprises 1035 }

netbackup	OBJECT IDENTIFIER ::= { veritas 1 }
vxvm		OBJECT IDENTIFIER ::= { veritas 2 }
vxfs		OBJECT IDENTIFIER ::= { veritas 3 }
vcs		OBJECT IDENTIFIER ::= { veritas 7 }
commonObjects	OBJECT IDENTIFIER ::= { veritas 301 }

job	OBJECT IDENTIFIER ::= { netbackup 1 }
config	OBJECT IDENTIFIER ::= { netbackup 2 }
media	OBJECT IDENTIFIER ::= { netbackup 4 }
dr	OBJECT IDENTIFIER ::= { netbackup 6 }

-- 
-- Sub MIB tree for NetBackup configuration
--

class	OBJECT IDENTIFIER ::= { config 2 }
client	OBJECT IDENTIFIER ::= { config 4 }
sched	OBJECT IDENTIFIER ::= { config 6 }
stu	OBJECT IDENTIFIER ::= { config 8 }

-- 
-- Sub MIB tree for Media and Media Table configuration
--

mediaTable OBJECT-TYPE
    	SYNTAX	SEQUENCE OF MediaEntry
	ACCESS	not-accessible
	STATUS	mandatory
	DESCRIPTION
		"A table of NetBackup media configuration information."
	::= { media 1 }

mediaEntry OBJECT-TYPE
	SYNTAX     MediaEntry
	ACCESS not-accessible
    	STATUS     mandatory
    	DESCRIPTION
        "An NBU media entry containing a media related information."
    	INDEX      { mediaIndex }
    	::= { mediaTable  1 }

MediaEntry ::= SEQUENCE {
    	mediaIndex	Integer32,
	mediaPool	DisplayString,
    	mediaId		DisplayString,
	mediaType	DisplayString,
	mediaRobotType	DisplayString,
	mediaRobotNum	Integer32,
	mediaRobotSlot	Integer32,
	mediaSideFace	DisplayString,
	mediaRetLevel	Integer32,
	mediaSize	Integer32,
	mediaStatus	DisplayString
}


mediaIndex	OBJECT-TYPE
	SYNTAX      Integer32 (0..65535)
	ACCESS  read-only
	STATUS      mandatory
	DESCRIPTION
        "It is Reference Index for media table."
	::= { mediaEntry 1 }

mediaPool	OBJECT-TYPE
	SYNTAX      DisplayString
	ACCESS  read-only
	STATUS      mandatory
	DESCRIPTION
        "The volume pool name where the media belongs to."
	::= { mediaEntry 2 }

mediaId		OBJECT-TYPE
	SYNTAX      DisplayString
	ACCESS  read-only
	STATUS      mandatory
	DESCRIPTION
        "It is media id for media table."
	::= { mediaEntry 3 }

mediaType	OBJECT-TYPE
	SYNTAX      DisplayString
	ACCESS  read-only
	STATUS      mandatory
	DESCRIPTION
        "The type of the media, 8MM etc."
	::= { mediaEntry 4 }

mediaRobotType	OBJECT-TYPE
	SYNTAX      DisplayString
	ACCESS  read-only
	STATUS      mandatory
	DESCRIPTION
        "The type of the robot where the media resides, TS8 etc."
	::= { mediaEntry 5 }

mediaRobotNum	OBJECT-TYPE
	SYNTAX      Integer32 (0..65535)
	ACCESS  read-only
	STATUS      mandatory
	DESCRIPTION
        "It is robot number where the media resides."
	::= { mediaEntry 6 }

mediaRobotSlot	OBJECT-TYPE
	SYNTAX      Integer32 (0..65535)
	ACCESS  read-only
	STATUS      mandatory
	DESCRIPTION
        "It is robot slot number where the media resides."
	::= { mediaEntry 7 }

mediaSideFace	OBJECT-TYPE
	SYNTAX      DisplayString
	ACCESS  read-only
	STATUS      mandatory
	DESCRIPTION
        "It is the robot face where the media resides."
	::= { mediaEntry 8 }

mediaRetLevel	OBJECT-TYPE
	SYNTAX      Integer32
	ACCESS  read-only
	STATUS      mandatory
	DESCRIPTION
        "It is the retention level of the media."
	::= { mediaEntry 9 }

mediaSize	OBJECT-TYPE
	SYNTAX      Integer32
	ACCESS  read-only
	STATUS      mandatory
	DESCRIPTION
        "It is media size in kbytes."
	::= { mediaEntry 10 }

mediaStatus	OBJECT-TYPE
	SYNTAX      DisplayString
	ACCESS  read-only
	STATUS      mandatory
	DESCRIPTION
        "It is the status of the media eg, available, frozen, full etc."
	::= { mediaEntry 11 }

volpool	OBJECT IDENTIFIER ::= { media 2 }
robot	OBJECT IDENTIFIER ::= { media 4 }
drive	OBJECT IDENTIFIER ::= { media 6 }
tape	OBJECT IDENTIFIER ::= { media 8 }

-- 
-- Sub MIB tree for Disaster Recovery
--

vault	OBJECT IDENTIFIER ::= { dr 2 }

--
-- NetBackup Class Table
--

classTable OBJECT-TYPE
    	SYNTAX	SEQUENCE OF ClassEntry
	ACCESS	not-accessible
	STATUS	mandatory
	DESCRIPTION
		"A table of NetBackup class configuration information."
	::= { class 1 }

classEntry OBJECT-TYPE
	SYNTAX     ClassEntry
	ACCESS not-accessible
    	STATUS     mandatory
    	DESCRIPTION
        "An NBU class entry containing a class related information."
    	INDEX      { classIndex }
    	::= { classTable  1 }

ClassEntry ::= SEQUENCE {
    	classIndex	Integer32,
    	className	DisplayString
}

classIndex	OBJECT-TYPE
	SYNTAX      Integer32 (0..65535)
	ACCESS  read-only
	STATUS      mandatory
	DESCRIPTION
        "It is Reference Index for class table."
	::= { classEntry 1 }

className	OBJECT-TYPE
	SYNTAX      DisplayString
	ACCESS  read-only
	STATUS      mandatory
	DESCRIPTION
        "The class name."
	::= { classEntry 2 }

--
-- NetBackup Client Table
--

clientTable OBJECT-TYPE
    	SYNTAX	SEQUENCE OF ClientEntry
	ACCESS	not-accessible
	STATUS	mandatory
	DESCRIPTION
		"A table of NetBackup client configuration information."
	::= { client 1 }

clientEntry OBJECT-TYPE
	SYNTAX     ClientEntry
	ACCESS not-accessible
    	STATUS     mandatory
    	DESCRIPTION
        "An NBU client entry containing a client related information."
    	INDEX      { clientIndex }
    	::= { clientTable  1 }

ClientEntry ::= SEQUENCE {
    	clientIndex	Integer32,
    	clientName	DisplayString
}

clientIndex	OBJECT-TYPE
	SYNTAX      Integer32 (0..65535)
	ACCESS  read-only
	STATUS      mandatory
	DESCRIPTION
        "It is Reference Index for client table."
	::= { clientEntry 1 }

clientName	OBJECT-TYPE
	SYNTAX      DisplayString
	ACCESS  read-only
	STATUS      mandatory
	DESCRIPTION
        "The client name."
	::= { clientEntry 2 }

--
-- NetBackup Sched Table
--

schedTable OBJECT-TYPE
    	SYNTAX	SEQUENCE OF SchedEntry
	ACCESS	not-accessible
	STATUS	mandatory
	DESCRIPTION
		"A table of NetBackup sched configuration information."
	::= { sched 1 }

schedEntry OBJECT-TYPE
	SYNTAX     SchedEntry
	ACCESS not-accessible
    	STATUS     mandatory
    	DESCRIPTION
        "An NBU sched entry containing a sched related information."
    	INDEX      { schedIndex }
    	::= { schedTable  1 }

SchedEntry ::= SEQUENCE {
    	schedIndex	Integer32,
    	schedName	DisplayString
}

schedIndex	OBJECT-TYPE
	SYNTAX      Integer32 (0..65535)
	ACCESS  read-only
	STATUS      mandatory
	DESCRIPTION
        "It is Reference Index for sched table."
	::= { schedEntry 1 }

schedName	OBJECT-TYPE
	SYNTAX      DisplayString
	ACCESS  read-only
	STATUS      mandatory
	DESCRIPTION
        "The sched name."
	::= { schedEntry 2 }

--
-- NetBackup Stu Table
--

stuTable OBJECT-TYPE
    	SYNTAX	SEQUENCE OF StuEntry
	ACCESS	not-accessible
	STATUS	mandatory
	DESCRIPTION
		"A table of NetBackup stu configuration information."
	::= { stu 1 }

stuEntry OBJECT-TYPE
	SYNTAX     StuEntry
	ACCESS not-accessible
    	STATUS     mandatory
    	DESCRIPTION
        "An NBU stu entry containing a stu related information."
    	INDEX      { stuIndex }
    	::= { stuTable  1 }

StuEntry ::= SEQUENCE {
    	stuIndex	Integer32,
    	stuName	DisplayString
}

stuIndex	OBJECT-TYPE
	SYNTAX      Integer32 (0..65535)
	ACCESS  read-only
	STATUS      mandatory
	DESCRIPTION
        "It is Reference Index for stu table."
	::= { stuEntry 1 }

stuName	OBJECT-TYPE
	SYNTAX      DisplayString
	ACCESS  read-only
	STATUS      mandatory
	DESCRIPTION
        "The stu name."
	::= { stuEntry 2 }

--
-- NetBackup Volpool Table
--

volpoolTable OBJECT-TYPE
    	SYNTAX	SEQUENCE OF VolpoolEntry
	ACCESS	not-accessible
	STATUS	mandatory
	DESCRIPTION
		"A table of NetBackup volpool configuration information."
	::= { volpool 1 }

volpoolEntry OBJECT-TYPE
	SYNTAX     VolpoolEntry
	ACCESS not-accessible
    	STATUS     mandatory
    	DESCRIPTION
        "An NBU volpool entry containing a volpool related information."
    	INDEX      { volpoolIndex }
    	::= { volpoolTable  1 }

VolpoolEntry ::= SEQUENCE {
    	volpoolIndex	Integer32,
    	volpoolName	DisplayString
}

volpoolIndex	OBJECT-TYPE
	SYNTAX      Integer32 (0..65535)
	ACCESS  read-only
	STATUS      mandatory
	DESCRIPTION
        "It is Reference Index for volpool table."
	::= { volpoolEntry 1 }

volpoolName	OBJECT-TYPE
	SYNTAX      DisplayString
	ACCESS  read-only
	STATUS      mandatory
	DESCRIPTION
        "The volpool name."
	::= { volpoolEntry 2 }


--
-- NetBackup Robot Table
--

robotTable OBJECT-TYPE
    	SYNTAX	SEQUENCE OF RobotEntry
	ACCESS	not-accessible
	STATUS	mandatory
	DESCRIPTION
		"A table of NetBackup robot configuration information."
	::= { robot 1 }

robotEntry OBJECT-TYPE
	SYNTAX     RobotEntry
	ACCESS not-accessible
    	STATUS     mandatory
    	DESCRIPTION
        "An NBU robot entry containing a robot related information."
    	INDEX      { robotIndex }
    	::= { robotTable  1 }

RobotEntry ::= SEQUENCE {
    	robotIndex	Integer32,
    	robotName	DisplayString
}

robotIndex	OBJECT-TYPE
	SYNTAX      Integer32 (0..65535)
	ACCESS  read-only
	STATUS      mandatory
	DESCRIPTION
        "It is Reference Index for robot table."
	::= { robotEntry 1 }

robotName	OBJECT-TYPE
	SYNTAX      DisplayString
	ACCESS  read-only
	STATUS      mandatory
	DESCRIPTION
        "The robot name."
	::= { robotEntry 2 }


--
-- NetBackup Drive Table
--

driveTable OBJECT-TYPE
    	SYNTAX	SEQUENCE OF DriveEntry
	ACCESS	not-accessible
	STATUS	mandatory
	DESCRIPTION
		"A table of NetBackup drive configuration information."
	::= { drive 1 }

driveEntry OBJECT-TYPE
	SYNTAX     DriveEntry
	ACCESS not-accessible
    	STATUS     mandatory
    	DESCRIPTION
        "An NBU drive entry containing a drive related information."
    	INDEX      { driveIndex }
    	::= { driveTable  1 }

DriveEntry ::= SEQUENCE {
    	driveIndex	Integer32,
    	driveName	DisplayString
}

driveIndex	OBJECT-TYPE
	SYNTAX      Integer32 (0..65535)
	ACCESS  read-only
	STATUS      mandatory
	DESCRIPTION
        "It is Reference Index for drive table."
	::= { driveEntry 1 }

driveName	OBJECT-TYPE
	SYNTAX      DisplayString
	ACCESS  read-only
	STATUS      mandatory
	DESCRIPTION
        "The drive name."
	::= { driveEntry 2 }


--
-- NetBackup Tape Table
--

tapeTable OBJECT-TYPE
    	SYNTAX	SEQUENCE OF TapeEntry
	ACCESS	not-accessible
	STATUS	mandatory
	DESCRIPTION
		"A table of NetBackup tape configuration information."
	::= { tape 1 }

tapeEntry OBJECT-TYPE
	SYNTAX     TapeEntry
	ACCESS not-accessible
    	STATUS     mandatory
    	DESCRIPTION
        "An NBU tape entry containing a tape related information."
    	INDEX      { tapeIndex }
    	::= { tapeTable  1 }

TapeEntry ::= SEQUENCE {
    	tapeIndex	Integer32,
    	tapeName	DisplayString
}

tapeIndex	OBJECT-TYPE
	SYNTAX      Integer32 (0..65535)
	ACCESS  read-only
	STATUS      mandatory
	DESCRIPTION
        "It is Reference Index for tape table."
	::= { tapeEntry 1 }

tapeName	OBJECT-TYPE
	SYNTAX      DisplayString
	ACCESS  read-only
	STATUS      mandatory
	DESCRIPTION
        "The tape name."
	::= { tapeEntry 2 }



--
-- NetBackup Vault Table
--

vaultTable OBJECT-TYPE
    	SYNTAX	SEQUENCE OF VaultEntry
	ACCESS	not-accessible
	STATUS	mandatory
	DESCRIPTION
		"A table of NetBackup vault configuration information."
	::= { vault 1 }

vaultEntry OBJECT-TYPE
	SYNTAX     VaultEntry
	ACCESS not-accessible
    	STATUS     mandatory
    	DESCRIPTION
        "An NBU vault entry containing a vault related information."
    	INDEX      { vaultIndex }
    	::= { vaultTable  1 }

VaultEntry ::= SEQUENCE {
    	vaultIndex	Integer32,
    	vaultName	DisplayString
}

vaultIndex	OBJECT-TYPE
	SYNTAX      Integer32 (0..65535)
	ACCESS  read-only
	STATUS      mandatory
	DESCRIPTION
        "It is Reference Index for vault table."
	::= { vaultEntry 1 }

vaultName	OBJECT-TYPE
	SYNTAX      DisplayString
	ACCESS  read-only
	STATUS      mandatory
	DESCRIPTION
        "The vault name."
	::= { vaultEntry 2 }


--
-- NetBackup Job specification
--

jobTable OBJECT-TYPE
    	SYNTAX	SEQUENCE OF JobEntry
	ACCESS	not-accessible
	STATUS	mandatory
	DESCRIPTION
		"A table of NetBackup jobs information."
	::= { job 1 }

jobEntry OBJECT-TYPE
	SYNTAX     JobEntry
	ACCESS not-accessible
    	STATUS     mandatory
    	DESCRIPTION
        "An NBU job entry containing a job related information."
    	INDEX      { jobIndex }
    	::= { jobTable  1 }

JobEntry ::= SEQUENCE {
    	jobIndex	Integer32,
--
--	use actual job id as jobIndex, save one variable jobId below.
--    	jobId           Integer32,
--
    	jobType		DisplayString,
    	jobState        DisplayString,
    	jobClass        DisplayString,
    	jobClient	DisplayString,
	jobSched	DisplayString,
	jobSchedType	DisplayString,
	jobStu		DisplayString,
	jobVolpool	DisplayString,
	jobKbytes	Integer32,
	jobMaster	DisplayString,
	jobErrExpl	DisplayString,
	jobErrReco	DisplayString,
	jobId		Integer32,
	jobErrCode	Integer32,
    	jobErrMsg       DisplayString,
    	jobErrFix       Integer32,
    	jobErrFixCmd    DisplayString
}


jobIndex OBJECT-TYPE
	SYNTAX      Integer32 (0..65535)
	ACCESS  read-only
	STATUS      mandatory
	DESCRIPTION
        	"It is the standard index for SNMP job table, the actual NetBackup job id is represented by jobId field."
	::= { jobEntry 1 }

jobType	OBJECT-TYPE
	SYNTAX      DisplayString
	ACCESS  read-only
	STATUS      mandatory
	DESCRIPTION
        	"The Backup type of NetBackup job, eg Backup or Restore etc."
	::= { jobEntry 2 }

jobState OBJECT-TYPE
	SYNTAX      DisplayString
	ACCESS  read-only
	STATUS      mandatory
	DESCRIPTION
        	"The State of NetBackup job, eg Done or Active etc."
	::= { jobEntry 3 }

jobClass OBJECT-TYPE
	SYNTAX      DisplayString
	ACCESS  read-only
	STATUS      mandatory
	DESCRIPTION
        	"The Class of NetBackup job."
	::= { jobEntry 4 }

jobClient OBJECT-TYPE
	SYNTAX      DisplayString
	ACCESS  read-only
	STATUS      mandatory
	DESCRIPTION
        	"The Client name of NetBackup job."
	::= { jobEntry 5 }

jobSched OBJECT-TYPE
	SYNTAX      DisplayString
	ACCESS  read-only
	STATUS      mandatory
	DESCRIPTION
        	"The Backup type of NetBackup job, eg Backup or Restore etc."
	::= { jobEntry 6 }


jobSchedType OBJECT-TYPE
	SYNTAX      DisplayString
	ACCESS  read-only
	STATUS      mandatory
	DESCRIPTION
        	"The Backup type of NetBackup job, eg Backup or Restore etc."
	::= { jobEntry 7 }

jobStu	OBJECT-TYPE
	SYNTAX      DisplayString
	ACCESS  read-only
	STATUS      mandatory
	DESCRIPTION
        	"The Backup storage unit name of NetBackup job."
	::= { jobEntry 8 }


jobVolpool	OBJECT-TYPE
	SYNTAX      DisplayString
	ACCESS  read-only
	STATUS      mandatory
	DESCRIPTION
        	"The Backup volume pool name of NetBackup job."
	::= { jobEntry 9 }

jobKbytes OBJECT-TYPE
	SYNTAX      Integer32 (0..65535)
	ACCESS  read-only
	STATUS      mandatory
	DESCRIPTION
        	"The Backup Kilo-bytes information of NetBackup job."
	::= { jobEntry 10 }

jobMaster	OBJECT-TYPE
	SYNTAX      DisplayString
	ACCESS  read-only
	STATUS      mandatory
	DESCRIPTION
        	"The master server hostname of NetBackup job."
	::= { jobEntry 11 }

jobErrExpl	OBJECT-TYPE
	SYNTAX      DisplayString
	ACCESS  read-only
	STATUS      mandatory
	DESCRIPTION
        	"The error message explanation of NetBackup job."
	::= { jobEntry 12 }

jobErrReco	OBJECT-TYPE
	SYNTAX      DisplayString
	ACCESS  read-only
	STATUS      mandatory
	DESCRIPTION
        	"The recommended action to correct error of NetBackup job."
	::= { jobEntry 13 }

jobId	OBJECT-TYPE
	SYNTAX      Integer32 (0..65535)
	ACCESS  read-only
	STATUS      mandatory
	DESCRIPTION
        "It is job Id for each NetBackup job, also served as Reference Index ."
	::= { jobEntry 14 }

jobErrCode 	OBJECT-TYPE
	SYNTAX      Integer32 (0..65535)
	ACCESS  read-only
	STATUS      mandatory
	DESCRIPTION
        	"It is job exit status code for the NetBackup job. 0 means no error."
	::= { jobEntry 100 }

jobErrMsg	OBJECT-TYPE
	SYNTAX      DisplayString
	ACCESS  read-only
	STATUS      mandatory
	DESCRIPTION
        	"The backup job error message of the NetBackup job."
	::= { jobEntry 101 }

jobErrFix	OBJECT-TYPE
	SYNTAX      Integer32 (0..65535)
	ACCESS  read-write
	STATUS      mandatory
	DESCRIPTION
        	"Setting this error fix flag to 1 to kick off the jobErrFixCmd."
	::= { jobEntry 102 }

jobErrFixCmd	OBJECT-TYPE
	SYNTAX      DisplayString
	ACCESS  read-write
	STATUS      mandatory
	DESCRIPTION
	       	"The command that gets run when the jobErrFix column is set to 1."
	::= { jobEntry 103 }


--
-- The extensible NetBackup SNMP control table 
--

nbuExtTable OBJECT-TYPE
    SYNTAX	SEQUENCE OF NBUExtEntry
    ACCESS	not-accessible
    STATUS	mandatory
    DESCRIPTION
	"A table of extensible commands to control NetBackup from SNMP 	framework via SNMP get and set protocol. The commands can start and stop NetBackup/Media Manager, start and kill backup jobs etc. These commands map can be configured in ENE agent's snmpd.conf file."
    ::= { netbackup 100 }

nbuEntry OBJECT-TYPE
    SYNTAX     NBUExtEntry
    ACCESS not-accessible
    STATUS     mandatory
    DESCRIPTION
        "An NBU entry containing an extensible modules and the results."
    INDEX      { nbuIndex }
    ::= { nbuExtTable  1 }

OpEnum ::= INTEGER { 
			other(1),
			startNbu(2),
			stopNbu(3),
			startMm(4),
			stopMm(5),
			userDef0(20),
			userDef1(21),
			userDef2(22),
			userDef3(23),
			userDef4(24),	
			userDef5(25),
			userDef6(26),
			userDef7(27),
			userDef8(28),
			userDef9(29)
		}

NBUExtEntry ::= SEQUENCE {
    	nbuIndex		OpEnum,
    	nbuNames		DisplayString,
    	nbuCommand		DisplayString,
    	nbuCtlFlag		Integer32,
	nbuResFile		DisplayString,
	nbuLockFile		DisplayString,
	nbuTimeout		Integer32,
	nbuFreq			Integer32,
    	nbuResult		Integer32,
    	nbuOutput		DisplayString,
    	nbuErrFix		Integer32,
    	nbuErrFixCmd		DisplayString
}

nbuIndex OBJECT-TYPE
    SYNTAX	OpEnum
    ACCESS	read-only
    STATUS	mandatory
    DESCRIPTION
	"Reference Index for extensible NBU scripts. It is an integer row number. A predefined map is available in snmpd.conf to map and customize the  map from index to the command."
    ::= { nbuEntry 1 }

nbuNames OBJECT-TYPE
    SYNTAX	DisplayString
    ACCESS	read-write
    STATUS	mandatory
    DESCRIPTION
	"A description of the extensible NBU command."
    ::= { nbuEntry 2 }

nbuCommand OBJECT-TYPE
    SYNTAX	DisplayString
    ACCESS	read-write
    STATUS	mandatory
    DESCRIPTION
	"The NBU command or scripts to be executed."
    ::= { nbuEntry 3 }

nbuCtlFlag OBJECT-TYPE
    SYNTAX	Integer32
    ACCESS	read-write
    STATUS	mandatory
    DESCRIPTION
	"When the flag is set to 1, the extensible NBU scripts in nbuCommand will be executed. Exit code will go to nbuResult, output go to nbuOutput."
    ::= { nbuEntry 4 }

nbuResFile OBJECT-TYPE
    SYNTAX	DisplayString
    ACCESS	read-only
    STATUS	mandatory
    DESCRIPTION
	"The result file path for excuting the nbuCommand scripts. It contains the exit status of the command in the first line. The stdout in the second line. So the Agent can pick it up after executing the command and set exit code to nbuResult, output go to nbuOutput."
    ::= { nbuEntry 5 }

nbuLockFile OBJECT-TYPE
    SYNTAX	DisplayString
    ACCESS	read-only
    STATUS	mandatory
    DESCRIPTION
	"The lock file path during excuting the nbuCommand scripts. Its presence indicate the nbuCommand is still in execution."
    ::= { nbuEntry 6 }

nbuTimeout OBJECT-TYPE
    SYNTAX	Integer32
    ACCESS	read-only
    STATUS	mandatory
    DESCRIPTION
	"The timeout before waiting for result of the executed NBU command."
    ::= { nbuEntry 7 }

nbuFreq OBJECT-TYPE
    SYNTAX	Integer32
    ACCESS	read-only
    STATUS	mandatory
    DESCRIPTION
	"The result checking frequency during waiting of the executed NBU command."
    ::= { nbuEntry 8 }

nbuResult OBJECT-TYPE
    SYNTAX	Integer32
    ACCESS	read-only
    STATUS	mandatory
    DESCRIPTION
	"The exit status of the executed NBU command."
    ::= { nbuEntry 100 }

nbuOutput OBJECT-TYPE
    SYNTAX	DisplayString
    ACCESS	read-only
    STATUS	mandatory
    DESCRIPTION
	"The firstline output of the executed NBU command."
    ::= { nbuEntry 101 }

nbuErrFix OBJECT-TYPE
    SYNTAX	Integer32
    ACCESS	read-write
    STATUS	mandatory
    DESCRIPTION
	"Setting this error fix flag to 1 to kick off the nbuErrFixCmd."
    ::= { nbuEntry 102 }
	
nbuErrFixCmd OBJECT-TYPE
    SYNTAX	DisplayString
    ACCESS	read-only
    STATUS	mandatory
    DESCRIPTION
	"The NBU command that gets run when the nbuErrFix column is 
	set to 1."
    ::= { nbuEntry 103 }

--
-- The VERITAS Cluster Server SNMP Event related Objects
--

vcsEventAttrs	OBJECT IDENTIFIER ::= { vcs 250 }

vcsTag	OBJECT-TYPE
    	SYNTAX		DisplayString
    	ACCESS	read-only
    	STATUS		mandatory
    	DESCRIPTION
	"A Tag describe the severity of the event:
	TAG_A: VCS internal message. Contact Customer Support.
	TAG_B: Messages indicating errors and exceptions.
	TAG_C: Messages indicating warnings.
	TAG_D: Messages indicating normal operations.
	TAG_E: Messages from agents indicating status, etc.
	"
    	::= { vcsEventAttrs 1 }

vcsHost	OBJECT-TYPE
    	SYNTAX		DisplayString
    	ACCESS	read-only
    	STATUS		mandatory
    	DESCRIPTION
	"The host name where the event occured."
    	::= { vcsEventAttrs 2 }

vcsRes	OBJECT-TYPE
    	SYNTAX		DisplayString
    	ACCESS	read-only
    	STATUS		mandatory
    	DESCRIPTION
	"The event related resource name."
    	::= { vcsEventAttrs 3 }

vcsResStat	OBJECT-TYPE
    	SYNTAX		DisplayString
    	ACCESS	read-only
    	STATUS		mandatory
    	DESCRIPTION
	"The state of the resource: online or offline."
    	::= { vcsEventAttrs 4 }

vcsAgent	OBJECT-TYPE
    	SYNTAX		DisplayString
    	ACCESS	read-only
    	STATUS		mandatory
    	DESCRIPTION
	"The event related Agent name."
    	::= { vcsEventAttrs 5 }

vcsNode	OBJECT-TYPE
    	SYNTAX		DisplayString
    	ACCESS	read-only
    	STATUS		mandatory
    	DESCRIPTION
	"The event related node name."
    	::= { vcsEventAttrs 6 }

vcsDate	OBJECT-TYPE
    	SYNTAX		DisplayString
    	ACCESS	read-only
    	STATUS		mandatory
    	DESCRIPTION
	"The date when event occur."
    	::= { vcsEventAttrs 7 }

vcsTime	OBJECT-TYPE
    	SYNTAX		DisplayString
    	ACCESS	read-only
    	STATUS		mandatory
    	DESCRIPTION
	"The time when event occur."
    	::= { vcsEventAttrs 8 }

vcsErrExpl	OBJECT-TYPE
	SYNTAX      DisplayString
	ACCESS  read-only
	STATUS      mandatory
	DESCRIPTION
        	"The error explanation."
	::= { vcsEventAttrs 98 }

vcsErrReco	OBJECT-TYPE
	SYNTAX      DisplayString
	ACCESS  read-only
	STATUS      mandatory
	DESCRIPTION
        	"The recommended action to correct VCS error."
	::= { vcsEventAttrs 99 }

vcsErrCode	OBJECT-TYPE
    	SYNTAX		Integer32
    	ACCESS	read-only
    	STATUS		mandatory
    	DESCRIPTION
	"The error code of the event."
    	::= { vcsEventAttrs 100 }

vcsErrMsg	OBJECT-TYPE
    	SYNTAX		DisplayString
    	ACCESS	read-only
    	STATUS		mandatory
    	DESCRIPTION
	"The detailed error message of the event."
    	::= { vcsEventAttrs 101 }

vrtsVcsEvent	OBJECT IDENTIFIER ::= { vcs 251 }

errorVcsEvent	TRAP-TYPE
	ENTERPRISE	vrtsVcsEvent
	VARIABLES	{ vcsTag, vcsDate, vcsTime, vcsErrMsg, vcsErrCode, vcsHost,
		vcsRes, vcsAgent, vcsNode }
	--STATUS      mandatory
	DESCRIPTION
	        "The VCS error event with TAG_A, TAG_B and TAG_C. Detailed error and corrective action information can be found from the objects associated with this event."
	--#TYPE      "The VCS error event occurred with following detailed information."
        --#SUMMARY   "Error Tag: (%s), Date: (%s), Time: (%s), Message: (%s), ErrCode: (%d), Host: (%s), Resource: (%s), Agent: (%s), Node: (%s)."
        --#ARGUMENTS {0,1,2,3,4,5,6,7,8}
        --#SEVERITY  MAJOR
        --#TIMEINDEX 1        
        --#STATE     OPERATIONAL

    	::= 1

normalVcsEvent	TRAP-TYPE
	ENTERPRISE	vrtsVcsEvent
	VARIABLES	{ vcsTag, vcsDate, vcsTime, vcsErrMsg, vcsErrCode, vcsHost, vcsRes, vcsAgent, vcsNode }
	-- STATUS      mandatory
	DESCRIPTION
	        "The normal VCS event with TAG_D, TAG_E. Detailed event information can be found from the objects associated with this event."
	--#TYPE      "The normal VCS event occurred with following detailed information."
        --#SUMMARY   "Error Tag: (%s), Date: (%s), Time: (%s), Message: (%s), ErrCode: (%d), Host: (%s), Resource: (%s), Agent: (%s), Node: (%s)."
        --#ARGUMENTS {0,1,2,3,4,5,6,7,8}
        --#SEVERITY  INFORMATIONAL
        --#TIMEINDEX 1        
        --#STATE     OPERATIONAL

    	::= 2

--
-- The extensible VERITAS Cluster Server SNMP control table 
--

vcsExtTable OBJECT-TYPE
    SYNTAX	SEQUENCE OF VCSExtEntry
    ACCESS	not-accessible
    STATUS	mandatory
    DESCRIPTION
	"A table of extensible commands to control VCS from SNMP 
	framework via SNMP get and set protocol. The commands can start and 
	stop VCS and its components, start and kill services, bring resource
	online and offline etc. These commands can be configured in 
	ENE agent's snmpd.conf file."
    ::= { vcs 100 }

vcsEntry OBJECT-TYPE
    SYNTAX     VCSExtEntry
    ACCESS not-accessible
    STATUS     mandatory
    DESCRIPTION
        "An VCS entry containing an extensible modules and the results."
    INDEX      { vcsIndex }
    ::= { vcsExtTable  1 }

VCSExtEntry ::= SEQUENCE {
    vcsIndex		Integer32,
    vcsNames		DisplayString,
    vcsCommand		DisplayString,
    vcsCtlFlag		Integer32,
    vcsResult		Integer32,
    vcsOutput		DisplayString,
    vcsErrFix		Integer32,
    vcsErrFixCmd	DisplayString
}

vcsIndex OBJECT-TYPE
    SYNTAX	Integer32 (0..65535)
    ACCESS	read-only
    STATUS	mandatory
    DESCRIPTION
	"Reference Index for extensible VCS scripts. It is an integer row number."
    ::= { vcsEntry 1 }

vcsNames OBJECT-TYPE
    SYNTAX	DisplayString
    ACCESS	read-only
    STATUS	mandatory
    DESCRIPTION
	"A description of the extensible VCS command."
    ::= { vcsEntry 2 }

vcsCommand OBJECT-TYPE
    SYNTAX	DisplayString
    ACCESS	read-only
    STATUS	mandatory
    DESCRIPTION
	"The VCS command or scripts to be executed."
    ::= { vcsEntry 3 }

vcsCtlFlag OBJECT-TYPE
    SYNTAX	Integer32
    ACCESS	read-write
    STATUS	mandatory
    DESCRIPTION
	"When the flag is set to 1, the extensible VCS scripts in vcsCommand will be executed. Exit code will go to vcsResult, output go to vcsOutput."
    ::= { vcsEntry 4 }

vcsResult OBJECT-TYPE
    SYNTAX	Integer32
    ACCESS	read-only
    STATUS	mandatory
    DESCRIPTION
	"The exit status of the executed VCS command."
    ::= { vcsEntry 100 }

vcsOutput OBJECT-TYPE
    SYNTAX	DisplayString
    ACCESS	read-only
    STATUS	mandatory
    DESCRIPTION
	"The firstlinw output of the executed VCS command."
    ::= { vcsEntry 101 }

vcsErrFix OBJECT-TYPE
    SYNTAX	Integer32
    ACCESS	read-write
    STATUS	mandatory
    DESCRIPTION
	"Setting this error fix flag to 1 to kick off the vcsErrFixCmd."
    ::= { vcsEntry 102 }
	
vcsErrFixCmd OBJECT-TYPE
    SYNTAX	DisplayString
    ACCESS	read-only
    STATUS	mandatory
    DESCRIPTION
	"The VCS command that gets run when the vcsErrFix column is set to 1."
    ::= { vcsEntry 103 }

--
-- The extensible NetBackup Job Error Event for 
-- Job error code 1-254
--

vrtsNbuJobEvent	OBJECT IDENTIFIER ::= { job 251 }

abnormalJobEvent	TRAP-TYPE
	ENTERPRISE	vrtsNbuJobEvent
	VARIABLES	{ jobId, jobClass, jobClient, 
		jobSched, jobSchedType, jobStu, 
		jobVolpool, jobErrCode, jobErrMsg,
		jobMaster, jobErrExpl, jobErrReco }
	--STATUS      mandatory
	DESCRIPTION
	        "The NetBackup job failed with error. Detailed job, error and corrective action information can be found from the objects associated with this event."
	--#TYPE      "The netback job failed with following detailed information."
        --#SUMMARY   "Job Id: (%d), Class: (%s), Client: (%s), Sched: (%s), SchedTYpe: (%s), Stu: (%s), VolPool: (%s), ErrCode: (%d), %s. Master: (%s), %s, %s"
        --#ARGUMENTS {0,1,2,3,4,5,6,7,8,9,10,11}
        --#SEVERITY  MAJOR
        --#TIMEINDEX 1        
        --#STATE     OPERATIONAL

    	::= 1

normalJobEvent	TRAP-TYPE
	ENTERPRISE	vrtsNbuJobEvent
	VARIABLES	{ jobId, jobClass, jobClient, 
		jobSched, jobSchedType, jobStu, 
		jobVolpool, jobErrCode, jobErrMsg,
		jobMaster, jobErrExpl, jobErrReco }
	--STATUS      mandatory
	DESCRIPTION
	        "The NetBackup job finished successfully. Detailed job information can be found from the objects associated with this event."
	--#TYPE      "The netback job finished successfully with following detailed information."
        --#SUMMARY   "Job Id: (%d), Class: (%s), Client: (%s), Sched: (%s), SchedTYpe: (%s), Stu: (%s), VolPool: (%s), ErrCode: (%d), %s. Master: (%s), %s, %s"
        --#ARGUMENTS {0,1,2,3,4,5,6,7,8,9,10,11}
        --#SEVERITY  INFORMATIONAL
        --#TIMEINDEX 1        
        --#STATE     OPERATIONAL

    	::= 2
--
-- The extensible NetBackup Job Error Event for 
-- Job error code 1-254
--

vrtsNbuExtEvent	OBJECT IDENTIFIER ::= { netbackup 101 }

nbuExtEvent	TRAP-TYPE
	ENTERPRISE	vrtsNbuExtEvent
	VARIABLES	{ nbuIndex, nbuNames, nbuCommand, 
		nbuResult, nbuOutput }
	-- STATUS      mandatory
	DESCRIPTION
	        "The NetBackup extensiable script execution result notificaiton with given exit status and output."
	--#TYPE      "The netbackup extensible scripts finished with following detailed information."
        --#SUMMARY   "Command Index: (%d), Command name: (%s), Command: (%s), Exit Status: (%d), Output: (%s)"
        --#ARGUMENTS {0,1,2,3,4}
        --#SEVERITY  INFORMATIONAL
        --#TIMEINDEX 1        
        --#STATE     OPERATIONAL

    	::= 1

--
-- The extensible NetBackup Error Event for 
-- general error code 301-310
-- 

vrtsNbuEvents	OBJECT IDENTIFIER ::= { netbackup 251 }
nbuTrapVars	OBJECT IDENTIFIER ::= { netbackup 250 }

nbuHost		OBJECT-TYPE
        SYNTAX      DisplayString
        ACCESS  read-only
        STATUS      mandatory
        DESCRIPTION
        "The hostname where NetBackup error event happened."
        ::= { nbuTrapVars 1 }

nbuErrcode	OBJECT-TYPE
        SYNTAX      Integer32
        ACCESS  read-only
        STATUS      mandatory
        DESCRIPTION
        "The error code of NetBackup error. 0 means no error."
        ::= { nbuTrapVars 100 }

nbuErrmsg	OBJECT-TYPE
        SYNTAX      DisplayString
        ACCESS  read-only
        STATUS      mandatory
        DESCRIPTION
        "The error message of NetBackup error."
        ::= { nbuTrapVars 101 }

dbBackupFailed	TRAP-TYPE
	ENTERPRISE	vrtsNbuEvents
	VARIABLES	{  nbuHost, nbuErrcode, nbuErrmsg }
	-- STATUS      mandatory
	DESCRIPTION
	"Description: The backup of the NB database failed.
	Resolution: Investigate why the NB database backup failed. Usually the All Log Entries Report will give you some idea as to why this failed."

	--#TYPE      "The backup of the NB database failed."
        --#SUMMARY   "Host: (%s), Error Code: (%d), Message: (%s)"
        --#ARGUMENTS {0,1,2}
        --#SEVERITY  CRITICAL
        --#TIMEINDEX 1        
        --#STATE     OPERATIONAL
    	::= 300

dbBackupIsDisabled	TRAP-TYPE
	ENTERPRISE	vrtsNbuEvents
	VARIABLES	{  nbuHost, nbuErrcode, nbuErrmsg }
	-- STATUS      mandatory
	DESCRIPTION
	"Description: Backup of the NetBackup database is mandatoryly disabled. 
	Resolution: No Immediate action is required. Periodically NetBackup will disable the ability to perform a NBU database backup while it is performing house-cleaning activities. Should the NB database backup be disabled for an extended period time, review the All Log Entries report to help determine why."

	--#TYPE      "Backup of the NetBackup database is currently disabled."
        --#SUMMARY   "Host: (%s), Error Code: (%d), Message: (%s)"
        --#ARGUMENTS {0,1,2}
        --#SEVERITY  WARNING
        --#TIMEINDEX 1        
        --#STATE     OPERATIONAL
    	::= 301

freezingMedia		TRAP-TYPE
	ENTERPRISE	vrtsNbuEvents
	VARIABLES	{  nbuHost, nbuErrcode, nbuErrmsg }
	-- STATUS      mandatory
	DESCRIPTION
	"Description: NetBackup has issued a 'freezing media' message.  
	Resolution:
	A piece of media (tape or optical) has been frozen either manually by an administrator or automatically by NetBackup. NetBackup will freeze media that has been previously written in another tape format (tar, ANSI,). NetBackup, by default will not overwrite these tapes unless a bp.conf entry to ALLOW_MEDIA_OVERWRITE is added, see the NetBackup Administrators Guide. Also investigate the All log Entries report and bptm logs for more information."

	--#TYPE      "NetBackup has issued a 'freezing media' message."
        --#SUMMARY   "Host: (%s), Error Code: (%d), Message: (%s)"
        --#ARGUMENTS {0,1,2}
        --#SEVERITY  WARNING
        --#TIMEINDEX 1        
        --#STATE     OPERATIONAL
    	::= 302

suspendingMedia		TRAP-TYPE
	ENTERPRISE	vrtsNbuEvents
	VARIABLES	{  nbuHost, nbuErrcode, nbuErrmsg }
	-- STATUS      mandatory
	DESCRIPTION
	"Description: NetBackup has issued a 'suspending media' message.  
	Resolution:
	NetBackup tried to use the identified media but had problems reading or writing to the tape. Investigate the cause through the All Log Entries report and / or bptm log."

	--#TYPE      "NetBackup has issued a 'suspending media' message."
        --#SUMMARY   "Host: (%s), Error Code: (%d), Message: (%s)"
        --#ARGUMENTS {0,1,2}
        --#SEVERITY  WARNING
        --#TIMEINDEX 1        
        --#STATE     OPERATIONAL
    	::= 303

mediaRequiredForRestore		TRAP-TYPE
	ENTERPRISE	vrtsNbuEvents
	VARIABLES	{  nbuHost, nbuErrcode, nbuErrmsg }
	-- STATUS      mandatory
	DESCRIPTION
	"Description: Media is needed for an NBU restore operation.  The event is sent via a user alarm in the action script.
	Resolution:
	The media identified is required for a restore that has been initiated. The media id is also identified in the Device Management Window. Locate the required tape, place it in the library or tape drive and satisfy the tape mount request through the Device Manager window. You may also deny the request through the Device Manager window."

	--#TYPE      "Media is needed for an NBU restore operation.  The event is sent via a user alarm in the action script."
        --#SUMMARY   "Host: (%s), Error Code: (%d), Message: (%s)"
        --#ARGUMENTS {0,1,2}
        --#SEVERITY  WARNING
        --#TIMEINDEX 1        
        --#STATE     OPERATIONAL
    	::= 304

downedDrive		TRAP-TYPE
	ENTERPRISE	vrtsNbuEvents
	VARIABLES	{  nbuHost, nbuErrcode, nbuErrmsg }
	-- STATUS      mandatory
	DESCRIPTION
	"Description: The operator or Media Manager has downed a drive. 
	Resolution:
	A tape drive is suspected of having problems. Investigate the All Log Entries report, bptm log, Operating System messages log (/var/adm/messages) to determine the cause. NetBackup may down a drive when having trouble reading a tape, if the tape is used in another drive and also has problems then the tape is suspended and the original downed drive is automatically brough up."

	--#TYPE      "The operator or Media Manager has downed a drive."
        --#SUMMARY   "Host: (%s), Error Code: (%d), Message: (%s)"
        --#ARGUMENTS {0,1,2}
        --#SEVERITY  CRITICAL
        --#TIMEINDEX 1        
        --#STATE     OPERATIONAL
    	::= 305

exceededCleaningFrequency	TRAP-TYPE
	ENTERPRISE	vrtsNbuEvents
	VARIABLES	{  nbuHost, nbuErrcode, nbuErrmsg }
	-- STATUS      mandatory
	DESCRIPTION
	"Description: A drive has exceeded its cleaning frequency.
	Resolution:
	This should not normally occur with most TLD devices such as with STK Silo's and DLT tape drives, which automatically handle cleanings. This error message only occurs when NetBackup is handling tape cleanings manually."

	--#TYPE      "A drive has exceeded its cleaning frequency."
        --#SUMMARY   "Host: (%s), Error Code: (%d), Message: (%s)"
        --#ARGUMENTS {0,1,2}
        --#SEVERITY  WARNING
        --#TIMEINDEX 1        
        --#STATE     OPERATIONAL
    	::= 306

exceededMaxMounts	TRAP-TYPE
	ENTERPRISE	vrtsNbuEvents
	VARIABLES	{  nbuHost, nbuErrcode, nbuErrmsg }
	-- STATUS      mandatory
	DESCRIPTION
	"Description: A media has exceeded its maximum number of mounts.  
	Resolution: 
	When the media was added to NetBackups' Media Manager, a maximum number of mounts was assigned. The media has reached this limit which normally signals that it should be retired and replaced with another piece of media. Data on the tape is still tracked on the tape and expires once the retention period of the image has passed."

	--#TYPE      "A media has exceeded its maximum number of mounts."
        --#SUMMARY   "Host: (%s), Error Code: (%d), Message: (%s)"
        --#ARGUMENTS {0,1,2}
        --#SEVERITY  CRITICAL
        --#TIMEINDEX 1        
        --#STATE     OPERATIONAL
    	::= 307

mountRequest		TRAP-TYPE
	ENTERPRISE	vrtsNbuEvents
	VARIABLES	{  nbuHost, nbuErrcode, nbuErrmsg }
	-- STATUS      mandatory
	DESCRIPTION
	"Description: A mount request is posted to the system log for a non-robotic device.  It may be either for the mount itself or because the media needs 'write enabled'.
	Resolution:
	This message will also be displayed in the Device Manager window. Place the tape in the required non-robotic drive and satisfy the request through the Device Manager window. Deny the request through the Device Manager window. Or remove the media from the tape drive, write enable it and return it to the tape drive. This message is normally issued for tape drives under Operator control rather than AVR or Robotic control."

	--#TYPE      "A mount request is posted to the system log for a non-robotic device.  It may be either for the mount itself or because the media needs 'write enabled'."
        --#SUMMARY   "Host: (%s), Error Code: (%d), Message: (%s)"
        --#ARGUMENTS {0,1,2}
        --#SEVERITY  WARNING
        --#TIMEINDEX 1        
        --#STATE     OPERATIONAL
    	::= 308

noCleaningTape	TRAP-TYPE
	ENTERPRISE	vrtsNbuEvents
	VARIABLES	{  nbuHost, nbuErrcode, nbuErrmsg }
	-- STATUS      mandatory
	DESCRIPTION
	"Description: There is no cleaning tape or the cleaning tape is used up. 
	Resolution:
	This message only occurs when NetBackup is handling tape drive cleanings and should not normally occur with most TLD devices."

	--#TYPE      "There is no cleaning tape or the cleaning tape is used up."
        --#SUMMARY   "Host: (%s), Error Code: (%d), Message: (%s)"
        --#ARGUMENTS {0,1,2}
        --#SEVERITY  WARNING
        --#TIMEINDEX 1        
        --#STATE     OPERATIONAL
    	::= 309

zeroCleaningsLeft	TRAP-TYPE
	ENTERPRISE	vrtsNbuEvents
	VARIABLES	{  nbuHost, nbuErrcode, nbuErrmsg }
	-- STATUS      mandatory
	DESCRIPTION
	"Description: The cleaning tape has no cleanings left.   
	Resolution: 
	This message only occurs when NetBackup is handling tape drive cleanings and the cleaning tape(s) have been used to their capacity. This should not normally occur with most TLD devices."

	--#TYPE      "The cleaning tape has no cleanings left."
        --#SUMMARY   "Host: (%s), Error Code: (%d), Message: (%s)"
        --#ARGUMENTS {0,1,2}
        --#SEVERITY  WARNING
        --#TIMEINDEX 1
        --#STATE     OPERATIONAL
    	::= 310

--
-- The extensible Log object for VERITAS products
-- 

log		OBJECT IDENTIFIER ::= { commonObjects 1 }

--
-- The extensible VERITAS monitored Error Log and message table
-- 

logTable OBJECT-TYPE
        SYNTAX  SEQUENCE OF LogEntry
        ACCESS      not-accessible
        STATUS  mandatory
        DESCRIPTION
        "A table of error log and error message based event management information configured in the logfile.conf and messages.conf of the ENE SNMP agent. "
        ::= { log 1 }

logEntry OBJECT-TYPE
        SYNTAX     LogEntry
        ACCESS not-accessible
        STATUS     mandatory
        DESCRIPTION
                "An log entry containing a log monitoring related information."
        INDEX      { logIndex }
        ::= { logTable  1 }

LogEntry ::= SEQUENCE {
        logIndex        Integer32,
	logHost		DisplayString,
	logPrdCode	Integer32,
	logPrdName	DisplayString,
	logObjName	DisplayString,
	logAttrName	DisplayString,
	logFile		DisplayString,
	logErrStrs	DisplayString,
	logDesc		DisplayString,
	logResolution	DisplayString,
	logErrFlag	Integer32,
        logErrcode      Integer32,
        logErrmsg       DisplayString,
        logErrFix       Integer32,
        logErrFixCmd    DisplayString
}

logIndex OBJECT-TYPE
        SYNTAX      Integer32 (0..65535)
        ACCESS  read-only
        STATUS      mandatory
        DESCRIPTION
        "It is the unique index of error log and message to be monitored."
        ::= { logEntry 1 }

logHost		OBJECT-TYPE
        SYNTAX      DisplayString
        ACCESS  read-only
        STATUS      mandatory
        DESCRIPTION
        "The hostname where log error event happened."
        ::= { logEntry 2 }

logPrdCode	OBJECT-TYPE
        SYNTAX      Integer32
        ACCESS  read-only
        STATUS      mandatory
        DESCRIPTION
        "The VERITAS product code of which the error log event is associated, it can be 0: NetBackup, 1: VxVM, 2: VxFS, 7: VCS etc."
        ::= { logEntry 3 }

logPrdName	OBJECT-TYPE
        SYNTAX      DisplayString
        ACCESS  read-only
        STATUS      mandatory
        DESCRIPTION
        "The VERITAS product name of which the error log event is associated, it can be NetBackup, VxVM, VxFS, VCS etc."
        ::= { logEntry 4 }

logObjName	OBJECT-TYPE
        SYNTAX      DisplayString
        ACCESS  read-only
        STATUS      mandatory
        DESCRIPTION
        "The object name of which the error log event is associated. For example, it can be NetBackup job, tape drive, or VxVM's subdisk, or VCS's service etc."
        ::= { logEntry 5 }

logAttrName	OBJECT-TYPE
        SYNTAX      DisplayString
        ACCESS  read-only
        STATUS      mandatory
        DESCRIPTION
         "The attribute name of which the error log event is associated. For example, it can be NetBackup job's Kbytes attribute, tape drive's number of drives, or VxVM's subdisk's size, or VCS's service's status etc."
        ::= { logEntry 6 }

logFile		OBJECT-TYPE
        SYNTAX      DisplayString
        ACCESS  read-only
        STATUS      mandatory
        DESCRIPTION
        "The log file name where the error strings are detected."
        ::= { logEntry 7 }

logErrStrs	OBJECT-TYPE
        SYNTAX      DisplayString
        ACCESS  read-only
        STATUS      mandatory
        DESCRIPTION
        "The error strings to monitor."
        ::= { logEntry 8 }

logDesc		OBJECT-TYPE
        SYNTAX      DisplayString
        ACCESS  read-only
        STATUS      mandatory
        DESCRIPTION
        "The description of the error log event."
        ::= { logEntry 9 }

logResolution	OBJECT-TYPE
        SYNTAX      DisplayString
        ACCESS  read-only
        STATUS      mandatory
        DESCRIPTION
        "The resolution of the error log event."
        ::= { logEntry 10 }

logErrFlag	OBJECT-TYPE
	SYNTAX      Integer32
    	ACCESS  read-only
    	STATUS      mandatory
    	DESCRIPTION
        " Set the flag to 1 to indicate the error strings is found in the specified error log. 0 means no error."
    	::= { logEntry 99 }

logErrcode	OBJECT-TYPE
        SYNTAX      Integer32
        ACCESS  read-only
        STATUS      mandatory
        DESCRIPTION
        "The error code of log error."
        ::= { logEntry 100 }

logErrmsg	OBJECT-TYPE
        SYNTAX      DisplayString
        ACCESS  read-only
        STATUS      mandatory
        DESCRIPTION
        "The error message of log error."
        ::= { logEntry 101 }

logErrFix        OBJECT-TYPE
        SYNTAX      Integer32 (0..65535)
        ACCESS  read-write
        STATUS      mandatory
        DESCRIPTION
        "Setting this error fix flag to 1 to kick off the logErrFixCmd."
        ::= { logEntry 102 }

logErrFixCmd     OBJECT-TYPE
        SYNTAX      DisplayString
        ACCESS  read-write
        STATUS      mandatory
        DESCRIPTION
        "The command that gets run when the logErrFix column is set to 1."
        ::= { logEntry 103 }

vrtsLogMonitor	OBJECT IDENTIFIER ::= { log 251 }

logEvent	TRAP-TYPE
	ENTERPRISE	vrtsLogMonitor
	VARIABLES	{  logHost, logObjName, logFile, logErrStrs, logDesc, logResolution, logErrcode, logErrmsg }
	-- STATUS      mandatory
	DESCRIPTION
	"The sequences of specific error strings are detected in given error log file on given host."

	--#TYPE      "The sequences of specific error strings are detected in given error log file on given host."
        --#SUMMARY   "Host: (%s), Object: (%s), logfile: (%s), error strings: (%s), desc: (%s), resolution: (%s), Error Code: (%d), Message: (%s)"
        --#ARGUMENTS {0,1,2,3,4,5,6,7}
        --#SEVERITY  MAJOR
        --#TIMEINDEX 1        
        --#STATE     OPERATIONAL
    	::= 1

--
-- The extensible process object for VERITAS products
-- On NT, it represent NT service
-- 

process		OBJECT IDENTIFIER ::= { commonObjects 2 }

--
-- The extensible VERITAS process control table
-- 

psTable 		OBJECT-TYPE
    	SYNTAX		SEQUENCE OF PsEntry
    	ACCESS	not-accessible
    	STATUS	mandatory
    	DESCRIPTION
	"A table containing information on running programs/daemons/service configured for monitoring in the process.conf file of the ENE SNMP agent. Processes violating the available number of running processes or CPU, IO threshold configured in process.conf, or services.conf on NT are flagged with numerical and textual errors."
    ::= { process 1 }

psEntry OBJECT-TYPE
    SYNTAX	PsEntry
    ACCESS	not-accessible
    STATUS	mandatory
    DESCRIPTION
        "An entry containing a process and its statistics."
    INDEX	{ psIndex }
    ::= { psTable  1 }

PsEntry ::= SEQUENCE {
	psIndex		Integer32,
	psId		Integer32,
   	psName		DisplayString,
--
-- use psAttr to represent monitoring process's 
-- availablility, hanging and runaway situation
--
	psAttr		DisplayString,
	psMin		Integer32,
	psMax		Integer32,
	psCount		Integer32,
	psCpuPct	DisplayString,
	psBytesIO	Integer32,
	psSlpMax	Integer32,
	psHost		DisplayString,
	psErrFlag	Integer32,
	psErrcode	Integer32,
	psErrmsg	DisplayString,
	psErrFix	Integer32,
	psErrFixCmd	DisplayString
}

psIndex			OBJECT-TYPE
	SYNTAX		Integer32 (0..65535)
	ACCESS	read-only
	STATUS		mandatory
	DESCRIPTION
	"Reference Index for each observed process or service."
    	::= { psEntry 1 }

psId			OBJECT-TYPE
	SYNTAX		Integer32 (0..65535)
	ACCESS	read-only
	STATUS		mandatory
	DESCRIPTION
	"Actual process id for each observed process."
	::= { psEntry 2 }

psName			OBJECT-TYPE
	SYNTAX		DisplayString
	ACCESS	read-only
	STATUS		mandatory
	DESCRIPTION
	"The process or service name that agent is counting and checking."
    	::= { psEntry 3 }

psAttr			OBJECT-TYPE
	SYNTAX		DisplayString
	ACCESS	read-only
	STATUS		mandatory
	DESCRIPTION
	"The process or service attribute name that agent is checking. It can be: existence, hanging or runaway."
    	::= { psEntry 4 }

psMin 			OBJECT-TYPE
	SYNTAX		Integer32
	ACCESS	read-only
	STATUS		mandatory
    	DESCRIPTION
	"The min threshold number of instances of monitored process that should be running. An error is generated if threshold is violated."
    	::= { psEntry 5 }

psMax 			OBJECT-TYPE
    	SYNTAX		Integer32
    	ACCESS	read-only
    	STATUS	mandatory
    	DESCRIPTION
	"The max threshold number of instances of monitored process that should be running. An error is generated if threshold is violated."
    	::= { psEntry 6 }

psCount 		OBJECT-TYPE
    	SYNTAX		Integer32
    	ACCESS	read-only
    	STATUS		mandatory
    	DESCRIPTION
	"The current number of process instances with the specified name."
	::= { psEntry 7 }

psCpuPct 		OBJECT-TYPE
    	SYNTAX		DisplayString
    	ACCESS	read-only
    	STATUS		mandatory
    	DESCRIPTION
	"The Percentage CPU threshold of the monitored process."
	::= { psEntry 8 }

psBytesIO 		OBJECT-TYPE
    	SYNTAX		Integer32
    	ACCESS	read-only
    	STATUS		mandatory
    	DESCRIPTION
	"The Bytes I/O threshold of the monitored process."
	::= { psEntry 9 }

psSlpMax 		OBJECT-TYPE
    	SYNTAX		Integer32
    	ACCESS	read-only
    	STATUS		mandatory
    	DESCRIPTION
	"The Maximum sleeping time threshold of the monitored process."
	::= { psEntry 10 }

psHost 			OBJECT-TYPE
    	SYNTAX		DisplayString
    	ACCESS	read-only
    	STATUS		mandatory
    	DESCRIPTION
	"The hostname of the monitored process."
	::= { psEntry 11 }

psErrFlag 		OBJECT-TYPE
   	SYNTAX      	Integer32
    	ACCESS  	read-only
    	STATUS      	mandatory
    	DESCRIPTION
        "Set the flag to 1 to indicate the error with the process. 0 means no error."
    	::= { psEntry 99 }

psErrcode		OBJECT-TYPE
	SYNTAX		Integer32
	ACCESS	read-only
	STATUS		mandatory
	DESCRIPTION
	"The error code of process error."
	::= { psEntry 100 }

psErrmsg		OBJECT-TYPE
    	SYNTAX		DisplayString
    	ACCESS	read-only
    	STATUS		mandatory
    	DESCRIPTION
	"The error message of the process error."
    	::= { psEntry 101 }

psErrFix 		OBJECT-TYPE
	SYNTAX		Integer32
	ACCESS	read-write
	STATUS		mandatory
	DESCRIPTION
	"Setting this error fix flag to 1 to kick off the psErrFixCmd."
	::= { psEntry 102 }

psErrFixCmd		OBJECT-TYPE
	SYNTAX		DisplayString
	ACCESS	read-only
	STATUS		mandatory
	DESCRIPTION
	"The command that will be executed when the psErrFix column is set to 1."
	::= { psEntry 103 }
--
-- Process Error Event
--

vrtsProcessMonitor      OBJECT IDENTIFIER ::= { process 251 }

processEvent        	TRAP-TYPE
	ENTERPRISE	vrtsProcessMonitor
        VARIABLES {  psHost, psId, psName, psAttr, psErrcode, psErrmsg }
        -- STATUS      mandatory
        DESCRIPTION
        "The monitored process has violated threshold condition of specified monitored attribute(existence, hanging or runaway) on given host."

        --#TYPE      "The monitored process has violated threshold condition of specified monitored attribute(existence, hanging or runaway) on given host."
        --#SUMMARY   "Host: (%s), Pid: (%d), Name: (%s), Attribute: (%s), Error Code: (%d), Msg: (%s)"
        --#ARGUMENTS {0,1,2,3,4,5}
        --#SEVERITY  MAJOR
        --#TIMEINDEX 1 
        --#STATE     OPERATIONAL
        ::= 1

--
-- The extensible process object for VERITAS products
-- On NT, it represent NT service
-- 

collector	OBJECT IDENTIFIER ::= { commonObjects 4 }

--
-- The extensible VERITAS collector table
-- 

clTable 		OBJECT-TYPE
    	SYNTAX		SEQUENCE OF ClEntry
    	ACCESS	not-accessible
    	STATUS	mandatory
    	DESCRIPTION
	"A table of collector based event management information configured in the collector.conf file of the ENE SNMP agent."
    ::= { collector 1 }

clEntry 		OBJECT-TYPE
   	SYNTAX		ClEntry
    	ACCESS	not-accessible
    	STATUS		mandatory
    	DESCRIPTION
        "An entry containing a collector information."
    	INDEX	{ clIndex }
    	::= { clTable  1 }

ClEntry ::= SEQUENCE {
	clIndex		Integer32,
	clName		DisplayString,
        clHost         	DisplayString,
	clScript	DisplayString,
	clSampFreq	Integer32,
	clFreq		Integer32,
	clTimeout	Integer32,
	clPrdCode	Integer32,
        clPrdName      	DisplayString,
        clObjName      	DisplayString,
        clAttrName    	DisplayString,
	clLow		Integer32,
	clHigh		Integer32,
	clCount		Integer32,
	clObjNames	DisplayString,
        clResolution   	DisplayString,
        clErrFlag      	Integer32,
        clErrcode      	Integer32,
        clErrmsg       	DisplayString,
        clErrFix       	Integer32,
        clErrFixCmd    	DisplayString
}

clIndex                 OBJECT-TYPE
        SYNTAX          Integer32 (0..65535)
        ACCESS      read-only
        STATUS          mandatory
        DESCRIPTION
        "Reference Index for each the collector."
        ::= { clEntry 1 }

clName                  OBJECT-TYPE
        SYNTAX          DisplayString
        ACCESS      read-only
        STATUS          mandatory
        DESCRIPTION
        "The collector name."
        ::= { clEntry 2 }

clHost         		OBJECT-TYPE
        SYNTAX      	DisplayString
        ACCESS  	read-only
        STATUS      	mandatory
        DESCRIPTION
        "The hostname where collector is running."
        ::= { clEntry 3 }

clScript         	OBJECT-TYPE
        SYNTAX      	DisplayString
        ACCESS  	read-only
        STATUS      	mandatory
        DESCRIPTION
        "The collector script file name, if will be prefixed with $ENEDir\config\Scripts directory"
        ::= { clEntry 4 }

clSampFreq         	OBJECT-TYPE
        SYNTAX      	Integer32
        ACCESS  	read-write
        STATUS      	mandatory
        DESCRIPTION
        "The frequency in seconds that the collector script is executed."
        ::= { clEntry 5 }

clFreq         	OBJECT-TYPE
        SYNTAX      	Integer32
        ACCESS  	read-write
        STATUS      	mandatory
        DESCRIPTION
        "The frequency in seconds which specifies how frequent should ENE agent check whether the collected data is ready. The optimal value can be obtained by finding out how long a collector session is usually taking."
        ::= { clEntry 6 }

clTimeout         	OBJECT-TYPE
        SYNTAX      	Integer32
        ACCESS  	read-write
        STATUS      	mandatory
        DESCRIPTION
        "If no data after clTimeout seconds, then the collecting session is aborted."
        ::= { clEntry 7 }

clPrdCode      		OBJECT-TYPE
        SYNTAX      	Integer32
        ACCESS 	read-only
        STATUS      	mandatory
        DESCRIPTION
        "The VERITAS product code of which the collector is associated, it can be 0: NetBackup, 1: VxVM, 2: VxFS, 7: VCS etc."
        ::= { clEntry 8 }

clPrdName      		OBJECT-TYPE
        SYNTAX      	DisplayString
        ACCESS  	read-only
        STATUS      	mandatory
        DESCRIPTION
        "The VERITAS product name of which the collector is associated, it can be NetBackup, VxVM, VxFS, VCS etc."
        ::= { clEntry 9 }

clObjName      		OBJECT-TYPE
        SYNTAX      	DisplayString
        ACCESS  	read-only
        STATUS      	mandatory
        DESCRIPTION
        "The object name of the collection. For example, it can be NetBackup job, tape drive, or VxVM's subdisk, or VCS's service etc."
        ::= { clEntry 10 }
	
clAttrName     		OBJECT-TYPE
        SYNTAX      	DisplayString
        ACCESS  	read-only
        STATUS      	mandatory
        DESCRIPTION
         "The attribute name of which the collection is associated. For example, it can be NetBackup job's Kbytes attribute, tape drive's number of drives, or VxVM's subdisk's size, or VCS's service's status etc."
        ::= { clEntry 11 }

clLow         		OBJECT-TYPE
        SYNTAX      	Integer32
        ACCESS  	read-write
        STATUS      	mandatory
        DESCRIPTION
        "Indicate low threshold for the collected attribute value. If violated, event will be sent."
        ::= { clEntry 12 }

clHigh         		OBJECT-TYPE
        SYNTAX      	Integer32
        ACCESS  	read-write
        STATUS      	mandatory
        DESCRIPTION
        "Indicate high threshold for the collected attribute value. If violated, event will be sent."
        ::= { clEntry 13 }

clCount        		OBJECT-TYPE
        SYNTAX      	Integer32
        ACCESS  	read-write
        STATUS      	mandatory
        DESCRIPTION
        "The number of objects which we care about whether its attribute value is within low and high threshold. 0 means we are all object."
        ::= { clEntry 14 }

clObjNames     		OBJECT-TYPE
        SYNTAX      	DisplayString
        ACCESS  	read-write
        STATUS      	mandatory
        DESCRIPTION
        "List of object names, seperated by ';', which we care when threshold is violated. Leave name empty make it a wild card, means we care all objects."
        ::= { clEntry 15 }

clResolution   		OBJECT-TYPE
        SYNTAX      	DisplayString
        ACCESS  	read-write
        STATUS      	mandatory
        DESCRIPTION
        "Text resulotion when threshold value is violated."
        ::= { clEntry 16 }

clErrFlag               OBJECT-TYPE
        SYNTAX          Integer32
        ACCESS      read-only
        STATUS          mandatory
        DESCRIPTION
        "Set the flag to 1 to indicate the threshold is violated. 0 means no error."
        ::= { clEntry 99 }

clErrcode               OBJECT-TYPE
        SYNTAX          Integer32
        ACCESS      read-only
        STATUS          mandatory
        DESCRIPTION
        "The error code of for errors from this collector."
        ::= { clEntry 100 }

clErrmsg                OBJECT-TYPE
        SYNTAX          DisplayString
        ACCESS      read-only
        STATUS          mandatory
        DESCRIPTION
        "The error message of the threshold violation."
        ::= { clEntry 101 }

clErrFix                OBJECT-TYPE
        SYNTAX          Integer32
        ACCESS      read-write
        STATUS          mandatory
        DESCRIPTION
        "Setting this error fix flag to 1 to kick off the clErrFixCmd."
        ::= { clEntry 102 }

clErrFixCmd             OBJECT-TYPE
        SYNTAX          DisplayString
        ACCESS      read-only
        STATUS          mandatory
        DESCRIPTION
        "The command that will be executed when the clErrFix column is set to 1.
"
        ::= { clEntry 103 }

--
-- Collector Error Event
--

vrtsCollectorMonitor      OBJECT IDENTIFIER ::= { collector 251 }

collectorEvent        	TRAP-TYPE
	ENTERPRISE	vrtsCollectorMonitor
        VARIABLES {  clName, clHost, clPrdName, clObjName, clAttrName, clErrcode, clErrmsg, clResolution }
        -- STATUS      mandatory
        DESCRIPTION
        "The collection has detected a threshold violation condition of specified objects attribute on given host."

        --#TYPE      "The collection has detected a threshold violation condition of specified objects attribute on given host."
        --#SUMMARY   "Collector: (%s), Host: (%s), Product: (%s), Object: (%s), Attribute: (%s), Error Code: (%d), Msg: (%s), Resolution: (%s)."
        --#ARGUMENTS {0,1,2,3,4,5,6,7}
        --#SEVERITY  MAJOR
        --#TIMEINDEX 1 
        --#STATE     OPERATIONAL
        ::= 1

frequency	OBJECT IDENTIFIER ::= { commonObjects 8 }

messagefreq         	OBJECT-TYPE
        SYNTAX      	Integer32
        ACCESS  	read-write
        STATUS      	mandatory
        DESCRIPTION
        "Number of seconds interval for message log checking, you can set it here based on your event notification requirements. The default value is 30 seconds."
        ::= { frequency 1 }

processfreq        	OBJECT-TYPE
        SYNTAX      	Integer32
        ACCESS  	read-write
        STATUS      	mandatory
        DESCRIPTION
        "Number of seconds interval for process checking, you can set it here based on your event notification requirements. The default value is 300 seconds."
        ::= { frequency 2 }

vxvmSamplefreq        	OBJECT-TYPE
        SYNTAX      	Integer32
        ACCESS  	read-write
        STATUS      	mandatory
        DESCRIPTION
        "Set how frequent, in seconds, should a vxvm collector be executed.you can set it here based on your event notification requirements. The default value is 50 minutes or 3000 seconds."
        ::= { frequency 11 }

vxvmCheckfreq        	OBJECT-TYPE
        SYNTAX      	Integer32
        ACCESS  	read-write
        STATUS      	mandatory
        DESCRIPTION
        "Set how frequent, in seconds, should ENE agent check whether the vxvm collected data is ready. The optimal value can be obtained by finding out how long a collector session is usually taking. The default value is 100 seconds."
        ::= { frequency 12 }

vxvmTimeout        	OBJECT-TYPE
        SYNTAX      	Integer32
        ACCESS  	read-write
        STATUS      	mandatory
        DESCRIPTION
        "If no vxvm collection data ready after vxvmTimeout seconds in the same collection session, then the collecting session is aborted. The default value is 350 seconds."
        ::= { frequency 13 }

vxfsSamplefreq        	OBJECT-TYPE
        SYNTAX      	Integer32
        ACCESS  	read-write
        STATUS      	mandatory
        DESCRIPTION
        "Set how frequent, in seconds, should a vxfs collector be executed.you can set it here based on your event notification requirements. The default value is 40 minutes or 2400 seconds."
        ::= { frequency 21 }

vxfsCheckfreq        	OBJECT-TYPE
        SYNTAX      	Integer32
        ACCESS  	read-write
        STATUS      	mandatory
        DESCRIPTION
        "Set how frequent, in seconds, should ENE agent check whether the vxfs collected data is ready. The optimal value can be obtained by finding out how long a collector session is usually taking. The default value is 100 seconds."
        ::= { frequency 22 }

vxfsTimeout        	OBJECT-TYPE
        SYNTAX      	Integer32
        ACCESS  	read-write
        STATUS      	mandatory
        DESCRIPTION
        "If no vxfs collection data ready after vxfsTimeout seconds in the same collection session, then the collecting session is aborted. The default value is 350 seconds."
        ::= { frequency 23 }

--
-- ENE generic events, such as cold start, warmstart, heart beat, shutdown etc
--

vrtsEneMonitor      OBJECT IDENTIFIER ::= { commonObjects 251 }

coldStart        	TRAP-TYPE
	ENTERPRISE	vrtsEneMonitor
        -- STATUS      mandatory
        DESCRIPTION
        "The SNMP ENE agent has started."

        --#TYPE      "The SNMP ENE agent has started."
        --#SUMMARY   "The SNMP ENE agent has started."
        --#ARGUMENTS {}
        --#SEVERITY  INFORMATIONAL
        --#TIMEINDEX 1 
        --#STATE     OPERATIONAL
        ::= 1

heartBeat        	TRAP-TYPE
	ENTERPRISE	vrtsEneMonitor
        -- STATUS      mandatory
        DESCRIPTION
        "The SNMP ENE agent heart beat event to signal it is alive."

        --#TYPE      "The SNMP ENE agent is alive."
        --#SUMMARY   "The SNMP ENE agent is alive."
        --#ARGUMENTS {}
        --#SEVERITY  INFORMATIONAL
        --#TIMEINDEX 1 
        --#STATE     OPERATIONAL
        ::= 3

shutDown        TRAP-TYPE
	ENTERPRISE	vrtsEneMonitor
        -- STATUS      mandatory
        DESCRIPTION
        "The SNMP ENE agent shut down."

        --#TYPE      "The SNMP ENE agent shut down."
        --#SUMMARY   "The SNMP ENE agent shut down."
        --#ARGUMENTS {}
        --#SEVERITY  INFORMATIONAL
        --#TIMEINDEX 1 
        --#STATE     OPERATIONAL
        ::= 5

--
-- The extensible VxVM SNMP control table 
--

vmExtTable OBJECT-TYPE
    SYNTAX	SEQUENCE OF VMExtEntry
    ACCESS	not-accessible
    STATUS	mandatory
    DESCRIPTION
	"A table of extensible commands to control VxVM from SNMP framework via SNMP get and set protocol. These commands can be configured in ENE agent's snmpd.conf file."
    ::= { vxvm 100 }

vmEntry OBJECT-TYPE
    SYNTAX     VMExtEntry
    ACCESS not-accessible
    STATUS     mandatory
    DESCRIPTION
        "A VM entry containing an extensible modules and the results."
    INDEX      { vmIndex }
    ::= { vmExtTable  1 }

VMExtEntry ::= SEQUENCE {
    	vmIndex			Integer32,
    	vmNames			DisplayString,
    	vmCommand		DisplayString,
    	vmCtlFlag		Integer32,
    	vmResult		Integer32,
    	vmOutput		DisplayString,
    	vmErrFix		Integer32,
    	vmErrFixCmd		DisplayString
}

vmIndex OBJECT-TYPE
    SYNTAX	Integer32 (0..65535)
    ACCESS	read-only
    STATUS	mandatory
    DESCRIPTION
	"Reference Index for extensible VM scripts. It is an integer row number. A predefined map is available in snmpd.conf to map the index to the command."
    ::= { vmEntry 1 }

vmNames OBJECT-TYPE
    SYNTAX	DisplayString
    ACCESS	read-write
    STATUS	mandatory
    DESCRIPTION
	"A description of the extensible VM command."
    ::= { vmEntry 2 }

vmCommand OBJECT-TYPE
    SYNTAX	DisplayString
    ACCESS	read-write
    STATUS	mandatory
    DESCRIPTION
	"A valid VM script path to be executed when vmCtlFlag is set to 1."
    ::= { vmEntry 3 }

vmCtlFlag OBJECT-TYPE
    SYNTAX	Integer32
    ACCESS	read-write
    STATUS	mandatory
    DESCRIPTION
	"When the flag is set to 1, the extensible VM scripts in vmCommand will be executed. Exit code will go to vmResult, output go to vmOutput."
    ::= { vmEntry 4 }

vmResult OBJECT-TYPE
    SYNTAX	Integer32
    ACCESS	read-only
    STATUS	mandatory
    DESCRIPTION
	"The exit status of the executed VM command."
    ::= { vmEntry 100 }

vmOutput OBJECT-TYPE
    SYNTAX	DisplayString
    ACCESS	read-only
    STATUS	mandatory
    DESCRIPTION
	"The firstline output of the executed VM command."
    ::= { vmEntry 101 }

vmErrFix OBJECT-TYPE
    SYNTAX	Integer32
    ACCESS	read-write
    STATUS	mandatory
    DESCRIPTION
	"Setting this error fix flag to 1 to kick off the vmErrFixCmd."
    ::= { vmEntry 102 }
	
vmErrFixCmd OBJECT-TYPE
    SYNTAX	DisplayString
    ACCESS	read-only
    STATUS	mandatory
    DESCRIPTION
	"The VM command that gets run when the vmErrFix column is  set to 1."
    ::= { vmEntry 103 }

--
-- The extensible VxFS SNMP control table 
--

fsExtTable OBJECT-TYPE
    SYNTAX	SEQUENCE OF FSExtEntry
    ACCESS	not-accessible
    STATUS	mandatory
    DESCRIPTION
	"A table of extensible commands to control VxFS from SNMP framework via SNMP get and set protocol. These commands can be configured in ENE agent's snmpd.conf file."
    ::= { vxfs 100 }

fsEntry OBJECT-TYPE
    SYNTAX     FSExtEntry
    ACCESS not-accessible
    STATUS     mandatory
    DESCRIPTION
        "A FS entry containing an extensible modules and the results."
    INDEX      { fsIndex }
    ::= { fsExtTable  1 }

FSExtEntry ::= SEQUENCE {
    	fsIndex			Integer32,
    	fsNames			DisplayString,
    	fsCommand		DisplayString,
    	fsCtlFlag		Integer32,
    	fsResult		Integer32,
    	fsOutput		DisplayString,
    	fsErrFix		Integer32,
    	fsErrFixCmd		DisplayString
}

fsIndex OBJECT-TYPE
    SYNTAX	Integer32 (0..65535)
    ACCESS	read-only
    STATUS	mandatory
    DESCRIPTION
	"Reference Index for extensible FS scripts. It is an integer row number. A predefined map is available in snmpd.conf to map the index to the command."
    ::= { fsEntry 1 }

fsNames OBJECT-TYPE
    SYNTAX	DisplayString
    ACCESS	read-write
    STATUS	mandatory
    DESCRIPTION
	"A description of the extensible FS command."
    ::= { fsEntry 2 }

fsCommand OBJECT-TYPE
    SYNTAX	DisplayString
    ACCESS	read-write
    STATUS	mandatory
    DESCRIPTION
	"A valid FS script path to be executed when fsCtlFlag is set to 1."
    ::= { fsEntry 3 }

fsCtlFlag OBJECT-TYPE
    SYNTAX	Integer32
    ACCESS	read-write
    STATUS	mandatory
    DESCRIPTION
	"When the flag is set to 1, the extensible FS scripts in fsCommand will be executed. Exit code will go to fsResult, output go to fsOutput."
    ::= { fsEntry 4 }

fsResult OBJECT-TYPE
    SYNTAX	Integer32
    ACCESS	read-only
    STATUS	mandatory
    DESCRIPTION
	"The exit status of the executed FS command."
    ::= { fsEntry 100 }

fsOutput OBJECT-TYPE
    SYNTAX	DisplayString
    ACCESS	read-only
    STATUS	mandatory
    DESCRIPTION
	"The firstline output of the executed FS command."
    ::= { fsEntry 101 }

fsErrFix OBJECT-TYPE
    SYNTAX	Integer32
    ACCESS	read-write
    STATUS	mandatory
    DESCRIPTION
	"Setting this error fix flag to 1 to kick off the fsErrFixCmd."
    ::= { fsEntry 102 }
	
fsErrFixCmd OBJECT-TYPE
    SYNTAX	DisplayString
    ACCESS	read-only
    STATUS	mandatory
    DESCRIPTION
	"The FS command that gets run when the fsErrFix column is  set to 1."
    ::= { fsEntry 103 }

--
-- The VERITAS Volume Manager SNMP Event related Objects
--

vxvmEventAttrs	OBJECT IDENTIFIER ::= { vxvm 250 }

vxvmHost	OBJECT-TYPE
    	SYNTAX		DisplayString
    	ACCESS	read-only
    	STATUS		mandatory
    	DESCRIPTION
	"The host name where the event occured."
    	::= { vxvmEventAttrs 1 }

vxvmType	OBJECT-TYPE
    	SYNTAX		DisplayString
    	ACCESS	read-only
    	STATUS		mandatory
    	DESCRIPTION
	"The event category: vxio, vxconfigd, vxdmp, vxdmpadm etc."
    	::= { vxvmEventAttrs 2 }

vxvmSeverity	OBJECT-TYPE
    	SYNTAX		DisplayString
    	ACCESS	read-only
    	STATUS		mandatory
    	DESCRIPTION
	"The severity of the event occured. Possible values are Critical, Major, Minor, Warning and Normal."
    	::= { vxvmEventAttrs 3 }

vxvmErrExpl	OBJECT-TYPE
	SYNTAX      DisplayString
	ACCESS  read-only
	STATUS      mandatory
	DESCRIPTION
        	"The error explanation."
	::= { vxvmEventAttrs 98 }

vxvmErrReco	OBJECT-TYPE
	SYNTAX      DisplayString
	ACCESS  read-only
	STATUS      mandatory
	DESCRIPTION
        	"The recommended action to correct VXVM error."
	::= { vxvmEventAttrs 99 }

vxvmErrCode	OBJECT-TYPE
    	SYNTAX		Integer32
    	ACCESS	read-only
    	STATUS		mandatory
    	DESCRIPTION
	"The error code of the event."
    	::= { vxvmEventAttrs 100 }

vxvmErrMsg	OBJECT-TYPE
    	SYNTAX		DisplayString
    	ACCESS	read-only
    	STATUS		mandatory
    	DESCRIPTION
	"The detailed error message of the event."
    	::= { vxvmEventAttrs 101 }


vrtsVxvmEvent	OBJECT IDENTIFIER ::= { vxvm 251 }

errorVxvmEvent	TRAP-TYPE
	ENTERPRISE      vrtsVxvmEvent
	VARIABLES	{ vxvmHost, vxvmType, vxvmSeverity, vxvmErrMsg }
	-- STATUS      mandatory
	DESCRIPTION
	        "The VXVM error event. Detailed error and corrective action information can be found from the objects associated with this event."
	--#TYPE      "The VXVM error event occurred with following detailed information."
        --#SUMMARY   "Error Host: (%s), Type: (%s), Severity: (%s), Error Message: (%s)."
        --#ARGUMENTS {0,1,2,3}
        --#SEVERITY  MAJOR
        --#TIMEINDEX 1        
        --#STATE     OPERATIONAL

    	::= 1

normalVxvmEvent	TRAP-TYPE
	ENTERPRISE      vrtsVxvmEvent
	VARIABLES	{ vxvmHost, vxvmType, vxvmSeverity, vxvmErrMsg }
	-- STATUS      mandatory
	DESCRIPTION
	        "The normal VXVM event. Detailed event information can be found from the objects associated with this event."
	--#TYPE      "The normal VXVM event occurred with following detailed information."
        --#SUMMARY   "Host: (%s), Type: (%s), Severity: (%s), Message: (%s)."
        --#ARGUMENTS {0,1,2,3}
        --#SEVERITY  INFORMATIONAL
        --#TIMEINDEX 1        
        --#STATE     OPERATIONAL

    	::= 2


--
-- The VERITAS File System SNMP Event related Objects
--

vxfsEventAttrs	OBJECT IDENTIFIER ::= { vxfs 250 }

vxfsHost	OBJECT-TYPE
    	SYNTAX		DisplayString
    	ACCESS	read-only
    	STATUS		mandatory
    	DESCRIPTION
	"The host name where the event occured."
    	::= { vxfsEventAttrs 1 }

vxfsMsgcnt	OBJECT-TYPE
    	SYNTAX		Integer32
    	ACCESS	read-only
    	STATUS		mandatory
    	DESCRIPTION
	"The event count for sequence purpose."
    	::= { vxfsEventAttrs 2 }

vxfsSeverity	OBJECT-TYPE
    	SYNTAX		DisplayString
    	ACCESS	read-only
    	STATUS		mandatory
    	DESCRIPTION
	"The severity of the event occured. Possible values are Critical, Major, Minor, Warning and Normal."
    	::= { vxfsEventAttrs 3 }

vxfsErrExpl	OBJECT-TYPE
	SYNTAX      DisplayString
	ACCESS  read-only
	STATUS      mandatory
	DESCRIPTION
        	"The error explanation."
	::= { vxfsEventAttrs 98 }

vxfsErrReco	OBJECT-TYPE
	SYNTAX      DisplayString
	ACCESS  read-only
	STATUS      mandatory
	DESCRIPTION
        	"The recommended action to correct VXFS error."
	::= { vxfsEventAttrs 99 }

vxfsErrCode	OBJECT-TYPE
    	SYNTAX		Integer32
    	ACCESS	read-only
    	STATUS		mandatory
    	DESCRIPTION
	"The error code of the event."
    	::= { vxfsEventAttrs 100 }

vxfsErrMsg	OBJECT-TYPE
    	SYNTAX		DisplayString
    	ACCESS	read-only
    	STATUS		mandatory
    	DESCRIPTION
	"The detailed error message of the event."
    	::= { vxfsEventAttrs 101 }

vrtsVxfsEvent	OBJECT IDENTIFIER ::= { vxfs 251 }

errorVxfsEvent	TRAP-TYPE
	ENTERPRISE      vrtsVxfsEvent
	VARIABLES	{ vxfsHost, vxfsMsgcnt, vxfsSeverity, vxfsErrCode, vxfsErrMsg }
	-- STATUS      mandatory
	DESCRIPTION
	        "The VXFS error event. Detailed error and corrective action information can be found from the objects associated with this event."

	--#TYPE      "The VXFS error event occurred with following detailed information."
        --#SUMMARY   "Error Host: (%s), MsgCnt: (%d), Severity: (%s), Code: (%d), Error Message: (%s)."
        --#ARGUMENTS {0,1,2,3,4}
        --#SEVERITY  MAJOR
        --#TIMEINDEX 1        
        --#STATE     OPERATIONAL

    	::= 1

normalVxfsEvent	TRAP-TYPE
	ENTERPRISE      vrtsVxfsEvent
	VARIABLES	{ vxfsHost, vxfsMsgcnt, vxfsSeverity, vxfsErrCode, vxfsErrMsg }
	-- STATUS      mandatory
	DESCRIPTION
	        "The normal VXFS event. Detailed event information can be found from the objects associated with this event."
	--#TYPE      "The normal VXFS event occurred with following detailed information."
        --#SUMMARY   "Host: (%s), MsgCnt: (%d), Severity: (%s), Code: (%d), Message: (%s)."
        --#ARGUMENTS {0,1,2,3,4}
        --#SEVERITY  INFORMATIONAL
        --#TIMEINDEX 1        
        --#STATE     OPERATIONAL

    	::= 2

END
