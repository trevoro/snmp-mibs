-- RS Firmware Agent Capabilities macro

RSTONE-RS-AGENTCAP-MIB DEFINITIONS ::= BEGIN

IMPORTS
    MODULE-IDENTITY
       FROM SNMPv2-SMI
    AGENT-CAPABILITIES
       FROM  SNMPv2-CONF
	riverstoneAgentCapabilities
		FROM RSTONE-SMI-MIB;

rstoneRsAgentCapabilityMIB MODULE-IDENTITY
   LAST-UPDATED "200106210000Z"  -- Jun 21, 2001
   ORGANIZATION "Riverstone Networks, Inc"
   CONTACT-INFO
	"Riverstone Networks, Inc
	 5200 Great America Parkway
	 Santa Clara CA USA 95054
	 PHONE:+1 408.878.6500
	 EMAIL: nms-eng@riverstonenet.com
	 WEB: http://www.riverstonenet.com"

   DESCRIPTION
     "This module defines agent capabilities for Riverstone RS RapidOS Software Product."

    REVISION     "200106210000Z"  -- Jun 21, 2001
    DESCRIPTION
         " Updated Agent Capabilities for firmware release 8.0"

    REVISION     "200103110000Z"  -- Mar 11, 2001
    DESCRIPTION
         " Updated Agent Capabilities for firmware release 7.0"

    REVISION     "200103070000Z"  -- Mar 07, 2001
    DESCRIPTION
		 " Fixed some errors in Agent Capabilities for firmware release 6.3"

    REVISION     "200012130000Z"
    DESCRIPTION
		 " Updated Agent Capabilities for firmware release 6.2, 6.3"

    REVISION     "200009180000Z"
    DESCRIPTION
		 " Updated Agent Capabilities for ATM-MIB for firmware release 6.1.x"

    REVISION     "200009120000Z"
    DESCRIPTION
         "Created agent capabilities mib for version 6.1.x of 
          Riverstone RS RapidOS software product. For agent capabilities of 
		  older versions of RapidOS, refer ssr-agent-capabilities mib"
        ::= { riverstoneAgentCapabilities 1 }


-- this branch is for device specific agent information descriptions via AGENT-CAPABILITIES macro

rsCapability OBJECT IDENTIFIER ::= {  rstoneRsAgentCapabilityMIB 1 }

rs61x AGENT-CAPABILITIES 
  PRODUCT-RELEASE 
     "6.1.x"
  STATUS  current
  DESCRIPTION
     "Firmware Release 6.1.x for Riverstone  RS RapidOS product line.
      The firmware supports Cable Modem Head End card in release 6.1 and 
	  ATM OC12 card in  release 6.1.1"
  REFERENCE 
     "http://www.riverstonenet.com/products"

     -- RFC 1907
     SUPPORTS SNMPv2-MIB
     INCLUDES { 
         systemGroup,
         snmpGroup, 
         snmpBasicNotificationsGroup,
         --  snmpSetGroup is not implemented, but is needed for SNMPv2-MIB compliance
         -- non mandatory groups
         snmpCommunityGroup,
         -- deprecated/obsolete support
         snmpObsoleteGroup
     }

     -- ********************* ************ ************ *************** ***
     -- RFC 2358
     SUPPORTS EtherLike-MIB
     INCLUDES { 
         etherStats100MbsGroup
     }

     -- ********************* ************ ************ *************** ***
     -- RFC 2233
     SUPPORTS IF-MIB
     INCLUDES { 
         ifGeneralInformationGroup, 
         ifStackGroup2,
         ifCounterDiscontinuityGroup,
         -- non mandatory groups
         ifFixedLengthGroup,
         ifHCFixedLengthGroup,
         ifPacketGroup,
         ifHCPacketGroup,
         ifVHCPacketGroup,
         ifRcvAddressGroup,
         -- deprecated/obsolete support
         ifOldObjectsGroup
     }
     VARIATION ifAlias
     ACCESS read-only
     DESCRIPTION "ifAlias is guarenteed to be unique across reboots. It takes the form Type : instance info
      for example: ifAlias.49 = IP interface: to-sc-BGPfeed or ifAlias.42 = VLAN: test1 or 
      ifAlias.35 = Physical port: et.14.5"

     VARIATION ifAdminStatus
     ACCESS read-only
     DESCRIPTION "For ifTypes corresponding to VLANs this object is read only."

     VARIATION ifLinkUpDownTrapEnable
     ACCESS read-only
     DESCRIPTION "For all ifTypes where ifConnectorPresent is not TRUE."

     VARIATION ifStackStatus
     ACCESS read-only
     DESCRIPTION "Command line interface(CLI) is used to change relationships."

     -- ********************* ************ ************ *************** ***
     -- RFC 2011
     SUPPORTS IP-MIB
     INCLUDES { 
         ipGroup,
         icmpGroup
     }
     VARIATION ipDefaultTTL
     ACCESS read-only
     DESCRIPTION "Command line interface(CLI) is used to change default ttl."

     -- ********************* ************ ************ *************** ***
     -- RFC 2096
     SUPPORTS IP-FORWARD-MIB
     INCLUDES { 
         ipForwardCidrRouteGroup
     }
     VARIATION ipCidrRouteIfIndex
     ACCESS read-only
     DESCRIPTION "Command line interface(CLI) is used to update Forwarding Information Base/FIB."

     VARIATION ipCidrRouteType
     ACCESS read-only
     DESCRIPTION "Command line interface(CLI) is used to update Forwarding Information Base/FIB."

     VARIATION ipCidrRouteInfo
     ACCESS read-only
     DESCRIPTION "Command line interface(CLI) is used to update Forwarding Information Base/FIB."

     VARIATION ipCidrRouteNextHopAS
     ACCESS read-only
     DESCRIPTION "Command line interface(CLI) is used to update Forwarding Information Base/FIB."

     VARIATION ipCidrRouteMetric1
     ACCESS read-only
     DESCRIPTION "Command line interface(CLI) is used to update Forwarding Information Base/FIB."

     VARIATION ipCidrRouteMetric2
     ACCESS read-only
     DESCRIPTION "Command line interface(CLI) is used to update Forwarding Information Base/FIB."

     VARIATION ipCidrRouteMetric3
     ACCESS read-only
     DESCRIPTION "Command line interface(CLI) is used to update Forwarding Information Base/FIB."

     VARIATION ipCidrRouteMetric4
     ACCESS read-only
     DESCRIPTION "Command line interface(CLI) is used to update Forwarding Information Base/FIB."

     VARIATION ipCidrRouteMetric5
     ACCESS read-only
     DESCRIPTION "Command line interface(CLI) is used to update Forwarding Information Base/FIB."

     VARIATION ipCidrRouteStatus
     ACCESS read-only
     DESCRIPTION "Command line interface(CLI) is used to update Forwarding Information Base/FIB."

     -- ********************* ************ ************ *************** ***
     -- RFC 2013
     SUPPORTS UDP-MIB
     INCLUDES { 
         udpGroup         
     }

     -- ********************* ************ ************ *************** ***
     -- RFC 2012
     SUPPORTS TCP-MIB
     INCLUDES { 
         tcpGroup         
     }
     VARIATION tcpConnState
     ACCESS read-only
     DESCRIPTION "Command line interface(CLI) is used to kill tcp sessions."

     -- ********************* ************ ************ *************** ***
     --  RFC 1657 
--     SUPPORTS BGP4-MIB
--     INCLUDES { 
--         This is an smiv1 mib, all objects read only. Specify in device config file to enable this mib.
--     }

     -- ********************* ************ ************ *************** ***
     -- RFC 1850    
     -- Specify in device config file to enable this mib.
     SUPPORTS OSPF-MIB
     INCLUDES { 
         ospfBasicGroup,
         ospfAreaGroup,
         ospfStubAreaGroup,
         ospfIfGroup,
         ospfIfMetricGroup,
         ospfVirtIfGroup,
         ospfNbrGroup,
         ospfVirtNbrGroup,
         ospfAreaAggregateGroup
     }
     VARIATION ospfRouterId
     ACCESS read-only
     DESCRIPTION "Command line interface(CLI) is used to set router id."

     VARIATION ospfAdminStat
     ACCESS read-only
     DESCRIPTION "Command line interface(CLI) is used to set ospf state."

     VARIATION ospfTOSSupport
     ACCESS read-only
     DESCRIPTION "Command line interface(CLI) is used to set ospf TOS support."

     VARIATION ospfExtLsdbLimit
     ACCESS read-only
     DESCRIPTION "Command line interface(CLI) is used to set ospf Lsdb Limit."

     VARIATION ospfMulticastExtensions
     ACCESS read-only
     DESCRIPTION "Command line interface(CLI) is used to set ospf multicast extensions."

     VARIATION ospfExitOverflowInterval
     ACCESS read-only
     DESCRIPTION "Command line interface(CLI) is used to set ospf exit overflow interval."

     VARIATION ospfDemandExtensions
     ACCESS read-only
     DESCRIPTION "Command line interface(CLI) is used to set ospf demand extensions."

     VARIATION ospfAuthType
     ACCESS read-only
     DESCRIPTION "Command line interface(CLI) is used to set ospf authorisation types."

     VARIATION ospfImportAsExtern
     ACCESS read-only
     DESCRIPTION "Command line interface(CLI) is used to set ospf Import AS external routes."

     VARIATION ospfAreaSummary
     ACCESS read-only
     DESCRIPTION "Command line interface(CLI) is used to set ospf area summary importation."

     VARIATION ospfAreaStatus
     ACCESS read-only
     DESCRIPTION "Command line interface(CLI) is used to create & delete ospf areas."

     VARIATION ospfStubMetric
     ACCESS read-only
     DESCRIPTION "Command line interface(CLI) is used to set ospf area stub metric."

     VARIATION ospfStubStatus
     ACCESS read-only
     DESCRIPTION "Command line interface(CLI) is used to create & delete stub areas."

     VARIATION ospfStubMetricType
     ACCESS read-only
     DESCRIPTION "Command line interface(CLI) is used to set ospf stub metric type."

     VARIATION ospfAreaRangeMask
     ACCESS read-only
     DESCRIPTION "Command line interface(CLI) is used to set ospf area range mask."

     VARIATION ospfAreaRangeStatus
     ACCESS read-only
     DESCRIPTION "Command line interface(CLI) is used to create & delete ranges."

     VARIATION ospfAreaRangeEffect
     ACCESS read-only
     DESCRIPTION "Command line interface(CLI) is used to set area range effect."

     VARIATION ospfHostMetric
     ACCESS read-only
     DESCRIPTION "Command line interface(CLI) is used to set host metric."

     VARIATION ospfHostStatus
     ACCESS read-only
     DESCRIPTION "Command line interface(CLI) is used to create & delete hosts."

     VARIATION ospfIfAreaId
     ACCESS read-only
     DESCRIPTION "Command line interface(CLI) is used to set Interface area id."

     VARIATION ospfIfType
     ACCESS read-only
     DESCRIPTION "Command line interface(CLI) is used to set Interface type."

     VARIATION ospfIfAdminStat
     ACCESS read-only
     DESCRIPTION "Command line interface(CLI) is used to set Interface admin status."

     VARIATION ospfIfRtrPriority
     ACCESS read-only
     DESCRIPTION "Command line interface(CLI) is used to set interface router priority."

     VARIATION ospfIfTransitDelay
     ACCESS read-only
     DESCRIPTION "Command line interface(CLI) is used to set interface transit delay."

     VARIATION ospfIfRetransInterval
     ACCESS read-only
     DESCRIPTION "Command line interface(CLI) is used to set interface retransmission interval."

     VARIATION ospfIfHelloInterval
     ACCESS read-only
     DESCRIPTION "Command line interface(CLI) is used to set hello interval."

     VARIATION ospfIfRtrDeadInterval
     ACCESS read-only
     DESCRIPTION "Command line interface(CLI) is used to set dead interval."

     VARIATION ospfIfPollInterval
     ACCESS read-only
     DESCRIPTION "Command line interface(CLI) is used to set poll interval."

     VARIATION ospfIfAuthKey
     ACCESS read-only
     DESCRIPTION "Command line interface(CLI) is used to set interface auth key."

     VARIATION ospfIfStatus
     ACCESS read-only
     DESCRIPTION "Command line interface(CLI) is used to create & delete interfaces."

     VARIATION ospfIfMulticastForwarding
     ACCESS read-only
     DESCRIPTION "Command line interface(CLI) is used to set multicast fwd."

     VARIATION ospfIfDemand
     ACCESS read-only
     DESCRIPTION "Command line interface(CLI) is used to set this attribute."

     VARIATION ospfIfAuthType
     ACCESS read-only
     DESCRIPTION "Command line interface(CLI) is used to set this feature."

     VARIATION ospfIfMetricValue
     ACCESS read-only
     DESCRIPTION "Command line interface(CLI) is used to set this feature."

     VARIATION ospfVirtIfTransitDelay
     ACCESS read-only
     DESCRIPTION "Command line interface(CLI) is used to set this feature."

     VARIATION ospfVirtIfRetransInterval
     ACCESS read-only
     DESCRIPTION "Command line interface(CLI) is used to set this feature."

     VARIATION ospfVirtIfHelloInterval
     ACCESS read-only
     DESCRIPTION "Command line interface(CLI) is used to set this feature."

     VARIATION ospfVirtIfRtrDeadInterval
     ACCESS read-only
     DESCRIPTION "Command line interface(CLI) is used to set this feature."

     VARIATION ospfVirtIfAuthKey
     ACCESS read-only
     DESCRIPTION "Command line interface(CLI) is used to set this feature."

     VARIATION ospfVirtIfStatus
     ACCESS read-only
     DESCRIPTION "Command line interface(CLI) is used to set this feature."

     VARIATION ospfVirtIfAuthType
     ACCESS read-only
     DESCRIPTION "Command line interface(CLI) is used to set this feature."

     VARIATION ospfNbrPriority
     ACCESS read-only
     DESCRIPTION "Command line interface(CLI) is used to set this feature."

     VARIATION ospfNbmaNbrStatus
     ACCESS read-only
     DESCRIPTION "Command line interface(CLI) is used to set this feature."

     VARIATION ospfAreaAggregateStatus
     ACCESS read-only
     DESCRIPTION "Command line interface(CLI) is used to set this feature."

     VARIATION ospfAreaAggregateEffect
     ACCESS read-only
     DESCRIPTION "Command line interface(CLI) is used to set this feature."

     SUPPORTS OSPF-TRAP-MIB
     INCLUDES { 
         ospfTrapControlGroup
     }

     -- ********************* ************ ************ *************** ***
     -- RFC 1724
     -- Specify in device config file to enable this mib.
     SUPPORTS RIPv2-MIB
     INCLUDES { 
         rip2GlobalGroup,
         rip2IfStatGroup,
         rip2IfConfGroup,
         rip2PeerGroup
     }
     VARIATION rip2IfStatStatus
     ACCESS read-only
     DESCRIPTION "Command line interface(CLI) is used to set this feature."
   
     VARIATION rip2IfConfDomain
     ACCESS read-only
     DESCRIPTION "Command line interface(CLI) is used to set this feature."

     VARIATION rip2IfConfAuthType
     ACCESS read-only
     DESCRIPTION "Command line interface(CLI) is used to set this feature."

     VARIATION rip2IfConfAuthKey
     ACCESS read-only
     DESCRIPTION "Command line interface(CLI) is used to set this feature."

     VARIATION rip2IfConfSend
     ACCESS read-only
     DESCRIPTION "Command line interface(CLI) is used to set this feature."

     VARIATION rip2IfConfReceive
     ACCESS read-only
     DESCRIPTION "Command line interface(CLI) is used to set this feature."

     VARIATION rip2IfConfDefaultMetric
     ACCESS read-only
     DESCRIPTION "Command line interface(CLI) is used to set this feature."

     VARIATION rip2IfConfStatus
     ACCESS read-only
     DESCRIPTION "Command line interface(CLI) is used to set this feature."

     VARIATION rip2IfConfSrcAddress
     ACCESS read-only
     DESCRIPTION "Command line interface(CLI) is used to set this feature."

     -- ********************* ************ ************ *************** ***
     -- RFC 1493
--    SUPPORTS BRIDGE-MIB
--    INCLUDES { 
--       smiv1 mib
--    }

     -- ********************* ************ ************ *************** ***
     -- RFC 2674
     SUPPORTS Q-BRIDGE-MIB
     INCLUDES { 
        qBridgeBaseGroup,
        qBridgeVlanGroup,
        qBridgeVlanStaticGroup,
        qBridgePortGroup,
        qBridgeFdbUnicastGroup,
        qBridgeServiceRequirementsGroup
     }
     -- note: qBridgeFdbMulticastGroup, mandatory, but not implemented in 6.1.x

     VARIATION dot1qGvrpStatus
     ACCESS read-only
     DEFVAL { disabled }
     DESCRIPTION "Firmware Version 6.1.x does not support GVRP/GARP."

     VARIATION dot1qForwardAllStaticPorts
     ACCESS read-only
     DESCRIPTION "Command line interface(CLI) is used to set this feature."

     VARIATION dot1qForwardAllForbiddenPorts
     ACCESS read-only
     DESCRIPTION "Command line interface(CLI) is used to set this feature."

     VARIATION dot1qForwardUnregisteredStaticPorts
     ACCESS read-only
     DESCRIPTION "Command line interface(CLI) is used to set this feature."

     VARIATION dot1qForwardUnregisteredForbiddenPorts
     ACCESS read-only
     DESCRIPTION "Command line interface(CLI) is used to set this feature."

     VARIATION dot1qStaticUnicastAllowedToGoTo
     ACCESS read-only
     DESCRIPTION "Command line interface(CLI) is used to set this feature."

     VARIATION dot1qStaticUnicastStatus
     ACCESS read-only
     DESCRIPTION "Command line interface(CLI) is used to set this feature."

     VARIATION dot1qStaticMulticastStaticEgressPorts
     ACCESS read-only
     DESCRIPTION "Command line interface(CLI) is used to set this feature."

     VARIATION dot1qStaticMulticastForbiddenEgressPorts
     ACCESS read-only
     DESCRIPTION "Command line interface(CLI) is used to set this feature."

     VARIATION dot1qStaticMulticastStatus
     ACCESS read-only
     DESCRIPTION "Command line interface(CLI) is used to set this feature."

     VARIATION dot1qVlanStaticName
     ACCESS read-only
     DESCRIPTION "Command line interface(CLI) is used to set this feature."

     VARIATION dot1qVlanStaticEgressPorts
     ACCESS read-only
     DESCRIPTION "Command line interface(CLI) is used to set this feature."

     VARIATION dot1qVlanForbiddenEgressPorts
     ACCESS read-only
     DESCRIPTION "Command line interface(CLI) is used to set this feature."

     VARIATION dot1qVlanStaticUntaggedPorts
     ACCESS read-only
     DESCRIPTION "Command line interface(CLI) is used to set this feature."

     VARIATION dot1qVlanStaticRowStatus
     ACCESS read-only
     DESCRIPTION "Command line interface(CLI) is used to set this feature."

     VARIATION dot1qPvid
     ACCESS read-only
     DESCRIPTION "Command line interface(CLI) is used to set this feature."

     VARIATION dot1qPortAcceptableFrameTypes
     ACCESS read-only
     DEFVAL { admitAll }
     DESCRIPTION "RapidOS firmware 6.1.x does not support admitOnlyVlanTagged option."

     VARIATION dot1qPortIngressFiltering
     ACCESS read-only
     DEFVAL { true }
     DESCRIPTION "RapidOS firmware 6.1.x does not support false option per port."

     VARIATION dot1qPortGvrpStatus
     ACCESS read-only
     DEFVAL { disabled }
     DESCRIPTION "GVRP/GARP not supported in firmware 6.1.x."


     -- ********************* ************ ************ *************** ***
     -- RFC 2674
     SUPPORTS P-BRIDGE-MIB
     INCLUDES { 
       pBridgeExtCapGroup,
       pBridgeDevicePriorityGroup,
       pBridgeDefaultPriorityGroup,
       pBridgePriorityGroup,
       pBridgeHCPortGroup
     }

     VARIATION dot1dTrafficClassesEnabled
     ACCESS read-only
     DEFVAL { true } 
     DESCRIPTION "RapidOS Firmware uses fixed traffic categorization per port in 6.1.x release."

     VARIATION dot1dGmrpStatus
     ACCESS read-only
     DEFVAL { disabled } 
     DESCRIPTION "Not supported in release 6.1.x."

     VARIATION dot1dPortDefaultUserPriority
     ACCESS read-only
     DESCRIPTION "RapidOS Firmware uses fixed traffic categorization per port in 6.1.x release."

     VARIATION dot1dRegenUserPriority
     ACCESS read-only
     DESCRIPTION "Command line interface(CLI) is used to set this feature."

     VARIATION dot1dTrafficClass
     ACCESS read-only
     DESCRIPTION "RapidOS Firmware uses fixed traffic categorization per port in 6.1.x release."

     -- ********************* ************ ************ *************** ***
     -- RFC 2115
     SUPPORTS FRAME-RELAY-DTE-MIB
     INCLUDES { 
       frPortGroup, 
       frCircuitGroup,
       frErrGroup,
       frTrapGroup
     }
     VARIATION frDlcmiState
     ACCESS read-only
     DESCRIPTION "Command line interface(CLI) is used to set this feature."

     VARIATION frDlcmiAddress
     ACCESS read-only
     DESCRIPTION "Command line interface(CLI) is used to set this feature."

     VARIATION frDlcmiAddressLen
     ACCESS read-only
     DESCRIPTION "Command line interface(CLI) is used to set this feature."

     VARIATION frDlcmiPollingInterval
     ACCESS read-only
     DESCRIPTION "Command line interface(CLI) is used to set this feature."
     
     VARIATION frDlcmiFullEnquiryInterval
     ACCESS read-only
     DESCRIPTION "Command line interface(CLI) is used to set this feature."

     VARIATION frDlcmiErrorThreshold
     ACCESS read-only
     DESCRIPTION "Command line interface(CLI) is used to set this feature."

     VARIATION frDlcmiMonitoredEvents
     ACCESS read-only
     DESCRIPTION "Command line interface(CLI) is used to set this feature."

     VARIATION frDlcmiMaxSupportedVCs
     ACCESS read-only
     DESCRIPTION "Command line interface(CLI) is used to set this feature."

     VARIATION frDlcmiMulticast
     ACCESS read-only
     DESCRIPTION "Command line interface(CLI) is used to set this feature."

     VARIATION frDlcmiRowStatus
     ACCESS read-only
     DESCRIPTION "Command line interface(CLI) is used to create & delete dlcmi's."

     VARIATION frCircuitState
     ACCESS read-only
     DESCRIPTION "Command line interface(CLI) is used to set this feature."

     VARIATION frCircuitCommittedBurst
     ACCESS read-only
     DESCRIPTION "Command line interface(CLI) is used to set this feature."

     VARIATION frCircuitExcessBurst
     ACCESS read-only
     DESCRIPTION "Command line interface(CLI) is used to set this feature."

     VARIATION frCircuitThroughput
     ACCESS read-only
     DESCRIPTION "Command line interface(CLI) is used to set this feature."

     VARIATION frCircuitMulticast
     ACCESS read-only
     DESCRIPTION "Command line interface(CLI) is used to set this feature."

     VARIATION frCircuitLogicalIfIndex
     ACCESS read-only
     DESCRIPTION "Command line interface(CLI) is used to set this feature."

     VARIATION frCircuitRowStatus
     ACCESS read-only
     DESCRIPTION "Command line interface(CLI) is used to set this feature."

     -- ********************* ************ ************ *************** ***
       -- RFC 1471
--     SUPPORTS PPP-LCP-MIB
--     INCLUDES { 
--       smiv1 mib - read only 
--     }

     -- ********************* ************ ************ *************** ***
       -- RFC 1472
--     SUPPORTS PPP-SEC-MIB
--     INCLUDES { 
--      smiv1 mib - read only
--     }

     -- ********************* ************ ************ *************** ***
       -- RFC 1473
--     SUPPORTS PPP-IP-NCP-MIB
--     INCLUDES { 
--       smiv1 mib - read only
--     }

     -- ********************* ************ ************ *************** ***
       -- RFC 1474
--     SUPPORTS PPP-BRIDGE-NCP-MIB
--     INCLUDES { 
--       smiv1 mib - read only
--     }

     -- ********************* ************ ************ *************** ***
     -- RFC 2495
     SUPPORTS DS1-MIB
     INCLUDES { 
        ds1NearEndConfigGroup,
        ds1NearEndStatisticsGroup
     }
     VARIATION dsx1LineType
     ACCESS read-only
     DESCRIPTION "Command line interface(CLI) is used to set this feature."

     VARIATION dsx1LineCoding
     ACCESS read-only
     DESCRIPTION "Command line interface(CLI) is used to set this feature."

     VARIATION dsx1SendCode
     ACCESS read-only
     DESCRIPTION "Command line interface(CLI) is used to set this feature."

     VARIATION dsx1CircuitIdentifier
     ACCESS read-only
     DESCRIPTION "Command line interface(CLI) is used to set this feature."

     VARIATION dsx1LoopbackConfig
     ACCESS read-only
     DESCRIPTION "Command line interface(CLI) is used to set this feature."

     VARIATION dsx1SignalMode
     ACCESS read-only
     DESCRIPTION "Command line interface(CLI) is used to set this feature."

     VARIATION dsx1TransmitClockSource
     ACCESS read-only
     DESCRIPTION "Command line interface(CLI) is used to set this feature."

     VARIATION dsx1Fdl
     ACCESS read-only
     DESCRIPTION "Command line interface(CLI) is used to set this feature."

     VARIATION dsx1LineLength
     ACCESS read-only
     DESCRIPTION "Command line interface(CLI) is used to set this feature."

     VARIATION dsx1LineStatusChangeTrapEnable
     ACCESS read-only
     DESCRIPTION "Command line interface(CLI) is used to set this feature."

     VARIATION dsx1Channelization
     ACCESS read-only
     DEFVAL  { disabled }
     DESCRIPTION "RapidOS Firmware 6.1.x does not implement channelized T1/E1."


     -- ********************* ************ ************ *************** ***
     -- RFC 2496
     SUPPORTS DS3-MIB
     INCLUDES { 
        ds3NearEndConfigGroup,
        ds3NearEndStatisticsGroup
     }

     VARIATION dsx3LineType
     ACCESS read-only
     DESCRIPTION "Command line interface(CLI) is used to set this feature."

     VARIATION dsx3LineCoding
     ACCESS read-only
     DESCRIPTION "Command line interface(CLI) is used to set this feature."

     VARIATION dsx3SendCode
     ACCESS read-only
     DESCRIPTION "Command line interface(CLI) is used to set this feature."

     VARIATION dsx3CircuitIdentifier
     ACCESS read-only
     DESCRIPTION "Command line interface(CLI) is used to set this feature."

     VARIATION dsx3LoopbackConfig
     ACCESS read-only
     DESCRIPTION "Command line interface(CLI) is used to set this feature."

     VARIATION dsx3TransmitClockSource
     ACCESS read-only
     DESCRIPTION "Command line interface(CLI) is used to set this feature."

     VARIATION dsx3LineLength
     ACCESS read-only
     DESCRIPTION "Command line interface(CLI) is used to set this feature."

     VARIATION dsx3LineStatusChangeTrapEnable
     ACCESS read-only
     DESCRIPTION "Command line interface(CLI) is used to set this feature."

     VARIATION dsx3Channelization
     ACCESS read-only
     DEFVAL { disabled }
     DESCRIPTION "RapidOS 6.1.x Firmware does not support channelized T3/E3."

     VARIATION dsx3Ds1ForRemoteLoop
     ACCESS read-only
     DESCRIPTION "Command line interface(CLI) is used to set this feature."

     -- ********************* ************ ************ *************** ***
     -- RFC 1595
     SUPPORTS SONET-MIB
     INCLUDES { 
        sonetMediumStuff, 
        sonetSectionStuff,
        sonetLineStuff,
        sonetFarEndLineStuff,
        sonetPathStuff,
        sonetFarEndPathStuff
     }

     -- ATM OC3 line cards with  modular physical port (MODPHY) have above instrumentation
     -- POS OC3/12 line cards do not yet support the SONET-MIB

     -- ********************* ************ ************ *************** ***
     -- RFC 1695
     SUPPORTS ATM-MIB
     INCLUDES { 
        atmInterfaceConfGroup,
        atmTrafficDescrGroup,
        atmInterfaceDs3PlcpGroup,
        atmInterfaceTCGroup,
        atmVccTerminationGroup,
        aal5VccGroup
     }    

     VARIATION atmInterfaceMaxVpcs
     ACCESS read-only 
     DESCRIPTION "This object is not settable"

     VARIATION atmInterfaceMaxVccs
     ACCESS read-only
     DESCRIPTION "This object is not settable"

     VARIATION atmInterfaceMaxActiveVpiBits
     ACCESS read-only
     DESCRIPTION "This object is not settable"
     
     VARIATION atmInterfaceMaxActiveVciBits
     ACCESS read-only
     DESCRIPTION "This object is not settable"

     VARIATION atmInterfaceIlmiVpi
     ACCESS not-implemented
     DESCRIPTION "Device does not support Ilmi"

     VARIATION atmInterfaceIlmiVci
     ACCESS not-implemented
     DESCRIPTION "Device does not support Ilmi"

     VARIATION atmInterfaceMyNeighborIpAddress
     ACCESS not-implemented
     DESCRIPTION "Firmware does not support this"

     VARIATION atmInterfaceMyNeighborIfName
     ACCESS not-implemented
     DESCRIPTION "Firmware does not support this"

     VARIATION atmTrafficDescrParam1
     ACCESS read-only
     DESCRIPTION "Command line interface(CLI) is used to set this feature"

     VARIATION atmTrafficDescrParam2
     ACCESS read-only
     DESCRIPTION "Command line interface(CLI) is used to set this feature"
     
     VARIATION atmTrafficDescrParam3
     ACCESS read-only
     DESCRIPTION "Command line interface(CLI) is used to set this feature"

     VARIATION atmTrafficDescrParam4
     ACCESS read-only
     DESCRIPTION "Command line interface(CLI) is used to set this feature"

     VARIATION atmTrafficDescrParam5
     ACCESS read-only
     DESCRIPTION "Command line interface(CLI) is used to set this feature"

     VARIATION atmTrafficQoSClass
     ACCESS read-only
     DESCRIPTION "Command line interface(CLI) is used to set this feature"

     VARIATION atmTrafficDescrRowStatus
     ACCESS not-implemented
     DESCRIPTION "Table is read-only"

     VARIATION atmInterfaceDs3PlcpSEFSs
     ACCESS not-implemented
     DESCRIPTION "Firmware does not support this"

     VARIATION atmInterfaceDs3PlcpAlarmState
     ACCESS not-implemented
     DESCRIPTION "Firmware does not support this"

     VARIATION atmInterfaceDs3PlcpUASs
     ACCESS not-implemented
     DESCRIPTION "Firmware does not support this"

     VARIATION atmInterfaceOCDEvents
     ACCESS not-implemented
     DESCRIPTION "Firmware does not support this"

     VARIATION atmInterfaceTCAlarmState
     ACCESS not-implemented
     DESCRIPTION "Firmware does not support this"

     VARIATION atmVclAdminStatus
     ACCESS read-only
     DESCRIPTION "Command line interface(CLI) is used to set this feature"

     VARIATION atmVclReceiveTrafficDescrIndex
     ACCESS read-only
     DESCRIPTION "Memory address is used as the index, CLI is used to set this"

     VARIATION atmVclTransmitTrafficDescrIndex
     ACCESS read-only
     DESCRIPTION "Memory address is used as the index, CLI is used to set this"
        
     VARIATION atmVccAalType
     ACCESS read-only
     DESCRIPTION "This object is not settable"

     VARIATION atmVclRowStatus
     ACCESS read-only
     DESCRIPTION "This object is not settable"

     -- ********************* ************ ************ *************** ***
     -- RFC 2618
     SUPPORTS RADIUS-AUTH-CLIENT-MIB
     INCLUDES { 
          radiusAuthClientMIBGroup
     }

     -- ********************* ************ ************ *************** ***
     -- RFC 1757/2819
       SUPPORTS RMON-MIB
       INCLUDES { 
         
         rmonEtherStatsGroup,
         rmonHistoryControlGroup,
         rmonEthernetHistoryGroup,
         rmonAlarmGroup,
         rmonHostGroup,   -- requires flow bridging hardware mode enabled
         rmonHostTopNGroup, 
         rmonMatrixGroup, -- requires flow bridging hardware mode enabled
         rmonFilterGroup,
         rmonPacketCaptureGroup,
         rmonEventGroup,
         rmonNotificationGroup
       }

     -- ********************* ************ ************ *************** ***
     -- RFC 2021
     SUPPORTS RMON2-MIB
     INCLUDES { 
        protocolDirectoryGroup,
        protocolDistributionGroup,
        addressMapGroup,
        nlHostGroup,
        nlMatrixGroup,
        alHostGroup,
        alMatrixGroup,
        usrHistoryGroup,
        probeInformationGroup,
        probeConfigurationGroup,
        rmon1EthernetEnhancementGroup
        -- rmon1EnhancementGroup supported except for filterProtocolDirDataLocalIndex,
        --  filterProtocolDirLocalIndex
     }
     VARIATION filterProtocolDirDataLocalIndex
     ACCESS not-implemented
     DESCRIPTION "Feature not available in firmware version 6.1.x."

     VARIATION filterProtocolDirLocalIndex
     ACCESS not-implemented
     DESCRIPTION "Feature not available in firmware version 6.1.x."

     -- NOTE: Sets to this mib are not persistent. RMON configuration
     -- may be done via CLI for persistence
     -- ********************* ************ ************ *************** ***
     -- From ietf vrrp mib Draft #9
     SUPPORTS VRRP-MIB
     INCLUDES { 
        vrrpOperGroup,
        vrrpStatsGroup,
        vrrpTrapGroup,
        vrrpNotificationGroup
     }
     VARIATION vrrpOperAdminState
     ACCESS read-only
     DESCRIPTION "Command line interface(CLI) is used to set this feature."

     VARIATION vrrpOperPriority
     ACCESS read-only
     DESCRIPTION "Command line interface(CLI) is used to set this feature."

     VARIATION vrrpOperPrimaryIpAddr
     ACCESS read-only
     DESCRIPTION "Command line interface(CLI) is used to set this feature."

     VARIATION vrrpOperAuthType
     ACCESS read-only
     DESCRIPTION "Command line interface(CLI) is used to set this feature."

     VARIATION vrrpOperAuthKey
     ACCESS read-only
     DESCRIPTION "Command line interface(CLI) is used to set this feature."

     VARIATION vrrpOperAdvertisementInterval
     ACCESS read-only
     DESCRIPTION "Command line interface(CLI) is used to set this feature."

     VARIATION vrrpOperPreemptMode
     ACCESS read-only
     DESCRIPTION "Command line interface(CLI) is used to set this feature."

     VARIATION vrrpOperProtocol
     ACCESS read-only
     DESCRIPTION "Command line interface(CLI) is used to set this feature."

     VARIATION vrrpOperRowStatus
     ACCESS read-only
     DESCRIPTION "Command line interface(CLI) is used to set this feature."

     VARIATION vrrpAssoIpAddrRowStatus
     ACCESS read-only
     DESCRIPTION "Command line interface(CLI) is used to set this feature."

     VARIATION vrrpTrapAuthFailure
     ACCESS not-implemented
     DESCRIPTION "TrapAuthFailure not implemented in 6.1.x."

     -- ********************* ************ ************ *************** ***

     SUPPORTS CTRON-LFAP-MIB
     INCLUDES { 
        lfapConfGroupV40
     }

     -- ********************* ************ ************ *************** ***

     SUPPORTS CTRON-SSR-POLICY-MIB
     INCLUDES { 
         polGroupV11        
     }

     -- ********************* ************ ************ *************** ***

     SUPPORTS CTRON-SSR-CONFIG-MIB
     INCLUDES { 
         configGroup20
     }

     
     -- ********************* ************ ************ *************** ***

     SUPPORTS CTRON-SSR-HARDWARE-MIB
     INCLUDES { 
         hwConfGroupV30
     }

     -- ********************* ************ ************ *************** ***

     SUPPORTS CTRON-SSR-SERVICE-STATUS-MIB
     INCLUDES { 
         ssConfGroupV11
     }

     -- ********************* ************ ************ *************** ***

     SUPPORTS CTRON-SSR-CAPACITY-MIB
     INCLUDES { 
         capConfGroupV10
     }

     -- ********************* ************ ************ *************** ***

	 SUPPORTS DOCS-IF-MIB
	 INCLUDES {
         docsIfBasicGroup, 
		 docsIfCmtsGroup
	 }

	 VARIATION docsIfQosProfMaxTxBurst
	 ACCESS read-write
	 DESCRIPTION "This variable returns the value in bits/second rather than
	 mini-slots because this is the expected type by Cablelabs."

     -- ********************* ************ ************ *************** ***

     SUPPORTS DOCS-BPI-MIB
     INCLUDES {
	     docsBpiCmtsGroup
	 }

     VARIATION docsBpiCmtsDefaultAuthLifetime
     ACCESS read-write
     DESCRIPTION "For testing purposes, this variable has an increased
     numeric range from 1 to 6048000."

     VARIATION docsBpiCmtsDefaultTEKLifetime
     ACCESS read-write
     DESCRIPTION "For testing purposes, this variable has an increased
     numeric range from 1 to 604800."

     VARIATION docsBpiCmtsAuthCmLifetime
     ACCESS read-write
     DESCRIPTION "For testing purposes, this variable has an increased
     numeric range from 1 to 6048000."

     VARIATION docsBpiCmtsAuthCmGraceTime
     ACCESS read-write
     DESCRIPTION "For testing purposes, this variable has an increased
     numeric range from 1 to 1800."

     VARIATION docsBpiCmtsTEKLifetime
     ACCESS read-write
     DESCRIPTION "For testing purposes, this variable has an increased
     numeric range from 1 to 604800."

     VARIATION docsBpiCmtsTEKGraceTime
     ACCESS read-write
     DESCRIPTION "For testing purposes, this variable has an increased
     numeric range from 1 to 1800."

     -- ********************* ************ ************ *************** ***

     SUPPORTS RIVERSTONE-STP-MIB
     INCLUDES {
	     rsStpBaseGroup
	 }

     VARIATION rsStpStatus
	 ACCESS not-implemented
	 DESCRIPTION "STP cannot be disabled globally on RS devices"

   ::= { rsCapability 1 }

rs62x AGENT-CAPABILITIES 
  PRODUCT-RELEASE 
     "6.2.x"
  STATUS  current
  DESCRIPTION
     "Firmware Release 6.2.x for Riverstone  RS RapidOS product line.
	  The firmware supports channelized T1/E1 card in release 6.2"
  REFERENCE 
     "http://www.riverstonenet.com/products"

     -- RFC 1907
     SUPPORTS SNMPv2-MIB
     INCLUDES { 
         systemGroup,
         snmpGroup, 
         snmpBasicNotificationsGroup,
         --  snmpSetGroup is not implemented, but is needed for SNMPv2-MIB compliance
         -- non mandatory groups
         snmpCommunityGroup,
         -- deprecated/obsolete support
         snmpObsoleteGroup
     }

     -- ********************* ************ ************ *************** ***
     -- RFC 2358
     SUPPORTS EtherLike-MIB
     INCLUDES { 
         etherStats100MbsGroup
     }

     -- ********************* ************ ************ *************** ***
     -- RFC 2233
     SUPPORTS IF-MIB
     INCLUDES { 
         ifGeneralInformationGroup, 
         ifStackGroup2,
         ifCounterDiscontinuityGroup,
         -- non mandatory groups
         ifFixedLengthGroup,
         ifHCFixedLengthGroup,
         ifPacketGroup,
         ifHCPacketGroup,
         ifVHCPacketGroup,
         ifRcvAddressGroup,
         -- deprecated/obsolete support
         ifOldObjectsGroup
     }
     VARIATION ifAlias
     ACCESS read-only
     DESCRIPTION "ifAlias is guarenteed to be unique across reboots. It takes the form Type : instance info
      for example: ifAlias.49 = IP interface: to-sc-BGPfeed or ifAlias.42 = VLAN: test1 or 
      ifAlias.35 = Physical port: et.14.5"

     VARIATION ifAdminStatus
     ACCESS read-only
     DESCRIPTION "For ifTypes corresponding to VLANs this object is read only."

     VARIATION ifLinkUpDownTrapEnable
     ACCESS read-only
     DESCRIPTION "For all ifTypes where ifConnectorPresent is not TRUE."

     VARIATION ifStackStatus
     ACCESS read-only
     DESCRIPTION "Command line interface(CLI) is used to change relationships."

     -- ********************* ************ ************ *************** ***
     -- RFC 2011
     SUPPORTS IP-MIB
     INCLUDES { 
         ipGroup,
         icmpGroup
     }
     VARIATION ipDefaultTTL
     ACCESS read-only
     DESCRIPTION "Command line interface(CLI) is used to change default ttl."

     -- ********************* ************ ************ *************** ***
     -- RFC 2096
     SUPPORTS IP-FORWARD-MIB
     INCLUDES { 
         ipForwardCidrRouteGroup
     }
     VARIATION ipCidrRouteIfIndex
     ACCESS read-only
     DESCRIPTION "Command line interface(CLI) is used to update Forwarding Information Base/FIB."

     VARIATION ipCidrRouteType
     ACCESS read-only
     DESCRIPTION "Command line interface(CLI) is used to update Forwarding Information Base/FIB."

     VARIATION ipCidrRouteInfo
     ACCESS read-only
     DESCRIPTION "Command line interface(CLI) is used to update Forwarding Information Base/FIB."

     VARIATION ipCidrRouteNextHopAS
     ACCESS read-only
     DESCRIPTION "Command line interface(CLI) is used to update Forwarding Information Base/FIB."

     VARIATION ipCidrRouteMetric1
     ACCESS read-only
     DESCRIPTION "Command line interface(CLI) is used to update Forwarding Information Base/FIB."

     VARIATION ipCidrRouteMetric2
     ACCESS read-only
     DESCRIPTION "Command line interface(CLI) is used to update Forwarding Information Base/FIB."

     VARIATION ipCidrRouteMetric3
     ACCESS read-only
     DESCRIPTION "Command line interface(CLI) is used to update Forwarding Information Base/FIB."

     VARIATION ipCidrRouteMetric4
     ACCESS read-only
     DESCRIPTION "Command line interface(CLI) is used to update Forwarding Information Base/FIB."

     VARIATION ipCidrRouteMetric5
     ACCESS read-only
     DESCRIPTION "Command line interface(CLI) is used to update Forwarding Information Base/FIB."

     VARIATION ipCidrRouteStatus
     ACCESS read-only
     DESCRIPTION "Command line interface(CLI) is used to update Forwarding Information Base/FIB."

     -- ********************* ************ ************ *************** ***
     -- RFC 2013
     SUPPORTS UDP-MIB
     INCLUDES { 
         udpGroup         
     }

     -- ********************* ************ ************ *************** ***
     -- RFC 2012
     SUPPORTS TCP-MIB
     INCLUDES { 
         tcpGroup         
     }
     VARIATION tcpConnState
     ACCESS read-only
     DESCRIPTION "Command line interface(CLI) is used to kill tcp sessions."

     -- ********************* ************ ************ *************** ***
     --  RFC 1657 
--     SUPPORTS BGP4-MIB
--     INCLUDES { 
--         This is an smiv1 mib, all objects read only. Specify in device config file to enable this mib.
--     }

     -- ********************* ************ ************ *************** ***
     -- RFC 1850    
     -- Specify in device config file to enable this mib.
     SUPPORTS OSPF-MIB
     INCLUDES { 
         ospfBasicGroup,
         ospfAreaGroup,
         ospfStubAreaGroup,
         ospfIfGroup,
         ospfIfMetricGroup,
         ospfVirtIfGroup,
         ospfNbrGroup,
         ospfVirtNbrGroup,
         ospfAreaAggregateGroup
     }
     VARIATION ospfRouterId
     ACCESS read-only
     DESCRIPTION "Command line interface(CLI) is used to set router id."

     VARIATION ospfAdminStat
     ACCESS read-only
     DESCRIPTION "Command line interface(CLI) is used to set ospf state."

     VARIATION ospfTOSSupport
     ACCESS read-only
     DESCRIPTION "Command line interface(CLI) is used to set ospf TOS support."

     VARIATION ospfExtLsdbLimit
     ACCESS read-only
     DESCRIPTION "Command line interface(CLI) is used to set ospf Lsdb Limit."

     VARIATION ospfMulticastExtensions
     ACCESS read-only
     DESCRIPTION "Command line interface(CLI) is used to set ospf multicast extensions."

     VARIATION ospfExitOverflowInterval
     ACCESS read-only
     DESCRIPTION "Command line interface(CLI) is used to set ospf exit overflow interval."

     VARIATION ospfDemandExtensions
     ACCESS read-only
     DESCRIPTION "Command line interface(CLI) is used to set ospf demand extensions."

     VARIATION ospfAuthType
     ACCESS read-only
     DESCRIPTION "Command line interface(CLI) is used to set ospf authorisation types."

     VARIATION ospfImportAsExtern
     ACCESS read-only
     DESCRIPTION "Command line interface(CLI) is used to set ospf Import AS external routes."

     VARIATION ospfAreaSummary
     ACCESS read-only
     DESCRIPTION "Command line interface(CLI) is used to set ospf area summary importation."

     VARIATION ospfAreaStatus
     ACCESS read-only
     DESCRIPTION "Command line interface(CLI) is used to create & delete ospf areas."

     VARIATION ospfStubMetric
     ACCESS read-only
     DESCRIPTION "Command line interface(CLI) is used to set ospf area stub metric."

     VARIATION ospfStubStatus
     ACCESS read-only
     DESCRIPTION "Command line interface(CLI) is used to create & delete stub areas."

     VARIATION ospfStubMetricType
     ACCESS read-only
     DESCRIPTION "Command line interface(CLI) is used to set ospf stub metric type."

     VARIATION ospfAreaRangeMask
     ACCESS read-only
     DESCRIPTION "Command line interface(CLI) is used to set ospf area range mask."

     VARIATION ospfAreaRangeStatus
     ACCESS read-only
     DESCRIPTION "Command line interface(CLI) is used to create & delete ranges."

     VARIATION ospfAreaRangeEffect
     ACCESS read-only
     DESCRIPTION "Command line interface(CLI) is used to set area range effect."

     VARIATION ospfHostMetric
     ACCESS read-only
     DESCRIPTION "Command line interface(CLI) is used to set host metric."

     VARIATION ospfHostStatus
     ACCESS read-only
     DESCRIPTION "Command line interface(CLI) is used to create & delete hosts."

     VARIATION ospfIfAreaId
     ACCESS read-only
     DESCRIPTION "Command line interface(CLI) is used to set Interface area id."

     VARIATION ospfIfType
     ACCESS read-only
     DESCRIPTION "Command line interface(CLI) is used to set Interface type."

     VARIATION ospfIfAdminStat
     ACCESS read-only
     DESCRIPTION "Command line interface(CLI) is used to set Interface admin status."

     VARIATION ospfIfRtrPriority
     ACCESS read-only
     DESCRIPTION "Command line interface(CLI) is used to set interface router priority."

     VARIATION ospfIfTransitDelay
     ACCESS read-only
     DESCRIPTION "Command line interface(CLI) is used to set interface transit delay."

     VARIATION ospfIfRetransInterval
     ACCESS read-only
     DESCRIPTION "Command line interface(CLI) is used to set interface retransmission interval."

     VARIATION ospfIfHelloInterval
     ACCESS read-only
     DESCRIPTION "Command line interface(CLI) is used to set hello interval."

     VARIATION ospfIfRtrDeadInterval
     ACCESS read-only
     DESCRIPTION "Command line interface(CLI) is used to set dead interval."

     VARIATION ospfIfPollInterval
     ACCESS read-only
     DESCRIPTION "Command line interface(CLI) is used to set poll interval."

     VARIATION ospfIfAuthKey
     ACCESS read-only
     DESCRIPTION "Command line interface(CLI) is used to set interface auth key."

     VARIATION ospfIfStatus
     ACCESS read-only
     DESCRIPTION "Command line interface(CLI) is used to create & delete interfaces."

     VARIATION ospfIfMulticastForwarding
     ACCESS read-only
     DESCRIPTION "Command line interface(CLI) is used to set multicast fwd."

     VARIATION ospfIfDemand
     ACCESS read-only
     DESCRIPTION "Command line interface(CLI) is used to set this attribute."

     VARIATION ospfIfAuthType
     ACCESS read-only
     DESCRIPTION "Command line interface(CLI) is used to set this feature."

     VARIATION ospfIfMetricValue
     ACCESS read-only
     DESCRIPTION "Command line interface(CLI) is used to set this feature."

     VARIATION ospfVirtIfTransitDelay
     ACCESS read-only
     DESCRIPTION "Command line interface(CLI) is used to set this feature."

     VARIATION ospfVirtIfRetransInterval
     ACCESS read-only
     DESCRIPTION "Command line interface(CLI) is used to set this feature."

     VARIATION ospfVirtIfHelloInterval
     ACCESS read-only
     DESCRIPTION "Command line interface(CLI) is used to set this feature."

     VARIATION ospfVirtIfRtrDeadInterval
     ACCESS read-only
     DESCRIPTION "Command line interface(CLI) is used to set this feature."

     VARIATION ospfVirtIfAuthKey
     ACCESS read-only
     DESCRIPTION "Command line interface(CLI) is used to set this feature."

     VARIATION ospfVirtIfStatus
     ACCESS read-only
     DESCRIPTION "Command line interface(CLI) is used to set this feature."

     VARIATION ospfVirtIfAuthType
     ACCESS read-only
     DESCRIPTION "Command line interface(CLI) is used to set this feature."

     VARIATION ospfNbrPriority
     ACCESS read-only
     DESCRIPTION "Command line interface(CLI) is used to set this feature."

     VARIATION ospfNbmaNbrStatus
     ACCESS read-only
     DESCRIPTION "Command line interface(CLI) is used to set this feature."

     VARIATION ospfAreaAggregateStatus
     ACCESS read-only
     DESCRIPTION "Command line interface(CLI) is used to set this feature."

     VARIATION ospfAreaAggregateEffect
     ACCESS read-only
     DESCRIPTION "Command line interface(CLI) is used to set this feature."

     SUPPORTS OSPF-TRAP-MIB
     INCLUDES { 
         ospfTrapControlGroup
     }

     -- ********************* ************ ************ *************** ***
     -- RFC 1724
     -- Specify in device config file to enable this mib.
     SUPPORTS RIPv2-MIB
     INCLUDES { 
         rip2GlobalGroup,
         rip2IfStatGroup,
         rip2IfConfGroup,
         rip2PeerGroup
     }
     VARIATION rip2IfStatStatus
     ACCESS read-only
     DESCRIPTION "Command line interface(CLI) is used to set this feature."
   
     VARIATION rip2IfConfDomain
     ACCESS read-only
     DESCRIPTION "Command line interface(CLI) is used to set this feature."

     VARIATION rip2IfConfAuthType
     ACCESS read-only
     DESCRIPTION "Command line interface(CLI) is used to set this feature."

     VARIATION rip2IfConfAuthKey
     ACCESS read-only
     DESCRIPTION "Command line interface(CLI) is used to set this feature."

     VARIATION rip2IfConfSend
     ACCESS read-only
     DESCRIPTION "Command line interface(CLI) is used to set this feature."

     VARIATION rip2IfConfReceive
     ACCESS read-only
     DESCRIPTION "Command line interface(CLI) is used to set this feature."

     VARIATION rip2IfConfDefaultMetric
     ACCESS read-only
     DESCRIPTION "Command line interface(CLI) is used to set this feature."

     VARIATION rip2IfConfStatus
     ACCESS read-only
     DESCRIPTION "Command line interface(CLI) is used to set this feature."

     VARIATION rip2IfConfSrcAddress
     ACCESS read-only
     DESCRIPTION "Command line interface(CLI) is used to set this feature."

     -- ********************* ************ ************ *************** ***
     -- RFC 1493
--    SUPPORTS BRIDGE-MIB
--    INCLUDES { 
--       smiv1 mib
--    }

     -- ********************* ************ ************ *************** ***
     -- RFC 2674
     SUPPORTS Q-BRIDGE-MIB
     INCLUDES { 
        qBridgeBaseGroup,
        qBridgeVlanGroup,
        qBridgeVlanStaticGroup,
        qBridgePortGroup,
        qBridgeFdbUnicastGroup,
        qBridgeServiceRequirementsGroup
     }
     -- note: qBridgeFdbMulticastGroup, mandatory, but not implemented in 6.2.x

     VARIATION dot1qGvrpStatus
     ACCESS read-only
     DEFVAL { disabled }
     DESCRIPTION "Firmware Version 6.2.x does not support GVRP/GARP."

     VARIATION dot1qForwardAllStaticPorts
     ACCESS read-only
     DESCRIPTION "Command line interface(CLI) is used to set this feature."

     VARIATION dot1qForwardAllForbiddenPorts
     ACCESS read-only
     DESCRIPTION "Command line interface(CLI) is used to set this feature."

     VARIATION dot1qForwardUnregisteredStaticPorts
     ACCESS read-only
     DESCRIPTION "Command line interface(CLI) is used to set this feature."

     VARIATION dot1qForwardUnregisteredForbiddenPorts
     ACCESS read-only
     DESCRIPTION "Command line interface(CLI) is used to set this feature."

     VARIATION dot1qStaticUnicastAllowedToGoTo
     ACCESS read-only
     DESCRIPTION "Command line interface(CLI) is used to set this feature."

     VARIATION dot1qStaticUnicastStatus
     ACCESS read-only
     DESCRIPTION "Command line interface(CLI) is used to set this feature."

     VARIATION dot1qStaticMulticastStaticEgressPorts
     ACCESS read-only
     DESCRIPTION "Command line interface(CLI) is used to set this feature."

     VARIATION dot1qStaticMulticastForbiddenEgressPorts
     ACCESS read-only
     DESCRIPTION "Command line interface(CLI) is used to set this feature."

     VARIATION dot1qStaticMulticastStatus
     ACCESS read-only
     DESCRIPTION "Command line interface(CLI) is used to set this feature."

     VARIATION dot1qVlanStaticName
     ACCESS read-only
     DESCRIPTION "Command line interface(CLI) is used to set this feature."

     VARIATION dot1qVlanStaticEgressPorts
     ACCESS read-only
     DESCRIPTION "Command line interface(CLI) is used to set this feature."

     VARIATION dot1qVlanForbiddenEgressPorts
     ACCESS read-only
     DESCRIPTION "Command line interface(CLI) is used to set this feature."

     VARIATION dot1qVlanStaticUntaggedPorts
     ACCESS read-only
     DESCRIPTION "Command line interface(CLI) is used to set this feature."

     VARIATION dot1qVlanStaticRowStatus
     ACCESS read-only
     DESCRIPTION "Command line interface(CLI) is used to set this feature."

     VARIATION dot1qPvid
     ACCESS read-only
     DESCRIPTION "Command line interface(CLI) is used to set this feature."

     VARIATION dot1qPortAcceptableFrameTypes
     ACCESS read-only
     DEFVAL { admitAll }
     DESCRIPTION "RapidOS firmware 6.2.x does not support admitOnlyVlanTagged option."

     VARIATION dot1qPortIngressFiltering
     ACCESS read-only
     DEFVAL { true }
     DESCRIPTION "RapidOS firmware 6.2.x does not support false option per port."

     VARIATION dot1qPortGvrpStatus
     ACCESS read-only
     DEFVAL { disabled }
     DESCRIPTION "GVRP/GARP not supported in firmware 6.2.x."


     -- ********************* ************ ************ *************** ***
     -- RFC 2674
     SUPPORTS P-BRIDGE-MIB
     INCLUDES { 
       pBridgeExtCapGroup,
       pBridgeDevicePriorityGroup,
       pBridgeDefaultPriorityGroup,
       pBridgePriorityGroup,
       pBridgeHCPortGroup
     }

     VARIATION dot1dTrafficClassesEnabled
     ACCESS read-only
     DEFVAL { true } 
     DESCRIPTION "RapidOS Firmware uses fixed traffic categorization per port in 6.2.x release."

     VARIATION dot1dGmrpStatus
     ACCESS read-only
     DEFVAL { disabled } 
     DESCRIPTION "Not supported in release 6.2.x."

     VARIATION dot1dPortDefaultUserPriority
     ACCESS read-only
     DESCRIPTION "RapidOS Firmware uses fixed traffic categorization per port in 6.2.x release."

     VARIATION dot1dRegenUserPriority
     ACCESS read-only
     DESCRIPTION "Command line interface(CLI) is used to set this feature."

     VARIATION dot1dTrafficClass
     ACCESS read-only
     DESCRIPTION "RapidOS Firmware uses fixed traffic categorization per port in 6.2.x release."

     -- ********************* ************ ************ *************** ***
     -- RFC 2115
     SUPPORTS FRAME-RELAY-DTE-MIB
     INCLUDES { 
       frPortGroup, 
       frCircuitGroup,
       frErrGroup,
       frTrapGroup
     }
     VARIATION frDlcmiState
     ACCESS read-only
     DESCRIPTION "Command line interface(CLI) is used to set this feature."

     VARIATION frDlcmiAddress
     ACCESS read-only
     DESCRIPTION "Command line interface(CLI) is used to set this feature."

     VARIATION frDlcmiAddressLen
     ACCESS read-only
     DESCRIPTION "Command line interface(CLI) is used to set this feature."

     VARIATION frDlcmiPollingInterval
     ACCESS read-only
     DESCRIPTION "Command line interface(CLI) is used to set this feature."
     
     VARIATION frDlcmiFullEnquiryInterval
     ACCESS read-only
     DESCRIPTION "Command line interface(CLI) is used to set this feature."

     VARIATION frDlcmiErrorThreshold
     ACCESS read-only
     DESCRIPTION "Command line interface(CLI) is used to set this feature."

     VARIATION frDlcmiMonitoredEvents
     ACCESS read-only
     DESCRIPTION "Command line interface(CLI) is used to set this feature."

     VARIATION frDlcmiMaxSupportedVCs
     ACCESS read-only
     DESCRIPTION "Command line interface(CLI) is used to set this feature."

     VARIATION frDlcmiMulticast
     ACCESS read-only
     DESCRIPTION "Command line interface(CLI) is used to set this feature."

     VARIATION frDlcmiRowStatus
     ACCESS read-only
     DESCRIPTION "Command line interface(CLI) is used to create & delete dlcmi's."

     VARIATION frCircuitState
     ACCESS read-only
     DESCRIPTION "Command line interface(CLI) is used to set this feature."

     VARIATION frCircuitCommittedBurst
     ACCESS read-only
     DESCRIPTION "Command line interface(CLI) is used to set this feature."

     VARIATION frCircuitExcessBurst
     ACCESS read-only
     DESCRIPTION "Command line interface(CLI) is used to set this feature."

     VARIATION frCircuitThroughput
     ACCESS read-only
     DESCRIPTION "Command line interface(CLI) is used to set this feature."

     VARIATION frCircuitMulticast
     ACCESS read-only
     DESCRIPTION "Command line interface(CLI) is used to set this feature."

     VARIATION frCircuitLogicalIfIndex
     ACCESS read-only
     DESCRIPTION "Command line interface(CLI) is used to set this feature."

     VARIATION frCircuitRowStatus
     ACCESS read-only
     DESCRIPTION "Command line interface(CLI) is used to set this feature."

     -- ********************* ************ ************ *************** ***
       -- RFC 1471
--     SUPPORTS PPP-LCP-MIB
--     INCLUDES { 
--       smiv1 mib - read only 
--     }

     -- ********************* ************ ************ *************** ***
       -- RFC 1472
--     SUPPORTS PPP-SEC-MIB
--     INCLUDES { 
--      smiv1 mib - read only
--     }

     -- ********************* ************ ************ *************** ***
       -- RFC 1473
--     SUPPORTS PPP-IP-NCP-MIB
--     INCLUDES { 
--       smiv1 mib - read only
--     }

     -- ********************* ************ ************ *************** ***
       -- RFC 1474
--     SUPPORTS PPP-BRIDGE-NCP-MIB
--     INCLUDES { 
--       smiv1 mib - read only
--     }

     -- ********************* ************ ************ *************** ***
     -- RFC 2495
     SUPPORTS DS1-MIB
     INCLUDES { 
        ds1NearEndConfigGroup,
        ds1NearEndStatisticsGroup
     }
     VARIATION dsx1LineType
     ACCESS read-only
     DESCRIPTION "Command line interface(CLI) is used to set this feature."

     VARIATION dsx1LineCoding
     ACCESS read-only
     DESCRIPTION "Command line interface(CLI) is used to set this feature."

     VARIATION dsx1SendCode
     ACCESS read-only
     DESCRIPTION "Command line interface(CLI) is used to set this feature."

     VARIATION dsx1CircuitIdentifier
     ACCESS read-only
     DESCRIPTION "Command line interface(CLI) is used to set this feature."

     VARIATION dsx1LoopbackConfig
     ACCESS read-only
     DESCRIPTION "Command line interface(CLI) is used to set this feature."

     VARIATION dsx1SignalMode
     ACCESS read-only
     DESCRIPTION "Command line interface(CLI) is used to set this feature."

     VARIATION dsx1TransmitClockSource
     ACCESS read-only
     DESCRIPTION "Command line interface(CLI) is used to set this feature."

     VARIATION dsx1Fdl
     ACCESS read-only
     DESCRIPTION "Command line interface(CLI) is used to set this feature."

     VARIATION dsx1LineLength
     ACCESS read-only
     DESCRIPTION "Command line interface(CLI) is used to set this feature."

     VARIATION dsx1LineStatusChangeTrapEnable
     ACCESS read-only
     DESCRIPTION "Command line interface(CLI) is used to set this feature."

     VARIATION dsx1Channelization
     ACCESS read-only
     DEFVAL  { disabled }
     DESCRIPTION "RapidOS Firmware 6.2.x does not implement channelized T1/E1."


     -- ********************* ************ ************ *************** ***
     -- RFC 2496
     SUPPORTS DS3-MIB
     INCLUDES { 
        ds3NearEndConfigGroup,
        ds3NearEndStatisticsGroup
     }

     VARIATION dsx3LineType
     ACCESS read-only
     DESCRIPTION "Command line interface(CLI) is used to set this feature."

     VARIATION dsx3LineCoding
     ACCESS read-only
     DESCRIPTION "Command line interface(CLI) is used to set this feature."

     VARIATION dsx3SendCode
     ACCESS read-only
     DESCRIPTION "Command line interface(CLI) is used to set this feature."

     VARIATION dsx3CircuitIdentifier
     ACCESS read-only
     DESCRIPTION "Command line interface(CLI) is used to set this feature."

     VARIATION dsx3LoopbackConfig
     ACCESS read-only
     DESCRIPTION "Command line interface(CLI) is used to set this feature."

     VARIATION dsx3TransmitClockSource
     ACCESS read-only
     DESCRIPTION "Command line interface(CLI) is used to set this feature."

     VARIATION dsx3LineLength
     ACCESS read-only
     DESCRIPTION "Command line interface(CLI) is used to set this feature."

     VARIATION dsx3LineStatusChangeTrapEnable
     ACCESS read-only
     DESCRIPTION "Command line interface(CLI) is used to set this feature."

     VARIATION dsx3Channelization
     ACCESS read-only
     DEFVAL { disabled }
     DESCRIPTION "RapidOS 6.2.x Firmware does not support channelized T3/E3."

     VARIATION dsx3Ds1ForRemoteLoop
     ACCESS read-only
     DESCRIPTION "Command line interface(CLI) is used to set this feature."

     -- ********************* ************ ************ *************** ***
     -- RFC 1595
     SUPPORTS SONET-MIB
     INCLUDES { 
        sonetMediumStuff, 
        sonetSectionStuff,
        sonetLineStuff,
        sonetFarEndLineStuff,
        sonetPathStuff,
        sonetFarEndPathStuff
     }

     -- ATM OC3 line cards with  modular physical port (MODPHY) have above instrumentation
     -- POS OC3/12 line cards do not yet support the SONET-MIB

     -- ********************* ************ ************ *************** ***
     -- RFC 1695
     SUPPORTS ATM-MIB
     INCLUDES { 
        atmInterfaceConfGroup,
        atmTrafficDescrGroup,
        atmInterfaceDs3PlcpGroup,
        atmInterfaceTCGroup,
        atmVccTerminationGroup,
        aal5VccGroup
     }    

     VARIATION atmInterfaceMaxVpcs
     ACCESS read-only 
     DESCRIPTION "This object is not settable"

     VARIATION atmInterfaceMaxVccs
     ACCESS read-only
     DESCRIPTION "This object is not settable"

     VARIATION atmInterfaceMaxActiveVpiBits
     ACCESS read-only
     DESCRIPTION "This object is not settable"
     
     VARIATION atmInterfaceMaxActiveVciBits
     ACCESS read-only
     DESCRIPTION "This object is not settable"

     VARIATION atmInterfaceIlmiVpi
     ACCESS not-implemented
     DESCRIPTION "Device does not support Ilmi"

     VARIATION atmInterfaceIlmiVci
     ACCESS not-implemented
     DESCRIPTION "Device does not support Ilmi"

     VARIATION atmInterfaceMyNeighborIpAddress
     ACCESS not-implemented
     DESCRIPTION "Firmware does not support this"

     VARIATION atmInterfaceMyNeighborIfName
     ACCESS not-implemented
     DESCRIPTION "Firmware does not support this"

     VARIATION atmTrafficDescrParam1
     ACCESS read-only
     DESCRIPTION "Command line interface(CLI) is used to set this feature"

     VARIATION atmTrafficDescrParam2
     ACCESS read-only
     DESCRIPTION "Command line interface(CLI) is used to set this feature"
     
     VARIATION atmTrafficDescrParam3
     ACCESS read-only
     DESCRIPTION "Command line interface(CLI) is used to set this feature"

     VARIATION atmTrafficDescrParam4
     ACCESS read-only
     DESCRIPTION "Command line interface(CLI) is used to set this feature"

     VARIATION atmTrafficDescrParam5
     ACCESS read-only
     DESCRIPTION "Command line interface(CLI) is used to set this feature"

     VARIATION atmTrafficQoSClass
     ACCESS read-only
     DESCRIPTION "Command line interface(CLI) is used to set this feature"

     VARIATION atmTrafficDescrRowStatus
     ACCESS not-implemented
     DESCRIPTION "Table is read-only"

     VARIATION atmInterfaceDs3PlcpSEFSs
     ACCESS not-implemented
     DESCRIPTION "Firmware does not support this"

     VARIATION atmInterfaceDs3PlcpAlarmState
     ACCESS not-implemented
     DESCRIPTION "Firmware does not support this"

     VARIATION atmInterfaceDs3PlcpUASs
     ACCESS not-implemented
     DESCRIPTION "Firmware does not support this"

     VARIATION atmInterfaceOCDEvents
     ACCESS not-implemented
     DESCRIPTION "Firmware does not support this"

     VARIATION atmInterfaceTCAlarmState
     ACCESS not-implemented
     DESCRIPTION "Firmware does not support this"

     VARIATION atmVclAdminStatus
     ACCESS read-only
     DESCRIPTION "Command line interface(CLI) is used to set this feature"

     VARIATION atmVclReceiveTrafficDescrIndex
     ACCESS read-only
     DESCRIPTION "Memory address is used as the index, CLI is used to set this"

     VARIATION atmVclTransmitTrafficDescrIndex
     ACCESS read-only
     DESCRIPTION "Memory address is used as the index, CLI is used to set this"
        
     VARIATION atmVccAalType
     ACCESS read-only
     DESCRIPTION "This object is not settable"

     VARIATION atmVclRowStatus
     ACCESS read-only
     DESCRIPTION "This object is not settable"

     -- ********************* ************ ************ *************** ***
     -- RFC 2618
     SUPPORTS RADIUS-AUTH-CLIENT-MIB
     INCLUDES { 
          radiusAuthClientMIBGroup
     }

     -- ********************* ************ ************ *************** ***
     -- RFC 1757/2819
       SUPPORTS RMON-MIB
       INCLUDES { 
         
         rmonEtherStatsGroup,
         rmonHistoryControlGroup,
         rmonEthernetHistoryGroup,
         rmonAlarmGroup,
         rmonHostGroup,   -- requires flow bridging hardware mode enabled
         rmonHostTopNGroup, 
         rmonMatrixGroup, -- requires flow bridging hardware mode enabled
         rmonFilterGroup,
         rmonPacketCaptureGroup,
         rmonEventGroup,
         rmonNotificationGroup
       }

     -- ********************* ************ ************ *************** ***
     -- RFC 2021
     SUPPORTS RMON2-MIB
     INCLUDES { 
        protocolDirectoryGroup,
        protocolDistributionGroup,
        addressMapGroup,
        nlHostGroup,
        nlMatrixGroup,
        alHostGroup,
        alMatrixGroup,
        usrHistoryGroup,
        probeInformationGroup,
        probeConfigurationGroup,
        rmon1EthernetEnhancementGroup
        -- rmon1EnhancementGroup supported except for filterProtocolDirDataLocalIndex,
        --  filterProtocolDirLocalIndex
     }
     VARIATION filterProtocolDirDataLocalIndex
     ACCESS not-implemented
     DESCRIPTION "Feature not available in firmware version 6.2.x."

     VARIATION filterProtocolDirLocalIndex
     ACCESS not-implemented
     DESCRIPTION "Feature not available in firmware version 6.2.x."

     -- NOTE: Sets to this mib are not persistent. RMON configuration
     -- may be done via CLI for persistence
     -- ********************* ************ ************ *************** ***
     -- From ietf vrrp mib Draft #9
     SUPPORTS VRRP-MIB
     INCLUDES { 
        vrrpOperGroup,
        vrrpStatsGroup,
        vrrpTrapGroup,
        vrrpNotificationGroup
     }
     VARIATION vrrpOperAdminState
     ACCESS read-only
     DESCRIPTION "Command line interface(CLI) is used to set this feature."

     VARIATION vrrpOperPriority
     ACCESS read-only
     DESCRIPTION "Command line interface(CLI) is used to set this feature."

     VARIATION vrrpOperPrimaryIpAddr
     ACCESS read-only
     DESCRIPTION "Command line interface(CLI) is used to set this feature."

     VARIATION vrrpOperAuthType
     ACCESS read-only
     DESCRIPTION "Command line interface(CLI) is used to set this feature."

     VARIATION vrrpOperAuthKey
     ACCESS read-only
     DESCRIPTION "Command line interface(CLI) is used to set this feature."

     VARIATION vrrpOperAdvertisementInterval
     ACCESS read-only
     DESCRIPTION "Command line interface(CLI) is used to set this feature."

     VARIATION vrrpOperPreemptMode
     ACCESS read-only
     DESCRIPTION "Command line interface(CLI) is used to set this feature."

     VARIATION vrrpOperProtocol
     ACCESS read-only
     DESCRIPTION "Command line interface(CLI) is used to set this feature."

     VARIATION vrrpOperRowStatus
     ACCESS read-only
     DESCRIPTION "Command line interface(CLI) is used to set this feature."

     VARIATION vrrpAssoIpAddrRowStatus
     ACCESS read-only
     DESCRIPTION "Command line interface(CLI) is used to set this feature."

     VARIATION vrrpTrapAuthFailure
     ACCESS not-implemented
     DESCRIPTION "TrapAuthFailure not implemented in 6.2.x."

     -- ********************* ************ ************ *************** ***

     SUPPORTS CTRON-LFAP-MIB
     INCLUDES { 
        lfapConfGroupV40
     }

     -- ********************* ************ ************ *************** ***

     SUPPORTS CTRON-SSR-POLICY-MIB
     INCLUDES { 
         polGroupV11        
     }

     -- ********************* ************ ************ *************** ***

     SUPPORTS CTRON-SSR-CONFIG-MIB
     INCLUDES { 
         configGroup20
     }

     
     -- ********************* ************ ************ *************** ***

     SUPPORTS CTRON-SSR-HARDWARE-MIB
     INCLUDES { 
         hwConfGroupV30
     }

     -- ********************* ************ ************ *************** ***

     SUPPORTS CTRON-SSR-SERVICE-STATUS-MIB
     INCLUDES { 
         ssConfGroupV11
     }

     -- ********************* ************ ************ *************** ***

     SUPPORTS CTRON-SSR-CAPACITY-MIB
     INCLUDES { 
         capConfGroupV10
     }

     -- ********************* ************ ************ *************** ***

	 SUPPORTS DOCS-IF-MIB
	 INCLUDES {
         docsIfBasicGroup, 
		 docsIfCmtsGroup
	 }

	 VARIATION docsIfQosProfMaxTxBurst
	 ACCESS read-write
	 DESCRIPTION "This variable returns the value in bits/second rather than
	 mini-slots because this is the expected type by Cablelabs."

     -- ********************* ************ ************ *************** ***

     SUPPORTS DOCS-BPI-MIB
     INCLUDES {
	     docsBpiCmtsGroup
	 }

     VARIATION docsBpiCmtsDefaultAuthLifetime
     ACCESS read-write
     DESCRIPTION "For testing purposes, this variable has an increased
     numeric range from 1 to 6048000."

     VARIATION docsBpiCmtsDefaultTEKLifetime
     ACCESS read-write
     DESCRIPTION "For testing purposes, this variable has an increased
     numeric range from 1 to 604800."

     VARIATION docsBpiCmtsAuthCmLifetime
     ACCESS read-write
     DESCRIPTION "For testing purposes, this variable has an increased
     numeric range from 1 to 6048000."

     VARIATION docsBpiCmtsAuthCmGraceTime
     ACCESS read-write
     DESCRIPTION "For testing purposes, this variable has an increased
     numeric range from 1 to 1800."

     VARIATION docsBpiCmtsTEKLifetime
     ACCESS read-write
     DESCRIPTION "For testing purposes, this variable has an increased
     numeric range from 1 to 604800."

     VARIATION docsBpiCmtsTEKGraceTime
     ACCESS read-write
     DESCRIPTION "For testing purposes, this variable has an increased
     numeric range from 1 to 1800."

     -- ********************* ************ ************ *************** ***

     SUPPORTS RIVERSTONE-STP-MIB
     INCLUDES {
	     rsStpBaseGroup
	 }

     VARIATION rsStpStatus
	 ACCESS not-implemented
	 DESCRIPTION "STP cannot be disabled globally on RS devices"

   ::= { rsCapability 2 }

rs63x AGENT-CAPABILITIES 
  PRODUCT-RELEASE 
     "6.3.x"
  STATUS  current
  DESCRIPTION
     "Firmware Release 6.3.x for Riverstone  RS RapidOS product line.
	  The firmware supports channelized T3/E3 card in release 6.3"
  REFERENCE 
     "http://www.riverstonenet.com/products"

     -- RFC 1907
     SUPPORTS SNMPv2-MIB
     INCLUDES { 
         systemGroup,
         snmpGroup, 
         snmpBasicNotificationsGroup,
         --  snmpSetGroup is not implemented, but is needed for SNMPv2-MIB compliance
         -- non mandatory groups
         snmpCommunityGroup,
         -- deprecated/obsolete support
         snmpObsoleteGroup
     }

     -- ********************* ************ ************ *************** ***
     -- RFC 2358
     SUPPORTS EtherLike-MIB
     INCLUDES { 
         etherStats100MbsGroup
     }

     -- ********************* ************ ************ *************** ***
     -- RFC 2233
     SUPPORTS IF-MIB
     INCLUDES { 
         ifGeneralInformationGroup, 
         ifStackGroup2,
         ifCounterDiscontinuityGroup,
         -- non mandatory groups
         ifFixedLengthGroup,
         ifHCFixedLengthGroup,
         ifPacketGroup,
         ifHCPacketGroup,
         ifVHCPacketGroup,
         ifRcvAddressGroup,
         -- deprecated/obsolete support
         ifOldObjectsGroup
     }
     VARIATION ifAlias
     ACCESS read-only
     DESCRIPTION "ifAlias is guarenteed to be unique across reboots. It takes the form Type : instance info
      for example: ifAlias.49 = IP interface: to-sc-BGPfeed or ifAlias.42 = VLAN: test1 or 
      ifAlias.35 = Physical port: et.14.5"

     VARIATION ifAdminStatus
     ACCESS read-only
     DESCRIPTION "For ifTypes corresponding to VLANs this object is read only."

     VARIATION ifLinkUpDownTrapEnable
     ACCESS read-only
     DESCRIPTION "For all ifTypes where ifConnectorPresent is not TRUE."

     VARIATION ifStackStatus
     ACCESS read-only
     DESCRIPTION "Command line interface(CLI) is used to change relationships."

     -- ********************* ************ ************ *************** ***
     -- RFC 2011
     SUPPORTS IP-MIB
     INCLUDES { 
         ipGroup,
         icmpGroup
     }
     VARIATION ipDefaultTTL
     ACCESS read-only
     DESCRIPTION "Command line interface(CLI) is used to change default ttl."

     -- ********************* ************ ************ *************** ***
     -- RFC 2096
     SUPPORTS IP-FORWARD-MIB
     INCLUDES { 
         ipForwardCidrRouteGroup
     }
     VARIATION ipCidrRouteIfIndex
     ACCESS read-only
     DESCRIPTION "Command line interface(CLI) is used to update Forwarding Information Base/FIB."

     VARIATION ipCidrRouteType
     ACCESS read-only
     DESCRIPTION "Command line interface(CLI) is used to update Forwarding Information Base/FIB."

     VARIATION ipCidrRouteInfo
     ACCESS read-only
     DESCRIPTION "Command line interface(CLI) is used to update Forwarding Information Base/FIB."

     VARIATION ipCidrRouteNextHopAS
     ACCESS read-only
     DESCRIPTION "Command line interface(CLI) is used to update Forwarding Information Base/FIB."

     VARIATION ipCidrRouteMetric1
     ACCESS read-only
     DESCRIPTION "Command line interface(CLI) is used to update Forwarding Information Base/FIB."

     VARIATION ipCidrRouteMetric2
     ACCESS read-only
     DESCRIPTION "Command line interface(CLI) is used to update Forwarding Information Base/FIB."

     VARIATION ipCidrRouteMetric3
     ACCESS read-only
     DESCRIPTION "Command line interface(CLI) is used to update Forwarding Information Base/FIB."

     VARIATION ipCidrRouteMetric4
     ACCESS read-only
     DESCRIPTION "Command line interface(CLI) is used to update Forwarding Information Base/FIB."

     VARIATION ipCidrRouteMetric5
     ACCESS read-only
     DESCRIPTION "Command line interface(CLI) is used to update Forwarding Information Base/FIB."

     VARIATION ipCidrRouteStatus
     ACCESS read-only
     DESCRIPTION "Command line interface(CLI) is used to update Forwarding Information Base/FIB."

     -- ********************* ************ ************ *************** ***
     -- RFC 2013
     SUPPORTS UDP-MIB
     INCLUDES { 
         udpGroup         
     }

     -- ********************* ************ ************ *************** ***
     -- RFC 2012
     SUPPORTS TCP-MIB
     INCLUDES { 
         tcpGroup         
     }
     VARIATION tcpConnState
     ACCESS read-only
     DESCRIPTION "Command line interface(CLI) is used to kill tcp sessions."

     -- ********************* ************ ************ *************** ***
     --  RFC 1657 
--     SUPPORTS BGP4-MIB
--     INCLUDES { 
--         This is an smiv1 mib, all objects read only. Specify in device config file to enable this mib.
--     }

     -- ********************* ************ ************ *************** ***
     -- RFC 1850    
     -- Specify in device config file to enable this mib.
     SUPPORTS OSPF-MIB
     INCLUDES { 
         ospfBasicGroup,
         ospfAreaGroup,
         ospfStubAreaGroup,
         ospfIfGroup,
         ospfIfMetricGroup,
         ospfVirtIfGroup,
         ospfNbrGroup,
         ospfVirtNbrGroup,
         ospfAreaAggregateGroup
     }
     VARIATION ospfRouterId
     ACCESS read-only
     DESCRIPTION "Command line interface(CLI) is used to set router id."

     VARIATION ospfAdminStat
     ACCESS read-only
     DESCRIPTION "Command line interface(CLI) is used to set ospf state."

     VARIATION ospfTOSSupport
     ACCESS read-only
     DESCRIPTION "Command line interface(CLI) is used to set ospf TOS support."

     VARIATION ospfExtLsdbLimit
     ACCESS read-only
     DESCRIPTION "Command line interface(CLI) is used to set ospf Lsdb Limit."

     VARIATION ospfMulticastExtensions
     ACCESS read-only
     DESCRIPTION "Command line interface(CLI) is used to set ospf multicast extensions."

     VARIATION ospfExitOverflowInterval
     ACCESS read-only
     DESCRIPTION "Command line interface(CLI) is used to set ospf exit overflow interval."

     VARIATION ospfDemandExtensions
     ACCESS read-only
     DESCRIPTION "Command line interface(CLI) is used to set ospf demand extensions."

     VARIATION ospfAuthType
     ACCESS read-only
     DESCRIPTION "Command line interface(CLI) is used to set ospf authorisation types."

     VARIATION ospfImportAsExtern
     ACCESS read-only
     DESCRIPTION "Command line interface(CLI) is used to set ospf Import AS external routes."

     VARIATION ospfAreaSummary
     ACCESS read-only
     DESCRIPTION "Command line interface(CLI) is used to set ospf area summary importation."

     VARIATION ospfAreaStatus
     ACCESS read-only
     DESCRIPTION "Command line interface(CLI) is used to create & delete ospf areas."

     VARIATION ospfStubMetric
     ACCESS read-only
     DESCRIPTION "Command line interface(CLI) is used to set ospf area stub metric."

     VARIATION ospfStubStatus
     ACCESS read-only
     DESCRIPTION "Command line interface(CLI) is used to create & delete stub areas."

     VARIATION ospfStubMetricType
     ACCESS read-only
     DESCRIPTION "Command line interface(CLI) is used to set ospf stub metric type."

     VARIATION ospfAreaRangeMask
     ACCESS read-only
     DESCRIPTION "Command line interface(CLI) is used to set ospf area range mask."

     VARIATION ospfAreaRangeStatus
     ACCESS read-only
     DESCRIPTION "Command line interface(CLI) is used to create & delete ranges."

     VARIATION ospfAreaRangeEffect
     ACCESS read-only
     DESCRIPTION "Command line interface(CLI) is used to set area range effect."

     VARIATION ospfHostMetric
     ACCESS read-only
     DESCRIPTION "Command line interface(CLI) is used to set host metric."

     VARIATION ospfHostStatus
     ACCESS read-only
     DESCRIPTION "Command line interface(CLI) is used to create & delete hosts."

     VARIATION ospfIfAreaId
     ACCESS read-only
     DESCRIPTION "Command line interface(CLI) is used to set Interface area id."

     VARIATION ospfIfType
     ACCESS read-only
     DESCRIPTION "Command line interface(CLI) is used to set Interface type."

     VARIATION ospfIfAdminStat
     ACCESS read-only
     DESCRIPTION "Command line interface(CLI) is used to set Interface admin status."

     VARIATION ospfIfRtrPriority
     ACCESS read-only
     DESCRIPTION "Command line interface(CLI) is used to set interface router priority."

     VARIATION ospfIfTransitDelay
     ACCESS read-only
     DESCRIPTION "Command line interface(CLI) is used to set interface transit delay."

     VARIATION ospfIfRetransInterval
     ACCESS read-only
     DESCRIPTION "Command line interface(CLI) is used to set interface retransmission interval."

     VARIATION ospfIfHelloInterval
     ACCESS read-only
     DESCRIPTION "Command line interface(CLI) is used to set hello interval."

     VARIATION ospfIfRtrDeadInterval
     ACCESS read-only
     DESCRIPTION "Command line interface(CLI) is used to set dead interval."

     VARIATION ospfIfPollInterval
     ACCESS read-only
     DESCRIPTION "Command line interface(CLI) is used to set poll interval."

     VARIATION ospfIfAuthKey
     ACCESS read-only
     DESCRIPTION "Command line interface(CLI) is used to set interface auth key."

     VARIATION ospfIfStatus
     ACCESS read-only
     DESCRIPTION "Command line interface(CLI) is used to create & delete interfaces."

     VARIATION ospfIfMulticastForwarding
     ACCESS read-only
     DESCRIPTION "Command line interface(CLI) is used to set multicast fwd."

     VARIATION ospfIfDemand
     ACCESS read-only
     DESCRIPTION "Command line interface(CLI) is used to set this attribute."

     VARIATION ospfIfAuthType
     ACCESS read-only
     DESCRIPTION "Command line interface(CLI) is used to set this feature."

     VARIATION ospfIfMetricValue
     ACCESS read-only
     DESCRIPTION "Command line interface(CLI) is used to set this feature."

     VARIATION ospfVirtIfTransitDelay
     ACCESS read-only
     DESCRIPTION "Command line interface(CLI) is used to set this feature."

     VARIATION ospfVirtIfRetransInterval
     ACCESS read-only
     DESCRIPTION "Command line interface(CLI) is used to set this feature."

     VARIATION ospfVirtIfHelloInterval
     ACCESS read-only
     DESCRIPTION "Command line interface(CLI) is used to set this feature."

     VARIATION ospfVirtIfRtrDeadInterval
     ACCESS read-only
     DESCRIPTION "Command line interface(CLI) is used to set this feature."

     VARIATION ospfVirtIfAuthKey
     ACCESS read-only
     DESCRIPTION "Command line interface(CLI) is used to set this feature."

     VARIATION ospfVirtIfStatus
     ACCESS read-only
     DESCRIPTION "Command line interface(CLI) is used to set this feature."

     VARIATION ospfVirtIfAuthType
     ACCESS read-only
     DESCRIPTION "Command line interface(CLI) is used to set this feature."

     VARIATION ospfNbrPriority
     ACCESS read-only
     DESCRIPTION "Command line interface(CLI) is used to set this feature."

     VARIATION ospfNbmaNbrStatus
     ACCESS read-only
     DESCRIPTION "Command line interface(CLI) is used to set this feature."

     VARIATION ospfAreaAggregateStatus
     ACCESS read-only
     DESCRIPTION "Command line interface(CLI) is used to set this feature."

     VARIATION ospfAreaAggregateEffect
     ACCESS read-only
     DESCRIPTION "Command line interface(CLI) is used to set this feature."

     SUPPORTS OSPF-TRAP-MIB
     INCLUDES { 
         ospfTrapControlGroup
     }

     -- ********************* ************ ************ *************** ***
     -- RFC 1724
     -- Specify in device config file to enable this mib.
     SUPPORTS RIPv2-MIB
     INCLUDES { 
         rip2GlobalGroup,
         rip2IfStatGroup,
         rip2IfConfGroup,
         rip2PeerGroup
     }
     VARIATION rip2IfStatStatus
     ACCESS read-only
     DESCRIPTION "Command line interface(CLI) is used to set this feature."
   
     VARIATION rip2IfConfDomain
     ACCESS read-only
     DESCRIPTION "Command line interface(CLI) is used to set this feature."

     VARIATION rip2IfConfAuthType
     ACCESS read-only
     DESCRIPTION "Command line interface(CLI) is used to set this feature."

     VARIATION rip2IfConfAuthKey
     ACCESS read-only
     DESCRIPTION "Command line interface(CLI) is used to set this feature."

     VARIATION rip2IfConfSend
     ACCESS read-only
     DESCRIPTION "Command line interface(CLI) is used to set this feature."

     VARIATION rip2IfConfReceive
     ACCESS read-only
     DESCRIPTION "Command line interface(CLI) is used to set this feature."

     VARIATION rip2IfConfDefaultMetric
     ACCESS read-only
     DESCRIPTION "Command line interface(CLI) is used to set this feature."

     VARIATION rip2IfConfStatus
     ACCESS read-only
     DESCRIPTION "Command line interface(CLI) is used to set this feature."

     VARIATION rip2IfConfSrcAddress
     ACCESS read-only
     DESCRIPTION "Command line interface(CLI) is used to set this feature."

     -- ********************* ************ ************ *************** ***
     -- RFC 1493
--    SUPPORTS BRIDGE-MIB
--    INCLUDES { 
--       smiv1 mib
--    }

     -- ********************* ************ ************ *************** ***
     -- RFC 2674
     SUPPORTS Q-BRIDGE-MIB
     INCLUDES { 
        qBridgeBaseGroup,
        qBridgeVlanGroup,
        qBridgeVlanStaticGroup,
        qBridgePortGroup,
        qBridgeFdbUnicastGroup,
        qBridgeServiceRequirementsGroup
     }
     -- note: qBridgeFdbMulticastGroup, mandatory, but not implemented in 6.3.x

     VARIATION dot1qGvrpStatus
     ACCESS read-only
     DEFVAL { disabled }
     DESCRIPTION "Firmware Version 6.3.x does not support GVRP/GARP."

     VARIATION dot1qForwardAllStaticPorts
     ACCESS read-only
     DESCRIPTION "Command line interface(CLI) is used to set this feature."

     VARIATION dot1qForwardAllForbiddenPorts
     ACCESS read-only
     DESCRIPTION "Command line interface(CLI) is used to set this feature."

     VARIATION dot1qForwardUnregisteredStaticPorts
     ACCESS read-only
     DESCRIPTION "Command line interface(CLI) is used to set this feature."

     VARIATION dot1qForwardUnregisteredForbiddenPorts
     ACCESS read-only
     DESCRIPTION "Command line interface(CLI) is used to set this feature."

     VARIATION dot1qStaticUnicastAllowedToGoTo
     ACCESS read-only
     DESCRIPTION "Command line interface(CLI) is used to set this feature."

     VARIATION dot1qStaticUnicastStatus
     ACCESS read-only
     DESCRIPTION "Command line interface(CLI) is used to set this feature."

     VARIATION dot1qStaticMulticastStaticEgressPorts
     ACCESS read-only
     DESCRIPTION "Command line interface(CLI) is used to set this feature."

     VARIATION dot1qStaticMulticastForbiddenEgressPorts
     ACCESS read-only
     DESCRIPTION "Command line interface(CLI) is used to set this feature."

     VARIATION dot1qStaticMulticastStatus
     ACCESS read-only
     DESCRIPTION "Command line interface(CLI) is used to set this feature."

     VARIATION dot1qVlanStaticName
     ACCESS read-only
     DESCRIPTION "Command line interface(CLI) is used to set this feature."

     VARIATION dot1qVlanStaticEgressPorts
     ACCESS read-only
     DESCRIPTION "Command line interface(CLI) is used to set this feature."

     VARIATION dot1qVlanForbiddenEgressPorts
     ACCESS read-only
     DESCRIPTION "Command line interface(CLI) is used to set this feature."

     VARIATION dot1qVlanStaticUntaggedPorts
     ACCESS read-only
     DESCRIPTION "Command line interface(CLI) is used to set this feature."

     VARIATION dot1qVlanStaticRowStatus
     ACCESS read-only
     DESCRIPTION "Command line interface(CLI) is used to set this feature."

     VARIATION dot1qPvid
     ACCESS read-only
     DESCRIPTION "Command line interface(CLI) is used to set this feature."

     VARIATION dot1qPortAcceptableFrameTypes
     ACCESS read-only
     DEFVAL { admitAll }
     DESCRIPTION "RapidOS firmware 6.3.x does not support admitOnlyVlanTagged option."

     VARIATION dot1qPortIngressFiltering
     ACCESS read-only
     DEFVAL { true }
     DESCRIPTION "RapidOS firmware 6.3.x does not support false option per port."

     VARIATION dot1qPortGvrpStatus
     ACCESS read-only
     DEFVAL { disabled }
     DESCRIPTION "GVRP/GARP not supported in firmware 6.3.x."


     -- ********************* ************ ************ *************** ***
     -- RFC 2674
     SUPPORTS P-BRIDGE-MIB
     INCLUDES { 
       pBridgeExtCapGroup,
       pBridgeDevicePriorityGroup,
       pBridgeDefaultPriorityGroup,
       pBridgePriorityGroup,
       pBridgeHCPortGroup
     }

     VARIATION dot1dTrafficClassesEnabled
     ACCESS read-only
     DEFVAL { true } 
     DESCRIPTION "RapidOS Firmware uses fixed traffic categorization per port in 6.3.x release."

     VARIATION dot1dGmrpStatus
     ACCESS read-only
     DEFVAL { disabled } 
     DESCRIPTION "Not supported in release 6.3.x."

     VARIATION dot1dPortDefaultUserPriority
     ACCESS read-only
     DESCRIPTION "RapidOS Firmware uses fixed traffic categorization per port in 6.3.x release."

     VARIATION dot1dRegenUserPriority
     ACCESS read-only
     DESCRIPTION "Command line interface(CLI) is used to set this feature."

     VARIATION dot1dTrafficClass
     ACCESS read-only
     DESCRIPTION "RapidOS Firmware uses fixed traffic categorization per port in 6.3.x release."

     -- ********************* ************ ************ *************** ***
     -- RFC 2115
     SUPPORTS FRAME-RELAY-DTE-MIB
     INCLUDES { 
       frPortGroup, 
       frCircuitGroup,
       frErrGroup,
       frTrapGroup
     }
     VARIATION frDlcmiState
     ACCESS read-only
     DESCRIPTION "Command line interface(CLI) is used to set this feature."

     VARIATION frDlcmiAddress
     ACCESS read-only
     DESCRIPTION "Command line interface(CLI) is used to set this feature."

     VARIATION frDlcmiAddressLen
     ACCESS read-only
     DESCRIPTION "Command line interface(CLI) is used to set this feature."

     VARIATION frDlcmiPollingInterval
     ACCESS read-only
     DESCRIPTION "Command line interface(CLI) is used to set this feature."
     
     VARIATION frDlcmiFullEnquiryInterval
     ACCESS read-only
     DESCRIPTION "Command line interface(CLI) is used to set this feature."

     VARIATION frDlcmiErrorThreshold
     ACCESS read-only
     DESCRIPTION "Command line interface(CLI) is used to set this feature."

     VARIATION frDlcmiMonitoredEvents
     ACCESS read-only
     DESCRIPTION "Command line interface(CLI) is used to set this feature."

     VARIATION frDlcmiMaxSupportedVCs
     ACCESS read-only
     DESCRIPTION "Command line interface(CLI) is used to set this feature."

     VARIATION frDlcmiMulticast
     ACCESS read-only
     DESCRIPTION "Command line interface(CLI) is used to set this feature."

     VARIATION frDlcmiRowStatus
     ACCESS read-only
     DESCRIPTION "Command line interface(CLI) is used to create & delete dlcmi's."

     VARIATION frCircuitState
     ACCESS read-only
     DESCRIPTION "Command line interface(CLI) is used to set this feature."

     VARIATION frCircuitCommittedBurst
     ACCESS read-only
     DESCRIPTION "Command line interface(CLI) is used to set this feature."

     VARIATION frCircuitExcessBurst
     ACCESS read-only
     DESCRIPTION "Command line interface(CLI) is used to set this feature."

     VARIATION frCircuitThroughput
     ACCESS read-only
     DESCRIPTION "Command line interface(CLI) is used to set this feature."

     VARIATION frCircuitMulticast
     ACCESS read-only
     DESCRIPTION "Command line interface(CLI) is used to set this feature."

     VARIATION frCircuitLogicalIfIndex
     ACCESS read-only
     DESCRIPTION "Command line interface(CLI) is used to set this feature."

     VARIATION frCircuitRowStatus
     ACCESS read-only
     DESCRIPTION "Command line interface(CLI) is used to set this feature."

     -- ********************* ************ ************ *************** ***
       -- RFC 1471
--     SUPPORTS PPP-LCP-MIB
--     INCLUDES { 
--       smiv1 mib - read only 
--     }

     -- ********************* ************ ************ *************** ***
       -- RFC 1472
--     SUPPORTS PPP-SEC-MIB
--     INCLUDES { 
--      smiv1 mib - read only
--     }

     -- ********************* ************ ************ *************** ***
       -- RFC 1473
--     SUPPORTS PPP-IP-NCP-MIB
--     INCLUDES { 
--       smiv1 mib - read only
--     }

     -- ********************* ************ ************ *************** ***
       -- RFC 1474
--     SUPPORTS PPP-BRIDGE-NCP-MIB
--     INCLUDES { 
--       smiv1 mib - read only
--     }

     -- ********************* ************ ************ *************** ***
	 -- RFC 2494
	 SUPPORTS DS0-MIB
	 INCLUDES {
		ds0ConfigGroup
	 }

     -- ********************* ************ ************ *************** ***
	 -- RFC 2494
	 SUPPORTS DS0BUNDLE-MIB
	 INCLUDES {
		ds0BundleConfigGroup
	 }

     -- ********************* ************ ************ *************** ***
     -- RFC 2495
     SUPPORTS DS1-MIB
     INCLUDES { 
        ds1NearEndConfigGroup,
        ds1NearEndStatisticsGroup,
		ds1NearEndOptionalConfigGroup,
		ds1ChanMappingGroup 
     }
     VARIATION dsx1LineType
     ACCESS read-only
     DESCRIPTION "Command line interface(CLI) is used to set this feature."

     VARIATION dsx1LineCoding
     ACCESS read-only
     DESCRIPTION "Command line interface(CLI) is used to set this feature."

     VARIATION dsx1SendCode
     ACCESS read-only
     DESCRIPTION "Command line interface(CLI) is used to set this feature."

     VARIATION dsx1CircuitIdentifier
     ACCESS read-only
     DESCRIPTION "Command line interface(CLI) is used to set this feature."

     VARIATION dsx1LoopbackConfig
     ACCESS read-only
     DESCRIPTION "Command line interface(CLI) is used to set this feature."

     VARIATION dsx1SignalMode
     ACCESS read-only
     DESCRIPTION "Command line interface(CLI) is used to set this feature."

     VARIATION dsx1TransmitClockSource
     ACCESS read-only
     DESCRIPTION "Command line interface(CLI) is used to set this feature."

     VARIATION dsx1Fdl
     ACCESS read-only
     DESCRIPTION "Command line interface(CLI) is used to set this feature."

     VARIATION dsx1LineLength
     ACCESS read-only
     DESCRIPTION "Command line interface(CLI) is used to set this feature."

     VARIATION dsx1LineStatusChangeTrapEnable
     ACCESS read-only
     DESCRIPTION "Command line interface(CLI) is used to set this feature."

     VARIATION dsx1Channelization
     ACCESS read-only
     DESCRIPTION "Command line interface(CLI) is used to set this feature."

     -- ********************* ************ ************ *************** ***
     -- RFC 2496
     SUPPORTS DS3-MIB
     INCLUDES { 
        ds3NearEndConfigGroup,
        ds3NearEndStatisticsGroup,
		ds3NearEndOptionalConfigGroup 
     }

     VARIATION dsx3LineType
     ACCESS read-only
     DESCRIPTION "Command line interface(CLI) is used to set this feature."

     VARIATION dsx3LineCoding
     ACCESS read-only
     DESCRIPTION "Command line interface(CLI) is used to set this feature."

     VARIATION dsx3SendCode
     ACCESS read-only
     DESCRIPTION "Command line interface(CLI) is used to set this feature."

     VARIATION dsx3CircuitIdentifier
     ACCESS read-only
     DESCRIPTION "Command line interface(CLI) is used to set this feature."

     VARIATION dsx3LoopbackConfig
     ACCESS read-only
     DESCRIPTION "Command line interface(CLI) is used to set this feature."

     VARIATION dsx3TransmitClockSource
     ACCESS read-only
     DESCRIPTION "Command line interface(CLI) is used to set this feature."

     VARIATION dsx3LineLength
     ACCESS read-only
     DESCRIPTION "Command line interface(CLI) is used to set this feature."

     VARIATION dsx3LineStatusChangeTrapEnable
     ACCESS read-only
     DESCRIPTION "Command line interface(CLI) is used to set this feature."

     VARIATION dsx3Channelization
     ACCESS read-only
     DESCRIPTION "Command line interface(CLI) is used to set this feature."

     VARIATION dsx3Ds1ForRemoteLoop
     ACCESS read-only
     DESCRIPTION "Command line interface(CLI) is used to set this feature."

     -- ********************* ************ ************ *************** ***
     -- RFC 1595
     SUPPORTS SONET-MIB
     INCLUDES { 
        sonetMediumStuff, 
        sonetSectionStuff,
        sonetLineStuff,
        sonetFarEndLineStuff,
        sonetPathStuff,
        sonetFarEndPathStuff
     }

     -- ATM OC3 line cards with  modular physical port (MODPHY) have above instrumentation
     -- POS OC3/12 line cards do not yet support the SONET-MIB

     -- ********************* ************ ************ *************** ***
     -- RFC 1695
     SUPPORTS ATM-MIB
     INCLUDES { 
        atmInterfaceConfGroup,
        atmTrafficDescrGroup,
        atmInterfaceDs3PlcpGroup,
        atmInterfaceTCGroup,
        atmVccTerminationGroup,
        aal5VccGroup
     }    

     VARIATION atmInterfaceMaxVpcs
     ACCESS read-only 
     DESCRIPTION "This object is not settable"

     VARIATION atmInterfaceMaxVccs
     ACCESS read-only
     DESCRIPTION "This object is not settable"

     VARIATION atmInterfaceMaxActiveVpiBits
     ACCESS read-only
     DESCRIPTION "This object is not settable"
     
     VARIATION atmInterfaceMaxActiveVciBits
     ACCESS read-only
     DESCRIPTION "This object is not settable"

     VARIATION atmInterfaceIlmiVpi
     ACCESS not-implemented
     DESCRIPTION "Device does not support Ilmi"

     VARIATION atmInterfaceIlmiVci
     ACCESS not-implemented
     DESCRIPTION "Device does not support Ilmi"

     VARIATION atmInterfaceMyNeighborIpAddress
     ACCESS not-implemented
     DESCRIPTION "Firmware does not support this"

     VARIATION atmInterfaceMyNeighborIfName
     ACCESS not-implemented
     DESCRIPTION "Firmware does not support this"

     VARIATION atmTrafficDescrParam1
     ACCESS read-only
     DESCRIPTION "Command line interface(CLI) is used to set this feature"

     VARIATION atmTrafficDescrParam2
     ACCESS read-only
     DESCRIPTION "Command line interface(CLI) is used to set this feature"
     
     VARIATION atmTrafficDescrParam3
     ACCESS read-only
     DESCRIPTION "Command line interface(CLI) is used to set this feature"

     VARIATION atmTrafficDescrParam4
     ACCESS read-only
     DESCRIPTION "Command line interface(CLI) is used to set this feature"

     VARIATION atmTrafficDescrParam5
     ACCESS read-only
     DESCRIPTION "Command line interface(CLI) is used to set this feature"

     VARIATION atmTrafficQoSClass
     ACCESS read-only
     DESCRIPTION "Command line interface(CLI) is used to set this feature"

     VARIATION atmTrafficDescrRowStatus
     ACCESS not-implemented
     DESCRIPTION "Table is read-only"

     VARIATION atmInterfaceDs3PlcpSEFSs
     ACCESS not-implemented
     DESCRIPTION "Firmware does not support this"

     VARIATION atmInterfaceDs3PlcpAlarmState
     ACCESS not-implemented
     DESCRIPTION "Firmware does not support this"

     VARIATION atmInterfaceDs3PlcpUASs
     ACCESS not-implemented
     DESCRIPTION "Firmware does not support this"

     VARIATION atmInterfaceOCDEvents
     ACCESS not-implemented
     DESCRIPTION "Firmware does not support this"

     VARIATION atmInterfaceTCAlarmState
     ACCESS not-implemented
     DESCRIPTION "Firmware does not support this"

     VARIATION atmVclAdminStatus
     ACCESS read-only
     DESCRIPTION "Command line interface(CLI) is used to set this feature"

     VARIATION atmVclReceiveTrafficDescrIndex
     ACCESS read-only
     DESCRIPTION "Memory address is used as the index, CLI is used to set this"

     VARIATION atmVclTransmitTrafficDescrIndex
     ACCESS read-only
     DESCRIPTION "Memory address is used as the index, CLI is used to set this"
        
     VARIATION atmVccAalType
     ACCESS read-only
     DESCRIPTION "This object is not settable"

     VARIATION atmVclRowStatus
     ACCESS read-only
     DESCRIPTION "This object is not settable"

     -- ********************* ************ ************ *************** ***
     -- RFC 2618
     SUPPORTS RADIUS-AUTH-CLIENT-MIB
     INCLUDES { 
          radiusAuthClientMIBGroup
     }

     -- ********************* ************ ************ *************** ***
     -- RFC 1757/2819
       SUPPORTS RMON-MIB
       INCLUDES { 
         
         rmonEtherStatsGroup,
         rmonHistoryControlGroup,
         rmonEthernetHistoryGroup,
         rmonAlarmGroup,
         rmonHostGroup,   -- requires flow bridging hardware mode enabled
         rmonHostTopNGroup, 
         rmonMatrixGroup, -- requires flow bridging hardware mode enabled
         rmonFilterGroup,
         rmonPacketCaptureGroup,
         rmonEventGroup,
         rmonNotificationGroup
       }

     -- ********************* ************ ************ *************** ***
     -- RFC 2021
     SUPPORTS RMON2-MIB
     INCLUDES { 
        protocolDirectoryGroup,
        protocolDistributionGroup,
        addressMapGroup,
        nlHostGroup,
        nlMatrixGroup,
        alHostGroup,
        alMatrixGroup,
        usrHistoryGroup,
        probeInformationGroup,
        probeConfigurationGroup,
        rmon1EthernetEnhancementGroup
        -- rmon1EnhancementGroup supported except for filterProtocolDirDataLocalIndex,
        --  filterProtocolDirLocalIndex
     }
     VARIATION filterProtocolDirDataLocalIndex
     ACCESS not-implemented
     DESCRIPTION "Feature not available in this firmware version "

     VARIATION filterProtocolDirLocalIndex
     ACCESS not-implemented
     DESCRIPTION "Feature not available in this firmware version "

     -- NOTE: Sets to this mib are not persistent. RMON configuration
     -- may be done via CLI for persistence
     -- ********************* ************ ************ *************** ***
     -- From ietf vrrp mib Draft #9
     SUPPORTS VRRP-MIB
     INCLUDES { 
        vrrpOperGroup,
        vrrpStatsGroup,
        vrrpTrapGroup,
        vrrpNotificationGroup
     }
     VARIATION vrrpOperAdminState
     ACCESS read-only
     DESCRIPTION "Command line interface(CLI) is used to set this feature."

     VARIATION vrrpOperPriority
     ACCESS read-only
     DESCRIPTION "Command line interface(CLI) is used to set this feature."

     VARIATION vrrpOperPrimaryIpAddr
     ACCESS read-only
     DESCRIPTION "Command line interface(CLI) is used to set this feature."

     VARIATION vrrpOperAuthType
     ACCESS read-only
     DESCRIPTION "Command line interface(CLI) is used to set this feature."

     VARIATION vrrpOperAuthKey
     ACCESS read-only
     DESCRIPTION "Command line interface(CLI) is used to set this feature."

     VARIATION vrrpOperAdvertisementInterval
     ACCESS read-only
     DESCRIPTION "Command line interface(CLI) is used to set this feature."

     VARIATION vrrpOperPreemptMode
     ACCESS read-only
     DESCRIPTION "Command line interface(CLI) is used to set this feature."

     VARIATION vrrpOperProtocol
     ACCESS read-only
     DESCRIPTION "Command line interface(CLI) is used to set this feature."

     VARIATION vrrpOperRowStatus
     ACCESS read-only
     DESCRIPTION "Command line interface(CLI) is used to set this feature."

     VARIATION vrrpAssoIpAddrRowStatus
     ACCESS read-only
     DESCRIPTION "Command line interface(CLI) is used to set this feature."

     VARIATION vrrpTrapAuthFailure
     ACCESS not-implemented
     DESCRIPTION "TrapAuthFailure not implemented in this firmware version"

     -- ********************* ************ ************ *************** ***

     SUPPORTS CTRON-LFAP-MIB
     INCLUDES { 
        lfapConfGroupV40
     }

     -- ********************* ************ ************ *************** ***

     SUPPORTS CTRON-SSR-POLICY-MIB
     INCLUDES { 
         polGroupV11        
     }

     -- ********************* ************ ************ *************** ***

     SUPPORTS CTRON-SSR-CONFIG-MIB
     INCLUDES { 
         configGroup20
     }

     
     -- ********************* ************ ************ *************** ***

     SUPPORTS CTRON-SSR-HARDWARE-MIB
     INCLUDES { 
         hwConfGroupV30
     }

     -- ********************* ************ ************ *************** ***

     SUPPORTS CTRON-SSR-SERVICE-STATUS-MIB
     INCLUDES { 
         ssConfGroupV11
     }

     -- ********************* ************ ************ *************** ***

     SUPPORTS CTRON-SSR-CAPACITY-MIB
     INCLUDES { 
         capConfGroupV10
     }

     -- ********************* ************ ************ *************** ***

	 SUPPORTS DOCS-IF-MIB
	 INCLUDES {
         docsIfBasicGroup, 
		 docsIfCmtsGroup
	 }

	 VARIATION docsIfQosProfMaxTxBurst
	 ACCESS read-write
	 DESCRIPTION "This variable returns the value in bits/second rather than
	 mini-slots because this is the expected type by Cablelabs."

     -- ********************* ************ ************ *************** ***

     SUPPORTS DOCS-BPI-MIB
     INCLUDES {
	     docsBpiCmtsGroup
	 }

     VARIATION docsBpiCmtsDefaultAuthLifetime
     ACCESS read-write
     DESCRIPTION "For testing purposes, this variable has an increased
     numeric range from 1 to 6048000."

     VARIATION docsBpiCmtsDefaultTEKLifetime
     ACCESS read-write
     DESCRIPTION "For testing purposes, this variable has an increased
     numeric range from 1 to 604800."

     VARIATION docsBpiCmtsAuthCmLifetime
     ACCESS read-write
     DESCRIPTION "For testing purposes, this variable has an increased
     numeric range from 1 to 6048000."

     VARIATION docsBpiCmtsAuthCmGraceTime
     ACCESS read-write
     DESCRIPTION "For testing purposes, this variable has an increased
     numeric range from 1 to 1800."

     VARIATION docsBpiCmtsTEKLifetime
     ACCESS read-write
     DESCRIPTION "For testing purposes, this variable has an increased
     numeric range from 1 to 604800."

     VARIATION docsBpiCmtsTEKGraceTime
     ACCESS read-write
     DESCRIPTION "For testing purposes, this variable has an increased
     numeric range from 1 to 1800."

     -- ********************* ************ ************ *************** ***

     SUPPORTS RIVERSTONE-STP-MIB
     INCLUDES {
	     rsStpBaseGroup
	 }

     VARIATION rsStpStatus
	 ACCESS not-implemented
	 DESCRIPTION "STP cannot be disabled globally on RS devices"

   ::= { rsCapability 3 }

rs70x AGENT-CAPABILITIES 
  PRODUCT-RELEASE 
     "7.0.x"
  STATUS  current
  DESCRIPTION
     "Firmware Release 7.0.x for Riverstone  RS RapidOS product line.
	  The firmware supports RS 38000 in this release. New software 
      features include rate limiting enhancements and stackable
      VLANs. New MIBs include RFC 2674 P/Q Bridge MIB SETs and 
	  IEEE LAG MIB"
  REFERENCE 
     "http://www.riverstonenet.com/products"

     -- RFC 1907
     SUPPORTS SNMPv2-MIB
     INCLUDES { 
         systemGroup,
         snmpGroup, 
         snmpBasicNotificationsGroup,
         --  snmpSetGroup is not implemented, but is needed for SNMPv2-MIB compliance
         -- non mandatory groups
         snmpCommunityGroup,
         -- deprecated/obsolete support
         snmpObsoleteGroup
     }

     -- ********************* ************ ************ *************** ***
     -- RFC 2358
     SUPPORTS EtherLike-MIB
     INCLUDES { 
         etherStats100MbsGroup
     }

     -- ********************* ************ ************ *************** ***
     -- RFC 2233
     SUPPORTS IF-MIB
     INCLUDES { 
         ifGeneralInformationGroup, 
         ifStackGroup2,
         ifCounterDiscontinuityGroup,
         -- non mandatory groups
         ifFixedLengthGroup,
         ifHCFixedLengthGroup,
         ifPacketGroup,
         ifHCPacketGroup,
         ifVHCPacketGroup,
         ifRcvAddressGroup,
         -- deprecated/obsolete support
         ifOldObjectsGroup
     }
     VARIATION ifAlias
     ACCESS read-only
     DESCRIPTION "ifAlias is guarenteed to be unique across reboots. It takes the form Type : instance info
      for example: ifAlias.49 = IP interface: to-sc-BGPfeed or ifAlias.42 = VLAN: test1 or 
      ifAlias.35 = Physical port: et.14.5"

     VARIATION ifAdminStatus
     ACCESS read-only
     DESCRIPTION "For ifTypes corresponding to VLANs this object is read only."

     VARIATION ifLinkUpDownTrapEnable
     ACCESS read-only
     DESCRIPTION "For all ifTypes where ifConnectorPresent is not TRUE."

     VARIATION ifStackStatus
     ACCESS read-only
     DESCRIPTION "Command line interface(CLI) is used to change relationships."

     -- ********************* ************ ************ *************** ***
     -- RFC 2011
     SUPPORTS IP-MIB
     INCLUDES { 
         ipGroup,
         icmpGroup
     }
     VARIATION ipDefaultTTL
     ACCESS read-only
     DESCRIPTION "Command line interface(CLI) is used to change default ttl."

     -- ********************* ************ ************ *************** ***
     -- RFC 2096
     SUPPORTS IP-FORWARD-MIB
     INCLUDES { 
         ipForwardCidrRouteGroup
     }
     VARIATION ipCidrRouteIfIndex
     ACCESS read-only
     DESCRIPTION "Command line interface(CLI) is used to update Forwarding Information Base/FIB."

     VARIATION ipCidrRouteType
     ACCESS read-only
     DESCRIPTION "Command line interface(CLI) is used to update Forwarding Information Base/FIB."

     VARIATION ipCidrRouteInfo
     ACCESS read-only
     DESCRIPTION "Command line interface(CLI) is used to update Forwarding Information Base/FIB."

     VARIATION ipCidrRouteNextHopAS
     ACCESS read-only
     DESCRIPTION "Command line interface(CLI) is used to update Forwarding Information Base/FIB."

     VARIATION ipCidrRouteMetric1
     ACCESS read-only
     DESCRIPTION "Command line interface(CLI) is used to update Forwarding Information Base/FIB."

     VARIATION ipCidrRouteMetric2
     ACCESS read-only
     DESCRIPTION "Command line interface(CLI) is used to update Forwarding Information Base/FIB."

     VARIATION ipCidrRouteMetric3
     ACCESS read-only
     DESCRIPTION "Command line interface(CLI) is used to update Forwarding Information Base/FIB."

     VARIATION ipCidrRouteMetric4
     ACCESS read-only
     DESCRIPTION "Command line interface(CLI) is used to update Forwarding Information Base/FIB."

     VARIATION ipCidrRouteMetric5
     ACCESS read-only
     DESCRIPTION "Command line interface(CLI) is used to update Forwarding Information Base/FIB."

     VARIATION ipCidrRouteStatus
     ACCESS read-only
     DESCRIPTION "Command line interface(CLI) is used to update Forwarding Information Base/FIB."

     -- ********************* ************ ************ *************** ***
     -- RFC 2013
     SUPPORTS UDP-MIB
     INCLUDES { 
         udpGroup         
     }

     -- ********************* ************ ************ *************** ***
     -- RFC 2012
     SUPPORTS TCP-MIB
     INCLUDES { 
         tcpGroup         
     }
     VARIATION tcpConnState
     ACCESS read-only
     DESCRIPTION "Command line interface(CLI) is used to kill tcp sessions."

     -- ********************* ************ ************ *************** ***
     --  RFC 1657 
--     SUPPORTS BGP4-MIB
--     INCLUDES { 
--         This is an smiv1 mib, all objects read only. Specify in device config file to enable this mib.
--     }

     -- ********************* ************ ************ *************** ***
     -- RFC 1850    
     -- Specify in device config file to enable this mib.
     SUPPORTS OSPF-MIB
     INCLUDES { 
         ospfBasicGroup,
         ospfAreaGroup,
         ospfStubAreaGroup,
         ospfIfGroup,
         ospfIfMetricGroup,
         ospfVirtIfGroup,
         ospfNbrGroup,
         ospfVirtNbrGroup,
         ospfAreaAggregateGroup
     }
     VARIATION ospfRouterId
     ACCESS read-only
     DESCRIPTION "Command line interface(CLI) is used to set router id."

     VARIATION ospfAdminStat
     ACCESS read-only
     DESCRIPTION "Command line interface(CLI) is used to set ospf state."

     VARIATION ospfTOSSupport
     ACCESS read-only
     DESCRIPTION "Command line interface(CLI) is used to set ospf TOS support."

     VARIATION ospfExtLsdbLimit
     ACCESS read-only
     DESCRIPTION "Command line interface(CLI) is used to set ospf Lsdb Limit."

     VARIATION ospfMulticastExtensions
     ACCESS read-only
     DESCRIPTION "Command line interface(CLI) is used to set ospf multicast extensions."

     VARIATION ospfExitOverflowInterval
     ACCESS read-only
     DESCRIPTION "Command line interface(CLI) is used to set ospf exit overflow interval."

     VARIATION ospfDemandExtensions
     ACCESS read-only
     DESCRIPTION "Command line interface(CLI) is used to set ospf demand extensions."

     VARIATION ospfAuthType
     ACCESS read-only
     DESCRIPTION "Command line interface(CLI) is used to set ospf authorisation types."

     VARIATION ospfImportAsExtern
     ACCESS read-only
     DESCRIPTION "Command line interface(CLI) is used to set ospf Import AS external routes."

     VARIATION ospfAreaSummary
     ACCESS read-only
     DESCRIPTION "Command line interface(CLI) is used to set ospf area summary importation."

     VARIATION ospfAreaStatus
     ACCESS read-only
     DESCRIPTION "Command line interface(CLI) is used to create & delete ospf areas."

     VARIATION ospfStubMetric
     ACCESS read-only
     DESCRIPTION "Command line interface(CLI) is used to set ospf area stub metric."

     VARIATION ospfStubStatus
     ACCESS read-only
     DESCRIPTION "Command line interface(CLI) is used to create & delete stub areas."

     VARIATION ospfStubMetricType
     ACCESS read-only
     DESCRIPTION "Command line interface(CLI) is used to set ospf stub metric type."

     VARIATION ospfAreaRangeMask
     ACCESS read-only
     DESCRIPTION "Command line interface(CLI) is used to set ospf area range mask."

     VARIATION ospfAreaRangeStatus
     ACCESS read-only
     DESCRIPTION "Command line interface(CLI) is used to create & delete ranges."

     VARIATION ospfAreaRangeEffect
     ACCESS read-only
     DESCRIPTION "Command line interface(CLI) is used to set area range effect."

     VARIATION ospfHostMetric
     ACCESS read-only
     DESCRIPTION "Command line interface(CLI) is used to set host metric."

     VARIATION ospfHostStatus
     ACCESS read-only
     DESCRIPTION "Command line interface(CLI) is used to create & delete hosts."

     VARIATION ospfIfAreaId
     ACCESS read-only
     DESCRIPTION "Command line interface(CLI) is used to set Interface area id."

     VARIATION ospfIfType
     ACCESS read-only
     DESCRIPTION "Command line interface(CLI) is used to set Interface type."

     VARIATION ospfIfAdminStat
     ACCESS read-only
     DESCRIPTION "Command line interface(CLI) is used to set Interface admin status."

     VARIATION ospfIfRtrPriority
     ACCESS read-only
     DESCRIPTION "Command line interface(CLI) is used to set interface router priority."

     VARIATION ospfIfTransitDelay
     ACCESS read-only
     DESCRIPTION "Command line interface(CLI) is used to set interface transit delay."

     VARIATION ospfIfRetransInterval
     ACCESS read-only
     DESCRIPTION "Command line interface(CLI) is used to set interface retransmission interval."

     VARIATION ospfIfHelloInterval
     ACCESS read-only
     DESCRIPTION "Command line interface(CLI) is used to set hello interval."

     VARIATION ospfIfRtrDeadInterval
     ACCESS read-only
     DESCRIPTION "Command line interface(CLI) is used to set dead interval."

     VARIATION ospfIfPollInterval
     ACCESS read-only
     DESCRIPTION "Command line interface(CLI) is used to set poll interval."

     VARIATION ospfIfAuthKey
     ACCESS read-only
     DESCRIPTION "Command line interface(CLI) is used to set interface auth key."

     VARIATION ospfIfStatus
     ACCESS read-only
     DESCRIPTION "Command line interface(CLI) is used to create & delete interfaces."

     VARIATION ospfIfMulticastForwarding
     ACCESS read-only
     DESCRIPTION "Command line interface(CLI) is used to set multicast fwd."

     VARIATION ospfIfDemand
     ACCESS read-only
     DESCRIPTION "Command line interface(CLI) is used to set this attribute."

     VARIATION ospfIfAuthType
     ACCESS read-only
     DESCRIPTION "Command line interface(CLI) is used to set this feature."

     VARIATION ospfIfMetricValue
     ACCESS read-only
     DESCRIPTION "Command line interface(CLI) is used to set this feature."

     VARIATION ospfVirtIfTransitDelay
     ACCESS read-only
     DESCRIPTION "Command line interface(CLI) is used to set this feature."

     VARIATION ospfVirtIfRetransInterval
     ACCESS read-only
     DESCRIPTION "Command line interface(CLI) is used to set this feature."

     VARIATION ospfVirtIfHelloInterval
     ACCESS read-only
     DESCRIPTION "Command line interface(CLI) is used to set this feature."

     VARIATION ospfVirtIfRtrDeadInterval
     ACCESS read-only
     DESCRIPTION "Command line interface(CLI) is used to set this feature."

     VARIATION ospfVirtIfAuthKey
     ACCESS read-only
     DESCRIPTION "Command line interface(CLI) is used to set this feature."

     VARIATION ospfVirtIfStatus
     ACCESS read-only
     DESCRIPTION "Command line interface(CLI) is used to set this feature."

     VARIATION ospfVirtIfAuthType
     ACCESS read-only
     DESCRIPTION "Command line interface(CLI) is used to set this feature."

     VARIATION ospfNbrPriority
     ACCESS read-only
     DESCRIPTION "Command line interface(CLI) is used to set this feature."

     VARIATION ospfNbmaNbrStatus
     ACCESS read-only
     DESCRIPTION "Command line interface(CLI) is used to set this feature."

     VARIATION ospfAreaAggregateStatus
     ACCESS read-only
     DESCRIPTION "Command line interface(CLI) is used to set this feature."

     VARIATION ospfAreaAggregateEffect
     ACCESS read-only
     DESCRIPTION "Command line interface(CLI) is used to set this feature."

     SUPPORTS OSPF-TRAP-MIB
     INCLUDES { 
         ospfTrapControlGroup
     }

     -- ********************* ************ ************ *************** ***
     -- RFC 1724
     -- Specify in device config file to enable this mib.
     SUPPORTS RIPv2-MIB
     INCLUDES { 
         rip2GlobalGroup,
         rip2IfStatGroup,
         rip2IfConfGroup,
         rip2PeerGroup
     }
     VARIATION rip2IfStatStatus
     ACCESS read-only
     DESCRIPTION "Command line interface(CLI) is used to set this feature."
   
     VARIATION rip2IfConfDomain
     ACCESS read-only
     DESCRIPTION "Command line interface(CLI) is used to set this feature."

     VARIATION rip2IfConfAuthType
     ACCESS read-only
     DESCRIPTION "Command line interface(CLI) is used to set this feature."

     VARIATION rip2IfConfAuthKey
     ACCESS read-only
     DESCRIPTION "Command line interface(CLI) is used to set this feature."

     VARIATION rip2IfConfSend
     ACCESS read-only
     DESCRIPTION "Command line interface(CLI) is used to set this feature."

     VARIATION rip2IfConfReceive
     ACCESS read-only
     DESCRIPTION "Command line interface(CLI) is used to set this feature."

     VARIATION rip2IfConfDefaultMetric
     ACCESS read-only
     DESCRIPTION "Command line interface(CLI) is used to set this feature."

     VARIATION rip2IfConfStatus
     ACCESS read-only
     DESCRIPTION "Command line interface(CLI) is used to set this feature."

     VARIATION rip2IfConfSrcAddress
     ACCESS read-only
     DESCRIPTION "Command line interface(CLI) is used to set this feature."

     -- ********************* ************ ************ *************** ***
     -- RFC 1493
--    SUPPORTS BRIDGE-MIB
--    INCLUDES { 
--       smiv1 mib
--    }

     -- ********************* ************ ************ *************** ***
     -- RFC 2674
     -- Updated 09/20/00

     SUPPORTS Q-BRIDGE-MIB
     INCLUDES {
        qBridgeBaseGroup,
        qBridgeVlanGroup,
        qBridgeVlanStaticGroup,
        qBridgePortGroup,
        qBridgeFdbUnicastGroup,
        qBridgeFdbMulticastGroup
     }     

     --qBridgeStaticVlanTable
     --Implicit Vlans are not accounted by SNMP.
     --Only 10 Non Active rows can be present in the temp table . If the user
     --tries to create more than 10 Non Active rows, BAD-VALUE will be returned.
     --Vlan name has to be specified when creating a vlan, apart from the vlan id.
     --This is a limitation of the RS family (RFC does not ask for the vlan name.)

     VARIATION dot1qVlanStaticUntaggedPorts
     ACCESS read-only 
     DESCRIPTION "No hardware support"

     VARIATION dot1qVlanStaticEgressPorts
     ACCESS read-write
     DESCRIPTION "Apart from permanent entries , non permanent entries ( 
	        in the active config and not in the startup config) will 
	        also be displayed."

     

     VARIATION dot1qPvid
     ACCESS read-write
     DESCRIPTION  "For Trunk-Port, PVID cannot be set. Trunk ports can be in 
	         more than one vlan (apart from being in default vlan). 
	         Get reports the default vlan ID."

     VARIATION dot1qPortGvrpStatus
     ACCESS read-only
     DESCRIPTION  "CLI is used to set this"

     -- ********************* ************ ************ *************** ***
        -- RFC 2674
        -- Update 09/26/00

        SUPPORTS P-BRIDGE-MIB
        INCLUDES {
            pBridgeExtCapGroup,
            pBridgeDevicePriorityGroup,
            pBridgeDefaultPriorityGroup,
            pBridgePriorityGroup,
	        pBridgePortGarpGroup
        }

-- pBridgeExtCapGroup: dot1dDeviceCapabilities :: 
-- dot1dExtendedFilteringServices ,dot1qConfigurablePvidTagging ,
-- dot1qSVLCapable,dot1qHybridCapable  not supported.


     VARIATION dot1dTrafficClassesEnabled
     ACCESS read-only
     DESCRIPTION "This is not settable through SNMP. However this can be
                  set using CLI by mapping all 1p priority levels to the
	        same traffic class."


-- pBridgeDefaultPriorityGroup: dot1dPortDefaultUserPriority If the user 
--			  configures default priority on a port and later
--			  configures a priority for a MAC / VLAN pair
--			  using CLI, CLI would report a conflict.

--			  When this variable is set through snmp, the 
--			  name used for the qos command would be 
--			  "snmp-priority-#portnum". This would be the 
--			  case, even if a priority was configured 
--			  through the cli (using qos set l2 command)
--			  with a different name (say priority-#portnum),
--			  and then modified through snmp.


     VARIATION dot1dPortNumTrafficClasses
     ACCESS read-only
     DESCRIPTION "This value is not settable. Setting this value is optional		        only."


     VARIATION dot1dPortGarpJoinTime
     ACCESS read-only
     DESCRIPTION "This is not settable."


     VARIATION dot1dPortGarpLeaveTime
     ACCESS read-only
     DESCRIPTION "This is not settable."


     VARIATION dot1dPortGarpLeaveAllTime
     ACCESS read-only
     DESCRIPTION "This is not settable."

     -- ********************* ************ ************ *************** ***
     -- RFC 2115
     SUPPORTS FRAME-RELAY-DTE-MIB
     INCLUDES { 
       frPortGroup, 
       frCircuitGroup,
       frErrGroup,
       frTrapGroup
     }
     VARIATION frDlcmiState
     ACCESS read-only
     DESCRIPTION "Command line interface(CLI) is used to set this feature."

     VARIATION frDlcmiAddress
     ACCESS read-only
     DESCRIPTION "Command line interface(CLI) is used to set this feature."

     VARIATION frDlcmiAddressLen
     ACCESS read-only
     DESCRIPTION "Command line interface(CLI) is used to set this feature."

     VARIATION frDlcmiPollingInterval
     ACCESS read-only
     DESCRIPTION "Command line interface(CLI) is used to set this feature."
     
     VARIATION frDlcmiFullEnquiryInterval
     ACCESS read-only
     DESCRIPTION "Command line interface(CLI) is used to set this feature."

     VARIATION frDlcmiErrorThreshold
     ACCESS read-only
     DESCRIPTION "Command line interface(CLI) is used to set this feature."

     VARIATION frDlcmiMonitoredEvents
     ACCESS read-only
     DESCRIPTION "Command line interface(CLI) is used to set this feature."

     VARIATION frDlcmiMaxSupportedVCs
     ACCESS read-only
     DESCRIPTION "Command line interface(CLI) is used to set this feature."

     VARIATION frDlcmiMulticast
     ACCESS read-only
     DESCRIPTION "Command line interface(CLI) is used to set this feature."

     VARIATION frDlcmiRowStatus
     ACCESS read-only
     DESCRIPTION "Command line interface(CLI) is used to create & delete dlcmi's."

     VARIATION frCircuitState
     ACCESS read-only
     DESCRIPTION "Command line interface(CLI) is used to set this feature."

     VARIATION frCircuitCommittedBurst
     ACCESS read-only
     DESCRIPTION "Command line interface(CLI) is used to set this feature."

     VARIATION frCircuitExcessBurst
     ACCESS read-only
     DESCRIPTION "Command line interface(CLI) is used to set this feature."

     VARIATION frCircuitThroughput
     ACCESS read-only
     DESCRIPTION "Command line interface(CLI) is used to set this feature."

     VARIATION frCircuitMulticast
     ACCESS read-only
     DESCRIPTION "Command line interface(CLI) is used to set this feature."

     VARIATION frCircuitLogicalIfIndex
     ACCESS read-only
     DESCRIPTION "Command line interface(CLI) is used to set this feature."

     VARIATION frCircuitRowStatus
     ACCESS read-only
     DESCRIPTION "Command line interface(CLI) is used to set this feature."

     -- ********************* ************ ************ *************** ***
       -- RFC 1471
--     SUPPORTS PPP-LCP-MIB
--     INCLUDES { 
--       smiv1 mib - read only 
--     }

     -- ********************* ************ ************ *************** ***
       -- RFC 1472
--     SUPPORTS PPP-SEC-MIB
--     INCLUDES { 
--      smiv1 mib - read only
--     }

     -- ********************* ************ ************ *************** ***
       -- RFC 1473
--     SUPPORTS PPP-IP-NCP-MIB
--     INCLUDES { 
--       smiv1 mib - read only
--     }

     -- ********************* ************ ************ *************** ***
       -- RFC 1474
--     SUPPORTS PPP-BRIDGE-NCP-MIB
--     INCLUDES { 
--       smiv1 mib - read only
--     }

     -- ********************* ************ ************ *************** ***
	 -- RFC 2494
	 SUPPORTS DS0-MIB
	 INCLUDES {
		ds0ConfigGroup
	 }

     -- ********************* ************ ************ *************** ***
	 -- RFC 2494
	 SUPPORTS DS0BUNDLE-MIB
	 INCLUDES {
		ds0BundleConfigGroup
	 }

     -- ********************* ************ ************ *************** ***
     -- RFC 2495
     SUPPORTS DS1-MIB
     INCLUDES { 
        ds1NearEndConfigGroup,
        ds1NearEndStatisticsGroup,
		ds1NearEndOptionalConfigGroup,
		ds1ChanMappingGroup 
     }
     VARIATION dsx1LineType
     ACCESS read-only
     DESCRIPTION "Command line interface(CLI) is used to set this feature."

     VARIATION dsx1LineCoding
     ACCESS read-only
     DESCRIPTION "Command line interface(CLI) is used to set this feature."

     VARIATION dsx1SendCode
     ACCESS read-only
     DESCRIPTION "Command line interface(CLI) is used to set this feature."

     VARIATION dsx1CircuitIdentifier
     ACCESS read-only
     DESCRIPTION "Command line interface(CLI) is used to set this feature."

     VARIATION dsx1LoopbackConfig
     ACCESS read-only
     DESCRIPTION "Command line interface(CLI) is used to set this feature."

     VARIATION dsx1SignalMode
     ACCESS read-only
     DESCRIPTION "Command line interface(CLI) is used to set this feature."

     VARIATION dsx1TransmitClockSource
     ACCESS read-only
     DESCRIPTION "Command line interface(CLI) is used to set this feature."

     VARIATION dsx1Fdl
     ACCESS read-only
     DESCRIPTION "Command line interface(CLI) is used to set this feature."

     VARIATION dsx1LineLength
     ACCESS read-only
     DESCRIPTION "Command line interface(CLI) is used to set this feature."

     VARIATION dsx1LineStatusChangeTrapEnable
     ACCESS read-only
     DESCRIPTION "Command line interface(CLI) is used to set this feature."

     VARIATION dsx1Channelization
     ACCESS read-only
     DESCRIPTION "Command line interface(CLI) is used to set this feature."

     -- ********************* ************ ************ *************** ***
     -- RFC 2496
     SUPPORTS DS3-MIB
     INCLUDES { 
        ds3NearEndConfigGroup,
        ds3NearEndStatisticsGroup,
		ds3NearEndOptionalConfigGroup 
     }

     VARIATION dsx3LineType
     ACCESS read-only
     DESCRIPTION "Command line interface(CLI) is used to set this feature."

     VARIATION dsx3LineCoding
     ACCESS read-only
     DESCRIPTION "Command line interface(CLI) is used to set this feature."

     VARIATION dsx3SendCode
     ACCESS read-only
     DESCRIPTION "Command line interface(CLI) is used to set this feature."

     VARIATION dsx3CircuitIdentifier
     ACCESS read-only
     DESCRIPTION "Command line interface(CLI) is used to set this feature."

     VARIATION dsx3LoopbackConfig
     ACCESS read-only
     DESCRIPTION "Command line interface(CLI) is used to set this feature."

     VARIATION dsx3TransmitClockSource
     ACCESS read-only
     DESCRIPTION "Command line interface(CLI) is used to set this feature."

     VARIATION dsx3LineLength
     ACCESS read-only
     DESCRIPTION "Command line interface(CLI) is used to set this feature."

     VARIATION dsx3LineStatusChangeTrapEnable
     ACCESS read-only
     DESCRIPTION "Command line interface(CLI) is used to set this feature."

     VARIATION dsx3Channelization
     ACCESS read-only
     DESCRIPTION "Command line interface(CLI) is used to set this feature."

     VARIATION dsx3Ds1ForRemoteLoop
     ACCESS read-only
     DESCRIPTION "Command line interface(CLI) is used to set this feature."

     -- ********************* ************ ************ *************** ***
     -- RFC 1595
     SUPPORTS SONET-MIB
     INCLUDES { 
        sonetMediumStuff, 
        sonetSectionStuff,
        sonetLineStuff,
        sonetFarEndLineStuff,
        sonetPathStuff,
        sonetFarEndPathStuff
     }

     -- ATM OC3 line cards with  modular physical port (MODPHY) have above instrumentation
     -- POS OC3/12 line cards do not yet support the SONET-MIB

     -- ********************* ************ ************ *************** ***
     -- RFC 1695
     SUPPORTS ATM-MIB
     INCLUDES { 
        atmInterfaceConfGroup,
        atmTrafficDescrGroup,
        atmInterfaceDs3PlcpGroup,
        atmInterfaceTCGroup,
        atmVccTerminationGroup,
        aal5VccGroup
     }    

     VARIATION atmInterfaceMaxVpcs
     ACCESS read-only 
     DESCRIPTION "This object is not settable"

     VARIATION atmInterfaceMaxVccs
     ACCESS read-only
     DESCRIPTION "This object is not settable"

     VARIATION atmInterfaceMaxActiveVpiBits
     ACCESS read-only
     DESCRIPTION "This object is not settable"
     
     VARIATION atmInterfaceMaxActiveVciBits
     ACCESS read-only
     DESCRIPTION "This object is not settable"

     VARIATION atmInterfaceIlmiVpi
     ACCESS not-implemented
     DESCRIPTION "Device does not support Ilmi"

     VARIATION atmInterfaceIlmiVci
     ACCESS not-implemented
     DESCRIPTION "Device does not support Ilmi"

     VARIATION atmInterfaceMyNeighborIpAddress
     ACCESS not-implemented
     DESCRIPTION "Firmware does not support this"

     VARIATION atmInterfaceMyNeighborIfName
     ACCESS not-implemented
     DESCRIPTION "Firmware does not support this"

     VARIATION atmTrafficDescrParam1
     ACCESS read-only
     DESCRIPTION "Command line interface(CLI) is used to set this feature"

     VARIATION atmTrafficDescrParam2
     ACCESS read-only
     DESCRIPTION "Command line interface(CLI) is used to set this feature"
     
     VARIATION atmTrafficDescrParam3
     ACCESS read-only
     DESCRIPTION "Command line interface(CLI) is used to set this feature"

     VARIATION atmTrafficDescrParam4
     ACCESS read-only
     DESCRIPTION "Command line interface(CLI) is used to set this feature"

     VARIATION atmTrafficDescrParam5
     ACCESS read-only
     DESCRIPTION "Command line interface(CLI) is used to set this feature"

     VARIATION atmTrafficQoSClass
     ACCESS read-only
     DESCRIPTION "Command line interface(CLI) is used to set this feature"

     VARIATION atmTrafficDescrRowStatus
     ACCESS not-implemented
     DESCRIPTION "Table is read-only"

     VARIATION atmInterfaceDs3PlcpSEFSs
     ACCESS not-implemented
     DESCRIPTION "Firmware does not support this"

     VARIATION atmInterfaceDs3PlcpAlarmState
     ACCESS not-implemented
     DESCRIPTION "Firmware does not support this"

     VARIATION atmInterfaceDs3PlcpUASs
     ACCESS not-implemented
     DESCRIPTION "Firmware does not support this"

     VARIATION atmInterfaceOCDEvents
     ACCESS not-implemented
     DESCRIPTION "Firmware does not support this"

     VARIATION atmInterfaceTCAlarmState
     ACCESS not-implemented
     DESCRIPTION "Firmware does not support this"

     VARIATION atmVclAdminStatus
     ACCESS read-only
     DESCRIPTION "Command line interface(CLI) is used to set this feature"

     VARIATION atmVclReceiveTrafficDescrIndex
     ACCESS read-only
     DESCRIPTION "Memory address is used as the index, CLI is used to set this"

     VARIATION atmVclTransmitTrafficDescrIndex
     ACCESS read-only
     DESCRIPTION "Memory address is used as the index, CLI is used to set this"
        
     VARIATION atmVccAalType
     ACCESS read-only
     DESCRIPTION "This object is not settable"

     VARIATION atmVclRowStatus
     ACCESS read-only
     DESCRIPTION "This object is not settable"

     -- ********************* ************ ************ *************** ***
     -- RFC 2618
     SUPPORTS RADIUS-AUTH-CLIENT-MIB
     INCLUDES { 
          radiusAuthClientMIBGroup
     }

     -- ********************* ************ ************ *************** ***
     -- RFC 1757/2819
       SUPPORTS RMON-MIB
       INCLUDES { 
         
         rmonEtherStatsGroup,
         rmonHistoryControlGroup,
         rmonEthernetHistoryGroup,
         rmonAlarmGroup,
         rmonHostGroup,   -- requires flow bridging hardware mode enabled
         rmonHostTopNGroup, 
         rmonMatrixGroup, -- requires flow bridging hardware mode enabled
         rmonFilterGroup,
         rmonPacketCaptureGroup,
         rmonEventGroup,
         rmonNotificationGroup
       }

     -- ********************* ************ ************ *************** ***
     -- RFC 2021
     SUPPORTS RMON2-MIB
     INCLUDES { 
        protocolDirectoryGroup,
        protocolDistributionGroup,
        addressMapGroup,
        nlHostGroup,
        nlMatrixGroup,
        alHostGroup,
        alMatrixGroup,
        usrHistoryGroup,
        probeInformationGroup,
        probeConfigurationGroup,
        rmon1EthernetEnhancementGroup
        -- rmon1EnhancementGroup supported except for filterProtocolDirDataLocalIndex,
        --  filterProtocolDirLocalIndex
     }
     VARIATION filterProtocolDirDataLocalIndex
     ACCESS not-implemented
     DESCRIPTION "Feature not available in this firmware version "

     VARIATION filterProtocolDirLocalIndex
     ACCESS not-implemented
     DESCRIPTION "Feature not available in this firmware version "

     -- NOTE: Sets to this mib are not persistent. RMON configuration
     -- may be done via CLI for persistence
     -- ********************* ************ ************ *************** ***
     -- From ietf vrrp mib Draft #9
     SUPPORTS VRRP-MIB
     INCLUDES { 
        vrrpOperGroup,
        vrrpStatsGroup,
        vrrpTrapGroup,
        vrrpNotificationGroup
     }
     VARIATION vrrpOperAdminState
     ACCESS read-only
     DESCRIPTION "Command line interface(CLI) is used to set this feature."

     VARIATION vrrpOperPriority
     ACCESS read-only
     DESCRIPTION "Command line interface(CLI) is used to set this feature."

     VARIATION vrrpOperPrimaryIpAddr
     ACCESS read-only
     DESCRIPTION "Command line interface(CLI) is used to set this feature."

     VARIATION vrrpOperAuthType
     ACCESS read-only
     DESCRIPTION "Command line interface(CLI) is used to set this feature."

     VARIATION vrrpOperAuthKey
     ACCESS read-only
     DESCRIPTION "Command line interface(CLI) is used to set this feature."

     VARIATION vrrpOperAdvertisementInterval
     ACCESS read-only
     DESCRIPTION "Command line interface(CLI) is used to set this feature."

     VARIATION vrrpOperPreemptMode
     ACCESS read-only
     DESCRIPTION "Command line interface(CLI) is used to set this feature."

     VARIATION vrrpOperProtocol
     ACCESS read-only
     DESCRIPTION "Command line interface(CLI) is used to set this feature."

     VARIATION vrrpOperRowStatus
     ACCESS read-only
     DESCRIPTION "Command line interface(CLI) is used to set this feature."

     VARIATION vrrpAssoIpAddrRowStatus
     ACCESS read-only
     DESCRIPTION "Command line interface(CLI) is used to set this feature."

     VARIATION vrrpTrapAuthFailure
     ACCESS not-implemented
     DESCRIPTION "TrapAuthFailure not implemented in this firmware version"

     -- ********************* ************ ************ *************** ***

     SUPPORTS CTRON-LFAP-MIB
     INCLUDES { 
        lfapConfGroupV40
     }

     -- ********************* ************ ************ *************** ***

     SUPPORTS CTRON-SSR-POLICY-MIB
     INCLUDES { 
         polGroupV11        
     }

     -- ********************* ************ ************ *************** ***

     SUPPORTS CTRON-SSR-CONFIG-MIB
     INCLUDES { 
         configGroup20
     }

     
     -- ********************* ************ ************ *************** ***

     SUPPORTS CTRON-SSR-HARDWARE-MIB
     INCLUDES { 
         hwConfGroupV30
     }

     -- ********************* ************ ************ *************** ***

     SUPPORTS CTRON-SSR-SERVICE-STATUS-MIB
     INCLUDES { 
         ssConfGroupV11
     }

     -- ********************* ************ ************ *************** ***

     SUPPORTS CTRON-SSR-CAPACITY-MIB
     INCLUDES { 
         capConfGroupV10
     }

     -- ********************* ************ ************ *************** ***

	 SUPPORTS DOCS-IF-MIB
	 INCLUDES {
         docsIfBasicGroup, 
		 docsIfCmtsGroup
	 }

	 VARIATION docsIfQosProfMaxTxBurst
	 ACCESS read-write
	 DESCRIPTION "This variable returns the value in bits/second rather than
	 mini-slots because this is the expected type by Cablelabs."

     -- ********************* ************ ************ *************** ***

     SUPPORTS DOCS-BPI-MIB
     INCLUDES {
	     docsBpiCmtsGroup
	 }

     VARIATION docsBpiCmtsDefaultAuthLifetime
     ACCESS read-write
     DESCRIPTION "For testing purposes, this variable has an increased
     numeric range from 1 to 6048000."

     VARIATION docsBpiCmtsDefaultTEKLifetime
     ACCESS read-write
     DESCRIPTION "For testing purposes, this variable has an increased
     numeric range from 1 to 604800."

     VARIATION docsBpiCmtsAuthCmLifetime
     ACCESS read-write
     DESCRIPTION "For testing purposes, this variable has an increased
     numeric range from 1 to 6048000."

     VARIATION docsBpiCmtsAuthCmGraceTime
     ACCESS read-write
     DESCRIPTION "For testing purposes, this variable has an increased
     numeric range from 1 to 1800."

     VARIATION docsBpiCmtsTEKLifetime
     ACCESS read-write
     DESCRIPTION "For testing purposes, this variable has an increased
     numeric range from 1 to 604800."

     VARIATION docsBpiCmtsTEKGraceTime
     ACCESS read-write
     DESCRIPTION "For testing purposes, this variable has an increased
     numeric range from 1 to 1800."

     -- ********************* ************ ************ *************** ***

     SUPPORTS RIVERSTONE-STP-MIB
     INCLUDES {
	     rsStpBaseGroup
	 }

     VARIATION rsStpStatus
	 ACCESS not-implemented
	 DESCRIPTION "STP cannot be disabled globally on RS devices"

    -- ********************* ************ ************ *************** ***

     -- IEEE 802.3ad , LAG MIB
     SUPPORTS LAG-MIB
     INCLUDES {
        dot3adAggGroup,
        dot3adAggPortGroup,
        dot3adTablesLastChangedGroup,
        dot3adAggPortListGroup,  
        dot3adAggPortStatsGroup,
        dot3adAggPortDebugGroup
     }

     VARIATION dot3adAggPartnerSystemPriority
     ACCESS read-only 
     DESCRIPTION "This object is not aggregator specific"
     
     VARIATION dot3adAggCollectorMaxDelay
     ACCESS read-only 
     DESCRIPTION "This object is not settable"
  
     VARIATION dot3adAggPortPartnerAdminSystemPriority
     ACCESS read-only 
     DESCRIPTION "This object is not settable"
  
     VARIATION dot3adAggPortPartnerAdminSystemID
     ACCESS read-only 
     DESCRIPTION "This object is not settable"
  
     VARIATION dot3adAggPortPartnerAdminKey
     ACCESS read-only 
     DESCRIPTION "This object is not settable"
  
     VARIATION dot3adAggPortPartnerAdminPort
     ACCESS read-only 
     DESCRIPTION "This object is not settable"
  
     VARIATION dot3adAggPortPartnerAdminPortPriority
     ACCESS read-only 
     DESCRIPTION "This object is not settable"
  
  
     VARIATION dot3adTablesLastChanged
     ACCESS not-implemented
     DESCRIPTION "Firmware does not support this"
  
     VARIATION dot3adAggPortDebugRxState
     ACCESS not-implemented
     DESCRIPTION "Firmware does not support this"
  
     VARIATION dot3adAggPortDebugLastRxTime
     ACCESS not-implemented
     DESCRIPTION "Firmware does not support this"
  
     VARIATION dot3adAggPortDebugMuxState
     ACCESS not-implemented
     DESCRIPTION "Firmware does not support this"
  
     VARIATION dot3adAggPortDebugMuxReason
     ACCESS not-implemented
     DESCRIPTION "Firmware does not support this"
  
     VARIATION dot3adAggPortDebugActorChurnState
     ACCESS not-implemented
     DESCRIPTION "Firmware does not support this"
  
     VARIATION dot3adAggPortDebugPartnerChurnState
     ACCESS not-implemented
     DESCRIPTION "Firmware does not support this"
  
     VARIATION dot3adAggPortDebugActorChurnCount
     ACCESS not-implemented
     DESCRIPTION "Firmware does not support this"
  
     VARIATION dot3adAggPortDebugPartnerChurnCount
     ACCESS not-implemented
     DESCRIPTION "Firmware does not support this"
  
     VARIATION dot3adAggPortDebugActorSyncTransitionCount
     ACCESS not-implemented
     DESCRIPTION "Firmware does not support this"
  
     VARIATION dot3adAggPortDebugPartnerSyncTransitionCount
     ACCESS not-implemented
     DESCRIPTION "Firmware does not support this"
  
     VARIATION dot3adAggPortDebugActorChangeCount
     ACCESS not-implemented
     DESCRIPTION "Firmware does not support this"
  
     VARIATION dot3adAggPortDebugPartnerChangeCount
     ACCESS not-implemented
     DESCRIPTION "Firmware does not support this"

    -- ********************* ************ ************ *************** ***
 
     SUPPORTS CISCO-BGP-POLICY-ACCOUNTING-MIB
     INCLUDES {
        cbpAcctTableGroup
     }
 
     -- ********************* ************ ************ *************** ***

   ::= { rsCapability 4 }

rs80x AGENT-CAPABILITIES 
  PRODUCT-RELEASE 
     "8.0.x"
  STATUS  current
  DESCRIPTION
     "Firmware Release 8.0.x for Riverstone  RS RapidOS product line.
	  The firmware supports RS 16000 in this release. It also
      supports MPLS hardware and software. Other software 
      features include SLR, Unnumbered Interfaces, per VLAN statistics
      and Hot CM failover (phase 1). New MIBs include VLAN statistics
      in RFC 2674 Q Bridge MIB and rstone-atm-mib for learning MAC
      addresses on a per VC basis."
  REFERENCE 
     "http://www.riverstonenet.com/products"

     -- RFC 1907
     SUPPORTS SNMPv2-MIB
     INCLUDES { 
         systemGroup,
         snmpGroup, 
         snmpBasicNotificationsGroup,
         --  snmpSetGroup is not implemented, but is needed for SNMPv2-MIB compliance
         -- non mandatory groups
         snmpCommunityGroup,
         -- deprecated/obsolete support
         snmpObsoleteGroup
     }

     -- ********************* ************ ************ *************** ***
     -- RFC 2358
     SUPPORTS EtherLike-MIB
     INCLUDES { 
         etherStats100MbsGroup
     }

     -- ********************* ************ ************ *************** ***
     -- RFC 2233
     SUPPORTS IF-MIB
     INCLUDES { 
         ifGeneralInformationGroup, 
         ifStackGroup2,
         ifCounterDiscontinuityGroup,
         -- non mandatory groups
         ifFixedLengthGroup,
         ifHCFixedLengthGroup,
         ifPacketGroup,
         ifHCPacketGroup,
         ifVHCPacketGroup,
         ifRcvAddressGroup,
         -- deprecated/obsolete support
         ifOldObjectsGroup
     }
     VARIATION ifAlias
     ACCESS read-only
     DESCRIPTION "ifAlias is guarenteed to be unique across reboots. It takes the form Type : instance info
      for example: ifAlias.49 = IP interface: to-sc-BGPfeed or ifAlias.42 = VLAN: test1 or 
      ifAlias.35 = Physical port: et.14.5"

     VARIATION ifAdminStatus
     ACCESS read-only
     DESCRIPTION "For ifTypes corresponding to VLANs this object is read only."

     VARIATION ifLinkUpDownTrapEnable
     ACCESS read-only
     DESCRIPTION "For all ifTypes where ifConnectorPresent is not TRUE."

     VARIATION ifStackStatus
     ACCESS read-only
     DESCRIPTION "Command line interface(CLI) is used to change relationships."

     -- ********************* ************ ************ *************** ***
     -- RFC 2011
     SUPPORTS IP-MIB
     INCLUDES { 
         ipGroup,
         icmpGroup
     }
     VARIATION ipDefaultTTL
     ACCESS read-only
     DESCRIPTION "Command line interface(CLI) is used to change default ttl."

     -- ********************* ************ ************ *************** ***
     -- RFC 2096
     SUPPORTS IP-FORWARD-MIB
     INCLUDES { 
         ipForwardCidrRouteGroup
     }
     VARIATION ipCidrRouteIfIndex
     ACCESS read-only
     DESCRIPTION "Command line interface(CLI) is used to update Forwarding Information Base/FIB."

     VARIATION ipCidrRouteType
     ACCESS read-only
     DESCRIPTION "Command line interface(CLI) is used to update Forwarding Information Base/FIB."

     VARIATION ipCidrRouteInfo
     ACCESS read-only
     DESCRIPTION "Command line interface(CLI) is used to update Forwarding Information Base/FIB."

     VARIATION ipCidrRouteNextHopAS
     ACCESS read-only
     DESCRIPTION "Command line interface(CLI) is used to update Forwarding Information Base/FIB."

     VARIATION ipCidrRouteMetric1
     ACCESS read-only
     DESCRIPTION "Command line interface(CLI) is used to update Forwarding Information Base/FIB."

     VARIATION ipCidrRouteMetric2
     ACCESS read-only
     DESCRIPTION "Command line interface(CLI) is used to update Forwarding Information Base/FIB."

     VARIATION ipCidrRouteMetric3
     ACCESS read-only
     DESCRIPTION "Command line interface(CLI) is used to update Forwarding Information Base/FIB."

     VARIATION ipCidrRouteMetric4
     ACCESS read-only
     DESCRIPTION "Command line interface(CLI) is used to update Forwarding Information Base/FIB."

     VARIATION ipCidrRouteMetric5
     ACCESS read-only
     DESCRIPTION "Command line interface(CLI) is used to update Forwarding Information Base/FIB."

     VARIATION ipCidrRouteStatus
     ACCESS read-only
     DESCRIPTION "Command line interface(CLI) is used to update Forwarding Information Base/FIB."

     -- ********************* ************ ************ *************** ***
     -- RFC 2013
     SUPPORTS UDP-MIB
     INCLUDES { 
         udpGroup         
     }

     -- ********************* ************ ************ *************** ***
     -- RFC 2012
     SUPPORTS TCP-MIB
     INCLUDES { 
         tcpGroup         
     }
     VARIATION tcpConnState
     ACCESS read-only
     DESCRIPTION "Command line interface(CLI) is used to kill tcp sessions."

     -- ********************* ************ ************ *************** ***
     --  RFC 1657 
--     SUPPORTS BGP4-MIB
--     INCLUDES { 
--         This is an smiv1 mib, all objects read only. Specify in device config file to enable this mib.
--     }

     -- ********************* ************ ************ *************** ***
     -- RFC 1850    
     -- Specify in device config file to enable this mib.
     SUPPORTS OSPF-MIB
     INCLUDES { 
         ospfBasicGroup,
         ospfAreaGroup,
         ospfStubAreaGroup,
         ospfIfGroup,
         ospfIfMetricGroup,
         ospfVirtIfGroup,
         ospfNbrGroup,
         ospfVirtNbrGroup,
         ospfAreaAggregateGroup
     }
     VARIATION ospfRouterId
     ACCESS read-only
     DESCRIPTION "Command line interface(CLI) is used to set router id."

     VARIATION ospfAdminStat
     ACCESS read-only
     DESCRIPTION "Command line interface(CLI) is used to set ospf state."

     VARIATION ospfTOSSupport
     ACCESS read-only
     DESCRIPTION "Command line interface(CLI) is used to set ospf TOS support."

     VARIATION ospfExtLsdbLimit
     ACCESS read-only
     DESCRIPTION "Command line interface(CLI) is used to set ospf Lsdb Limit."

     VARIATION ospfMulticastExtensions
     ACCESS read-only
     DESCRIPTION "Command line interface(CLI) is used to set ospf multicast extensions."

     VARIATION ospfExitOverflowInterval
     ACCESS read-only
     DESCRIPTION "Command line interface(CLI) is used to set ospf exit overflow interval."

     VARIATION ospfDemandExtensions
     ACCESS read-only
     DESCRIPTION "Command line interface(CLI) is used to set ospf demand extensions."

     VARIATION ospfAuthType
     ACCESS read-only
     DESCRIPTION "Command line interface(CLI) is used to set ospf authorisation types."

     VARIATION ospfImportAsExtern
     ACCESS read-only
     DESCRIPTION "Command line interface(CLI) is used to set ospf Import AS external routes."

     VARIATION ospfAreaSummary
     ACCESS read-only
     DESCRIPTION "Command line interface(CLI) is used to set ospf area summary importation."

     VARIATION ospfAreaStatus
     ACCESS read-only
     DESCRIPTION "Command line interface(CLI) is used to create & delete ospf areas."

     VARIATION ospfStubMetric
     ACCESS read-only
     DESCRIPTION "Command line interface(CLI) is used to set ospf area stub metric."

     VARIATION ospfStubStatus
     ACCESS read-only
     DESCRIPTION "Command line interface(CLI) is used to create & delete stub areas."

     VARIATION ospfStubMetricType
     ACCESS read-only
     DESCRIPTION "Command line interface(CLI) is used to set ospf stub metric type."

     VARIATION ospfAreaRangeMask
     ACCESS read-only
     DESCRIPTION "Command line interface(CLI) is used to set ospf area range mask."

     VARIATION ospfAreaRangeStatus
     ACCESS read-only
     DESCRIPTION "Command line interface(CLI) is used to create & delete ranges."

     VARIATION ospfAreaRangeEffect
     ACCESS read-only
     DESCRIPTION "Command line interface(CLI) is used to set area range effect."

     VARIATION ospfHostMetric
     ACCESS read-only
     DESCRIPTION "Command line interface(CLI) is used to set host metric."

     VARIATION ospfHostStatus
     ACCESS read-only
     DESCRIPTION "Command line interface(CLI) is used to create & delete hosts."

     VARIATION ospfIfAreaId
     ACCESS read-only
     DESCRIPTION "Command line interface(CLI) is used to set Interface area id."

     VARIATION ospfIfType
     ACCESS read-only
     DESCRIPTION "Command line interface(CLI) is used to set Interface type."

     VARIATION ospfIfAdminStat
     ACCESS read-only
     DESCRIPTION "Command line interface(CLI) is used to set Interface admin status."

     VARIATION ospfIfRtrPriority
     ACCESS read-only
     DESCRIPTION "Command line interface(CLI) is used to set interface router priority."

     VARIATION ospfIfTransitDelay
     ACCESS read-only
     DESCRIPTION "Command line interface(CLI) is used to set interface transit delay."

     VARIATION ospfIfRetransInterval
     ACCESS read-only
     DESCRIPTION "Command line interface(CLI) is used to set interface retransmission interval."

     VARIATION ospfIfHelloInterval
     ACCESS read-only
     DESCRIPTION "Command line interface(CLI) is used to set hello interval."

     VARIATION ospfIfRtrDeadInterval
     ACCESS read-only
     DESCRIPTION "Command line interface(CLI) is used to set dead interval."

     VARIATION ospfIfPollInterval
     ACCESS read-only
     DESCRIPTION "Command line interface(CLI) is used to set poll interval."

     VARIATION ospfIfAuthKey
     ACCESS read-only
     DESCRIPTION "Command line interface(CLI) is used to set interface auth key."

     VARIATION ospfIfStatus
     ACCESS read-only
     DESCRIPTION "Command line interface(CLI) is used to create & delete interfaces."

     VARIATION ospfIfMulticastForwarding
     ACCESS read-only
     DESCRIPTION "Command line interface(CLI) is used to set multicast fwd."

     VARIATION ospfIfDemand
     ACCESS read-only
     DESCRIPTION "Command line interface(CLI) is used to set this attribute."

     VARIATION ospfIfAuthType
     ACCESS read-only
     DESCRIPTION "Command line interface(CLI) is used to set this feature."

     VARIATION ospfIfMetricValue
     ACCESS read-only
     DESCRIPTION "Command line interface(CLI) is used to set this feature."

     VARIATION ospfVirtIfTransitDelay
     ACCESS read-only
     DESCRIPTION "Command line interface(CLI) is used to set this feature."

     VARIATION ospfVirtIfRetransInterval
     ACCESS read-only
     DESCRIPTION "Command line interface(CLI) is used to set this feature."

     VARIATION ospfVirtIfHelloInterval
     ACCESS read-only
     DESCRIPTION "Command line interface(CLI) is used to set this feature."

     VARIATION ospfVirtIfRtrDeadInterval
     ACCESS read-only
     DESCRIPTION "Command line interface(CLI) is used to set this feature."

     VARIATION ospfVirtIfAuthKey
     ACCESS read-only
     DESCRIPTION "Command line interface(CLI) is used to set this feature."

     VARIATION ospfVirtIfStatus
     ACCESS read-only
     DESCRIPTION "Command line interface(CLI) is used to set this feature."

     VARIATION ospfVirtIfAuthType
     ACCESS read-only
     DESCRIPTION "Command line interface(CLI) is used to set this feature."

     VARIATION ospfNbrPriority
     ACCESS read-only
     DESCRIPTION "Command line interface(CLI) is used to set this feature."

     VARIATION ospfNbmaNbrStatus
     ACCESS read-only
     DESCRIPTION "Command line interface(CLI) is used to set this feature."

     VARIATION ospfAreaAggregateStatus
     ACCESS read-only
     DESCRIPTION "Command line interface(CLI) is used to set this feature."

     VARIATION ospfAreaAggregateEffect
     ACCESS read-only
     DESCRIPTION "Command line interface(CLI) is used to set this feature."

     SUPPORTS OSPF-TRAP-MIB
     INCLUDES { 
         ospfTrapControlGroup
     }

     -- ********************* ************ ************ *************** ***
     -- RFC 1724
     -- Specify in device config file to enable this mib.
     SUPPORTS RIPv2-MIB
     INCLUDES { 
         rip2GlobalGroup,
         rip2IfStatGroup,
         rip2IfConfGroup,
         rip2PeerGroup
     }
     VARIATION rip2IfStatStatus
     ACCESS read-only
     DESCRIPTION "Command line interface(CLI) is used to set this feature."
   
     VARIATION rip2IfConfDomain
     ACCESS read-only
     DESCRIPTION "Command line interface(CLI) is used to set this feature."

     VARIATION rip2IfConfAuthType
     ACCESS read-only
     DESCRIPTION "Command line interface(CLI) is used to set this feature."

     VARIATION rip2IfConfAuthKey
     ACCESS read-only
     DESCRIPTION "Command line interface(CLI) is used to set this feature."

     VARIATION rip2IfConfSend
     ACCESS read-only
     DESCRIPTION "Command line interface(CLI) is used to set this feature."

     VARIATION rip2IfConfReceive
     ACCESS read-only
     DESCRIPTION "Command line interface(CLI) is used to set this feature."

     VARIATION rip2IfConfDefaultMetric
     ACCESS read-only
     DESCRIPTION "Command line interface(CLI) is used to set this feature."

     VARIATION rip2IfConfStatus
     ACCESS read-only
     DESCRIPTION "Command line interface(CLI) is used to set this feature."

     VARIATION rip2IfConfSrcAddress
     ACCESS read-only
     DESCRIPTION "Command line interface(CLI) is used to set this feature."

     -- ********************* ************ ************ *************** ***
     -- RFC 1493
--    SUPPORTS BRIDGE-MIB
--    INCLUDES { 
--       smiv1 mib
--    }

     -- ********************* ************ ************ *************** ***
     -- RFC 2674
     -- Updated 09/20/00

     SUPPORTS Q-BRIDGE-MIB
     INCLUDES {
        qBridgeBaseGroup,
        qBridgeVlanGroup,
        qBridgeVlanStaticGroup,
        qBridgePortGroup,
        qBridgeFdbUnicastGroup,
        qBridgeFdbMulticastGroup
     }     

     --qBridgeStaticVlanTable
     --Implicit Vlans are not accounted by SNMP.
     --Only 10 Non Active rows can be present in the temp table . If the user
     --tries to create more than 10 Non Active rows, BAD-VALUE will be returned.
     --Vlan name has to be specified when creating a vlan, apart from the vlan id.
     --This is a limitation of the RS family (RFC does not ask for the vlan name.)

     VARIATION dot1qVlanStaticUntaggedPorts
     ACCESS read-only 
     DESCRIPTION "No hardware support"

     VARIATION dot1qVlanStaticEgressPorts
     ACCESS read-write
     DESCRIPTION "Apart from permanent entries , non permanent entries ( 
	        in the active config and not in the startup config) will 
	        also be displayed."

     

     VARIATION dot1qPvid
     ACCESS read-write
     DESCRIPTION  "For Trunk-Port, PVID cannot be set. Trunk ports can be in 
	         more than one vlan (apart from being in default vlan). 
	         Get reports the default vlan ID."

     VARIATION dot1qPortGvrpStatus
     ACCESS read-only
     DESCRIPTION  "CLI is used to set this"

     VARIATION dot1qTpVlanPortInFrames
     DESCRIPTION "For this object to exist, per-VLAN statistics must first be 
                  enabled through the CLI for each port to be monitored.  

                  SmartTRUNKs are currently not supported."

     VARIATION dot1qTpVlanPortOutFrames
     DESCRIPTION "For this object to exist, per-VLAN statistics must first be 
                  enabled through the CLI for each port to be monitored.  

                  SmartTRUNKs are currently not supported.

                  When an egress port is oversubscribed, the value of this
                  object may be larger than the actual value, since the RS
                  platform cannot account for packets dropped internally 
                  at this level of granularity."

     VARIATION dot1qTpVlanPortInDiscards
     DESCRIPTION "The RS platform does not support the collection of this
                  statistic."

     VARIATION dot1qTpVlanPortInOverflowFrames
     DESCRIPTION "For this object to exist, per-VLAN statistics must first be 
                  enabled through the CLI for each port to be monitored.  

                  SmartTRUNKs are currently not supported."

     VARIATION dot1qTpVlanPortOutOverflowFrames
     DESCRIPTION "For this object to exist, per-VLAN statistics must first be 
                  enabled through the CLI for each port to be monitored.  

                  SmartTRUNKs are currently not supported.

                  When an egress port is oversubscribed, the value of this
                  object may be larger than the actual value, since the RS
                  platform cannot account for packets dropped internally 
                  at this level of granularity."

     VARIATION dot1qTpVlanPortInOverflowDiscards
     DESCRIPTION "The RS platform does not support the collection of this
                  statistic."

     VARIATION dot1qTpVlanPortHCInFrames
     DESCRIPTION "For this object to exist, per-VLAN statistics must first be 
                  enabled through the CLI for each port to be monitored.  

                  SmartTRUNKs are currently not supported."

     VARIATION dot1qTpVlanPortHCOutFrames
     DESCRIPTION "For this object to exist, per-VLAN statistics must first be 
                  enabled through the CLI for each port to be monitored.  

                  SmartTRUNKs are currently not supported.

                  When an egress port is oversubscribed, the value of this
                  object may be larger than the actual value, since the RS
                  platform cannot account for packets dropped internally 
                  at this level of granularity."

     VARIATION dot1qTpVlanPortHCInDiscards
     DESCRIPTION "The RS platform does not support the collection of this
                  statistic."
     -- ********************* ************ ************ *************** ***
        -- RFC 2674
        -- Update 09/26/00

        SUPPORTS P-BRIDGE-MIB
        INCLUDES {
            pBridgeExtCapGroup,
            pBridgeDevicePriorityGroup,
            pBridgeDefaultPriorityGroup,
            pBridgePriorityGroup,
	        pBridgePortGarpGroup
        }

-- pBridgeExtCapGroup: dot1dDeviceCapabilities :: 
-- dot1dExtendedFilteringServices ,dot1qConfigurablePvidTagging ,
-- dot1qSVLCapable,dot1qHybridCapable  not supported.


     VARIATION dot1dTrafficClassesEnabled
     ACCESS read-only
     DESCRIPTION "This is not settable through SNMP. However this can be
                  set using CLI by mapping all 1p priority levels to the
	        same traffic class."


-- pBridgeDefaultPriorityGroup: dot1dPortDefaultUserPriority If the user 
--			  configures default priority on a port and later
--			  configures a priority for a MAC / VLAN pair
--			  using CLI, CLI would report a conflict.

--			  When this variable is set through snmp, the 
--			  name used for the qos command would be 
--			  "snmp-priority-#portnum". This would be the 
--			  case, even if a priority was configured 
--			  through the cli (using qos set l2 command)
--			  with a different name (say priority-#portnum),
--			  and then modified through snmp.


     VARIATION dot1dPortNumTrafficClasses
     ACCESS read-only
     DESCRIPTION "This value is not settable. Setting this value is optional		        only."


     VARIATION dot1dPortGarpJoinTime
     ACCESS read-only
     DESCRIPTION "This is not settable."


     VARIATION dot1dPortGarpLeaveTime
     ACCESS read-only
     DESCRIPTION "This is not settable."


     VARIATION dot1dPortGarpLeaveAllTime
     ACCESS read-only
     DESCRIPTION "This is not settable."

     -- ********************* ************ ************ *************** ***
     -- RFC 2115
     SUPPORTS FRAME-RELAY-DTE-MIB
     INCLUDES { 
       frPortGroup, 
       frCircuitGroup,
       frErrGroup,
       frTrapGroup
     }
     VARIATION frDlcmiState
     ACCESS read-only
     DESCRIPTION "Command line interface(CLI) is used to set this feature."

     VARIATION frDlcmiAddress
     ACCESS read-only
     DESCRIPTION "Command line interface(CLI) is used to set this feature."

     VARIATION frDlcmiAddressLen
     ACCESS read-only
     DESCRIPTION "Command line interface(CLI) is used to set this feature."

     VARIATION frDlcmiPollingInterval
     ACCESS read-only
     DESCRIPTION "Command line interface(CLI) is used to set this feature."
     
     VARIATION frDlcmiFullEnquiryInterval
     ACCESS read-only
     DESCRIPTION "Command line interface(CLI) is used to set this feature."

     VARIATION frDlcmiErrorThreshold
     ACCESS read-only
     DESCRIPTION "Command line interface(CLI) is used to set this feature."

     VARIATION frDlcmiMonitoredEvents
     ACCESS read-only
     DESCRIPTION "Command line interface(CLI) is used to set this feature."

     VARIATION frDlcmiMaxSupportedVCs
     ACCESS read-only
     DESCRIPTION "Command line interface(CLI) is used to set this feature."

     VARIATION frDlcmiMulticast
     ACCESS read-only
     DESCRIPTION "Command line interface(CLI) is used to set this feature."

     VARIATION frDlcmiRowStatus
     ACCESS read-only
     DESCRIPTION "Command line interface(CLI) is used to create & delete dlcmi's."

     VARIATION frCircuitState
     ACCESS read-only
     DESCRIPTION "Command line interface(CLI) is used to set this feature."

     VARIATION frCircuitCommittedBurst
     ACCESS read-only
     DESCRIPTION "Command line interface(CLI) is used to set this feature."

     VARIATION frCircuitExcessBurst
     ACCESS read-only
     DESCRIPTION "Command line interface(CLI) is used to set this feature."

     VARIATION frCircuitThroughput
     ACCESS read-only
     DESCRIPTION "Command line interface(CLI) is used to set this feature."

     VARIATION frCircuitMulticast
     ACCESS read-only
     DESCRIPTION "Command line interface(CLI) is used to set this feature."

     VARIATION frCircuitLogicalIfIndex
     ACCESS read-only
     DESCRIPTION "Command line interface(CLI) is used to set this feature."

     VARIATION frCircuitRowStatus
     ACCESS read-only
     DESCRIPTION "Command line interface(CLI) is used to set this feature."

     -- ********************* ************ ************ *************** ***
       -- RFC 1471
--     SUPPORTS PPP-LCP-MIB
--     INCLUDES { 
--       smiv1 mib - read only 
--     }

     -- ********************* ************ ************ *************** ***
       -- RFC 1472
--     SUPPORTS PPP-SEC-MIB
--     INCLUDES { 
--      smiv1 mib - read only
--     }

     -- ********************* ************ ************ *************** ***
       -- RFC 1473
--     SUPPORTS PPP-IP-NCP-MIB
--     INCLUDES { 
--       smiv1 mib - read only
--     }

     -- ********************* ************ ************ *************** ***
       -- RFC 1474
--     SUPPORTS PPP-BRIDGE-NCP-MIB
--     INCLUDES { 
--       smiv1 mib - read only
--     }

     -- ********************* ************ ************ *************** ***
	 -- RFC 2494
	 SUPPORTS DS0-MIB
	 INCLUDES {
		ds0ConfigGroup
	 }

     -- ********************* ************ ************ *************** ***
	 -- RFC 2494
	 SUPPORTS DS0BUNDLE-MIB
	 INCLUDES {
		ds0BundleConfigGroup
	 }

     -- ********************* ************ ************ *************** ***
     -- RFC 2495
     SUPPORTS DS1-MIB
     INCLUDES { 
        ds1NearEndConfigGroup,
        ds1NearEndStatisticsGroup,
		ds1NearEndOptionalConfigGroup,
		ds1ChanMappingGroup 
     }
     VARIATION dsx1LineType
     ACCESS read-only
     DESCRIPTION "Command line interface(CLI) is used to set this feature."

     VARIATION dsx1LineCoding
     ACCESS read-only
     DESCRIPTION "Command line interface(CLI) is used to set this feature."

     VARIATION dsx1SendCode
     ACCESS read-only
     DESCRIPTION "Command line interface(CLI) is used to set this feature."

     VARIATION dsx1CircuitIdentifier
     ACCESS read-only
     DESCRIPTION "Command line interface(CLI) is used to set this feature."

     VARIATION dsx1LoopbackConfig
     ACCESS read-only
     DESCRIPTION "Command line interface(CLI) is used to set this feature."

     VARIATION dsx1SignalMode
     ACCESS read-only
     DESCRIPTION "Command line interface(CLI) is used to set this feature."

     VARIATION dsx1TransmitClockSource
     ACCESS read-only
     DESCRIPTION "Command line interface(CLI) is used to set this feature."

     VARIATION dsx1Fdl
     ACCESS read-only
     DESCRIPTION "Command line interface(CLI) is used to set this feature."

     VARIATION dsx1LineLength
     ACCESS read-only
     DESCRIPTION "Command line interface(CLI) is used to set this feature."

     VARIATION dsx1LineStatusChangeTrapEnable
     ACCESS read-only
     DESCRIPTION "Command line interface(CLI) is used to set this feature."

     VARIATION dsx1Channelization
     ACCESS read-only
     DESCRIPTION "Command line interface(CLI) is used to set this feature."

     -- ********************* ************ ************ *************** ***
     -- RFC 2496
     SUPPORTS DS3-MIB
     INCLUDES { 
        ds3NearEndConfigGroup,
        ds3NearEndStatisticsGroup,
		ds3NearEndOptionalConfigGroup 
     }

     VARIATION dsx3LineType
     ACCESS read-only
     DESCRIPTION "Command line interface(CLI) is used to set this feature."

     VARIATION dsx3LineCoding
     ACCESS read-only
     DESCRIPTION "Command line interface(CLI) is used to set this feature."

     VARIATION dsx3SendCode
     ACCESS read-only
     DESCRIPTION "Command line interface(CLI) is used to set this feature."

     VARIATION dsx3CircuitIdentifier
     ACCESS read-only
     DESCRIPTION "Command line interface(CLI) is used to set this feature."

     VARIATION dsx3LoopbackConfig
     ACCESS read-only
     DESCRIPTION "Command line interface(CLI) is used to set this feature."

     VARIATION dsx3TransmitClockSource
     ACCESS read-only
     DESCRIPTION "Command line interface(CLI) is used to set this feature."

     VARIATION dsx3LineLength
     ACCESS read-only
     DESCRIPTION "Command line interface(CLI) is used to set this feature."

     VARIATION dsx3LineStatusChangeTrapEnable
     ACCESS read-only
     DESCRIPTION "Command line interface(CLI) is used to set this feature."

     VARIATION dsx3Channelization
     ACCESS read-only
     DESCRIPTION "Command line interface(CLI) is used to set this feature."

     VARIATION dsx3Ds1ForRemoteLoop
     ACCESS read-only
     DESCRIPTION "Command line interface(CLI) is used to set this feature."

     -- ********************* ************ ************ *************** ***
     -- RFC 1595
     SUPPORTS SONET-MIB
     INCLUDES { 
        sonetMediumStuff, 
        sonetSectionStuff,
        sonetLineStuff,
        sonetFarEndLineStuff,
        sonetPathStuff,
        sonetFarEndPathStuff
     }

     -- ATM OC3 line cards with  modular physical port (MODPHY) have above instrumentation
     -- POS OC3/12 line cards do not yet support the SONET-MIB

     -- ********************* ************ ************ *************** ***
     -- RFC 1695
     SUPPORTS ATM-MIB
     INCLUDES { 
        atmInterfaceConfGroup,
        atmTrafficDescrGroup,
        atmInterfaceDs3PlcpGroup,
        atmInterfaceTCGroup,
        atmVccTerminationGroup,
        aal5VccGroup
     }    

     VARIATION atmInterfaceMaxVpcs
     ACCESS read-only 
     DESCRIPTION "This object is not settable"

     VARIATION atmInterfaceMaxVccs
     ACCESS read-only
     DESCRIPTION "This object is not settable"

     VARIATION atmInterfaceMaxActiveVpiBits
     ACCESS read-only
     DESCRIPTION "This object is not settable"
     
     VARIATION atmInterfaceMaxActiveVciBits
     ACCESS read-only
     DESCRIPTION "This object is not settable"

     VARIATION atmInterfaceIlmiVpi
     ACCESS not-implemented
     DESCRIPTION "Device does not support Ilmi"

     VARIATION atmInterfaceIlmiVci
     ACCESS not-implemented
     DESCRIPTION "Device does not support Ilmi"

     VARIATION atmInterfaceMyNeighborIpAddress
     ACCESS not-implemented
     DESCRIPTION "Firmware does not support this"

     VARIATION atmInterfaceMyNeighborIfName
     ACCESS not-implemented
     DESCRIPTION "Firmware does not support this"

     VARIATION atmTrafficDescrParam1
     ACCESS read-only
     DESCRIPTION "Command line interface(CLI) is used to set this feature"

     VARIATION atmTrafficDescrParam2
     ACCESS read-only
     DESCRIPTION "Command line interface(CLI) is used to set this feature"
     
     VARIATION atmTrafficDescrParam3
     ACCESS read-only
     DESCRIPTION "Command line interface(CLI) is used to set this feature"

     VARIATION atmTrafficDescrParam4
     ACCESS read-only
     DESCRIPTION "Command line interface(CLI) is used to set this feature"

     VARIATION atmTrafficDescrParam5
     ACCESS read-only
     DESCRIPTION "Command line interface(CLI) is used to set this feature"

     VARIATION atmTrafficQoSClass
     ACCESS read-only
     DESCRIPTION "Command line interface(CLI) is used to set this feature"

     VARIATION atmTrafficDescrRowStatus
     ACCESS not-implemented
     DESCRIPTION "Table is read-only"

     VARIATION atmInterfaceDs3PlcpSEFSs
     ACCESS not-implemented
     DESCRIPTION "Firmware does not support this"

     VARIATION atmInterfaceDs3PlcpAlarmState
     ACCESS not-implemented
     DESCRIPTION "Firmware does not support this"

     VARIATION atmInterfaceDs3PlcpUASs
     ACCESS not-implemented
     DESCRIPTION "Firmware does not support this"

     VARIATION atmInterfaceOCDEvents
     ACCESS not-implemented
     DESCRIPTION "Firmware does not support this"

     VARIATION atmInterfaceTCAlarmState
     ACCESS not-implemented
     DESCRIPTION "Firmware does not support this"

     VARIATION atmVclAdminStatus
     ACCESS read-only
     DESCRIPTION "Command line interface(CLI) is used to set this feature"

     VARIATION atmVclReceiveTrafficDescrIndex
     ACCESS read-only
     DESCRIPTION "Memory address is used as the index, CLI is used to set this"

     VARIATION atmVclTransmitTrafficDescrIndex
     ACCESS read-only
     DESCRIPTION "Memory address is used as the index, CLI is used to set this"
        
     VARIATION atmVccAalType
     ACCESS read-only
     DESCRIPTION "This object is not settable"

     VARIATION atmVclRowStatus
     ACCESS read-only
     DESCRIPTION "This object is not settable"

     -- ********************* ************ ************ *************** ***
     -- RFC 2618
     SUPPORTS RADIUS-AUTH-CLIENT-MIB
     INCLUDES { 
          radiusAuthClientMIBGroup
     }

     -- ********************* ************ ************ *************** ***
     -- RFC 1757/2819
       SUPPORTS RMON-MIB
       INCLUDES { 
         
         rmonEtherStatsGroup,
         rmonHistoryControlGroup,
         rmonEthernetHistoryGroup,
         rmonAlarmGroup,
         rmonHostGroup,   -- requires flow bridging hardware mode enabled
         rmonHostTopNGroup, 
         rmonMatrixGroup, -- requires flow bridging hardware mode enabled
         rmonFilterGroup,
         rmonPacketCaptureGroup,
         rmonEventGroup,
         rmonNotificationGroup
       }

     -- ********************* ************ ************ *************** ***
     -- RFC 2021
     SUPPORTS RMON2-MIB
     INCLUDES { 
        protocolDirectoryGroup,
        protocolDistributionGroup,
        addressMapGroup,
        nlHostGroup,
        nlMatrixGroup,
        alHostGroup,
        alMatrixGroup,
        usrHistoryGroup,
        probeInformationGroup,
        probeConfigurationGroup,
        rmon1EthernetEnhancementGroup
        -- rmon1EnhancementGroup supported except for filterProtocolDirDataLocalIndex,
        --  filterProtocolDirLocalIndex
     }
     VARIATION filterProtocolDirDataLocalIndex
     ACCESS not-implemented
     DESCRIPTION "Feature not available in this firmware version "

     VARIATION filterProtocolDirLocalIndex
     ACCESS not-implemented
     DESCRIPTION "Feature not available in this firmware version "

     -- NOTE: Sets to this mib are not persistent. RMON configuration
     -- may be done via CLI for persistence
     -- ********************* ************ ************ *************** ***
     -- From ietf vrrp mib Draft #9
     SUPPORTS VRRP-MIB
     INCLUDES { 
        vrrpOperGroup,
        vrrpStatsGroup,
        vrrpTrapGroup,
        vrrpNotificationGroup
     }
     VARIATION vrrpOperAdminState
     ACCESS read-only
     DESCRIPTION "Command line interface(CLI) is used to set this feature."

     VARIATION vrrpOperPriority
     ACCESS read-only
     DESCRIPTION "Command line interface(CLI) is used to set this feature."

     VARIATION vrrpOperPrimaryIpAddr
     ACCESS read-only
     DESCRIPTION "Command line interface(CLI) is used to set this feature."

     VARIATION vrrpOperAuthType
     ACCESS read-only
     DESCRIPTION "Command line interface(CLI) is used to set this feature."

     VARIATION vrrpOperAuthKey
     ACCESS read-only
     DESCRIPTION "Command line interface(CLI) is used to set this feature."

     VARIATION vrrpOperAdvertisementInterval
     ACCESS read-only
     DESCRIPTION "Command line interface(CLI) is used to set this feature."

     VARIATION vrrpOperPreemptMode
     ACCESS read-only
     DESCRIPTION "Command line interface(CLI) is used to set this feature."

     VARIATION vrrpOperProtocol
     ACCESS read-only
     DESCRIPTION "Command line interface(CLI) is used to set this feature."

     VARIATION vrrpOperRowStatus
     ACCESS read-only
     DESCRIPTION "Command line interface(CLI) is used to set this feature."

     VARIATION vrrpAssoIpAddrRowStatus
     ACCESS read-only
     DESCRIPTION "Command line interface(CLI) is used to set this feature."

     VARIATION vrrpTrapAuthFailure
     ACCESS not-implemented
     DESCRIPTION "TrapAuthFailure not implemented in this firmware version"

     -- ********************* ************ ************ *************** ***

     SUPPORTS CTRON-LFAP-MIB
     INCLUDES { 
        lfapConfGroupV40
     }

     -- ********************* ************ ************ *************** ***

     SUPPORTS CTRON-SSR-POLICY-MIB
     INCLUDES { 
         polGroupV11        
     }

     -- ********************* ************ ************ *************** ***

     SUPPORTS CTRON-SSR-CONFIG-MIB
     INCLUDES { 
         configGroup20
     }

     
     -- ********************* ************ ************ *************** ***

     SUPPORTS CTRON-SSR-HARDWARE-MIB
     INCLUDES { 
         hwConfGroupV30
     }

     -- ********************* ************ ************ *************** ***

     SUPPORTS CTRON-SSR-SERVICE-STATUS-MIB
     INCLUDES { 
         ssConfGroupV11
     }

     -- ********************* ************ ************ *************** ***

     SUPPORTS CTRON-SSR-CAPACITY-MIB
     INCLUDES { 
         capConfGroupV10
     }

     -- ********************* ************ ************ *************** ***

	 SUPPORTS DOCS-IF-MIB
	 INCLUDES {
         docsIfBasicGroup, 
		 docsIfCmtsGroup
	 }

	 VARIATION docsIfQosProfMaxTxBurst
	 ACCESS read-write
	 DESCRIPTION "This variable returns the value in bits/second rather than
	 mini-slots because this is the expected type by Cablelabs."

     -- ********************* ************ ************ *************** ***

     SUPPORTS DOCS-BPI-MIB
     INCLUDES {
	     docsBpiCmtsGroup
	 }

     VARIATION docsBpiCmtsDefaultAuthLifetime
     ACCESS read-write
     DESCRIPTION "For testing purposes, this variable has an increased
     numeric range from 1 to 6048000."

     VARIATION docsBpiCmtsDefaultTEKLifetime
     ACCESS read-write
     DESCRIPTION "For testing purposes, this variable has an increased
     numeric range from 1 to 604800."

     VARIATION docsBpiCmtsAuthCmLifetime
     ACCESS read-write
     DESCRIPTION "For testing purposes, this variable has an increased
     numeric range from 1 to 6048000."

     VARIATION docsBpiCmtsAuthCmGraceTime
     ACCESS read-write
     DESCRIPTION "For testing purposes, this variable has an increased
     numeric range from 1 to 1800."

     VARIATION docsBpiCmtsTEKLifetime
     ACCESS read-write
     DESCRIPTION "For testing purposes, this variable has an increased
     numeric range from 1 to 604800."

     VARIATION docsBpiCmtsTEKGraceTime
     ACCESS read-write
     DESCRIPTION "For testing purposes, this variable has an increased
     numeric range from 1 to 1800."

     -- ********************* ************ ************ *************** ***

     SUPPORTS RIVERSTONE-STP-MIB
     INCLUDES {
	     rsStpBaseGroup
	 }

     VARIATION rsStpStatus
	 ACCESS not-implemented
	 DESCRIPTION "STP cannot be disabled globally on RS devices"

    -- ********************* ************ ************ *************** ***

     -- IEEE 802.3ad , LAG MIB
     SUPPORTS LAG-MIB
     INCLUDES {
        dot3adAggGroup,
        dot3adAggPortGroup,
        dot3adTablesLastChangedGroup,
        dot3adAggPortListGroup,  
        dot3adAggPortStatsGroup,
        dot3adAggPortDebugGroup
     }

     VARIATION dot3adAggPartnerSystemPriority
     ACCESS read-only 
     DESCRIPTION "This object is not aggregator specific"
     
     VARIATION dot3adAggCollectorMaxDelay
     ACCESS read-only 
     DESCRIPTION "This object is not settable"
  
     VARIATION dot3adAggPortPartnerAdminSystemPriority
     ACCESS read-only 
     DESCRIPTION "This object is not settable"
  
     VARIATION dot3adAggPortPartnerAdminSystemID
     ACCESS read-only 
     DESCRIPTION "This object is not settable"
  
     VARIATION dot3adAggPortPartnerAdminKey
     ACCESS read-only 
     DESCRIPTION "This object is not settable"
  
     VARIATION dot3adAggPortPartnerAdminPort
     ACCESS read-only 
     DESCRIPTION "This object is not settable"
  
     VARIATION dot3adAggPortPartnerAdminPortPriority
     ACCESS read-only 
     DESCRIPTION "This object is not settable"
  
  
     VARIATION dot3adTablesLastChanged
     ACCESS not-implemented
     DESCRIPTION "Firmware does not support this"
  
     VARIATION dot3adAggPortDebugRxState
     ACCESS not-implemented
     DESCRIPTION "Firmware does not support this"
  
     VARIATION dot3adAggPortDebugLastRxTime
     ACCESS not-implemented
     DESCRIPTION "Firmware does not support this"
  
     VARIATION dot3adAggPortDebugMuxState
     ACCESS not-implemented
     DESCRIPTION "Firmware does not support this"
  
     VARIATION dot3adAggPortDebugMuxReason
     ACCESS not-implemented
     DESCRIPTION "Firmware does not support this"
  
     VARIATION dot3adAggPortDebugActorChurnState
     ACCESS not-implemented
     DESCRIPTION "Firmware does not support this"
  
     VARIATION dot3adAggPortDebugPartnerChurnState
     ACCESS not-implemented
     DESCRIPTION "Firmware does not support this"
  
     VARIATION dot3adAggPortDebugActorChurnCount
     ACCESS not-implemented
     DESCRIPTION "Firmware does not support this"
  
     VARIATION dot3adAggPortDebugPartnerChurnCount
     ACCESS not-implemented
     DESCRIPTION "Firmware does not support this"
  
     VARIATION dot3adAggPortDebugActorSyncTransitionCount
     ACCESS not-implemented
     DESCRIPTION "Firmware does not support this"
  
     VARIATION dot3adAggPortDebugPartnerSyncTransitionCount
     ACCESS not-implemented
     DESCRIPTION "Firmware does not support this"
  
     VARIATION dot3adAggPortDebugActorChangeCount
     ACCESS not-implemented
     DESCRIPTION "Firmware does not support this"
  
     VARIATION dot3adAggPortDebugPartnerChangeCount
     ACCESS not-implemented
     DESCRIPTION "Firmware does not support this"

    -- ********************* ************ ************ *************** ***
 
     SUPPORTS CISCO-BGP-POLICY-ACCOUNTING-MIB
     INCLUDES {
        cbpAcctTableGroup
     }
 
     -- ********************* ************ ************ *************** ***
 
     SUPPORTS RSTONE-ATM-MIB
     INCLUDES {
        rsAtmFdbBaseGroup 
     }
 
     -- ********************* ************ ************ *************** ***

   ::= { rsCapability 5 }
END
