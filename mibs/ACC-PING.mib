ACC-PING DEFINITIONS ::= BEGIN

    IMPORTS
	 OBJECT-TYPE, IpAddress, TimeTicks, Gauge, Counter FROM RFC1155-SMI
        accTrapLogSeqNum FROM ACC-SYSTEM
	accBRG, DisplayString, RowStatus, IfIndex, SmdsAddress
             FROM ACC-MIB;

-- Ping Group
      accPing         OBJECT IDENTIFIER ::= { accBRG 30 }
         accPingDest	OBJECT-TYPE 
			SYNTAX  IpAddress
			ACCESS read-write
			STATUS mandatory
			DESCRIPTION
		" IP address of the  destination
		  for generated Ping packets."
			::= { accPing 1 }
         accPingReqCnt	OBJECT-TYPE 
			SYNTAX  INTEGER (0..1000)
			ACCESS read-write
			STATUS mandatory
			DESCRIPTION
		" Count of Ping packets left to be
		  generated.  Setting this variable to a nonzero value
		  causes the Ping generator to be (re)started.  Setting
		  this variable to zero causes the Ping generator to be
		  stopped. "
			::= { accPing 2 }
         accPingDataMin	OBJECT-TYPE 
			SYNTAX  INTEGER (4..1500)
			ACCESS read-write
			STATUS mandatory
			DESCRIPTION
		" Minimum number of data bytes
		  included in the Ping packet.  The first four bytes
		  of data always carry a timestamp, the remaining
		  data is an incrementing byte data pattern. "
			::= { accPing 3 }
         accPingDataMax	OBJECT-TYPE 
			SYNTAX  INTEGER (4..1500)
			ACCESS read-write
			STATUS mandatory
			DESCRIPTION
		" Maximum number of data bytes
		  included in the Ping packet.  If this value is
		  greater than accPingDataMin, the data field length
		  of the Ping packet is a random value between accPingDataMin
		  and accPingDataMax.  Otherwise the data field length
		  is fixed and specified by accPingDataMin. "
			::= { accPing 4 }
         accPingTimeMin	OBJECT-TYPE 
			SYNTAX  INTEGER (0..15)
			ACCESS read-write
			STATUS mandatory
			DESCRIPTION
		" Time (seconds) to delay before
		  generating the next Ping packet, after correctly
		  receiving the expected Ping response for the previously
		  generated Ping packet. "
			::= { accPing 5 }
         accPingTimeMax	OBJECT-TYPE 
			SYNTAX  INTEGER (1..60)
			ACCESS read-write
			STATUS mandatory
			DESCRIPTION
		" Time (seconds) to wait for a
		  correct Ping response before giving up and generating
		  the next Ping packet. "
			::= { accPing 6 }
         accPingSndPkts	OBJECT-TYPE 
			SYNTAX  Counter
			ACCESS read-only
			STATUS mandatory
			DESCRIPTION
		" Number of Ping packets
		  generated since the current Ping activity was initiated. "
			::= { accPing 7 }
         accPingSndBytes	OBJECT-TYPE 
			SYNTAX  Counter
			ACCESS read-only
			STATUS mandatory
			DESCRIPTION
		" Number of Ping data bytes
		  generated since the current Ping activity was initiated. "
			::= { accPing 8 }
         accPingRcvPkts	OBJECT-TYPE 
			SYNTAX  Counter
			ACCESS read-only
			STATUS mandatory
			DESCRIPTION
		" Number of Ping responses
		  received since the current Ping activity was initiated. "
			::= { accPing 9 }
         accPingRcvBytes	OBJECT-TYPE 
			SYNTAX  Counter
			ACCESS read-only
			STATUS mandatory
			DESCRIPTION
		" Number of Ping data bytes
		  received since the current Ping activity was initiated. "
			::= { accPing 10 }
         accPingRcvOKs	OBJECT-TYPE 
			SYNTAX  Counter
			ACCESS read-only
			STATUS mandatory
			DESCRIPTION
		" Number of correct Ping
		  responses received since the current Ping activity was
		  initiated. "
			::= { accPing 11 }
         accPingRcvBads	OBJECT-TYPE 
			SYNTAX  Counter
			ACCESS read-only
			STATUS mandatory
			DESCRIPTION
		" Number of incorrect Ping
		  responses received since the current Ping activity was
		  initiated. "
			::= { accPing 12 }
         accPingDelayMin	OBJECT-TYPE 
			SYNTAX  INTEGER
			ACCESS read-only
			STATUS mandatory
			DESCRIPTION
		" Minimum round trip delay, in
		  milliseconds, experienced by the Ping packet and
		  the Ping response. "
			::= { accPing 13 }
         accPingDelayMax	OBJECT-TYPE 
			SYNTAX  INTEGER
			ACCESS read-only
			STATUS mandatory
			DESCRIPTION
		" Maximum round trip delay, in
		  milliseconds, experienced by the Ping packet and
		  the Ping response. "
			::= { accPing 14 }
         accPingDelayAvg	OBJECT-TYPE 
			SYNTAX  INTEGER
			ACCESS read-only
			STATUS mandatory
			DESCRIPTION
		" Average round trip delay, in
		  milliseconds, experienced by the Ping packet and
		  the Ping response. "
			::= { accPing 15 }

END
