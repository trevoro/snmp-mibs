IPV4DNS-MIB

   --FORCE-INCLUDE <mib.h>
   --FORCE-INCLUDE <snmpdefs.h>
   --FORCE-INCLUDE <snmpstat.h>
   --FORCE-INCLUDE "mibproto.h"
 
   DEFINITIONS ::= BEGIN

	IMPORTS
		MODULE-IDENTITY, OBJECT-TYPE, IpAddress
			FROM SNMPv2-SMI
		RowStatus, DisplayString
			FROM SNMPv2-TC
		apIpv4Dns
			FROM APENT-MIB;


    apIpv4DnsMib MODULE-IDENTITY
	   LAST-UPDATED "9801282000Z" -- Wed January 28 20:00:00 EST 1998
	   ORGANIZATION "ArrowPoint Communications Inc."
	   CONTACT-INFO
	   "Postal:               ArrowPoint Communications Inc.
				                 50 Nagog Park
				                 Acton, Massachusetts 01720
	   Tel:                   +1 978-206-3000  option 1
	   E-Mail:                support@arrowpoint.com"
       DESCRIPTION
	"This MIB module describes the ArrowPoint enterprise
	 MIB support for IPv4 DNS configuration"
      ::= { apIpv4Dns 1}

--arrowpoint
-- apmgmt
--  ipv4Ext
--   apIpv4Dns
--	   apIpv4Dns Scalars
--     apIpv4DnsTable

-- IPv4 Dns Table configuration information

-- Host table

apIpv4DnsDefaultSuffix OBJECT-TYPE
	SYNTAX      DisplayString (SIZE (0..64))
	MAX-ACCESS  read-write
	STATUS		current
	DESCRIPTION
		"The default Suffix to be used in conjunction with DSN queries"
	::= {apIpv4Dns 2}

apIpv4DnsPrimary OBJECT-TYPE
	SYNTAX		IpAddress
	MAX-ACCESS	read-write
	STATUS		current
	DESCRIPTION
		"The default DNS address to use for DNS queries"
	::= {apIpv4Dns 3}

apIpv4DnsTable OBJECT-TYPE
	SYNTAX      SEQUENCE OF ApIpv4DnsEntry
	MAX-ACCESS  not-accessible
	STATUS      current
	DESCRIPTION
		"A table of secondary DNS addresses"
	::= {apIpv4Dns 4}

apIpv4DnsEntry OBJECT-TYPE
	SYNTAX      ApIpv4DnsEntry
	MAX-ACCESS  not-accessible
	STATUS      current
	DESCRIPTION
	       "ArrowPoint secondary DNS record"
	INDEX  { apIpv4DnsSecondaryIP}
	::= {apIpv4DnsTable 1}

ApIpv4DnsEntry ::=
	SEQUENCE {
	       apIpv4DnsSecondaryIP         IpAddress,
	       apIpv4DnsStatus              RowStatus
		 }

apIpv4DnsSecondaryIP OBJECT-TYPE
	SYNTAX      IpAddress
	MAX-ACCESS  read-only
	STATUS      current
	DESCRIPTION
	       "The secondary DNS IP Address"
	::= {apIpv4DnsEntry 1}

apIpv4DnsStatus OBJECT-TYPE
	SYNTAX      RowStatus
	MAX-ACCESS  read-create
	STATUS      current
	DESCRIPTION
	       "Status object for this row"
	::= {apIpv4DnsEntry 2}

END
