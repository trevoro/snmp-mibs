-- *****************************************************************
-- RBUC.mib:  Codan's RBUC product MIB
--
-- Created by Magdalena Raltcheva
--
-- Copyright (c) 2009 by Codan Limited.
-- All rights reserved.
--
-- *****************************************************************

RBUC-MIB DEFINITIONS ::= BEGIN

IMPORTS
	MODULE-IDENTITY, OBJECT-TYPE,
	NOTIFICATION-TYPE,
	Integer32, TimeTicks,
	IpAddress, Gauge32, Counter32		FROM SNMPv2-SMI
	DisplayString, DateAndTime,
	TEXTUAL-CONVENTION,
	TestAndIncr,TimeInterval, TruthValue			FROM SNMPv2-TC
	satcomMibs 							FROM CODAN-SMI;

rbucMIB MODULE-IDENTITY
   LAST-UPDATED "200902110000Z"
   ORGANIZATION "Codan Limited."
   CONTACT-INFO
        "       Magda Raltcheva
        Postal: Codan Limited
                81 Graves St.
                Newton 5074
                Australia
        Tel:    +61-8-83050311
        Fax:    +61-8-83050411
        Web:	www.codan.com.au"

	DESCRIPTION
		"The Structure of Management Information for the
		 Codan enterprise.	
		 Copyright(c) 2009 All rights reserved"

	REVISION      "200902110000Z"
	DESCRIPTION
		"1.0 Initial version of this MIB module."
        ::= { satcomMibs 1 }   -- assigned by IANA


-- ***##############################################################***
--              CodanMIB Textual Convention Definitions
-- ***##############################################################***

ComponentRevision ::= TEXTUAL-CONVENTION
    DISPLAY-HINT "vxx.yy"
    STATUS      current
    DESCRIPTION
        "The hex value in the first octet - xx - represents the major revision no.
        and the hex value in the second octet - yy - represents the minor revision no."
    SYNTAX      DisplayString(SIZE(2))



FaultStatus ::= TEXTUAL-CONVENTION
    STATUS       current
    DESCRIPTION
        "Describes all the possible faults in the system as a bit pattern."
    SYNTAX      BITS {                   
                    pafault(0),
                    lofault(1), -- lo unlock error
					internalfault(2),
					rcfault(3),
					lnbfault(4)
					}
TxStatus ::= TEXTUAL-CONVENTION
    STATUS       current
    DESCRIPTION
        "Describes all the possible faults in the system as a bit pattern."
    SYNTAX      BITS {                   
                    txrs232(0), -- tx from rs232
                    txrs485(1), -- tx from rs485
					txfsk(2),	-- tx from fsk
					txfsk(3),	-- tx from http
					txsnmp(4),	-- tx from snmp
					txtelnet(5)	-- tx from telnet
					}

-- ***##############################################################***
--              Groups within the rbuc MIB
-- ***##############################################################***

configuration		OBJECT IDENTIFIER ::= { rbucMIB 1 }
status				OBJECT IDENTIFIER ::= { rbucMIB 2 }
info				OBJECT IDENTIFIER ::= { rbucMIB 3 }


-- ####################################################################
-- *** RBUC Configuration groups - run time changing settings ***
-- ####################################################################

-- *** Configuration groups -  ***
txSettings          OBJECT IDENTIFIER ::= { configuration 1 }
pktProtocol			OBJECT IDENTIFIER ::= { configuration 2 }
rcSetting	        OBJECT IDENTIFIER ::= { configuration 3 }
freqs				OBJECT IDENTIFIER ::= { configuration 4 }
misc				OBJECT IDENTIFIER ::= { configuration 5 }

-- Tx Settings Group

txOn OBJECT-TYPE
    SYNTAX      INTEGER
    MAX-ACCESS  read-write
    STATUS      current
    DESCRIPTION
        "Sets Tx on/off."
    ::= { txSettings 1 }

txDefault OBJECT-TYPE
    SYNTAX      TruthValue
    MAX-ACCESS  read-write
    STATUS      current
    DESCRIPTION
        "Sets Tx default 1-last 0-off."
    ::= { txSettings 2 }

txAttenuator OBJECT-TYPE
    SYNTAX      INTEGER (0..15)
    UNITS      "dBm"
    MAX-ACCESS  read-write
    STATUS      current
    DESCRIPTION
        "Sets/Gets Tx attenuation value in 1dBm steps."
    ::= { txSettings 3 }

-- Packet Protocol Settings Group

protocol		OBJECT-TYPE
    SYNTAX      INTEGER (0..4)
    MAX-ACCESS  read-write
    STATUS      current
    DESCRIPTION
        "Sets/Gets packet protocol 0 - ASCII, 1 - CODAN, 2 - ."
    ::= { pktProtocol 1 }

address		OBJECT-TYPE
    SYNTAX      INTEGER
    MAX-ACCESS  read-write
    STATUS      current
    DESCRIPTION
        "Sets/Gets packet address: 0-31 NDSatcom ..."
    ::= { pktProtocol 2 }

-- Redundancy Controller Group

mode OBJECT-TYPE
    SYNTAX      INTEGER (0..2)
    MAX-ACCESS  read-write
    STATUS      current
    DESCRIPTION
        "Sets/Gets redundancy mode 0-none, 1-warm, 2-hot."
    ::= { rcSetting 1 }

onLine OBJECT-TYPE
    SYNTAX      TruthValue
    MAX-ACCESS  read-write
    STATUS      current
    DESCRIPTION
        "Sets/Gets redundancy mode on on/off line state."
    ::= { rcSetting 2 }


-- Frequency Group 

rfFreq OBJECT-TYPE
    SYNTAX      INTEGER
    UNITS      "MHz"
    MAX-ACCESS  read-write
    STATUS      current
    DESCRIPTION
        "Sets/Gets the RBUC RF frequency."
    ::= { freqs 1 }

ifFreq OBJECT-TYPE
    SYNTAX      INTEGER
    UNITS      "MHz"
    MAX-ACCESS  read-write
    STATUS      current
    DESCRIPTION
        "Sets/Gets the RBUC IF frequency."
    ::= { freqs 2 }

loFreq OBJECT-TYPE
    SYNTAX      INTEGER
    UNITS      "MHz"
    MAX-ACCESS  read-write
    STATUS      current
    DESCRIPTION
        "Sets/Gets the RBUC LO frequency."
    ::= { freqs 3 }

-- Miscellaneous Group

serIf OBJECT-TYPE
    SYNTAX      DisplayString
    MAX-ACCESS  read-write
    STATUS      current
    DESCRIPTION
        "Sets/Gets serial interface - rate, length, parity, stop, terminate RS422/485."
    ::= { misc 1 }

serEcho OBJECT-TYPE
    SYNTAX		TruthValue
    MAX-ACCESS  read-write
    STATUS      current
    DESCRIPTION
        "Sets/Gets serial interface echo on/off."
    ::= { misc 2 }

pwrAlarmThresh OBJECT-TYPE
    SYNTAX		DisplayString 
    UNITS      "dB"
    MAX-ACCESS  read-write
    STATUS      current
    DESCRIPTION
        "Sets/Gets power alarm threshold."
    ::= { misc 3 }

burstPwrThresh OBJECT-TYPE
    SYNTAX      DisplayString
    UNITS      "dB"
    MAX-ACCESS  read-write
    STATUS      current
    DESCRIPTION
        "Sets/Gets burst power threshold."
    ::= { misc 4 }

refSource OBJECT-TYPE
    SYNTAX		TruthValue
    MAX-ACCESS  read-write
    STATUS      current
    DESCRIPTION
        "Sets/Gets reference source 0-external, 1-internal."
    ::= { misc 5 }

ledState OBJECT-TYPE
    SYNTAX		TruthValue
    MAX-ACCESS  read-write
    STATUS      current
    DESCRIPTION
        "SetS/Gets LEDs status on/off."
    ::= { misc 6 }
 

-- ####################################################################
-- *** RBUC Status  Group ***
-- ####################################################################

paStatus OBJECT-TYPE
    SYNTAX      INTEGER{
                    off (0),
                    on  (1)
                    }
    MAX-ACCESS  read-only
    STATUS      current
    DESCRIPTION
        "Gets to 1 when PA is on."
    ::= { status 1 }

txPower OBJECT-TYPE
    SYNTAX      DisplayString
    UNITS      "dB"
    MAX-ACCESS  read-only
    STATUS      current
    DESCRIPTION
        "Gets Tx power format x.x dB."
    ::= { status 2}

txBurstPower OBJECT-TYPE
    SYNTAX      DisplayString
    UNITS      "dB"
    MAX-ACCESS  read-only
    STATUS      current
    DESCRIPTION
        "Gets Tx power. Format is x.x,y.y,z.z, where x.x is current burst 
	power, y.y is min and z.z is max burts power."
    ::= { status 3}

faults OBJECT-TYPE
    SYNTAX      INTEGER
    MAX-ACCESS  read-only
    STATUS      current
    DESCRIPTION
        "Gets the current fault status. Format - Bit0 PA fault, Bit1 Fan fault,
	Bit2 Power fault, Bit3 Temp fault, Bit4 10MHz fault, Bit5 Internal fault
	Bit6 LNB fault, Bit7 Red'cy Cont fault."
    ::= { status 4}

latchedFaults OBJECT-TYPE
    SYNTAX      INTEGER
    MAX-ACCESS  read-only
    STATUS      current
    DESCRIPTION
        "Gets the current latched faults. Format is same as Faults."
    ::= { status 5}

temperature OBJECT-TYPE
    SYNTAX      DisplayString
    MAX-ACCESS  read-only
    STATUS      current
    DESCRIPTION
        "Gets the BUC temperature. Format is x.x."
    ::= { status 6}

minMaxTemperature OBJECT-TYPE
    SYNTAX      DisplayString
    MAX-ACCESS  read-only
    STATUS      current
    DESCRIPTION
        "Gets the BUC temperature. Format is x.x,y.y where x.x is max
	and y.y is min temperature."
    ::= { status 7}

systemSetting OBJECT-TYPE
    SYNTAX      INTEGER (0..2047)
    MAX-ACCESS  read-only
    STATUS      current
    DESCRIPTION
        "Gets the current system status. Format is 
	Bit0 - PA state, Bit1 - RS232 Tx, Bit2 - FSK Tx, Bit3 - RS485 Tx
	Bit4 - Redundancy mode, Bit5 - Online,
	Bit6..Bit7 - Redundancy cold or hot mode, Bit8 - HTTP Tx, Bit9 - TELNET Tx,
	Bit10 - SNMP Tx."
    ::= { status 8}

systemPoll OBJECT-TYPE
    SYNTAX      INTEGER  (0..3)
    MAX-ACCESS  read-only
    STATUS      current
    DESCRIPTION
        "Gets the system poll status. Format is
	Bit0 - Fault, Bit1 - System change."
    ::= { status 9}

deviceType OBJECT-TYPE
    SYNTAX      DisplayString
    MAX-ACCESS  read-only
    STATUS      current
    DESCRIPTION
        "Gets the device type. Format is X,Y where X is the model and 
	Y is software version."
    ::= { status 10}

gateway OBJECT-TYPE
    SYNTAX      DisplayString
    MAX-ACCESS  read-only
    STATUS      current
    DESCRIPTION
        "Gets the BUC gateway address."
    ::= { status 11}

ipAddr OBJECT-TYPE
    SYNTAX      DisplayString
    MAX-ACCESS  read-only
    STATUS      current
    DESCRIPTION
        "Gets the BUC IP address."
    ::= { status 12}

macAddress OBJECT-TYPE
    SYNTAX      DisplayString
    MAX-ACCESS  read-only
    STATUS      current
    DESCRIPTION
        "Gets the BUC MAC address."
    ::= { status 13}

netmask OBJECT-TYPE
    SYNTAX      DisplayString
    MAX-ACCESS  read-only
    STATUS      current
    DESCRIPTION
        "Gets the BUC netmask."
    ::= { status 14}

refPower OBJECT-TYPE
    SYNTAX      DisplayString
    MAX-ACCESS  read-only
    STATUS      current
    DESCRIPTION
        "Gets the BUC reference power."
    ::= { status 15}

bucConfiguration OBJECT-TYPE
    SYNTAX      DisplayString
    MAX-ACCESS  read-only
    STATUS      current
    DESCRIPTION
        "Gets the BUC configuration."
    ::= { status 16}

buildStandard OBJECT-TYPE
    SYNTAX      DisplayString
    MAX-ACCESS  read-only
    STATUS      current
    DESCRIPTION
        "Gets the BUC build standard."
    ::= { status 17}


-- ####################################################################
-- *** RBUC Info groups - version, model serial No ***
-- ####################################################################


idInfo  OBJECT-TYPE
    SYNTAX     DisplayString
    MAX-ACCESS read-only
    STATUS     current
    DESCRIPTION
    "Gets the module firmware revision, serial number and model. This string
    will have a zero length if the revision is unknown."
    ::= { info 1 }

limits  OBJECT-TYPE
    SYNTAX     DisplayString
    MAX-ACCESS read-only
    STATUS     current
    DESCRIPTION
    "Gets the limit data for the BUC. Format is:
	Power meter MIN/MAX , IF,RF and LO frequencies.
	This string will have a zero length if the revision is unknown."
    ::= { info 2 }

pktProtocolsInfo  OBJECT-TYPE
    SYNTAX     DisplayString
    MAX-ACCESS read-only
    STATUS     current
    DESCRIPTION
    "Gets supported packet protocols and the corresponding address ranges."
    ::= { info 3 }

END
