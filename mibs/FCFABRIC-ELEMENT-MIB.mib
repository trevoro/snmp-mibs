FCFABRIC-ELEMENT-MIB DEFINITIONS ::= BEGIN

IMPORTS
    MODULE-IDENTITY, OBJECT-TYPE,
    experimental, Counter32, Gauge32, TimeTicks
        FROM SNMPv2-SMI
    TEXTUAL-CONVENTION, TruthValue, DisplayString
        FROM SNMPv2-TC;


fibreChannel MODULE-IDENTITY
    LAST-UPDATED "9702070000Z"
    ORGANIZATION "ANSI X3T11 Fibre Channel Working Group"
    CONTACT-INFO "     Kha Sin Teow
                       Brocade Communications Systems,
                       2231 Calle De Luna,
                       Santa Clara, CA 95054-1002
                       U.S.A
                       Tel: +1 408 588 4100
                       Fax: +1 408 588 4101
                       Email: khasin@BrocadeComm.COM"
    DESCRIPTION "The MIB module for Fibre Channel Fabric Element."
    REVISION "9702070000Z"
    DESCRIPTION "Version 1.9"
    ::= { experimental 42 }

fcFabric OBJECT IDENTIFIER ::= { fibreChannel 2 }

        -- Fabric Element
           fcFe OBJECT IDENTIFIER ::= { fcFabric 1 }

        -- Groups under fcFe
           fcFeConfig       OBJECT IDENTIFIER ::= { fcFe 1 }
           fcFeOp           OBJECT IDENTIFIER ::= { fcFe 2 }
           fcFeError        OBJECT IDENTIFIER ::= { fcFe 3 }
           fcFeAcct         OBJECT IDENTIFIER ::= { fcFe 4 }
           fcFeCap          OBJECT IDENTIFIER ::= { fcFe 5 }

        -- Type definitions.

        MilliSeconds ::= INTEGER (0..4294967295)

        MicroSeconds ::= INTEGER (0..4294967295)

        FcNameId ::= OCTET STRING (SIZE (8))
                -- Worldwide Name or Fibre Channel Name associated with
                -- an FC entity.  It's a Network_Destination_ID or
                -- Network_Source_ID composed of a value up to 60 bits
                -- wide, occupying the remaining 8 bytes while the first
                -- nibble identifies the format of the Name_Identifier with
                -- hex values:
                -- 0: ignored
                -- 1: IEEE 48-bit address,
                -- 2: IEEE extended,
                -- 3: Locally assigned,
                -- 4: 32-bit IP address,
                -- C: CCITT 60-bit individual address, and
                -- E: CCITT 60-bit group address.
                -- ([1] (19.3, Tables 41-44)).

        FabricName ::= FcNameId
                -- The Name Identifier of a Fabric.  Each Fabric shall
                -- provide a unique Fabric Name.
                -- Only the following formats are allowed:
                --   CCITT individual & group, IEEE, and Local.
                -- ([1](19.3.3, 23.7.3)).

        FcPortName ::= FcNameId
                -- The Name Identifier associated with a port
                -- Only the following formats are allowed:
                --   CCITT individual & group, IEEE, IEEE extended, and Local.
                -- ([1](19.3.3, 23.6.4 and 23.7.2))).

        FcAddressId ::= OCTET STRING (SIZE (3))
                -- Fibre Channel Address Identifier.  A 24-bit value unique
                -- within the address domain of a Fabric ([1](18.3))).

        FcRxDataFieldSize ::= INTEGER (128..2112)
                -- Receive Data_Field Size ([1](23.6.2.4, 23.6.8.5))).

        FcBbCredit ::= INTEGER (0..32767)
                -- Buffer-to-buffer Credit
                -- ([1](23.6.2.2, 23.7.1.2))).

        -- FC-PH version ([1](23.7.1.1)))
        FcphVersion ::= INTEGER (0..255)

        -- Class 1 Stacked Connect Support/Mode
        -- [1] (23.7.4.2)
        FcStackedConnMode ::= INTEGER {
                none            (1),
                transparent     (2),
                lockedDown      (3)
        }

        -- Class of Service Capability Set
        FcCosCap ::= INTEGER (0..127)
                -- bit 0        Class F
                -- bit 1        Class 1
                -- bit 2        Class 2
                -- bit 3        Class 3
                -- bit 4        Class 4
                -- bits 5-7     reserved for future

        -- FC-0 Baud Rates (FC-PH(REV 7.3(6.1))
        Fc0BaudRate ::= INTEGER {
                other           (1),    -- none of below
                oneEighth       (2),    -- 155 Mbaud
                quarter         (4),    -- 266 Mbaud
                half            (8),    -- 532 Mbaud
                full            (16),   --   1 Gbaud
                double          (32),   --   2 Gbaud
                quadruple       (64)    --   4 Gbaud
        }

        -- Baud Rate Capability Set
        Fc0BaudRateCap ::= INTEGER (0..127)
                -- bit 0        other
                -- bit 1        oneEighth
                -- bit 2        quarter
                -- bit 3        half
                -- bit 4        full
                -- bit 5        double
                -- bit 6        quadruple
                -- bits 7-8     reserved for future

        -- FC-0 Media Capability Set
        Fc0MediaCap ::= INTEGER (0..65535)
                -- bit 0        unknown
                -- bit 1        single mode fibre (sm)
                -- bit 2        multi-mode fibre 50 micron (m5)
                -- bit 3        multi-mode fibre 62.5 micron (m6)
                -- bit 4        video cable (tv)
                -- bit 5        miniature cable (mi)
                -- bit 6        shielded twisted pair (stp)
                -- bit 7        unshielded twisted pair (utp)
                -- bits 8-15    reserved for future use

        -- A specific FC-0 medium type associated with a port
        -- FC-PH Rev 7.3 (6.1)
        Fc0Medium ::= INTEGER {
                unknown (1),
                sm      (2),    -- single mode
                m5      (4),    -- multimode 50 microns
                m6      (8),    -- multimode 62.5 microns
                tv      (16),   -- video cable
                mi      (32),   -- miniature cable
                stp     (64)    -- twisted pair
        }



        -- The FC-0 transmitter type of a port
        -- FC-PH Rev 7.3 (6.1)
        Fc0TxType ::= INTEGER {
                        unknown         (1),
                        longWaveLaser   (2),
                        shortWaveLaser  (3),
                        longWaveLED     (4),
                        electrical      (5),
                        shortWaveLaser-noOFC    (6) -- no open fibre control
        }

        -- The FC-0 distance range associated with a port transmitter
        -- [1] (5.7)
        Fc0Distance ::= INTEGER {
                        unknown         (1),
                        long            (2),
                        intermediate    (3),
                        short           (4)
        }

        -- Module and Port Capacity
        FcFeModuleCapacity ::= INTEGER (1..256)
         FcFeFPortCapacity ::= INTEGER (1..256)

        -- Module and Port Index
        FcFeModuleIndex ::= INTEGER (1..256)
         FcFeFPortIndex ::= INTEGER (1..256)
        -- The Configuration group

        -- This group consists of scalar objects and tables.
        -- It contains the configuration and service parameters
        -- of the Fabric Element and the F_Ports.
        -- The group represents a set of parameters associated with
        -- the Fabric Element or an F_Port to support its N_Ports.
        -- Implementation of this group is mandatory.

        fcFabricName OBJECT-TYPE
            SYNTAX      FabricName
            MAX-ACCESS  read-only
            STATUS      current
            DESCRIPTION
               "The Name_Identifier of the Fabric to which this Fabric
                Element belongs.
                [1](23.7.3), [2](3.1.29), [3](3.1.21)"
            ::= { fcFeConfig 1 }

        fcElementName OBJECT-TYPE
            SYNTAX      FcNameId
            MAX-ACCESS  read-only
            STATUS      current
            DESCRIPTION
               "The Name_Identifier of the Fabric Element.
                [2](3.1.22), [3](3.1.14)"
            ::= { fcFeConfig 2 }

        fcFeModuleCapacity OBJECT-TYPE
            SYNTAX      FcFeModuleCapacity
            MAX-ACCESS  read-only
            STATUS      current
            DESCRIPTION
               "The maximum number of modules in the Fabric Element,
                regardless of their current state."
            ::= { fcFeConfig 3 }

        -- The Module Table.
        -- This table contains one entry for each module,
        -- information of the modules.

        fcFeModuleTable OBJECT-TYPE
            SYNTAX      SEQUENCE OF FcFeModuleEntry
            MAX-ACCESS  not-accessible
            STATUS      current
            DESCRIPTION
               "A table that contains, one entry for each module in the
                Fabric Element, information of the modules."
            ::= { fcFeConfig 4 }

        fcFeModuleEntry OBJECT-TYPE
            SYNTAX      FcFeModuleEntry
            MAX-ACCESS  not-accessible
            STATUS      current
            DESCRIPTION
               "An entry containing the configuration parameters of a
                module."
            INDEX { fcFeModuleIndex }
            ::= { fcFeModuleTable 1 }

        FcFeModuleEntry ::=
            SEQUENCE {
                fcFeModuleIndex
                    FcFeModuleIndex,
                fcFeModuleDescr
                    DisplayString,
                fcFeModuleObjectID
                    OBJECT IDENTIFIER,
                fcFeModuleOperStatus
                    INTEGER,
                fcFeModuleLastChange
                    TimeTicks,
                fcFeModuleFPortCapacity
                    FcFeFPortCapacity
            }

        fcFeModuleIndex OBJECT-TYPE
            SYNTAX      FcFeModuleIndex
            MAX-ACCESS  read-only
            STATUS      current
            DESCRIPTION
               "This object identifies the module within the Fabric Ele-
                ment for which this entry contains information. This
                value is never greater than fcFeModuleCapacity."
            ::= { fcFeModuleEntry 1 }

        fcFeModuleDescr OBJECT-TYPE
            SYNTAX      DisplayString
            MAX-ACCESS  read-only
            STATUS      current
            DESCRIPTION
               "A textual description of the module. This value should
                include the full name and version identification of the
                module. It should contain printable ASCII characters."
            ::= { fcFeModuleEntry 2 }

        fcFeModuleObjectID OBJECT-TYPE
            SYNTAX      OBJECT IDENTIFIER
            MAX-ACCESS  read-only
            STATUS      current
            DESCRIPTION
               "The vendor's authoritative identification of the module.
                This value may be allocated within the SMI enterprises
                subtree (1.3.6.1.4.1) and provides a straight-forward
                and unambiguous means for determining what kind of mod-
                ule is being managed.

                For example, this object could take the value
                1.3.6.1.4.1.9999.3.9 if vendor 'Neufe Inc.' was assigned
                the subtree 1.3.6.1.4.1.99649, and had assigned the
                identifier 1.3.6.1.4.1.99649.3.9 to its 'FeFiFo-16 Plug-
                InCard.'"
            ::= { fcFeModuleEntry 3 }

        fcFeModuleOperStatus    OBJECT-TYPE
            SYNTAX      INTEGER {
                            online  (1), -- functional
                            offline (2), -- not available
                            testing (3), -- under testing
                            faulty  (4)  -- defective
                        }
            ACCESS      read-only
            STATUS      current
            DESCRIPTION
               "This object indicates the operational status of the mod-
                ule:
                online(1)   the module is functioning properly;
                offline(2)  the module is not available;
                testing(3)  the module is under testing; and
                faulty(4)   the module is defective in some way."
            ::= { fcFeModuleEntry 4 }

        fcFeModuleLastChange OBJECT-TYPE
            SYNTAX      TimeTicks
            MAX-ACCESS  read-only
            STATUS      current
            DESCRIPTION
               "This object contains the value of sysUpTime when the
                module entered its current operational status. A value
                of zero indicates that the operational status of the
                module has not changed since the agent last restarted."
            ::= { fcFeModuleEntry 5 }

        fcFeModuleFPortCapacity OBJECT-TYPE
            SYNTAX      FcFeFPortCapacity
            MAX-ACCESS  read-only
            STATUS      current
            DESCRIPTION
               "The number of F_Ports that can be contained within the
                module. Within each module, the ports are uniquely num-
                bered in the range from 1 to fcFeModuleFPortCapacity
                inclusive. However, the numbers are not required to be
                contiguous."
            ::= { fcFeModuleEntry 6 }

        -- the F_Port Configuration Table.
        -- This table contains, one entry for each F_Port,
        -- configuration parameters of the ports.

        fcFPortConfigTable OBJECT-TYPE
            SYNTAX      SEQUENCE OF FcFPortConfigEntry
            MAX-ACCESS  not-accessible
            STATUS      current
            DESCRIPTION
               "A table that contains, one entry for each F_Port in the
                Fabric Element, configuration and service parameters of
                the F_Ports.
                [1](23)"
            ::= { fcFeConfig 5 }

        fcFPortConfigEntry OBJECT-TYPE
            SYNTAX      FcFPortConfigEntry
            MAX-ACCESS  not-accessible
            STATUS      current
            DESCRIPTION
               "An entry containing the configuration and service param-
                eters of a F_Port.
                [1](23)"
            INDEX { fcFPortConfigModuleIndex, fcFPortConfigFPortIndex }
            ::= { fcFPortConfigTable 1 }

        FcFPortConfigEntry ::=
            SEQUENCE {
                fcFPortConfigModuleIndex
                    FcFeModuleIndex,
                fcFPortConfigFPortIndex
                    FcFeFPortIndex,
                fcFPortName
                    FcPortName,
                -- F_Port common service parameters
                fcFPortFcphVersionHigh
                    FcphVersion,
                fcFPortFcphVersionLow
                    FcphVersion,
                fcFPortBbCredit
                    FcBbCredit,
                fcFPortRxBufSize
                    FcRxDataFieldSize,
                fcFPortRatov
                    MilliSeconds,
                fcFPortEdtov
                    MilliSeconds,
                -- F_Port class service parameters
                fcFPortCosSupported
                    FcCosCap,
                fcFPortIntermixSupported
                    TruthValue,
                fcFPortStackedConnMode
                    FcStackedConnMode,
                fcFPortClass2SeqDeliv
                    TruthValue,
                fcFPortClass3SeqDeliv
                    TruthValue,
                fcFPortHoldTime
                    MicroSeconds,
                fcFPortBaudRate
                    Fc0BaudRate,
                fcFPortMedium
                    Fc0Medium,
                fcFPortTxType
                    Fc0TxType,
                fcFPortDistance
                    Fc0Distance
            }

        fcFPortConfigModuleIndex OBJECT-TYPE
            SYNTAX      FcFeModuleIndex
            MAX-ACCESS  read-only
            STATUS      current
            DESCRIPTION
               "This object identifies the module containing the F_Port
                for which this entry contains information."
            ::= { fcFPortConfigEntry 1 }

        fcFPortConfigFPortIndex OBJECT-TYPE
            SYNTAX      FcFeFPortIndex
            MAX-ACCESS  read-only
            STATUS      current
            DESCRIPTION
               "This object identifies the F_Port within the module.
                This number ranges from 1 to the value of fcFeModule-
                PortCapacity for the associated module. The value
                remains constant for the identified F_Port until the
                module is re-initialized."
            ::= { fcFPortConfigEntry 2 }

        fcFPortName  OBJECT-TYPE
            SYNTAX      FcPortName
            MAX-ACCESS  read-only
            STATUS      current
            DESCRIPTION
               "The name identifier of this F_Port.  Each F_Port has a
                unique port name within the address space of the Fabric.
                [1](19.3.3, 23.7.2), [2](3.1.53) [3](3.1.44)"
            ::= { fcFPortConfigEntry 3 }


            -- F_Port common service parameters

        fcFPortFcphVersionHigh OBJECT-TYPE
            SYNTAX      FcphVersion
            MAX-ACCESS  read-only
            STATUS      current
            DESCRIPTION
               "The highest or most recent version of FC-PH that the
                F_Port is configured to support.
                [1](23.7.1.1), [2](10.4.1)"
            ::= { fcFPortConfigEntry 4 }

        fcFPortFcphVersionLow OBJECT-TYPE
            SYNTAX      FcphVersion
            MAX-ACCESS  read-only
            STATUS      current
            DESCRIPTION
               "The lowest or earliest version of FC-PH that the F_Port
                is configured to support.
                [1](23.7.1.1), [2](10.4.1)"
            ::= { fcFPortConfigEntry 5 }

        fcFPortBbCredit OBJECT-TYPE
            SYNTAX      FcBbCredit
            MAX-ACCESS  read-only
            STATUS      current
            DESCRIPTION
               "The total number of receive buffers available for hold-
                ing Class 1 connect-request, Class 2 or 3 frames from
                the attached N_Port.  It is for buffer-to-buffer flow
                control in the direction from the attached N_Port (if
                applicable) to F_Port.
                [1](23.7.1.2), [2](10.4.1), [3](15.2)."
            ::= { fcFPortConfigEntry 6 }

        fcFPortRxBufSize OBJECT-TYPE
            SYNTAX      FcRxDataFieldSize
            MAX-ACCESS  read-only
            STATUS      current
            DESCRIPTION
               "The largest Data_Field Size (in octets) for an FT_1
                frame that can be received by the F_Port.
                [1](17.4, 23.7.1.4)"
            ::= { fcFPortConfigEntry 7 }

        fcFPortRatov OBJECT-TYPE
            SYNTAX      MilliSeconds
            MAX-ACCESS  read-only
            STATUS      current
            DESCRIPTION
               "The Resource_Allocation_Timeout Value configured for the
                F_Port.  This is used as the timeout value for determin-
                ing when to reuse an N_Port resource such as a Recov-
                ery_Qualifier.  It represents E_D_TOV (see next object)
                plus twice the maximum time that a frame may be delayed
                within the Fabric and still be delivered.
                [1](23.7.1.6, 29.2.1.3), [3](14.4.1.2)."
            ::= { fcFPortConfigEntry 8 }

        fcFPortEdtov OBJECT-TYPE
            SYNTAX      MilliSeconds
            MAX-ACCESS  read-only
            STATUS      current
            DESCRIPTION
               "The E_D_TOV value configured for the F_Port. The
                Error_Detect_Timeout Value is used as the timeout value
                for detecting an error condition.
                [1](23.7.1.5, 29.2.1.2), [3](14.4.1.4)"
            ::= { fcFPortConfigEntry 9 }


        -- F_Port class service parameters

        fcFPortCosSupported OBJECT-TYPE
            SYNTAX      FcCosCap
            MAX-ACCESS  read-only
            STATUS      current
            DESCRIPTION
               "A value indicating the set of Classes of Service sup-
                ported by the F_Port.
                [1](23.7.4.1), [2](Table 10.2), [3](15.3.5.1, 15.3.5.2)"
            ::= { fcFPortConfigEntry 10 }

        fcFPortIntermixSupported OBJECT-TYPE
            SYNTAX      TruthValue
            MAX-ACCESS  read-only
            STATUS      current
            DESCRIPTION
               "A flag indicating whether or not the F_Port supports an
                Intermixed Dedicated Connection.
                [1](23.7.4.2)"
            ::= { fcFPortConfigEntry 11 }

        fcFPortStackedConnMode OBJECT-TYPE
            SYNTAX      FcStackedConnMode
            MAX-ACCESS  read-only
            STATUS      current
            DESCRIPTION
               "A value indicating the mode of Stacked Connect supported
                by the F_Port.
                [1](23.7.4.2)"
            ::= { fcFPortConfigEntry 12 }

        fcFPortClass2SeqDeliv OBJECT-TYPE
            SYNTAX      TruthValue
            MAX-ACCESS  read-only
            STATUS      current
            DESCRIPTION
               "A flag indicating whether or not Class 2 Sequential
                Delivery is supported by the F_Port.
                [1](23.7.4.2)"
            ::= { fcFPortConfigEntry 13 }

        fcFPortClass3SeqDeliv OBJECT-TYPE
            SYNTAX      TruthValue
            MAX-ACCESS  read-only
            STATUS      current
            DESCRIPTION
               "A flag indicating whether or not Class 3 Sequential
                Delivery is supported by the F_Port.
                [1](23.7.4.2)"
            ::= { fcFPortConfigEntry 14 }

        fcFPortHoldTime OBJECT-TYPE
            SYNTAX      MicroSeconds
            MAX-ACCESS  read-only
            STATUS      current
            DESCRIPTION
               "The maximum time (in microseconds) that the F_Port shall
                hold a frame before discarding the frame if it is unable
                to deliver the frame. The value 0 means that the F_Port
                does not support this parameter."
            ::= { fcFPortConfigEntry 15 }

        fcFPortBaudRate OBJECT-TYPE
            SYNTAX      Fc0BaudRate
            MAX-ACCESS  read-only
            STATUS      current
            DESCRIPTION
               "The FC-0 baud rate of the F_Port.
                [1](5.1)"
            ::= { fcFPortConfigEntry 16 }

        fcFPortMedium OBJECT-TYPE
            SYNTAX      Fc0Medium
            MAX-ACCESS  read-only
            STATUS      current
            DESCRIPTION
               "The FC-0 medium of the F_Port.
                [1](5.1)"
            ::= { fcFPortConfigEntry 17 }

        fcFPortTxType OBJECT-TYPE
            SYNTAX      Fc0TxType
            MAX-ACCESS  read-only
            STATUS      current
            DESCRIPTION
               "The FC-0 transmitter type of the F_Port.
                [1](5.1)"
            ::= { fcFPortConfigEntry 18 }

        fcFPortDistance OBJECT-TYPE
            SYNTAX      Fc0Distance
            MAX-ACCESS  read-only
            STATUS      current
            DESCRIPTION
               "The FC-0 distance range of the F_Port transmitter.
                [1](5.1)"
            ::= { fcFPortConfigEntry 19 }



        -- the Operation group

        -- This group consists of tables that contains operational
        -- status and established service parameters for the Fabric
        -- Element and the attached N_Ports.
        -- Implementation of this group is mandatory.

        -- The F_Port Operation table
        -- This table contains, one entry for each F_Port,
        -- the operational status and parameters of the F_Ports.

        fcFPortOperTable OBJECT-TYPE
            SYNTAX      SEQUENCE OF FcFPortOperEntry
            MAX-ACCESS  not-accessible
            STATUS      current
            DESCRIPTION
               "A table that contains, one entry for each F_Port in the
                Fabric Element, operational status and parameters of the
                F_Ports."
            ::= { fcFeOp 1 }

        fcFPortOperEntry OBJECT-TYPE
            SYNTAX      FcFPortOperEntry
            MAX-ACCESS  not-accessible
            STATUS      current
            DESCRIPTION
               "An entry containing operational status and parameters of
                a F_Port.
                [1]"
            INDEX { fcFPortOperModuleIndex, fcFPortOperFPortIndex }
            ::= { fcFPortOperTable 1 }

        FcFPortOperEntry ::=
            SEQUENCE {
                fcFPortOperModuleIndex
                    FcFeModuleIndex,
                fcFPortOperFPortIndex
                    FcFeFPortIndex,
                fcFPortID
                    FcAddressId,
                fcFPortAttachedPortName
                    FcPortName,
                fcFPortConnectedPort
                    FcAddressId,
                fcFPortBbCreditAvailable
                    Gauge32
            }

        fcFPortOperModuleIndex OBJECT-TYPE
            SYNTAX      FcFeModuleIndex
            MAX-ACCESS  read-only
            STATUS      current
            DESCRIPTION
               "This object identifies the module containing the F_Port
                for which this entry contains information."
            ::= { fcFPortOperEntry 1 }

        fcFPortOperFPortIndex OBJECT-TYPE
            SYNTAX      FcFeFPortIndex
            MAX-ACCESS  read-only
            STATUS      current
            DESCRIPTION
               "This object identifies the F_Port within the module.
                This number ranges from 1 to the value of fcFeModule-
                PortCapacity for the associated module. The value
                remains constant for the identified F_Port until the
                module is re-initialized."
            ::= { fcFPortOperEntry 2 }

        fcFPortID    OBJECT-TYPE
            SYNTAX      FcAddressId
            MAX-ACCESS  read-only
            STATUS      current
            DESCRIPTION
               "The address identifier by which this F_Port is identi-
                fied within the Fabric.  The F_Port may assign its
                address identifier to its attached N_Port during Fabric
                Login.
                [1](23.3), [2](4.5.1)"
            ::= { fcFPortOperEntry 3 }

        fcFPortAttachedPortName OBJECT-TYPE
            SYNTAX      FcPortName
            MAX-ACCESS  read-only
            STATUS      current
            DESCRIPTION
               "The port name of the attached N_Port, if applicable. If
                the value of this object is '0000000000000000'H, this
                F_Port has no N_Port attached to it.
                [1](23.6.4)"
            ::= { fcFPortOperEntry 4 }
            
        fcFPortConnectedPort OBJECT-TYPE
            SYNTAX      FcAddressId
            MAX-ACCESS  read-only
            STATUS      current
            DESCRIPTION
               "The address identifier of the destination F_Port with
                which this F_Port is currently engaged in a Class 1 con-
                nection. If the value of this object is '000000'H, this
                F_Port is not engaged in a Class 1 connection.
                [1](28)"
            ::= { fcFPortOperEntry 5 }

        fcFPortBbCreditAvailable OBJECT-TYPE
            SYNTAX      Gauge32
            MAX-ACCESS  read-only
            STATUS      current
            DESCRIPTION
               "The number of buffers currently available for receiving
                frames from the attached port in the buffer-to-buffer
                flow control. The value should be less than or equal to
                fcFPortBbCredit.
                [1](26)"
            ::= { fcFPortOperEntry 6 }


        -- The Fabric Login table
        --
        -- This table contains, one entry for each F_Port in the
        -- Fabric Element, the Service Parameters that have been
        -- established from the most recent Fabric Login
        -- (implicit or explicit).

        fcFPortFlogiTable OBJECT-TYPE
            SYNTAX      SEQUENCE OF FcFPortFlogiEntry
            MAX-ACCESS  not-accessible
            STATUS      current
            DESCRIPTION
               "A table that contains, one entry for each F_Port in the
                Fabric Element, services parameters established from the
                most recent Fabric Login (explicit or implicit).
                [1](23.3)"
            ::= { fcFeOp 2 }

        fcFPortFlogiEntry OBJECT-TYPE
            SYNTAX      FcFPortFlogiEntry
            MAX-ACCESS  not-accessible
            STATUS      current
            DESCRIPTION
               "An entry containing service parameters established from
                a successful Fabric Login.
                [1](23.3)"
            INDEX { fcFPortFlogiModuleIndex, fcFPortFlogiFPortIndex }
            ::= { fcFPortFlogiTable 1 }

        FcFPortFlogiEntry ::=
            SEQUENCE {
                fcFPortFlogiModuleIndex
                    FcFeModuleIndex,
                fcFPortFlogiFPortIndex
                    FcFeFPortIndex,
                fcFPortFcphVersionAgreed
                    FcphVersion,
                fcFPortNPortBbCredit
                    FcBbCredit,
                fcFPortNPortRxDataFieldSize
                    FcRxDataFieldSize,
                fcFPortCosSuppAgreed
                    FcCosCap,
                fcFPortIntermixSuppAgreed
                    TruthValue,
                fcFPortStackedConnModeAgreed
                    FcStackedConnMode,
                fcFPortClass2SeqDelivAgreed
                    TruthValue,
                fcFPortClass3SeqDelivAgreed
                    TruthValue
            }

        fcFPortFlogiModuleIndex OBJECT-TYPE
            SYNTAX      FcFeModuleIndex
            MAX-ACCESS  read-only
            STATUS      current
            DESCRIPTION
               "This object identifies the module containing the F_Port
                for which this entry contains information."
            ::= { fcFPortFlogiEntry 1 }

        fcFPortFlogiFPortIndex OBJECT-TYPE
            SYNTAX      FcFeFPortIndex
            MAX-ACCESS  read-only
            STATUS      current
            DESCRIPTION
               "This object identifies the F_Port within the module.
                This number ranges from 1 to the value of fcFeModule-
                PortCapacity for the associated module. The value
                remains constant for the identified F_Port until the
                module is re-initialized."
            ::= { fcFPortFlogiEntry 2 }

        fcFPortFcphVersionAgreed OBJECT-TYPE
            SYNTAX      FcphVersion
            MAX-ACCESS  read-only
            STATUS      current
            DESCRIPTION
               "The version of FC-PH that the F_Port has agreed to sup-
                port from the Fabric Login
                [1](23.7.1.1)"
            ::= { fcFPortFlogiEntry 3 }

        fcFPortNPortBbCredit OBJECT-TYPE
            SYNTAX      FcBbCredit
            MAX-ACCESS  read-only
            STATUS      current
            DESCRIPTION
               "The total number of buffers available for holding Class
                1 connect-request, Class 2 or Class 3 frames to be
                transmitted to the attached N_Port.  It is for buffer-
                to-buffer flow control in the direction from F_Port to
                N_Port.
                [1](23.6.2.2)"
            ::= { fcFPortFlogiEntry 4 }

        fcFPortNPortRxDataFieldSize OBJECT-TYPE
            SYNTAX      FcRxDataFieldSize
            MAX-ACCESS  read-only
            STATUS      current
            DESCRIPTION
               "The Receive Data Field Size of the attached N_Port. This
                is a binary value that specifies the largest Data Field
                Size for an FT_1 frame that can be received by the
                N_Port. The value is in number of bytes and ranges from
                128 to 2112 inclusive.
                [1](23.6.2.4)"
            ::= { fcFPortFlogiEntry 5 }

        fcFPortCosSuppAgreed OBJECT-TYPE
            SYNTAX      FcCosCap
            MAX-ACCESS  read-only
            STATUS      current
            DESCRIPTION
               "A flag indicating that the attached N_Port has requested
                the F_Port for the support of classes of services and
                the F_Port has granted the request.
                [1](23.6.7.1, 23.7.4.1)"
            ::= { fcFPortFlogiEntry 6 }

        fcFPortIntermixSuppAgreed OBJECT-TYPE
            SYNTAX      TruthValue
            MAX-ACCESS  read-only
            STATUS      current
            DESCRIPTION
               "A flag indicating that the attached N_Port has requested
                the F_Port for the support of Intermix and the F_Port
                has granted the request. This flag is only valid if
                Class 1 service is supported.
                [1](23.6.7.2, 23.7.4.2)"
            ::= { fcFPortFlogiEntry 7 }

        fcFPortStackedConnModeAgreed OBJECT-TYPE
            SYNTAX      FcStackedConnMode
            MAX-ACCESS  read-only
            STATUS      current
            DESCRIPTION
               "A value indicating whether the F_Port has agreed to sup-
                port stacked connect from the Fabric Login. This is only
                meaningful if Class 1 service has been agreed.
                [1](23.6.7.2, 23.7.4.2)"
            ::= { fcFPortFlogiEntry 8 }

        fcFPortClass2SeqDelivAgreed OBJECT-TYPE
            SYNTAX      TruthValue
            MAX-ACCESS  read-only
            STATUS      current
            DESCRIPTION
               "A flag indicating whether the F_Port has agreed to sup-
                port Class 2 sequential delivery from the Fabric Login.
                This is only meaningful if Class 2 service has been
                agreed.
                [1](23.6.7.1, 23.7.4.1)"
            ::= { fcFPortFlogiEntry 9 }

        fcFPortClass3SeqDelivAgreed OBJECT-TYPE
            SYNTAX      TruthValue
            MAX-ACCESS  read-only
            STATUS      current
            DESCRIPTION
               "A flag indicating whether the F_Port has agreed to sup-
                port Class 3 sequential delivery from the Fabric Login.
                This is only meaningful if Class 3 service has been
                agreed.
                [1](23.6.7.1, 23.7.4.1)"
            ::= { fcFPortFlogiEntry 10 }

        -- the F_Port Physical Level table
        -- This table contains, one entry for each F_Port in the
        -- Fabric Element, the physical level status and parameters
        -- of the F_Ports.

        fcFPortPhysTable OBJECT-TYPE
            SYNTAX      SEQUENCE OF FcFPortPhysEntry
            MAX-ACCESS  not-accessible
            STATUS      current
            DESCRIPTION
               "A table that contains, one entry for each F_Port in the
                Fabric Element, physical level status and parameters of
                the F_Ports.
                [1](16.5, 29.2)"
            ::= { fcFeOp 3 }

        fcFPortPhysEntry OBJECT-TYPE
            SYNTAX      FcFPortPhysEntry
            MAX-ACCESS  not-accessible
            STATUS      current
            DESCRIPTION
               "An entry containing physical level status and parameters
                of a F_Port.
                [1](16.5, 29.2)"
            INDEX { fcFPortPhysModuleIndex, fcFPortPhysFPortIndex }
            ::= { fcFPortPhysTable 1 }

        FcFPortPhysEntry ::=
            SEQUENCE {
                fcFPortPhysModuleIndex
                    FcFeModuleIndex,
                fcFPortPhysFPortIndex
                    FcFeFPortIndex,
                fcFPortPhysAdminStatus
                    INTEGER,
                fcFPortPhysOperStatus
                    INTEGER,
                fcFPortPhysLastChange
                    TimeTicks,
                fcFPortPhysRttov
                    MilliSeconds
            }

        fcFPortPhysModuleIndex OBJECT-TYPE
            SYNTAX      FcFeModuleIndex
            MAX-ACCESS  read-only
            STATUS      current
            DESCRIPTION
               "This object identifies the module containing the F_Port
                for which this entry contains information."
            ::= { fcFPortPhysEntry 1 }

        fcFPortPhysFPortIndex OBJECT-TYPE
            SYNTAX      FcFeFPortIndex
            MAX-ACCESS  read-only
            STATUS      current
            DESCRIPTION
               "This object identifies the F_Port within the module.
                This number ranges from 1 to the value of fcFeModule-
                PortCapacity for the associated module. The value
                remains constant for the identified F_Port until the
                module is re-initialized."
            ::= { fcFPortPhysEntry 2 }

        fcFPortPhysAdminStatus OBJECT-TYPE
            SYNTAX      INTEGER {
                            online  (1),  -- place port online
                            offline (2),  -- take port offline
                            testing (3)   -- initiate test procedures
                        }
            ACCESS      read-write
            STATUS      mandatory
            DESCRIPTION
               "The desired state of the F_Port.  A management station
                may place the F_Port in a desired state by setting this
                object accordingly.  The testing(3) state indicates that
                no operational frames can be passed.  When a Fabric Ele-
                ment initializes, all F_Ports start with fcFPortPhysAd-
                minStatus in the offline(2) state.  As the result of
                either explicit management action or per configuration
                information accessible by the Fabric Element, fcFPort-
                PhysAdminStatus is then changed to either the online(1)
                or testing(3) states, or remains in the offline state.
                [1](16.5)"
                ::= { fcFPortPhysEntry 3 }

            fcFPortPhysOperStatus   OBJECT-TYPE
                SYNTAX      INTEGER {
                    online       (1), -- Login may proceed
                    offline      (2), -- Login cannot proceed
                    testing      (3), -- port is under test
                    link-failure (4)  -- failure after online/testing
                    -- Other values may be used to indicate
                    -- diagnostic for failed test.
                }
                ACCESS      read-only
                STATUS      mandatory
                DESCRIPTION
                   "The current operational status of the F_Port.  The
                    testing(3) indicates that no operational frames can
                    be passed.  If fcFPortPhysAdminStatus is offline(2)
                    then fcFPortPhysOperStatus should be offline(2). If
                    fcFPortPhysAdminStatus is changed to online(1) then
                    fcFPortPhysOperStatus should change to online(1) if
                    the F_Port is ready to accept Fabric Login request
                    from the attached N_Port; it should proceed and
                    remain in the link-failure(4) state if and only if
                    there is a fault that prevents it from going to the
                    online(1) state.
                    [1](16.5)"
                ::= { fcFPortPhysEntry 4 }

            fcFPortPhysLastChange OBJECT-TYPE
                SYNTAX      TimeTicks
                MAX-ACCESS  read-only
                STATUS      current
                DESCRIPTION
                   "The value of sysUpTime at the time the F_Port
                    entered its current operational status. A value of
                    zero indicates that the F_Port's operational status
                    has not changed since the agent last restarted."
                ::= { fcFPortPhysEntry 5 }

            fcFPortPhysRttov OBJECT-TYPE
                SYNTAX      MilliSeconds
                MAX-ACCESS  read-write
                STATUS      current
                DESCRIPTION
                   "The Receiver_Transmitter_Timeout value of the
                    F_Port. This is used by the receiver logic to detect
                    Loss of Synchronization.
                    [1](29.2.1.1)"
                ::= { fcFPortPhysEntry 6 }


        -- the Error group
        -- This group consists of tables that contain information about
        -- the various types of errors detected.  The management station
        -- may use the information in this group to determine the
        -- quality of the link between the F_Port and its attached N_Port.
        -- Implementation of this group is optional.

        -- the F_Port Error table
        -- This table contains, one entry for each F_Port in the Fabric
        -- Element, counters recording numbers of errors detected
        -- since the management agent re-initialized.
        -- The first 6 columnar objects after the port index corresponds
        -- to the counters in the Link Error Status Block ([1](29.8)).

        fcFPortErrorTable OBJECT-TYPE
            SYNTAX      SEQUENCE OF FcFPortErrorEntry
            MAX-ACCESS  not-accessible
            STATUS      current
            DESCRIPTION
               "A table that contains, one entry for each F_Port, coun-
                ters that record the numbers of errors detected.
                [1](29)"
            ::= { fcFeError 1 }

        fcFPortErrorEntry OBJECT-TYPE
            SYNTAX      FcFPortErrorEntry
            MAX-ACCESS  not-accessible
            STATUS      current
            DESCRIPTION
               "An entry containing error counters of a F_Port.
                [1](29)"
            INDEX { fcFPortErrorModuleIndex, fcFPortErrorFPortIndex }
            ::= { fcFPortErrorTable 1 }


        FcFPortErrorEntry ::=
            SEQUENCE {
                fcFPortErrorModuleIndex
                    FcFeModuleIndex,
                fcFPortErrorFPortIndex
                    FcFeFPortIndex,
                fcFPortLinkFailures
                    Counter32,
                fcFPortSyncLosses
                    Counter32,
                fcFPortSigLosses
                    Counter32,
                fcFPortPrimSeqProtoErrors
                    Counter32,
                fcFPortInvalidTxWords
                    Counter32,
                fcFPortInvalidCrcs
                    Counter32,
                fcFPortDelimiterErrors
                    Counter32,
                fcFPortAddressIdErrors
                    Counter32,
                fcFPortLinkResetIns
                    Counter32,
                fcFPortLinkResetOuts
                    Counter32,
                fcFPortOlsIns
                    Counter32,
                fcFPortOlsOuts
                    Counter32
            }

        fcFPortErrorModuleIndex OBJECT-TYPE
            SYNTAX      FcFeModuleIndex
            MAX-ACCESS  read-only
            STATUS      current
            DESCRIPTION
               "This object identifies the module containing the F_Port
                for which this entry contains information."
            ::= { fcFPortErrorEntry 1 }

        fcFPortErrorFPortIndex OBJECT-TYPE
            SYNTAX      FcFeFPortIndex
            MAX-ACCESS  read-only
            STATUS      current
            DESCRIPTION
               "This object identifies the F_Port within the module.
                This number ranges from 1 to the value of fcFeModule-
                PortCapacity for the associated module. The value
                remains constant for the identified F_Port until the
                module is re-initialized."
            ::= { fcFPortErrorEntry 2 }

        fcFPortLinkFailures OBJECT-TYPE
            SYNTAX      Counter32
            MAX-ACCESS  read-only
            STATUS      current
            DESCRIPTION
               "The number of link failures detected by this F_Port.
                [1](29.8, Figure 82)"
            ::= { fcFPortErrorEntry 3 }

        fcFPortSyncLosses OBJECT-TYPE
            SYNTAX      Counter32
            MAX-ACCESS  read-only
            STATUS      current
            DESCRIPTION
               "The number of loss of synchronization detected by the
                F_Port.
                [1](12.1.1.2, 29.8)"
            ::= { fcFPortErrorEntry 4 }

        fcFPortSigLosses OBJECT-TYPE
            SYNTAX      Counter32
            MAX-ACCESS  read-only
            STATUS      current
            DESCRIPTION
               "The number of loss of signal detected by the F_Port.
                [1](12.1.1.2, 29.8)"
            ::= { fcFPortErrorEntry 5 }

        fcFPortPrimSeqProtoErrors OBJECT-TYPE
            SYNTAX      Counter32
            MAX-ACCESS  read-only
            STATUS      current
            DESCRIPTION
               "The number of primitive sequence protocol errors
                detected by the F_Port.
                [1](29.3.3, 29.8 )"
            ::= { fcFPortErrorEntry 6 }

        fcFPortInvalidTxWords OBJECT-TYPE
            SYNTAX      Counter32
            MAX-ACCESS  read-only
            STATUS      current
            DESCRIPTION
               "The number of invalid transmission word detected by the
                F_Port.
                [1](29.3.2, 29.8)"
            ::= { fcFPortErrorEntry 7 }

        fcFPortInvalidCrcs OBJECT-TYPE
            SYNTAX      Counter32
            MAX-ACCESS  read-only
            STATUS      current
            DESCRIPTION
               "The number of invalid CRC detected by this F_Port.
                [1](29.8)"
            ::= { fcFPortErrorEntry 8 }

        fcFPortDelimiterErrors OBJECT-TYPE
            SYNTAX      Counter32
            MAX-ACCESS  read-only
            STATUS      current
            DESCRIPTION
               "The number of Delimiter Errors detected by this F_Port.
                [1](29.9, Table 112)"
            ::= { fcFPortErrorEntry 9 }

        fcFPortAddressIdErrors OBJECT-TYPE
            SYNTAX      Counter32
            MAX-ACCESS  read-only
            STATUS      current
            DESCRIPTION
               "The number of address identifier errors detected by this
                F_Port.
                [1](29.9, Table 112)"
            ::= { fcFPortErrorEntry 10 }

        fcFPortLinkResetIns OBJECT-TYPE
            SYNTAX      Counter32
            MAX-ACCESS  read-only
            STATUS      current
            DESCRIPTION
               "The number of Link Reset Protocol received by this
                F_Port from the attached N_Port.
                [1](16.6.5, 29.9)"
            ::= { fcFPortErrorEntry 11 }

        fcFPortLinkResetOuts OBJECT-TYPE
            SYNTAX      Counter32
            MAX-ACCESS  read-only
            STATUS      current
            DESCRIPTION
               "The number of Link Reset Protocol issued by this F_Port
                to the attached N_Port.
                [1](16.6.5, 29.9)"
            ::= { fcFPortErrorEntry 12 }

        fcFPortOlsIns OBJECT-TYPE
            SYNTAX      Counter32
            MAX-ACCESS  read-only
            STATUS      current
            DESCRIPTION
               "The number of Offline Sequence received by this F_Port.
                [1](16.4.3)"
            ::= { fcFPortErrorEntry 13 }

        fcFPortOlsOuts OBJECT-TYPE
            SYNTAX      Counter32
            MAX-ACCESS  read-only
            STATUS      current
            DESCRIPTION
               "The number of Offline Sequence issued by this F_Port.
                [1](16.4.3)"
            ::= { fcFPortErrorEntry 14 }



        -- Accounting Groups:
        -- (1) Class 1 Accounting Group,
        -- (2) Class 2 Accounting Group, and
        -- (3) Class 3 Accounting Group.
        -- Each group consists of a table that contains accounting
        -- information for the F_Ports in the Fabric Element.


        -- Implementation of each group is optional.

        -- the Class 1 Accounting table
        -- This table contains, one entry for each F_Port in the Fabric
        -- Element, Counter32s for certain types of events occurred in the
        -- the F_Ports since the the management agent has re-initialized.
        -- Implementation of this group is optional.

        fcFPortC1AcctTable OBJECT-TYPE
            SYNTAX      SEQUENCE OF FcFPortC1AcctEntry
            MAX-ACCESS  not-accessible
            STATUS      current
            DESCRIPTION
               "A table that contains, one entry for each F_Port in the
                Fabric Element, Class 1 accounting information recorded
                since the management agent has re-initialized."
            ::= { fcFeAcct 1 }

        fcFPortC1AcctEntry OBJECT-TYPE
            SYNTAX      FcFPortC1AcctEntry
            MAX-ACCESS  not-accessible
            STATUS      current
            DESCRIPTION
               "An entry containing Class 1 accounting information for
                each F_Port."
            INDEX { fcFPortC1AcctModuleIndex, fcFPortC1AcctFPortIndex }
            ::= { fcFPortC1AcctTable 1 }

        FcFPortC1AcctEntry ::=
            SEQUENCE {
                fcFPortC1AcctModuleIndex
                    FcFeModuleIndex,
                fcFPortC1AcctFPortIndex
                    FcFeFPortIndex,
                fcFPortC1InConnections
                    Counter32,
                fcFPortC1OutConnections
                    Counter32,
                fcFPortC1FbsyFrames
                    Counter32,
                fcFPortC1FrjtFrames
                    Counter32,
                fcFPortC1ConnTime
                    Counter32,
                fcFPortC1InFrames
                    Counter32,
                fcFPortC1OutFrames
                    Counter32,
                fcFPortC1InOctets
                    Counter32,
                fcFPortC1OutOctets
                    Counter32,
                fcFPortC1Discards
                    Counter32
            }

        fcFPortC1AcctModuleIndex OBJECT-TYPE
            SYNTAX      FcFeModuleIndex
            MAX-ACCESS  read-only
            STATUS      current
            DESCRIPTION
               "This object identifies the module containing the F_Port
                for which this entry contains information."
            ::= { fcFPortC1AcctEntry 1 }

        fcFPortC1AcctFPortIndex OBJECT-TYPE
            SYNTAX      FcFeFPortIndex
            MAX-ACCESS  read-only
            STATUS      current
            DESCRIPTION
               "This object identifies the F_Port within the module.
                This number ranges from 1 to the value of fcFeModule-
                PortCapacity for the associated module. The value
                remains constant for the identified F_Port until the
                module is re-initialized."
            ::= { fcFPortC1AcctEntry 2 }

        fcFPortC1InConnections OBJECT-TYPE
            SYNTAX      Counter32
            MAX-ACCESS  read-only
            STATUS      current
            DESCRIPTION
               "The number of Class 1 connections successfully estab-
                lished in which the attached N_Port is the source of the
                connect-request.
                [1](28)"
            ::= { fcFPortC1AcctEntry 3 }

        fcFPortC1OutConnections OBJECT-TYPE
            SYNTAX      Counter32
            MAX-ACCESS  read-only
            STATUS      current
            DESCRIPTION
               "The number of Class 1 connections successfully estab-
                lished in which the attached N_Port is the destination
                of the connect-request.
                [1](28)"
            ::= { fcFPortC1AcctEntry 4 }

        fcFPortC1FbsyFrames OBJECT-TYPE
            SYNTAX      Counter32
            MAX-ACCESS  read-only
            STATUS      current
            DESCRIPTION
               "The number of F_BSY frames generated by this F_Port
                against Class 1 connect-request.
                [1](20.3.3.1)"
            ::= { fcFPortC1AcctEntry 5 }

        fcFPortC1FrjtFrames OBJECT-TYPE
            SYNTAX      Counter32
            MAX-ACCESS  read-only
            STATUS      current
            DESCRIPTION
               "The number of F_RJT frames generated by this F_Port
                against Class 1 connect-request.
                [1](20.3.3.3)"
            ::= { fcFPortC1AcctEntry 6 }

        fcFPortC1ConnTime OBJECT-TYPE
            SYNTAX      Counter32
            MAX-ACCESS  read-only
            STATUS      current
            DESCRIPTION
               "The cumulative time that this F_Port has been engaged in
                Class 1 connection.  The amount of time of each connec-
                tion is counted in octets from after a connect-request
                has been accepted until the connection is disengaged,
                either by an EOFdt or Link Reset.
                [1](22.1)"
            ::= { fcFPortC1AcctEntry 7 }

        fcFPortC1InFrames OBJECT-TYPE
            SYNTAX      Counter32
            MAX-ACCESS  read-only
            STATUS      current
            DESCRIPTION
               "The number of Class 1 frames (other than Class 1 con-
                nect-request) received by this F_Port from its attached
                N_Port.
                [1](20.1)"
            ::= { fcFPortC1AcctEntry 8 }

        fcFPortC1OutFrames OBJECT-TYPE
            SYNTAX      Counter32
            MAX-ACCESS  read-only
            STATUS      current
            DESCRIPTION
               "The number of Class 1 frames (other than Class 1 con-
                nect-request) delivered through this F_Port to its
                attached N_Port.
                [1](20.1)"
            ::= { fcFPortC1AcctEntry 9 }

        fcFPortC1InOctets OBJECT-TYPE
            SYNTAX      Counter32
            MAX-ACCESS  read-only
            STATUS      current
            DESCRIPTION
               "The number of Class 1 frame octets, including the frame
                delimiters,  received by this F_Port from its attached
                N_Port
                [1](20.1))"
            ::= { fcFPortC1AcctEntry 10 }

        fcFPortC1OutOctets OBJECT-TYPE
            SYNTAX      Counter32
            MAX-ACCESS  read-only
            STATUS      current
            DESCRIPTION
               "The number of Class 1 frame octets, including the frame
                delimiters, delivered through this F_Port its attached
                N_Port.
                [1](20.1)"
            ::= { fcFPortC1AcctEntry 11 }

        fcFPortC1Discards OBJECT-TYPE
            SYNTAX      Counter32
            MAX-ACCESS  read-only
            STATUS      current
            DESCRIPTION
               "The number of Class 1 frames discarded by this F_Port.
                [1](20.1)"
            ::= { fcFPortC1AcctEntry 12 }


        -- the Class 2 Accounting table
        -- This table contains, one entry for each F_Port in the Fabric
        -- Element, Counter32s for certain types of events occurred in the
        -- the F_Ports since the the management agent has re-initialized.
        -- Implementation of this group is optional.

        fcFPortC2AcctTable OBJECT-TYPE
            SYNTAX      SEQUENCE OF FcFPortC2AcctEntry
            MAX-ACCESS  not-accessible
            STATUS      current
            DESCRIPTION
               "A table that contains, one entry for each F_Port in the
                Fabric Element, Class 2 accounting information recorded
                since the management agent has re-initialized."
            ::= { fcFeAcct 2 }

        fcFPortC2AcctEntry OBJECT-TYPE
            SYNTAX      FcFPortC2AcctEntry
            MAX-ACCESS  not-accessible
            STATUS      current
            DESCRIPTION
               "An entry containing Class 2 accounting information for
                each F_Port."
            INDEX { fcFPortC2AcctModuleIndex, fcFPortC2AcctFPortIndex }
            ::= { fcFPortC2AcctTable 1 }

        FcFPortC2AcctEntry ::=
            SEQUENCE {
                fcFPortC2AcctModuleIndex
                    FcFeModuleIndex,
                fcFPortC2AcctFPortIndex
                    FcFeFPortIndex,
                fcFPortC2InFrames
                    Counter32,
                fcFPortC2OutFrames
                    Counter32,
                fcFPortC2InOctets
                    Counter32,
                fcFPortC2OutOctets
                    Counter32,
                fcFPortC2Discards
                    Counter32,
                fcFPortC2FbsyFrames
                    Counter32,
                fcFPortC2FrjtFrames
                    Counter32
            }

        fcFPortC2AcctModuleIndex OBJECT-TYPE
            SYNTAX      FcFeModuleIndex
            MAX-ACCESS  read-only
            STATUS      current
            DESCRIPTION
               "This object identifies the module containing the F_Port
                for which this entry contains information."
            ::= { fcFPortC2AcctEntry 1 }

        fcFPortC2AcctFPortIndex OBJECT-TYPE
            SYNTAX      FcFeFPortIndex
            MAX-ACCESS  read-only
            STATUS      current
            DESCRIPTION
               "This object identifies the F_Port within the module.
                This number ranges from 1 to the value of fcFeModule-
                PortCapacity for the associated module. The value
                remains constant for the identified F_Port until the
                module is re-initialized."
            ::= { fcFPortC2AcctEntry 2 }

        fcFPortC2InFrames OBJECT-TYPE
            SYNTAX      Counter32
            MAX-ACCESS  read-only
            STATUS      current
            DESCRIPTION
               "The number of Class 2 frames received by this F_Port
                from its attached N_Port.
                [1](20.2)"
            ::= { fcFPortC2AcctEntry 3 }

        fcFPortC2OutFrames OBJECT-TYPE
            SYNTAX      Counter32
            MAX-ACCESS  read-only
            STATUS      current
            DESCRIPTION
               "The number of Class 2 frames delivered through this
                F_Port to its attached N_Port.
                [1](20.2)"
            ::= { fcFPortC2AcctEntry 4 }

        fcFPortC2InOctets OBJECT-TYPE
            SYNTAX      Counter32
            MAX-ACCESS  read-only
            STATUS      current
            DESCRIPTION
               "The number of Class 2 frame octets, including the frame
                delimiters, received by this F_Port from its attached
                N_Port.
                [1](20.2)"
            ::= { fcFPortC2AcctEntry 5 }

        fcFPortC2OutOctets OBJECT-TYPE
            SYNTAX      Counter32
            MAX-ACCESS  read-only
            STATUS      current
            DESCRIPTION
               "The number of Class 2 frame octets, including the frame
                delimiters, delivered through this F_Port to its
                attached N_Port.
                [1](20.2)"
            ::= { fcFPortC2AcctEntry 6 }

        fcFPortC2Discards OBJECT-TYPE
            SYNTAX      Counter32
            MAX-ACCESS  read-only
            STATUS      current
            DESCRIPTION
               "The number of Class 2 frames discarded by this F_Port.
                [1](22.2)"
            ::= { fcFPortC2AcctEntry 7 }


        fcFPortC2FbsyFrames OBJECT-TYPE
            SYNTAX      Counter32
            MAX-ACCESS  read-only
            STATUS      current
            DESCRIPTION
               "The number of F_BSY frames generated by this F_Port
                against Class 2 frames.
                [1](20.3.3.1)"
            ::= { fcFPortC2AcctEntry 8 }

        fcFPortC2FrjtFrames OBJECT-TYPE
            SYNTAX      Counter32
            MAX-ACCESS  read-only
            STATUS      current
            DESCRIPTION
               "The number of F_RJT frames generated by this F_Port
                against Class 2 frames.
                [1](20.3.3.3)"
            ::= { fcFPortC2AcctEntry 9 }

        -- the Class 3 Accounting Group
        -- This table contains, one entry for each F_Port in the Fabric
        -- Element, Counter32s for certain types of events occurred in the
        -- the F_Ports since the management agent has re-initialized.
        -- Implementation of this group is optional.

        fcFPortC3AcctTable OBJECT-TYPE
            SYNTAX      SEQUENCE OF FcFPortC3AcctEntry
            MAX-ACCESS  not-accessible
            STATUS      current
            DESCRIPTION
               "A table that contains, one entry for each F_Port in the
                Fabric Element, Class 3 accounting information recorded
                since the management agent has re-initialized."
            ::= { fcFeAcct 3 }

        fcFPortC3AcctEntry OBJECT-TYPE
            SYNTAX      FcFPortC3AcctEntry
            MAX-ACCESS  not-accessible
            STATUS      current
            DESCRIPTION
               "An entry containing Class 3 accounting information for
                each F_Port."
            INDEX { fcFPortC3AcctModuleIndex, fcFPortC3AcctFPortIndex }
            ::= { fcFPortC3AcctTable 1 }

        FcFPortC3AcctEntry ::=
            SEQUENCE {
                fcFPortC3AcctModuleIndex
                    FcFeModuleIndex,
                fcFPortC3AcctFPortIndex
                    FcFeFPortIndex,
                fcFPortC3InFrames
                    Counter32,
                fcFPortC3OutFrames
                    Counter32,
                fcFPortC3InOctets
                    Counter32,
                fcFPortC3OutOctets
                    Counter32,
                fcFPortC3Discards
                    Counter32
            }

        fcFPortC3AcctModuleIndex OBJECT-TYPE
            SYNTAX      FcFeModuleIndex
            MAX-ACCESS  read-only
            STATUS      current
            DESCRIPTION
               "This object identifies the module containing the F_Port
                for which this entry contains information."
            ::= { fcFPortC3AcctEntry 1 }

        fcFPortC3AcctFPortIndex OBJECT-TYPE
            SYNTAX      FcFeFPortIndex
            MAX-ACCESS  read-only
            STATUS      current
            DESCRIPTION
               "This object identifies the F_Port within the module.
                This number ranges from 1 to the value of fcFeModule-
                PortCapacity for the associated module. The value
                remains constant for the identified F_Port until the
                module is re-initialized."
            ::= { fcFPortC3AcctEntry 2 }

        fcFPortC3InFrames OBJECT-TYPE
            SYNTAX      Counter32
            MAX-ACCESS  read-only
            STATUS      current
            DESCRIPTION
               "The number of Class 3 frames received by this F_Port
                from its attached N_Port.
                [1](22.3)"
            ::= { fcFPortC3AcctEntry 3 }

        fcFPortC3OutFrames OBJECT-TYPE
            SYNTAX      Counter32
            MAX-ACCESS  read-only
            STATUS      current
            DESCRIPTION
               "The number of Class 3 frames delivered through this
                F_Port to its attached N_Port.
                [1](22.3)"
            ::= { fcFPortC3AcctEntry 4 }

        fcFPortC3InOctets OBJECT-TYPE
            SYNTAX      Counter32
            MAX-ACCESS  read-only
            STATUS      current
            DESCRIPTION
               "The number of Class 3 frame octets, including the frame
                delimiters, received by this F_Port from its attached
                N_Port.
                [1](22.3))"
            ::= { fcFPortC3AcctEntry 5 }

        fcFPortC3OutOctets OBJECT-TYPE
            SYNTAX      Counter32
            MAX-ACCESS  read-only
            STATUS      current
            DESCRIPTION
               "The number of Class 3 frame octets, including the frame
                delimiters, delivered through this F_Port to its
                attached N_Port.
                [1](22.3)"
            ::= { fcFPortC3AcctEntry 6 }

        fcFPortC3Discards OBJECT-TYPE
            SYNTAX      Counter32
            MAX-ACCESS  read-only
            STATUS      current
            DESCRIPTION
               "The number of Class 3 frames discarded by this F_Port.
                [1](22.3)"
            ::= { fcFPortC3AcctEntry 7 }


        -- The Capability Group - consists of a table describing



        -- information about what each F_Port is inherently capable
        -- of operating or supporting.
        -- A capability may be used, as expressed in its respective
        -- object value in the Configuration group.
        -- Implementation of this group is optional.

        fcFPortCapTable OBJECT-TYPE
            SYNTAX      SEQUENCE OF FcFPortCapEntry
            MAX-ACCESS  not-accessible
            STATUS      current
            DESCRIPTION
               "A table that contains, one entry for each F_Port, the
                capabilities of the port within the Fabric Element.
                [1](23)"
            ::= { fcFeCap 1 }

        fcFPortCapEntry OBJECT-TYPE
            SYNTAX      FcFPortCapEntry
            MAX-ACCESS  not-accessible
            STATUS      current
            DESCRIPTION
               "An entry containing the capabilities of a F_Port.
                [1](23)"
            INDEX { fcFPortCapModuleIndex, fcFPortCapFPortIndex }
            ::= { fcFPortCapTable 1 }


        FcFPortCapEntry ::=
            SEQUENCE {
                fcFPortCapModuleIndex
                    FcFeModuleIndex,
                fcFPortCapFPortIndex
                    FcFeFPortIndex,
                fcFPortCapFcphVersionHigh
                    FcphVersion,
                fcFPortCapFcphVersionLow
                    FcphVersion,
                fcFPortCapBbCreditMax
                    FcBbCredit,
                fcFPortCapBbCreditMin
                    FcBbCredit,
                fcFPortCapRxDataFieldSizeMax
                    FcRxDataFieldSize,
                fcFPortCapRxDataFieldSizeMin
                    FcRxDataFieldSize,
                fcFPortCapCos
                    FcCosCap,
                fcFPortCapIntermix
                    TruthValue,
                fcFPortCapStackedConnMode
                    FcStackedConnMode,
                fcFPortCapClass2SeqDeliv
                    TruthValue,
                fcFPortCapClass3SeqDeliv
                    TruthValue,
                fcFPortCapHoldTimeMax
                    MicroSeconds,
                fcFPortCapHoldTimeMin
                    MicroSeconds,
                fcFPortCapBaudRates
                    Fc0BaudRateCap,
                fcFPortCapMedia
                    Fc0MediaCap
            }

        fcFPortCapModuleIndex OBJECT-TYPE
            SYNTAX      FcFeModuleIndex
            MAX-ACCESS  read-only
            STATUS      current
            DESCRIPTION
               "This object identifies the module containing the F_Port
                for which this entry contains information."
            ::= { fcFPortCapEntry 1 }

        fcFPortCapFPortIndex OBJECT-TYPE
            SYNTAX      FcFeFPortIndex
            MAX-ACCESS  read-only
            STATUS      current
            DESCRIPTION
               "This object identifies the F_Port within the module.
                This number ranges from 1 to the value of fcFeModule-
                PortCapacity for the associated module. The value
                remains constant for the identified F_Port until the
                module is re-initialized."
            ::= { fcFPortCapEntry 2 }

        fcFPortCapFcphVersionHigh OBJECT-TYPE
            SYNTAX      FcphVersion
            MAX-ACCESS  read-only
            STATUS      current
            DESCRIPTION
               "The highest or most recent version of FC-PH that the
                F_Port is capable of supporting.
                [1](23.7.1.1), [2](10.4.1)"
            ::= { fcFPortCapEntry 3 }

        fcFPortCapFcphVersionLow OBJECT-TYPE
            SYNTAX      FcphVersion
            MAX-ACCESS  read-only
            STATUS      current
            DESCRIPTION
               "The lowest or earliest version of FC-PH that the F_Port
                is capable of supporting.
                [1](23.7.1.1), [2](10.4.1)"
            ::= { fcFPortCapEntry 4 }

        fcFPortCapBbCreditMax OBJECT-TYPE
            SYNTAX      FcBbCredit
            MAX-ACCESS  read-only
            STATUS      current
            DESCRIPTION
               "The maximum number of receive buffers available for
                holding Class 1 connect-request, Class 2 or Class 3
                frames from the attached N_Port.
                [1](23.7.1.2), [2](10.4.1), [3](15.2)"
            ::= { fcFPortCapEntry 5 }

        fcFPortCapBbCreditMin OBJECT-TYPE
            SYNTAX      FcBbCredit
            MAX-ACCESS  read-only
            STATUS      current
            DESCRIPTION
               "The minimum number of receive buffers available for
                holding Class 1 connect-request, Class 2 or Class 3
                frames from the attached N_Port.
                [1](23.7.1.2), [2](10.4.1), [3](15.2)"
            ::= { fcFPortCapEntry 6 }

        fcFPortCapRxDataFieldSizeMax OBJECT-TYPE
            SYNTAX      FcRxDataFieldSize
            MAX-ACCESS  read-only
            STATUS      current
            DESCRIPTION
               "The maximum size in bytes of the Data Field in a frame
                that the F_Port is capable of receiving from its
                attached N_Port.
                [1](23.6.2.4)"
            ::= { fcFPortCapEntry 7 }

        fcFPortCapRxDataFieldSizeMin OBJECT-TYPE
            SYNTAX      FcRxDataFieldSize
            MAX-ACCESS  read-only
            STATUS      current
            DESCRIPTION
               "The minimum size in bytes of the Data Field in a frame
                that the F_Port is capable of receiving from its
                attached N_Port.
                [1](23.6.2.4)"
            ::= { fcFPortCapEntry 8 }

        fcFPortCapCos OBJECT-TYPE
            SYNTAX      FcCosCap
            MAX-ACCESS  read-only
            STATUS      current
            DESCRIPTION
               "A value indicating the set of Classes of Service that
                the F_Port is capable of supporting.
                [1](23.7.4.1), [2](Table 10.2), [3](15.3.5.1, 15.3.5.2)"
            ::= { fcFPortCapEntry 9 }

        fcFPortCapIntermix OBJECT-TYPE
            SYNTAX      TruthValue
            MAX-ACCESS  read-only
            STATUS      current
            DESCRIPTION
               "A flag indicating whether or not the F_Port is capable
                of supporting the intermixing of Class 2 and Class 3
                frames during a Class 1 connection. This flag is only
                valid if the port is capable of supporting Class 1 ser-
                vice.
                [1](23.7.4.2)"
            ::= { fcFPortCapEntry 10 }

        fcFPortCapStackedConnMode OBJECT-TYPE
            SYNTAX      FcStackedConnMode
            MAX-ACCESS  read-only
            STATUS      current
            DESCRIPTION
               "A value indicating the mode of Stacked Connect request
                that the F_Port is capable of supporting.
                [1](23.7.4.2)"
            ::= { fcFPortCapEntry 11 }

        fcFPortCapClass2SeqDeliv OBJECT-TYPE
            SYNTAX      TruthValue
            MAX-ACCESS  read-only
            STATUS      current
            DESCRIPTION
               "A flag indicating whether or not the F_Port is capable
                of supporting Class 2 Sequential Delivery.
                [1](23.7.4.2)"
            ::= { fcFPortCapEntry 12 }

        fcFPortCapClass3SeqDeliv OBJECT-TYPE
            SYNTAX      TruthValue
            MAX-ACCESS  read-only
            STATUS      current
            DESCRIPTION
               "A flag indicating whether or not the F_Port is capable
                of supporting Class 3 Sequential Delivery.
                [1](23.7.4.2)"
            ::= { fcFPortCapEntry 13 }

        fcFPortCapHoldTimeMax OBJECT-TYPE
            SYNTAX      MicroSeconds
            MAX-ACCESS  read-only
            STATUS      current
            DESCRIPTION
               "The maximum holding time (in microseconds) that the
                F_Port is capable of supporting."
            ::= { fcFPortCapEntry 14 }

        fcFPortCapHoldTimeMin OBJECT-TYPE
            SYNTAX      MicroSeconds
            MAX-ACCESS  read-only
            STATUS      current
            DESCRIPTION
               "The minimum holding time (in microseconds) that the
                F_Port is capable of supporting."
            ::= { fcFPortCapEntry 15 }

        fcFPortCapBaudRates OBJECT-TYPE
            SYNTAX      Fc0BaudRateCap
            MAX-ACCESS  read-only
            STATUS      current
            DESCRIPTION
               "A value indicating the set of baud rates that the F_Port
                is capable of supporting.
                [1](5.1)"
            ::= { fcFPortCapEntry 16 }

        fcFPortCapMedia OBJECT-TYPE
            SYNTAX      Fc0MediaCap
            MAX-ACCESS  read-only
            STATUS      current
            DESCRIPTION
               "A value indicating the set of media that the F_Port is
                capable of supporting.
                [1](5.1)"
            ::= { fcFPortCapEntry 17 }

        END
        -- End of Object Definitions
