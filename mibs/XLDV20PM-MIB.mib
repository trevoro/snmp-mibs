-- ***************************************************************
     --  *************************************************************
     --   ***********************************************************
     --    *********************************************************
     --    **                                                     **
     --    **  The ICN WN BA E12 SNMP-Team proudly presents:      **
     --    **                                                     **
     --    **                  The XLD MIB                        **
     --    **           for Performance Management                **
     --    **              on physical layer                      **
     --    **          on drop area interfaces with               **
     --    **                      ADSL                           **
     --    **        and on feeder area interfaces for            **
     --    **              STM-1, STS3c, DS3, E3                  **
     --    **              LU-IMA                                 **
     --    **                                                     **
     --    **                                                     **
     --    **           for Performance Management                **
     --    **              on ATM layer                           **
     --    **          at VPC or VPC segments or                  **
     --    **          at VCC or VCC segments or                  **
     --    **                                                     **
     --    **                                                     **
     --    **                                                     **
     --    *********************************************************
     --   ***********************************************************
     --  *************************************************************
     -- ***************************************************************



     XLDV20PM-MIB      DEFINITIONS ::= BEGIN


     IMPORTS
         OBJECT-TYPE
               FROM RFC-1212
         TRAP-TYPE
               FROM RFC-1215
         Counter,TimeTicks,Gauge
               FROM RFC1155-SMI
         onu
               FROM AN-MIB


     -- --------------------------------------------------------------
     --            I m p o r t s  from  X L D V 2 0 - M I B
     -- --------------------------------------------------------------

        Xldv20ControlStatus,
        Xldv20AdminState,
        Xldv20FlowDirection,
        Unsigned16,
        xldv20IfIndex,
        xldv20TvTimeAndDate,
        xldv20Traps
                FROM XLDV20-MIB
			Unsigned32 FROM SNMPv2-SMI;


     --  LAST-UPDATED "99-10-11, Version 2.0"
     --  ORGANIZATION "Siemens AG, ICN WN BA E"
     --  CONTACT-INFO
     --  "      Angelika Svoboda
     --         ICN WN BA E 12
     --         Tel.: +49 89 722 48063
     --
     --         Thomas Vetter
     --         ICN WN BA E 12
     --         Tel.: +49 89 722 44323
     --

     -- **************************************************************
     --                      Versions and Revisions
     -- **************************************************************
     --
     -- --------------------------------------------------------------
     -- 00-09-04    ADD:  HPOV comment tags for HPVO - tools ....../tv
     -- --------------------------------------------------------------
     -- 00-02-08    MR2441: extension description of       V2.0  asvo
     --             xxxElapsedTime attributes
     -- --------------------------------------------------------------
     -- 00-02-08    MR2410: change type of                 V2.0  asvo
     --             xldv20pmTvIntervalType  
     -- --------------------------------------------------------------
     -- 00-18-04    change types of threshold limits to    V2.0  asvo
     --             Unsigned32
     -- --------------------------------------------------------------
     -- 00-22-03    change OID-sequnce from onu 6 to onu 5 V2.0  tv  
     -- --------------------------------------------------------------
     -- 00-29-02    First Issue of XLDV20PM-MIB            V2.0  asvo
     -- --------------------------------------------------------------
     -- --------------------------------------------------------------
     -- **************************************************************
     --         PLEASE CHANGE THE DATE OF LAST-UPDATE ABOVE !!!
     -- **************************************************************

     -- **************************************************************
     --             Information Block for Version Control
     --             of MIB nodes and attributes (template)
     -- **************************************************************
     --
     -- info-TRAPTYPE:  alarm/event            ==>> for traps only
     -- info-VALUE:     minValue..maxValue; attrValue[(V1.0->)]
     -- info-TRAPID:    trap-ID
     -- info-ROU:       GET  SET [db,gf,up,tm,hm,ut,so,sn,cp]
     -- info-FAILEDSRC: hwm, tlm, callp       ==>> for alarm traps only
     -- info-FAILEDOBJ: [hwm] LU155,LUDSX3,LUPON,CMU,SUAD,SUVD,LTAD,
     -- info-FAILEDOBJ: [hwm] LIETH,LI25,NTAD,NTVD,
     -- info-FAILEDOBJ: [tlm] S1n(= STM-1 NePPTP),S1f,S3n,E3n,D3n,S3f,
     -- info-FAILEDOBJ: [tlm] D3f,E3f,Pon,Adc(= Adc-PPTP),Adr,Vdc,Vdr,
     -- info-FAILEDOBJ: [tlm] Ibm(= Ibm-PPTP),Eth,Tca  
     -- info-FAILEDOBJ: [callp] VpcTP, VccTP  
     -- info-IMPL:      [V2.0,V2.x]:[rw,ro,*]
     -- info-IMPL:      e.g.: V2.0-> (= all vers. begin. with V1.1U)
     -- info-IMPL:      e.g.: V2.0:*->V2.1  V2.0:rw->2.1   V2.1:* 
     -- info-VERCTRL:   [GET,SET [db,asw,agent,blocked] or "-" 
     --                             (blocked == blocked by SNMP agent)
     --                             ("-"     == no special handling)
     -- **************************************************************


     xldv20Pm        OBJECT IDENTIFIER ::= { onu 5 }
     -- info-IMPL:      V2.0-> 
     -- info-VERCTRL:   -

     -- ==============================================================
     --       TEXTUAL-CONVENTIONs for  X L D V 2 0 P M - M I B
     -- ==============================================================

     -- --------------------------------------------------------------
     --                         T y p e s                
     -- --------------------------------------------------------------

     -- An Interval type identifier to select between the 15 minute
     -- counters and the day counter.
     --
     Xldv20pmIntervalType ::=
         INTEGER { min15(1),
                   day(2) }

     -- The PM Control request commands from the TMN-OS
     --
     Xldv20pmControlReq ::=
         INTEGER { noRequest                       (1),
                   resetIndividCurrent             (2),
                   setNrHistEntriesSize            (3),
                   paramFaulty                     (4),
                   nrHistEntriesSizeNotAcceptable  (5),
                   dataDaseMemoryNotAvailable      (6),
                   create                          (7),  -- PMo on Atm
                   delete                          (8),  -- PMo on Atm
                   addEndpoint                     (9),  -- PMo on Atm
                   removeEndpoint                  (10), -- PMo on Atm
                   indexLimitExceeded              (11), -- PMo on Atm
                   atmPmObjectActive               (12), -- PMo on Atm
                   atmPmObjectNotExists            (13), -- PMo on Atm
                   endpointExistsAlready           (14), -- PMo on Atm

                   requestBusy                     (15),-- user command handling
                   setDataFailed                   (16),-- user command handling
                   aswTimeout                      (17),-- user command handling
                   commandFailed                   (18),-- user command handling
                   commandSucceeded                (19) -- user command handling
                  }

                    
     -- A type identifier to select the overall PM event counter
     -- These counters define a threshold limit profile.
     --
     Xldv20pmCounterName ::=
         INTEGER { 
            noPmCounter(0),
            neBackgroundBlockErrors(1),          -- s1n, adc, e3n
            neCodeViolations(2),                 -- s3n
            neCodeViolationsCP(3),               -- d3n
            neCodeViolationsP(4),                -- d3n
            neCodeViolationsPLCP(5),             -- d3n
            neErroredSeconds(6),                 -- s1n, s3n, adc, e3n
            neErroredSecondsCP(7),               -- d3n
            neErroredSecondsPLCP(8),             -- d3n
            neSas(9),                            -- d3n
            neSeverelyErroredFrameSeconds(10),   -- s3n
            neSeverelyErroredSeconds(11),        -- s1n, s3n, adc, e3n
            neSeverelyErroredSecondsCP(12),      -- d3n
            neSeverelyErroredSecondsPLCP(13),    -- d3n
            neUnavailableSeconds(14),            -- s1n, s3n, adc, e3n
            neUnavailableSecondsPLCP(15),        -- s3n
            neAisSeconds(16),                    -- s1n
            neOfsSeconds(17),                    -- s1n
            neLosSeconds(18),                    -- s1n
            feBackgroundBlockErrors(19),         -- s1f, adr, e3f
            feCodeViolations(20),                -- s3f
            feCodeViolationsCP(21),              -- d3f
            feCodeViolationsPLCP(22),            -- d3f
            feErroredSeconds(23),                -- s1f, s3f, adr, e3f
            feErroredSecondsCP(24),              -- d3f
            feErroredSecondsPLCP(25),            -- d3f
            feSas(26),                           -- d3f
            feSeverelyErroredSeconds(27),        -- s1f, s3f, adr, e3f
            feSeverelyErroredSecondsCP(28),      -- d3f
            feSeverelyErroredSecondsPLCP(29),    -- d3f
            feUnavailableSeconds(30),            -- s1f, s3f, adr, e3f
            feUnavailableSecondsPLCP(31),        -- s3f
            discardedCells(32),                  -- tca
            imaGroupUnavailSecs(33),             -- IMA Group
            imaGroupNeNumFailures(34),           -- IMA Group
            imaLinkImaViolations(35),            -- IMA Link
            imaLinkOifAnomalies(36),             -- IMA Link
            imaLinkNeSevErroredSecs(37),         -- IMA Link
            imaLinkFeSevErroredSecs(38),         -- IMA Link
            imaLinkNeUnavailSecs(39),            -- IMA Link
            imaLinkFeUnavailSecs(40),            -- IMA Link
            imaLinkNeTxUnusableSecs(41),         -- IMA link
            imaLinkNeRxUnusableSecs(42),         -- IMA link
            imaLinkFeTxUnusableSecs(43),         -- IMA link
            imaLinkFeRxUnusableSecs(44),         -- IMA link
            imaLinkNeTxNumFailures(45),          -- IMA link
            imaLinkNeRxNumFailures(46),          -- IMA link
            maxPmCounter(47)
                 }     

     -- A type identifier to select valid combination of TLM interfaces and OAM
     -- levels. To be used witin trap xldv20pmTrThresholdCrossingAlert.
     --
     Xldv20pmType ::=
         INTEGER { 
            pmTypeUnknown(0),
            s1F1PMo(1),              -- for Performance Monitoring
            s1F2PMo(2),
            s1F3PMo(3),
            s3F1PMo(4),
            s3F2PMo(5),
            s3F3PMo(6),
            d3F2PMo(7),
            d3F3PMo(8),
            e3F3PMo(9),
            adcF3PMo(10),
            s1PrM(11),               -- for Protocol Monitoring
            s3PrM(12),
            e3PrM(13),
            d3PrM(14),
            adcPrM(15),
            e1ImaPrM(16),            -- for PrM on E1/Ds1
            d1ImaPrM(17),
            e1ImaPMo(18),            -- for PMo on E1/Ds1
            d1ImaPMo(19),
            atmImaPMo(20),
            maxPmType(21)
                 }     

     -- --------------------------------------------------------------
     --                         T y p e s  for PM on ATM layer
     -- --------------------------------------------------------------

     -- An flow type identifier to select between the segement or
     -- endToEnd flow on F4 (VPC) or F5 (VCC) level
     --
     Xldv20pmFlowType ::=
         INTEGER {
            undefined(0),
            f4Segment(1),
            f4EndToEnd(2),
            f5Segment(3),
            f5EndToEnd(4)
                    }

     -- A type identifier to estimate the validity of a PM event
     -- counter
     --
     Xldv20pmSuspectType ::=
         INTEGER { undefined(0),
                   reliable(1),
                   suspect(2) }

     -- A type which selects the type and termination point
     -- of cross connection index
     --
     Xldv20pmConnectionIndexType ::=
         INTEGER { 
                   undefined(0),
                   vplUni(1),
                   vplNni(2),
                   vclUni(3),
                   vclNni(4)
                   }
     
     -- A type which selects the role of endpoint
     --
     Xldv20pmRoleType ::=
          INTEGER { undefined(0),
                    analyseWithBackwardReporting(1),
                    analyseWithoutBackwardReporting(2),
                    generateWithCollect(3),
                    generateWithoutCollect(4)}

     -- A type which selects the type of endpoint
     --
    Xldv20pmEndpointType ::=
          INTEGER { source(1),
                    sink(2) }

     -- A type which selects the block size
     -- A number of user cells after which a Pmo cell is inserted.
     --
     Xldv20pmBlockSizeType ::=
          INTEGER { undefined(0),
                    blockSize128(128),
                    blockSize256(256),
                    blockSize512(512),
                    blockSize1024(1024) }

     Xldv20pmAtmCounterType ::=
         INTEGER { 
            transmittedUserCells(1),
            lostUserCells(2), 
            misinsertedUserCells(3) }


     -- ==============================================================
     --      M a i n  g r o u p s  of the  X L D V 1 1 P M - M I B
     -- ==============================================================

     xldv20pmPerformanceManagementControl   OBJECT IDENTIFIER ::= { xldv20Pm 1 }
     -- info-IMPL:      V2.0-> 
     -- info-VERCTRL:   -

     xldv20pmPerformanceMonitoring          OBJECT IDENTIFIER ::= { xldv20Pm 2 }
     -- info-IMPL:      V2.0-> 
     -- info-VERCTRL:   -

     xldv20pmProtocolMonitoring             OBJECT IDENTIFIER ::= { xldv20Pm 3 }
     -- info-IMPL:      V2.0-> 
     -- info-VERCTRL:   -

     xldv20pmThresholding                 OBJECT IDENTIFIER ::= { xldv20Pm 4 }
     -- info-IMPL:      V2.0-> 
     -- info-VERCTRL:   -

     xldv20pmTraps                        OBJECT IDENTIFIER ::= { xldv20Pm 5 }
     -- info-IMPL:      V2.0-> 
     -- info-VERCTRL:   -


     -- ==============================================================
     --        P e r f o r m a n c e   M a n a g e m e n t  (PM)
     --                  C o n t r o l  g r o u p
     -- ==============================================================


     xldv20pmControl OBJECT IDENTIFIER
     -- info-IMPL:      V2.0-> 
     -- info-VERCTRL:   -
        ::= { xldv20pmPerformanceManagementControl 1 }

     -- This managed entity manages the user commands for
     -- of Performance Mangement.
     --
     -- An instance of this managed entity shall be automatically
     -- created by the ATM NE immediately following ATM NE
     -- initialization.


    xldv20pmCoIfIndex OBJECT-TYPE
     -- info-VALUE:     -
     -- info-ROU:       GET db  SET db
     -- info-IMPL:      V2.0-> 
     -- info-VERCTRL:   -
        SYNTAX        Unsigned16
        ACCESS        read-write
        STATUS        mandatory
        DESCRIPTION
             " This attribute provides the interface index of
               the PM object for which PM parameters are
               configured . "
        --DEFAULT test-function-async     fsnPmCoTest
        --DEFAULT next-function-async     fsnPmCoNext
        --DEFAULT set-function-async      fsnPmCoSet
        --DEFAULT get-function-async      fsnPmCoGet
        ::= { xldv20pmControl 1 }

    xldv20pmCoNrHistEntriesSize OBJECT-TYPE
     -- info-VALUE:     1..96
     -- info-ROU:       GET db  SET db
     -- info-IMPL:      V2.0-> 
     -- info-VERCTRL:   -
        SYNTAX        INTEGER (1..96)
        ACCESS        read-write
        STATUS        mandatory
        DESCRIPTION
             " This attribute is used to set the number of 15 minutes
               history entries which should be stored for history
               collection.
               Default value is 1. "
        --DEFAULT test-function-async     fsnPmCoTest
        --DEFAULT next-function-async     fsnPmCoNext
        --DEFAULT set-function-async      fsnPmCoSet
        --DEFAULT get-function-async      fsnPmCoGet
        ::= { xldv20pmControl 2 }

    xldv20pmCoIntervalType OBJECT-TYPE
     -- info-VALUE:     min15(1), day(2)
     -- info-ROU:       GET db  SET db
     -- info-IMPL:      V2.0-> 
     -- info-VERCTRL:   -
        SYNTAX        Xldv20pmIntervalType
        ACCESS        read-write
        STATUS        mandatory
        DESCRIPTION
             " This attribute identifies whether a 15 minutes interval
               or a day interval is selected in case of a
               resetIndividCurrent command. "
        --DEFAULT test-function-async     fsnPmCoTest
        --DEFAULT next-function-async     fsnPmCoNext
        --DEFAULT set-function-async      fsnPmCoSet
        --DEFAULT get-function-async      fsnPmCoGet
        ::= { xldv20pmControl 3 }

     xldv20pmCoControlReq OBJECT-TYPE
     -- info-VALUE:     noRequest(1), resetIndividCurrent(2),
     -- info-VALUE:     setNrHistEntriesSize(3), paramFaulty(4),
     -- info-VALUE:     nrHistEntriesSizeNotAcceptable(5),
     -- info-VALUE:     dataDaseMemoryNotAvailable(6)
     -- info-VALUE:     requestBusy(15), setDataFailed(16), aswTimeout(17)
     -- info-ROU:       GET db  SET pm
     -- info-IMPL:      V2.0-> 
     -- info-VERCTRL:   -
        SYNTAX        Xldv20pmControlReq
        ACCESS        read-write
        STATUS        mandatory
        DESCRIPTION
             " This attribute identifies a control command given by the
               SNMP agent.
               A reset for any individual PM object is possible via
               command resetIndividCurrent.
               The command setNrHistEntriesSize is used to set the
               number of 15 minutes history entries for history
               collection at a particular interface. "
        --DEFAULT test-function-async     fsnPmCoTest
        --DEFAULT next-function-async     fsnPmCoNext
        --DEFAULT set-function-async      fsnPmCoSet
        --DEFAULT get-function-async      fsnPmCoGet
        ::= { xldv20pmControl 4 }

    xldv20pmCoControlStatus OBJECT-TYPE
     -- info-VALUE:     requestIdle(1)..requestBusy(2),
     -- info-VALUE:     requestPassed(3)..requestFailed(4)
     -- info-ROU:       GET db
     -- info-IMPL:      V2.0-> 
     -- info-VERCTRL:   -
        SYNTAX        Xldv20ControlStatus
        ACCESS        read-only
        STATUS        mandatory
        DESCRIPTION
             " The status of a control request. "
        --DEFAULT next-function-async     fsnPmCoNext
        --DEFAULT get-function-async      fsnPmCoGet
        ::= { xldv20pmControl 5 }

    xldv20pmCoRemainingHistoryEntriesSize OBJECT-TYPE
     -- info-VALUE:     0..2000
     -- info-ROU:       GET db
     -- info-IMPL:      V2.0-> 
     -- info-VERCTRL:   -
        SYNTAX        INTEGER (0..2000)
        ACCESS        read-only
        STATUS        mandatory
        DESCRIPTION
             " This attribute indicates the number of remaining history
               entries which are available for the 15 minutes history
               collection wthin the ONU. 
               PM on physical and ATM layer use the same history memory
               which is limited in total to 2000 entries.
               The manager can read this attribute after the execution
               of the setNrHistEntriesSize command . "
        --DEFAULT next-function-async     fsnPmCoNext
        --DEFAULT get-function-async      fsnPmCoGet
        ::= { xldv20pmControl 6 }
    
    xldv20pmCoOAMLevel OBJECT-TYPE
     -- info-VALUE:     1..3
     -- info-ROU:       GET db
     -- info-IMPL:      V2.0-> 
     -- info-VERCTRL:   -
        SYNTAX        INTEGER (1..3)
        ACCESS        read-write
        STATUS        mandatory
        DESCRIPTION
             " This attribute selects the OAM level
             f1 (1), f2 (2), f3 (3) . "
        --DEFAULT test-function-async     fsnPmCoTest
        --DEFAULT next-function-async     fsnPmCoNext
        --DEFAULT set-function-async      fsnPmCoSet
        --DEFAULT get-function-async      fsnPmCoGet
        ::= { xldv20pmControl 7 }

    xldv20pmCoControlReqResult OBJECT-TYPE
     -- info-VALUE:     see Xldv20pmControlReq
     -- info-ROU:       GET db
     -- info-IMPL:      V2.0-> 
     -- info-VERCTRL:   -
        SYNTAX        Xldv20pmControlReq
        ACCESS        read-only
        STATUS        mandatory
        DESCRIPTION
             " The result of the last user command. "
        --DEFAULT next-function-async     fsnPmCoNext
        --DEFAULT get-function-async      fsnPmCoGet
        ::= { xldv20pmControl 8 }

     xldv20pmCoControlTimeStamp OBJECT-TYPE
     -- info-VALUE:   0..2Giga
     -- info-ROU:     GET db
     -- info-IMPL:      V2.0-> 
     -- info-VERCTRL: -
        SYNTAX        TimeTicks
        ACCESS        read-only
        STATUS        mandatory
        DESCRIPTION
           " The time stamp of the last command (end of command). "
        --DEFAULT next-function-async     fsnPmCoNext
        --DEFAULT get-function-async      fsnPmCoGet
        ::= { xldv20pmControl 9 }


     -- --------------------------------------------------------------
     --        PMo  on  ATM Layer                          
     --             C o n t r o l O b j e c t
     -- --------------------------------------------------------------

     xldv20pmAtmControl OBJECT IDENTIFIER
     -- info-IMPL:      V2.0-> 
     -- info-VERCTRL:   -
        ::= { xldv20pmPerformanceManagementControl 2 }

     -- This managed entity manages the user commands for
     -- of Performance Mangement.
     --
     -- An instance of this managed entity shall be automatically
     -- created by the ATM NE immediately following ATM NE
     -- initialization.

    xldv20pmAcoIndex OBJECT-TYPE
     -- info-VALUE:     -
     -- info-ROU:       GET db  SET db
     -- info-IMPL:      V2.0-> 
     -- info-VERCTRL:   -
        SYNTAX        Unsigned16
        ACCESS        read-write
        STATUS        mandatory
        DESCRIPTION
             " This attribute provides the index of the AtmPm object
             for which PM parameters shall be configured . "
        --DEFAULT test-function-async     fsnPmAcoTest
        --DEFAULT next-function-async     fsnPmAcoNext
        --DEFAULT set-function-async      fsnPmAcoSet
        --DEFAULT get-function-async      fsnPmAcoGet
        ::= { xldv20pmAtmControl 1 }

    xldv20pmAcoNrHistEntriesSize OBJECT-TYPE
     -- info-VALUE:     1..96 (default 1)
     -- info-VALUE:     day counter : 1, min15 counter : 1..96
     -- info-ROU:       GET db  SET db
     -- info-IMPL:      V2.0-> 
     -- info-VERCTRL:   -
        SYNTAX        INTEGER (1..96)
        ACCESS        read-write
        STATUS        mandatory
        DESCRIPTION
             " This attribute is used to set the number of 15 minutes
               history entries which should be stored for history
               collection. 
               The set HistEntrySize value is found in the 
               xldv20pmAcHistEntrySize. "
        --DEFAULT test-function-async     fsnPmAcoTest
        --DEFAULT next-function-async     fsnPmAcoNext
        --DEFAULT set-function-async      fsnPmAcoSet
        --DEFAULT get-function-async      fsnPmAcoGet
        ::= { xldv20pmAtmControl 2 }

    xldv20pmAcoIntervalType OBJECT-TYPE
     -- info-VALUE:     min15(1), day(2)
     -- info-ROU:       GET db  SET db
     -- info-IMPL:      V2.0-> 
     -- info-VERCTRL:   -
        SYNTAX        Xldv20pmIntervalType
        ACCESS        read-write
        STATUS        mandatory
        DESCRIPTION
             " This attribute identifies whether a 15 minutes interval
               or a day interval is selected in case of a
               resetIndividCurrent command. "
        --DEFAULT test-function-async     fsnPmAcoTest
        --DEFAULT next-function-async     fsnPmAcoNext
        --DEFAULT set-function-async      fsnPmAcoSet
        --DEFAULT get-function-async      fsnPmAcoGet
        ::= { xldv20pmAtmControl 3 }

     xldv20pmAcoControlReq OBJECT-TYPE
     -- info-VALUE:     noRequest(1), resetIndividCurrent(2),
     -- info-VALUE:     setNrHistEntriesSize(3), paramFaulty(4),
     -- info-VALUE:     nrHistEntriesSizeNotAcceptable(5),
     -- info-VALUE:     dataDaseMemoryNotAvailable(6)
     -- info-VALUE:     create(7), delete(8), addEndpoint(9),
     -- info-VALUE:     removeEndpoint(10),indexLimitExceeded(11)
     -- info-VALUE:     atmPmObjectActive(12), atmPmObjectNotExists(13),
     -- info-VALUE:     atmPmObjectExistsAlready(14), endpointExistsAlready(15) 
     -- info-VALUE:     requestBusy(15), setDataFailed(16), aswTimeout(17)
     -- info-ROU:       GET db  SET pm
     -- info-IMPL:      V2.0-> 
     -- info-VERCTRL:   -
        SYNTAX        Xldv20pmControlReq
        ACCESS        read-write
        STATUS        mandatory
        DESCRIPTION
             " This attribute identifies a control command given by the
               SNMP agent.
               A reset for any individual PM object is possible via
               command resetIndividCurrent.
               The command setNrHistEntriesSize is used to set the
               number of 15 minutes history entries for history
               collection at a particular interface.
               The commands create/delete are used to create/delete
               AtmPm monitoring objectes (entry in table
               xldv20pmAtmObjectsTable).
               The commands addEndpoint/deleteEndpoint are used to
               add or delete AtmPm endpoints to/from an PMo monitoring
               object. "
        --DEFAULT test-function-async     fsnPmAcoTest
        --DEFAULT next-function-async     fsnPmAcoNext
        --DEFAULT set-function-async      fsnPmAcoSet
        --DEFAULT get-function-async      fsnPmAcoGet
        ::= { xldv20pmAtmControl 4 }

    xldv20pmAcoControlStatus OBJECT-TYPE
     -- info-VALUE:     requestIdle(1)..requestBusy(2),
     -- info-VALUE:     requestPassed(3)..requestFailed(4)
     -- info-ROU:       GET db
     -- info-IMPL:      V2.0-> 
     -- info-VERCTRL:   -
        SYNTAX        Xldv20ControlStatus
        ACCESS        read-only
        STATUS        mandatory
        DESCRIPTION
             " The status of a control request. "
        --DEFAULT next-function-async     fsnPmAcoNext
        --DEFAULT get-function-async      fsnPmAcoGet
        ::= { xldv20pmAtmControl 5 }

    xldv20pmAcoRemainingHistoryEntriesSize OBJECT-TYPE
     -- info-VALUE:     0..2000
     -- info-ROU:       GET db
     -- info-IMPL:      V2.0-> 
     -- info-VERCTRL:   -
        SYNTAX        INTEGER (0..2000)
        ACCESS        read-only
        STATUS        mandatory
        DESCRIPTION
             " This attribute indicates the number of remaining history
               entries which are available for the 15 minutes history
               collection within the ONU.
               PM on physical and ATM layer use the same history memory
               which is limited in total to 2000 entries.
               Commonly used by PM on physical and ATM layer
               The manager can read this attribute after the execution
               of the setNrHistEntriesSize command . "
        --DEFAULT next-function-async     fsnPmAcoNext
        --DEFAULT get-function-async      fsnPmAcoGet
        ::= { xldv20pmAtmControl 6 }
    
    xldv20pmAcoFlowType OBJECT-TYPE
     -- info-VALUE:     f4Segment(1), f4EndToEnd(2)
     -- info-VALUE:     f5Segment(3), f5EndToEnd(4)
     -- info-ROU:       GET db  SET db
     -- info-IMPL:      V2.0-> 
     -- info-VERCTRL:   -
        SYNTAX        Xldv20pmFlowType
        ACCESS        read-write
        STATUS        mandatory
        DESCRIPTION
             " This attribute identifies the flow type :
               F4 (VP) or F5 (VC) segment or endToEnd flow. "
        --DEFAULT test-function-async     fsnPmAcoTest
        --DEFAULT next-function-async     fsnPmAcoNext
        --DEFAULT set-function-async      fsnPmAcoSet
        --DEFAULT get-function-async      fsnPmAcoGet
        ::= { xldv20pmAtmControl 7 }

    xldv20pmAcoFlowDirection OBJECT-TYPE
     -- info-VALUE:     inwards(2), outwards(3)
     -- info-ROU:       GET db  SET db
     -- info-IMPL:      V2.0-> 
     -- info-VERCTRL:   -
        SYNTAX        Xldv20FlowDirection
        ACCESS        read-write
        STATUS        mandatory
        DESCRIPTION
             " The flow direction of OAM cells.
               'inwards' means flow direction from outside (external interface)
               to cross connection.
               'outwards' means flow direction from inside to external interface. "
        --DEFAULT test-function-async     fsnPmAcoTest
        --DEFAULT next-function-async     fsnPmAcoNext
        --DEFAULT set-function-async      fsnPmAcoSet
        --DEFAULT get-function-async      fsnPmAcoGet
        ::= { xldv20pmAtmControl 8 }

    xldv20pmAcoConnectionIndex OBJECT-TYPE
     -- info-VALUE:     1..2048
     -- info-ROU:       GET db  SET db
     -- info-IMPL:      V2.0-> 
     -- info-VERCTRL:   -
        SYNTAX        INTEGER (1..2048)
        ACCESS        read-write
        STATUS        mandatory
        DESCRIPTION
             " This attribute identifies the index of a
             Vpl or Vcl cross connection. "
        --DEFAULT test-function-async     fsnPmAcoTest
        --DEFAULT next-function-async     fsnPmAcoNext
        --DEFAULT set-function-async      fsnPmAcoSet
        --DEFAULT get-function-async      fsnPmAcoGet
        ::= { xldv20pmAtmControl 9 }

    xldv20pmAcoConnectionIndexType OBJECT-TYPE
     -- info-VALUE:     vplUni(1),vplNni(2),vclUni(3),vclNni(4)
     -- info-ROU:       GET db  SET db
     -- info-IMPL:      V2.0-> 
     -- info-VERCTRL:   -
        SYNTAX        Xldv20pmConnectionIndexType
        ACCESS        read-write
        STATUS        mandatory
        DESCRIPTION
             " This attribute identifies the type of connection index
             and the termination point. It is in case of 
             vplUni/vplNni : index of Vpl CC (xldv20AccVpiNniIndex)
             vclUni/vplNni : index of Vcl CC (xldv20VcxIndex). "
        --DEFAULT test-function-async     fsnPmAcoTest
        --DEFAULT next-function-async     fsnPmAcoNext
        --DEFAULT set-function-async      fsnPmAcoSet
        --DEFAULT get-function-async      fsnPmAcoGet
        ::= { xldv20pmAtmControl 10 }
    
    xldv20pmAcoRole OBJECT-TYPE
     -- info-VALUE:     analyseWithBackwardReporting(1),
     -- info-VALUE:     analyseWithoutBackwardReporting(2),
     -- info-VALUE:     generateWithCollect(3), generateWithoutCollect(4)
     -- info-ROU:       GET db  SET db
     -- info-IMPL:      V2.0-> 
     -- info-VERCTRL:   -
        SYNTAX        Xldv20pmRoleType
        ACCESS        read-write
        STATUS        mandatory
        DESCRIPTION
             " The role of endpoint.
             'analyseWithBackwardReporting' (sink) means extracting
             forward monitoring (FM) OAM cells, sending back 
             backward reporting OAM cells and no data collection
             for current and history table.  
             'analyseWithoutBackwardReporting' (sink) means extracting
             FM cells without any other OAM handling
             and also collecting data.  
             'generateWithCollect' (source) means inserting FM cells,
             extracting backward reporting cells if they arrive 
             and collect data for current and history table.  
             'generateWithoutCollect' (source) means inserting FM cells
             but without collecting data.
             The CMU, the Ethernet part of the Twin NT s capable of 
	     operating as inserting or extracting point. "
        --DEFAULT test-function-async     fsnPmAcoTest
        --DEFAULT next-function-async     fsnPmAcoNext
        --DEFAULT set-function-async      fsnPmAcoSet
        --DEFAULT get-function-async      fsnPmAcoGet
        ::= { xldv20pmAtmControl 12 }

    xldv20pmAcoEndpointType OBJECT-TYPE
     -- info-VALUE:     source(1), sink(2)
     -- info-ROU:       GET db  SET db
     -- info-IMPL:      V2.0-> 
     -- info-VERCTRL:   -
        SYNTAX        Xldv20pmEndpointType
        ACCESS        read-write
        STATUS        mandatory
        DESCRIPTION
             " Identifies the type of endpoint. "
        --DEFAULT test-function-async     fsnPmAcoTest
        --DEFAULT next-function-async     fsnPmAcoNext
        --DEFAULT set-function-async      fsnPmAcoSet
        --DEFAULT get-function-async      fsnPmAcoGet
        ::= { xldv20pmAtmControl 13 }

    xldv20pmAcoControlReqResult OBJECT-TYPE
     -- info-VALUE:     see Xldv20pmControlReq
     -- info-ROU:       GET db
     -- info-IMPL:      V2.0-> 
     -- info-VERCTRL:   -
        SYNTAX        Xldv20pmControlReq
        ACCESS        read-only
        STATUS        mandatory
        DESCRIPTION
             " The result of the last user command. "
        --DEFAULT next-function-async     fsnPmAcoNext
        --DEFAULT get-function-async      fsnPmAcoGet
        ::= { xldv20pmAtmControl 14 }

     xldv20pmAcoControlTimeStamp OBJECT-TYPE
     -- info-VALUE:   0..2Giga
     -- info-ROU:     GET db
     -- info-IMPL:      V2.0-> 
     -- info-VERCTRL: -
        SYNTAX        TimeTicks
        ACCESS        read-only
        STATUS        mandatory
        DESCRIPTION
           " The time stamp of the last command (end of command). "
        --DEFAULT next-function-async     fsnPmAcoNext
        --DEFAULT get-function-async      fsnPmAcoGet
        ::= { xldv20pmAtmControl 15 }

     -- ==============================================================
     --       P e r f o r m a n c e   M o n i t o r i n g  (PMo)
     --                         g r o u p
     -- ==============================================================

     -- ------------------------------------------------------------------
     --  PMo o n  p h y s i c a l  l a y e r
     -- ------------------------------------------------------------------
     --
     -- Description of the PMo Events of the PM common group.
     -- To the common group belong those type of TLM interfaces
     -- which have the same performance monitoring counters.
     -- These are the interface types : adc, adr, vdc, vdr, e3n, e3f.
     --
     -- Errored Seconds (ES)
     -- An Errored Second is a  one second interval containing one or
     -- more crc-i or crc-ni anomalies, or one or more loss of signal
     -- or severely errored frame (SEF) defects applicable to adc/adr
     -- interfaces
     --
     -- Severely Errored Seconds (SEF)
     -- A one second period in which at least 30% of the blocks are in
     -- error or as a one second period which contains a Severely
     -- Disturbed Period . SDP is usually estimated as the occurrence
     -- of a network defect, such as loss of signal, loss of frame,
     -- or other alarm indicators
     --
     -- Background Block Error (BBE)
     -- A Background Block Error is an errored-block not occurring as
     -- part of an SES
     --
     -- Unavailable Seconds (UAS)
     -- A period of unavailable time begins at the onset of 10 consecu-
     -- tive SES events. These ten seconds are considered to be part of
     -- unavailable time. A new period of available time begins at the
     -- onset of ten consecutive non-SES events. These 10 seconds are
     -- considered to be part of available time.
     -- Note: during Unavailable Seconds (UAS), performance parameters
     --       are not counted, exception is the UAS themselves, they
     --       are counted further.



     -- --------------------------------------------------------------
     --               PMo Common Current Data Table
     -- --------------------------------------------------------------

     xldv20pmCommonCurrentTable OBJECT-TYPE
     -- info-IMPL:      V2.0-> 
     -- info-VERCTRL:   -
        SYNTAX        SEQUENCE OF Xldv20pmCommonCurrentEntry
        ACCESS        not-accessible
        STATUS        mandatory
        DESCRIPTION
             " This table contains the entries for the current 15 minute interval
               or the current day of PMo objects of the common group.
               (adc, adr, e3n and e3f) . "
        --DEFAULT test-function-async     fsnPmCcEntryTest
        --DEFAULT next-function-async     fsnPmCcEntryNext
        --DEFAULT set-function-async      fsnPmCcEntrySet
        --DEFAULT get-function-async      fsnPmCcEntryGet
        ::= { xldv20pmPerformanceMonitoring 2 }

     xldv20pmCommonCurrentEntry OBJECT-TYPE
     -- info-IMPL:      V2.0-> 
     -- info-VERCTRL:   -
        SYNTAX        Xldv20pmCommonCurrentEntry
        ACCESS        not-accessible
        STATUS        mandatory
        DESCRIPTION
             " An entry describing the Common Current Data Table . "
        INDEX { xldv20IfIndex,
                xldv20pmCcIntervalType,
                xldv20pmCcOAMLevel }
        ::= { xldv20pmCommonCurrentTable 1 }

     Xldv20pmCommonCurrentEntry ::=
        SEQUENCE { xldv20pmCcIntervalType         Xldv20pmIntervalType,
                   xldv20pmCcOAMLevel                    INTEGER,
                   xldv20pmCcAdminState           Xldv20AdminState,
                   xldv20pmCcSuspectFlag          Xldv20pmSuspectType,
                   xldv20pmCcHistEntrySize               INTEGER,
                   xldv20pmCcNrHistEntriesAvailable      INTEGER,
                   xldv20pmCcElapsedTime                 INTEGER,
                   xldv20pmCcThresholdLimitIndex         INTEGER,
                   xldv20pmCcNeErroredSeconds            Counter,
                   xldv20pmCcFeErroredSeconds            Counter,
                   xldv20pmCcNeSeverelyErroredSeconds    Counter,
                   xldv20pmCcFeSeverelyErroredSeconds    Counter,
                   xldv20pmCcNeBackgroundBlockErrors     Counter,
                   xldv20pmCcFeBackgroundBlockErrors     Counter,
                   xldv20pmCcNeUnavailableSeconds        Counter,
                   xldv20pmCcFeUnavailableSeconds        Counter }

     xldv20pmCcIntervalType OBJECT-TYPE
     -- info-VALUE:     min15(1), day(2)
     -- info-ROU:       GET  db
     -- info-IMPL:      V2.0-> 
     -- info-VERCTRL:   -
        SYNTAX        Xldv20pmIntervalType
        ACCESS        read-only
        STATUS        mandatory
        DESCRIPTION
             " This attribute is used to select between the
               15 min  or the day accumulation types. "
        ::= { xldv20pmCommonCurrentEntry 1 }

     xldv20pmCcOAMLevel OBJECT-TYPE
     -- info-VALUE:     1..3
     -- info-ROU:       GET db
     -- info-IMPL:      V2.0-> 
     -- info-VERCTRL:   -
        SYNTAX        INTEGER (1..3)
        ACCESS        read-only
        STATUS        mandatory
        DESCRIPTION
             " This attribute is used to select between the
               3 OAM levels f1 (1), f2 (2) and f3 (3) . "
        ::= { xldv20pmCommonCurrentEntry 2 }

     xldv20pmCcAdminState OBJECT-TYPE
     -- info-VALUE:     unlocked(1), locked(2)
     -- info-ROU:       GET db  SET pm
     -- info-IMPL:      V2.0-> 
     -- info-VERCTRL:   -
        SYNTAX        Xldv20AdminState
        ACCESS        read-write
        STATUS        mandatory
        DESCRIPTION
             " This read-write attribute is used to activate (unlock)
               and deactivate (lock) the functions (incl. collection)
               performed by this managed entity.
               Note: the 15min  collection object must be activated,
                     before day collection can operate. "
        ::= { xldv20pmCommonCurrentEntry 3 }

     xldv20pmCcSuspectFlag OBJECT-TYPE
     -- info-VALUE:     reliable(1), suspect(2)
     -- info-ROU:       GET db
     -- info-IMPL:      V2.0-> 
     -- info-VERCTRL:   -
        SYNTAX        Xldv20pmSuspectType
        ACCESS        read-only
        STATUS        mandatory
        DESCRIPTION
             " This read-only attribute will be set to indicate that
               troubles arose during an interval and that the counter
               values are suspect and incomplete. "
        ::= { xldv20pmCommonCurrentEntry 4 }

     xldv20pmCcHistEntrySize OBJECT-TYPE
     -- info-VALUE:     1..96
     -- info-ROU:       GET db
     -- info-IMPL:      V2.0-> 
     -- info-VERCTRL:   -
        SYNTAX        INTEGER (1..96)
        ACCESS        read-only
        STATUS        mandatory
        DESCRIPTION
             " The number of 15min history entries configured at the particular interface. This
               attribute is used for history data collection.
               The default value is 1 and means at least one history entry
               is desired . "
        ::= { xldv20pmCommonCurrentEntry 5 }

     xldv20pmCcNrHistEntriesAvailable OBJECT-TYPE
     -- info-VALUE:     0..96
     -- info-ROU:       GET db
     -- info-IMPL:      V2.0-> 
     -- info-VERCTRL:   -
        SYNTAX        INTEGER (0..96)
        ACCESS        read-only
        STATUS        mandatory
        DESCRIPTION
             " This read-only attribute indicates how many HistEntries
               are already available.
               The range of values is between 0 and xldv20pmCcHistEntrySize,
               thereby 0 means that this entry is not valid . "
        ::= { xldv20pmCommonCurrentEntry 6 }

     xldv20pmCcElapsedTime OBJECT-TYPE
     -- info-VALUE:     0..900 (sec) for min15,
     -- info-VALUE:     0..1440 (min) for day
     -- info-ROU:       GET db
     -- info-IMPL:      V2.0-> 
     -- info-VERCTRL:   -
        SYNTAX        INTEGER(0..1440)
        ACCESS        read-only
        STATUS        mandatory
        DESCRIPTION
             " This read-only attribute represents the difference
               between the current time and the start of the present
               summary interval. 
	       Units are seconds when 15 minute interval is selected 
	       or minutes for day interval.
               (Note: accurate to the sample time interval). "
        ::= { xldv20pmCommonCurrentEntry 7 }

     xldv20pmCcThresholdLimitIndex OBJECT-TYPE
     -- info-VALUE:     1..30
     -- info-ROU:       GET db  SET pm
     -- info-IMPL:      V2.0-> 
     -- info-VERCTRL:   -
        SYNTAX        INTEGER (1..30)
        ACCESS        read-write
        STATUS        mandatory
        DESCRIPTION
             " This read-write attribute provides an index to the
               ThresholdLimitTable managed entity that contains the
               threshold limits for the performance parameters reported
               by this managed entity.
               When the value of this attribute is set to 1, default
               threshold limits shall be used . "
        ::= { xldv20pmCommonCurrentEntry 8 }

     xldv20pmCcNeErroredSeconds OBJECT-TYPE
     -- info-VALUE:     -
     -- info-ROU:       GET db
     -- info-IMPL:      V2.0-> 
     -- info-VERCTRL:   -
        SYNTAX        Counter
        ACCESS        read-only
        STATUS        mandatory
        DESCRIPTION
             " A near end counter of Errored Seconds (ES)
	     over a 15 min/day interval.
             Counter appearence depends on interface type and OAM
             level :
                - adc, e3n: valid for F3 level . "
        ::= { xldv20pmCommonCurrentEntry 9 }

     xldv20pmCcFeErroredSeconds OBJECT-TYPE
     -- info-VALUE:     -
     -- info-ROU:       GET db
     -- info-IMPL:      V2.0-> 
     -- info-VERCTRL:   -
        SYNTAX        Counter
        ACCESS        read-only
        STATUS        mandatory
        DESCRIPTION
             " A far end counter of 
             Errored Seconds (ES) over a 15 min /day interval. 
             Counter appearence depends on interface type and OAM level :
                - adr, e3f: valid for F3 level . "
        ::= { xldv20pmCommonCurrentEntry 10 }

     xldv20pmCcNeSeverelyErroredSeconds OBJECT-TYPE
     -- info-VALUE:     -
     -- info-ROU:       GET db
     -- info-IMPL:      V2.0-> 
     -- info-VERCTRL:   -
        SYNTAX        Counter
        ACCESS        read-only
        STATUS        mandatory
        DESCRIPTION
             " Represents a near end counter of
               Severely Errored Seconds (SES) over a 15 min /day
               interval.
               Counter appearence depends on interface type and OAM level :
                - adc, e3n: valid for F3 level . "
        ::= { xldv20pmCommonCurrentEntry 11 }

     xldv20pmCcFeSeverelyErroredSeconds OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a far end counter of
               Severely Errored Seconds (SES) over a 15 min /day
               interval.
               Counter appearence depends on interface type and OAM level :
                - adr, e3f: valid for F3 level . "
        ::= { xldv20pmCommonCurrentEntry 12 }

     xldv20pmCcNeBackgroundBlockErrors OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a near end counter for
               Background Block Errors (BBE) over a 15 min /day
               interval.
               Counter appearence depends on interface type and OAM
               level :
                - adc, e3n: valid for F3 level . "
        ::= { xldv20pmCommonCurrentEntry 13 }

     xldv20pmCcFeBackgroundBlockErrors OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a far end counter for
               Background Block Errors (BBE) over a 15 min /day
               interval.
               Counter appearence depends on interface type and OAM
               level :
                - adr, e3f: valid for F3 level . "
        ::= { xldv20pmCommonCurrentEntry 14 }

     xldv20pmCcNeUnavailableSeconds OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a counter of
               Unavailable Seconds (UAS) within the current 15 minute interval
               or current day.
               Counter applicable for : adc, e3n and f3 level . "
        ::= { xldv20pmCommonCurrentEntry 15 }

     xldv20pmCcFeUnavailableSeconds OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a far end counter of
               Unavailable Seconds (UAS) within the current 15 minute interval
               or current day.
               Counter applicable for : adr, e3f and F3 level . "
        ::= { xldv20pmCommonCurrentEntry 16 }


     -- --------------------------------------------------------------
     --        PMo  C o m m o n  H i s t o r y  D a t a  Table
     -- --------------------------------------------------------------

     xldv20pmCommonHistoryTable OBJECT-TYPE
     -- info-IMPL:      V2.0-> 
     -- info-VERCTRL:   -
        SYNTAX        SEQUENCE OF Xldv20pmCommonHistoryEntry
        ACCESS        not-accessible
        STATUS        mandatory
        DESCRIPTION
             " This table contains the entries for the PMo objects of
               the 15 min /one day-history data collection results at
               the respective adc, adr drop area
               interfaces . "
        --DEFAULT get-function-async      fsnPmChEntryGet
        --DEFAULT next-function-async     fsnPmChEntryNext
        ::= { xldv20pmPerformanceMonitoring 3 }

     xldv20pmCommonHistoryEntry OBJECT-TYPE
     -- info-IMPL:      V2.0-> 
     -- info-VERCTRL:   -
        SYNTAX        Xldv20pmCommonHistoryEntry
        ACCESS        not-accessible
        STATUS        mandatory
        DESCRIPTION
             " An entry describing the Common History Data Table . "
        INDEX { xldv20IfIndex,
                xldv20pmChIntervalType,
                xldv20pmChOAMLevel,
                xldv20pmChHistEntryNr }
        ::= { xldv20pmCommonHistoryTable 1 }

     Xldv20pmCommonHistoryEntry ::=
        SEQUENCE { xldv20pmChIntervalType        Xldv20pmIntervalType,
                   xldv20pmChOAMLevel                 INTEGER,
                   xldv20pmChHistEntryNr              INTEGER,
                   xldv20pmChSuspectFlag         Xldv20pmSuspectType,
                   xldv20pmChPeriodEndTime            INTEGER,
                   xldv20pmChNeErroredSeconds           Counter,
                   xldv20pmChFeErroredSeconds           Counter,
                   xldv20pmChNeSeverelyErroredSeconds   Counter,
                   xldv20pmChFeSeverelyErroredSeconds   Counter,
                   xldv20pmChNeBackgroundBlockErrors    Counter,
                   xldv20pmChFeBackgroundBlockErrors    Counter,
                   xldv20pmChNeUnavailableSeconds       Counter,
                   xldv20pmChFeUnavailableSeconds       Counter }

     xldv20pmChIntervalType OBJECT-TYPE
     -- info-VALUE:     min 5(1), day(2)
     -- info-ROU:       GET db
     -- info-IMPL:      V2.0-> 
     -- info-VERCTRL:   -
        SYNTAX        Xldv20pmIntervalType
        ACCESS        read-only
        STATUS        mandatory
        DESCRIPTION
             " This type attribute is used to select between the
               15 min  or the day accumulation types. "
        ::= { xldv20pmCommonHistoryEntry 1 }

     xldv20pmChOAMLevel OBJECT-TYPE
     -- info-VALUE:     1..3
     -- info-ROU:       GET db
     -- info-IMPL:      V2.0-> 
     -- info-VERCTRL:   -
        SYNTAX        INTEGER (1..3)
        ACCESS        read-only
        STATUS        mandatory
        DESCRIPTION
             " This attribute is used to select between the
               3 OAM levels f1 (1), f2 (2) and f3 (3) . "
        ::= { xldv20pmCommonHistoryEntry 2 }

     xldv20pmChHistEntryNr OBJECT-TYPE
     -- info-VALUE:     1..96
     -- info-ROU:       GET db
     -- info-IMPL:      V2.0-> 
     -- info-VERCTRL:   -
        SYNTAX        INTEGER (1..96)
        ACCESS        read-only
        STATUS        mandatory
        DESCRIPTION
             " This attribute is an index used to address the PM history entry.
             Entry 1 is the most recent, entry 96 is 24 hours ago.
             The range of values is between 1 and xldv20pmCcHistEntrySize . " 
        ::= { xldv20pmCommonHistoryEntry 3 }

     xldv20pmChSuspectFlag OBJECT-TYPE
     -- info-VALUE:     reliable(1), suspect(2)
     -- info-ROU:       GET db
     -- info-IMPL:      V2.0-> 
     -- info-VERCTRL:   -
        SYNTAX        Xldv20pmSuspectType
        ACCESS        read-only
        STATUS        mandatory
        DESCRIPTION
             " Will be set to indicate that
               troubles arose during an interval and that the counter
               values are suspect and incomplete. "
        ::= { xldv20pmCommonHistoryEntry 4 }

     xldv20pmChPeriodEndTime OBJECT-TYPE
     -- info-VALUE:     0..2147483647
     -- info-ROU:       GET  db
     -- info-IMPL:      V2.0-> 
     -- info-VERCTRL:   -
        SYNTAX        INTEGER (0..2147483647)
        ACCESS        read-only
        STATUS        mandatory
        DESCRIPTION
             " Date/time at the end of the selected interval. "
        ::= { xldv20pmCommonHistoryEntry 5 }

     xldv20pmChNeErroredSeconds OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a near end counter of Errored
               Seconds (ES) over a 15 min /day interval.
               Counter applicable for : adc, e3n and F3 level . "
        ::= { xldv20pmCommonHistoryEntry 6 }

     xldv20pmChFeErroredSeconds OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a far end counter of Errored
               Seconds (ES) within the current 15 minute interval or current day.
               Counter applicable for : adr, e3f and F3 level . "
        ::= { xldv20pmCommonHistoryEntry 7 }

     xldv20pmChNeSeverelyErroredSeconds OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a near end counter of
               Severely Errored Seconds (SES) within the current 15 minute
               interval or current day.
               Counter applicable for : adc, e3n and F3 level . "
        ::= { xldv20pmCommonHistoryEntry 8 }

     xldv20pmChFeSeverelyErroredSeconds OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a far end counter of
               Severely Errored Seconds (SES) within the current 15 minute
               interval or current day.
               Counter applicable for : adr, e3f and F3 level . "
        ::= { xldv20pmCommonHistoryEntry 9 }

     xldv20pmChNeBackgroundBlockErrors OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a near end counter for
               Background Block Errors (BBE) over a 15 min /day
               interval.
               Counter applicable for : adc, e3n and F3 level . "
        ::= { xldv20pmCommonHistoryEntry 10 }

     xldv20pmChFeBackgroundBlockErrors OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a far end counter for
               Background Block Errors (BBE) over a 15 min /day
               interval.
               Counter applicable for : adr, e3n and F3 level . "
        ::= { xldv20pmCommonHistoryEntry 11 }

     xldv20pmChNeUnavailableSeconds OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a near end counter of
               Unavailable Seconds (UAS) for a 15 min /day interval.
               Counter applicable for : adc, e3n and F3 level . "
        ::= { xldv20pmCommonHistoryEntry 12 }

     xldv20pmChFeUnavailableSeconds OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a far end counter of
               Unavailable Seconds (UAS) for a 15 min /day interval.
               Counter applicable for : adr, e3f and F3 level . "
        ::= { xldv20pmCommonHistoryEntry 13 }


     -- --------------------------------------------------------------
     --          Pmo  S T S 3  C u r r e n t  D a t a  Table
     -- --------------------------------------------------------------

     xldv20pmS3CurrentTable OBJECT-TYPE
     -- info-IMPL:      V2.0-> 
        SYNTAX        SEQUENCE OF Xldv20pmS3CurrentEntry
        ACCESS        not-accessible
        STATUS        mandatory
        DESCRIPTION
             " This table contains the entries for the current 15 minute interval
               or the current day for STS3c near-end and far-end PPTPs. "
        --DEFAULT test-function-async     fsnPmS3cEntryTest
        --DEFAULT next-function-async     fsnPmS3cEntryNext
        --DEFAULT set-function-async      fsnPmS3cEntrySet
        --DEFAULT get-function-async      fsnPmS3cEntryGet
        ::= { xldv20pmPerformanceMonitoring 4 }

     xldv20pmS3CurrentEntry OBJECT-TYPE
     -- info-IMPL:      V2.0-> 
     -- info-VERCTRL:   -
        SYNTAX        Xldv20pmS3CurrentEntry
        ACCESS        not-accessible
        STATUS        mandatory
        DESCRIPTION
             " An entry describing the STS3 near-end and far-end
               Current Data Table . "
        INDEX { xldv20IfIndex,
                xldv20pmS3cIntervalType,
                xldv20pmS3cOAMLevel }
        ::= { xldv20pmS3CurrentTable 1 }

     Xldv20pmS3CurrentEntry ::=
        SEQUENCE { xldv20pmS3cIntervalType            Xldv20pmIntervalType,
                   xldv20pmS3cOAMLevel                       INTEGER,
                   xldv20pmS3cAdminState              Xldv20AdminState,
                   xldv20pmS3cSuspectFlag             Xldv20pmSuspectType,
                   xldv20pmS3cHistEntrySize                  INTEGER,
                   xldv20pmS3cNrHistEntriesAvailable         INTEGER,
                   xldv20pmS3cElapsedTime                    INTEGER,
                   xldv20pmS3cThresholdLimitIndex            INTEGER,
                   xldv20pmS3cNeErroredSeconds               Counter,
                   xldv20pmS3cFeErroredSeconds               Counter,
                   xldv20pmS3cNeSeverelyErroredSeconds       Counter,
                   xldv20pmS3cFeSeverelyErroredSeconds       Counter,
                   xldv20pmS3cNeCodeViolations               Counter,
                   xldv20pmS3cFeCodeViolations               Counter,
                   xldv20pmS3cNeUnavailableSeconds           Counter,
                   xldv20pmS3cFeUnavailableSeconds           Counter,
                   xldv20pmS3cNeSeverelyErroredFrameSeconds  Counter }

     xldv20pmS3cIntervalType OBJECT-TYPE
     -- info-VALUE:     min15(1), day(2)
     -- info-ROU:       GET db
     -- info-IMPL:      V2.0-> 
     -- info-VERCTRL:   -
        SYNTAX        Xldv20pmIntervalType
        ACCESS        read-only
        STATUS        mandatory
        DESCRIPTION
             " This type attribute is used to select between the
               15 min  or the day accumulation types. "
        ::= { xldv20pmS3CurrentEntry 1 }

     xldv20pmS3cOAMLevel OBJECT-TYPE
     -- info-VALUE:     1..3
     -- info-ROU:       GET db
     -- info-IMPL:      V2.0-> 
     -- info-VERCTRL:   -
        SYNTAX        INTEGER (1..3)
        ACCESS        read-only
        STATUS        mandatory
        DESCRIPTION
             " This attribute is used to select between the
               3 OAM levels f1 (1), f2 (2) and f3 (3) . "
        ::= { xldv20pmS3CurrentEntry 2 }

     xldv20pmS3cAdminState OBJECT-TYPE
     -- info-VALUE:     unlocked(1), locked(2)
     -- info-ROU:       GET  db SET pm
     -- info-IMPL:      V2.0-> 
     -- info-VERCTRL:   -
        SYNTAX        Xldv20AdminState
        ACCESS        read-write
        STATUS        mandatory
        DESCRIPTION
             " This read-write attribute is used to activate (unlock)
               and deactivate (lock) the functions (incl. collection)
               performed by this managed entity.
               Note: the 15min  collection object must be activated,
                     before day collection can operate. "
        ::= { xldv20pmS3CurrentEntry 3 }

     xldv20pmS3cSuspectFlag OBJECT-TYPE
     -- info-VALUE:     reliable(1), suspect(2)
     -- info-ROU:       GET db
     -- info-IMPL:      V2.0-> 
     -- info-VERCTRL:   -
        SYNTAX        Xldv20pmSuspectType
        ACCESS        read-only
        STATUS        mandatory
        DESCRIPTION
             " This read-only attribute will be set to indicate that
               troubles arose during an interval and that the counter
               values are suspect and incomplete. "
        ::= { xldv20pmS3CurrentEntry 4 }

     xldv20pmS3cHistEntrySize OBJECT-TYPE
     -- info-VALUE:     1..96
     -- info-ROU:       GET db
     -- info-IMPL:      V2.0-> 
     -- info-VERCTRL:   -
        SYNTAX        INTEGER (1..96)
        ACCESS        read-only
        STATUS        mandatory
        DESCRIPTION
             " This read-only attribute indicates the number of 15min 
               history entries configured at the particular interface.
               The default value is 1 and means that at least one
               history entry is provided . "
        ::= { xldv20pmS3CurrentEntry 5 }

     xldv20pmS3cNrHistEntriesAvailable OBJECT-TYPE
     -- info-VALUE:     0..96
     -- info-ROU:       GET db
     -- info-IMPL:      V2.0-> 
     -- info-VERCTRL:   -
        SYNTAX        INTEGER (0..96)
        ACCESS        read-only
        STATUS        mandatory
        DESCRIPTION
             " This read-only attribute indicates how many history entries
               are already available.
               The range of values is between 0 and xldv20S3cHistEntrySize,
               thereby 0 means that this entry is not valid . "
        ::= { xldv20pmS3CurrentEntry 6 }

     xldv20pmS3cElapsedTime OBJECT-TYPE
     -- info-VALUE:     0..900 (sec) for min15
     -- info-VALUE:     0..1440 (min) for day
     -- info-ROU:       GET db
     -- info-IMPL:      V2.0-> 
     -- info-VERCTRL:   -
        SYNTAX        INTEGER (0..1440)
        ACCESS        read-only
        STATUS        mandatory
        DESCRIPTION
             " This read-only attribute represents the difference
               between the current time and the start of the present
               summary interval.
	       Units are seconds when 15 minute interval is selected 
	       or minutes for day interval.
               (Note: accurate to the sample time interval). "
        ::= { xldv20pmS3CurrentEntry 7 }

     xldv20pmS3cThresholdLimitIndex OBJECT-TYPE
     -- info-VALUE:     1..30
     -- info-ROU:       GET db  SET pm
     -- info-IMPL:      V2.0-> 
     -- info-VERCTRL:   -
        SYNTAX        INTEGER (1..30)
        ACCESS        read-write
        STATUS        mandatory
        DESCRIPTION
             " This read-write attribute provides an index to the
               ThresholdLimitTable managed entity that contains the
               threshold limits for the performance parameters reported
               by this managed entity.
               When the value of this attribute is set to 1, default
               threshold limits shall be used
               The range of values is [1,30]. "
        ::= { xldv20pmS3CurrentEntry 8 }

     xldv20pmS3cNeErroredSeconds OBJECT-TYPE
     -- info-VALUE:     -
     -- info-ROU:       GET  SET [db,pm]
     -- info-IMPL:      V2.0-> 
     -- info-VERCTRL:   -
        SYNTAX        Counter
        ACCESS        read-only
        STATUS        mandatory
        DESCRIPTION
             " This read-only attribute represents a counter of Errored Seconds (ES)
             within the current 15min interval or current day.
             Counter applicable for : s3n and F1, F2, F3 levels . "
        ::= { xldv20pmS3CurrentEntry 9 }

     xldv20pmS3cFeErroredSeconds OBJECT-TYPE
     -- info-VALUE:     -
     -- info-ROU:       GET  SET [db,pm]
     -- info-IMPL:      V2.0-> 
     -- info-VERCTRL:   -
        SYNTAX        Counter
        ACCESS        read-only
        STATUS        mandatory
        DESCRIPTION
             " This read-only attribute represents a counter of
             Errored Seconds (ES) within the current 15min interval or current day.
             Counter applicable for : s3f and F2 and F3 levels . "
        ::= { xldv20pmS3CurrentEntry 10 }

     xldv20pmS3cNeSeverelyErroredSeconds OBJECT-TYPE
     -- info-VALUE:     -
     -- info-ROU:       GET  SET [db,pm]
     -- info-IMPL:      V2.0-> 
     -- info-VERCTRL:   -
        SYNTAX        Counter
        ACCESS        read-only
        STATUS        mandatory
        DESCRIPTION
             " This read-only attribute represents a counter of
               Severely Errored Seconds (SES) within the current
               15min interval or current day.
               Counter applicable for : s3n and F2 and F3 levels . "
        ::= { xldv20pmS3CurrentEntry 11 }

     xldv20pmS3cFeSeverelyErroredSeconds OBJECT-TYPE
     -- info-VALUE:     -
     -- info-ROU:       GET  SET [db,pm]
     -- info-IMPL:      V2.0-> 
     -- info-VERCTRL:   -
        SYNTAX        Counter
        ACCESS        read-only
        STATUS        mandatory
        DESCRIPTION
             " This read-only attribute represents a counter of
               Severely Errored Seconds (SES) within the current 15min interval
               or current day.
               Counter applicable for : s3f and for F2 and F3 levels . "
        ::= { xldv20pmS3CurrentEntry 12 }

     xldv20pmS3cNeCodeViolations OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a counter of
               Code Violations Errors within the current 15min interval
               or current day.
               Counter applicable for : s3n and F1, F2, F3 levels . "
        ::= { xldv20pmS3CurrentEntry 13 }

     xldv20pmS3cFeCodeViolations OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a counter of
               Code Violations Errors within the current 15min interval
               or current day.
               Counter applicable for : s3f and F2 and F3 levels . "
        ::= { xldv20pmS3CurrentEntry 14 }

     xldv20pmS3cNeUnavailableSeconds OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a counter of
               Unavailable Seconds (UAS) within the current 15min interval
               or current day.
               Counter applicable for : s3n and F2 and F3 levels . "
        ::= { xldv20pmS3CurrentEntry 15 }

     xldv20pmS3cFeUnavailableSeconds OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a counter of
               Unavailable Seconds (UAS) within the current 15min interval
               or current day.
               Counter applicable for : s3f and level F2 and F3 . "
        ::= { xldv20pmS3CurrentEntry 16 }

     xldv20pmS3cNeSeverelyErroredFrameSeconds OBJECT-TYPE
     -- info-VALUE:     -
     -- info-ROU:       GET  db
     -- info-IMPL:      V2.0-> 
     -- info-VERCTRL:   -
        SYNTAX        Counter
        ACCESS        read-only
        STATUS        mandatory
        DESCRIPTION
             " This read-only attribute represents a counter of
               Severely Errored Frame Seconds within the current 15min interval
               or current day.
               Counter applicable for : s3n and F1 level only. "
        ::= { xldv20pmS3CurrentEntry 17 }


     -- --------------------------------------------------------------
     --         Pmo  S T S 3  H i s t o r y  D a t a  Table
     -- --------------------------------------------------------------

     xldv20pmS3HistoryTable OBJECT-TYPE
     -- info-IMPL:      V2.0-> 
     -- info-VERCTRL:   -
        SYNTAX        SEQUENCE OF Xldv20pmS3HistoryEntry
        ACCESS        not-accessible
        STATUS        mandatory
        DESCRIPTION
             " This table contains the entries for the PMo history
               objects at the near-end and far-end STS3c interfaces.
               It contains results that are overtaken from the
               s3CurrentTable PM-object at the end of a 15 min /day
               interval . "
        --DEFAULT next-function-async     fsnPmS3hEntryNext
        --DEFAULT get-function-async      fsnPmS3hEntryGet
        ::= { xldv20pmPerformanceMonitoring 5 }

     xldv20pmS3HistoryEntry OBJECT-TYPE
     -- info-IMPL:      V2.0-> 
     -- info-VERCTRL:   -
        SYNTAX        Xldv20pmS3HistoryEntry
        ACCESS        not-accessible
        STATUS        mandatory
        DESCRIPTION
             " An entry describing the STS3 near-end and far-end
               History Data Table . "
        INDEX { xldv20IfIndex,
                xldv20pmS3hIntervalType,
                xldv20pmS3hOAMLevel,
                xldv20pmS3hHistEntryNr }
        ::= { xldv20pmS3HistoryTable 1 }

     Xldv20pmS3HistoryEntry ::=
        SEQUENCE { xldv20pmS3hIntervalType        Xldv20pmIntervalType,
                   xldv20pmS3hOAMLevel                       INTEGER,
                   xldv20pmS3hHistEntryNr                    INTEGER,
                   xldv20pmS3hSuspectFlag         Xldv20pmSuspectType,
                   xldv20pmS3hPeriodEndTime                  INTEGER,
                   xldv20pmS3hNeErroredSeconds               Counter,
                   xldv20pmS3hFeErroredSeconds               Counter,
                   xldv20pmS3hNeSeverelyErroredSeconds       Counter,
                   xldv20pmS3hFeSeverelyErroredSeconds       Counter,
                   xldv20pmS3hNeCodeViolations               Counter,
                   xldv20pmS3hFeCodeViolations               Counter,
                   xldv20pmS3hNeUnavailableSeconds           Counter,
                   xldv20pmS3hFeUnavailableSeconds           Counter,
                   xldv20pmS3hNeSeverelyErroredFrameSeconds  Counter }

     xldv20pmS3hIntervalType OBJECT-TYPE
     -- info-VALUE:     min15(1) , day(2)
     -- info-IMPL:      V2.0-> 
     -- info-VERCTRL:   -
        SYNTAX        Xldv20pmIntervalType
        ACCESS        read-only
        STATUS        mandatory
        DESCRIPTION
             " This type attribute is used to select between the
               15 min  or the day accumulation types. "
        ::= { xldv20pmS3HistoryEntry 1 }

     xldv20pmS3hOAMLevel OBJECT-TYPE
     -- info-VALUE:     1(f1), 2(f2), 3(f3)
     -- info-IMPL:      V2.0-> 
     -- info-VERCTRL:   -
        SYNTAX        INTEGER (1..3)
        ACCESS        read-only
        STATUS        mandatory
        DESCRIPTION
             " This attribute is used to select between the
               3 OAM levels f1 (1), f2 (2) and f3 (3) . "
        ::= { xldv20pmS3HistoryEntry 2 }

     xldv20pmS3hHistEntryNr OBJECT-TYPE
     -- info-VALUE:     1..96
     -- info-IMPL:      V2.0-> 
     -- info-VERCTRL:   -
        SYNTAX        INTEGER (1..96)
        ACCESS        read-only
        STATUS        mandatory
        DESCRIPTION
             " This attribute is used as index to address the history entry.
             Entry 1 is the most recent, entry 96 is 24 hours ago.
             The range of values is between 1 and xldv20S3cHistEntrySize . " 
        ::= { xldv20pmS3HistoryEntry 3 }

     xldv20pmS3hSuspectFlag OBJECT-TYPE
     -- info-VALUE:     reliable(1), suspect(2)
     -- info-ROU:       GET  db
     -- info-IMPL:      V2.0-> 
     -- info-VERCTRL:   -
        SYNTAX        Xldv20pmSuspectType
        ACCESS        read-only
        STATUS        mandatory
        DESCRIPTION
             " This read-only attribute will be set to indicate that
               troubles arose during an interval and that the counter
               values are suspect and incomplete. "
        ::= { xldv20pmS3HistoryEntry 4 }

     xldv20pmS3hPeriodEndTime OBJECT-TYPE
     -- info-VALUE:     0..2147483647
     -- info-ROU:       GET  SET [db,pm]
     -- info-IMPL:      V2.0-> 
     -- info-VERCTRL:   -
        SYNTAX        INTEGER(0..2147483647)
        ACCESS        read-only
        STATUS        mandatory
        DESCRIPTION
             " This read-only attribute is a record of date/time at the
               end of an interval . "
        ::= { xldv20pmS3HistoryEntry 5 }

     xldv20pmS3hNeErroredSeconds OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a set of history
               counter for Errored Seconds (ES) for the passed up to 96
               periods of 15 minutes and the passed day interval.
               Counter applicable for : s3n and F1, F2, F3 levels . "
        ::= { xldv20pmS3HistoryEntry 6 }
     
     xldv20pmS3hFeErroredSeconds OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a set of history
               counter for Errored Seconds (ES) for the passed up to 96
               periods of 15 minutes and the passed day interval.
               Counter applicable for : s3f and F2 and F3 levels . "
        ::= { xldv20pmS3HistoryEntry 7 }

     xldv20pmS3hNeSeverelyErroredSeconds OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a set of history
               counter for Severely Errored Seconds (SES) for the
               passed up to 96 periods of 15 minutes and the passed day
               interval.
               Counter applicable for : s3n and F2 and F3 levels . "
        ::= { xldv20pmS3HistoryEntry 8 }

     xldv20pmS3hFeSeverelyErroredSeconds OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a set of history
               counter for Severely Errored Seconds (SES) for the
               passed up to 96 periods of 15 minutes and the passed day
               interval.
               Counter applicable for : s3f and F2 and F3 levels . "
        ::= { xldv20pmS3HistoryEntry 9 }

     xldv20pmS3hNeCodeViolations OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a set of history
               counter for Code Violations Errors for the passed up to
               96 periods of 15 minutes and the passed day interval.
               Counter applicable for : s3n and F1, F2, F3 levels . "
        ::= { xldv20pmS3HistoryEntry 10 }

     xldv20pmS3hFeCodeViolations OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a set of history
               counter for Code Violations Errors for the passed up to
               96 periods of 15 minutes and the passed day interval.
               Counter applicable for : s3f and F2 and F3 levels . "
        ::= { xldv20pmS3HistoryEntry 11 }

     xldv20pmS3hNeUnavailableSeconds OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a set of history
               counter for Unavailable Seconds (UAS) for the passed up 
               to 96 periods of 15 minutes and the passed day interval.
               Counter applicable for : s3n and F2 and F3 levels . "
        ::= { xldv20pmS3HistoryEntry 12 }

     xldv20pmS3hFeUnavailableSeconds OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a set of history
               counter for Unavailable Seconds (UAS) for the passed up 
               to 96 periods of 15 minutes and the passed day interval.
               Counter applicable for : s3f and F2 and F3 levels . "
        ::= { xldv20pmS3HistoryEntry 13 }

     xldv20pmS3hNeSeverelyErroredFrameSeconds OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a set of history
               counter for Severely Errored Frame Seconds for the
               passed up to 96 periods of 15 minutes and the passed day
               interval.
               Counter applicable for : s3n and F1 level only . "
        ::= { xldv20pmS3HistoryEntry 14 }



     -- --------------------------------------------------------------
     --           PMo  D S 3  C u r r e n t  D a t a  Table
     -- --------------------------------------------------------------

     xldv20pmD3CurrentTable OBJECT-TYPE
     -- info-IMPL:      V2.0-> 
     -- info-VERCTRL:   -
        SYNTAX        SEQUENCE OF Xldv20pmD3CurrentEntry
        ACCESS        not-accessible
        STATUS        mandatory
        DESCRIPTION
             " This table contains the entries for the current 15 minute interval
               or the current day for DS3 near-end and far-end PPTPs.
               Note: Day PM collection uses the 15min  interval results . "
        --DEFAULT test-function-async     fsnPmD3cEntryTest
        --DEFAULT next-function-async     fsnPmD3cEntryNext
        --DEFAULT set-function-async      fsnPmD3cEntrySet
        --DEFAULT get-function-async      fsnPmD3cEntryGet
        ::= { xldv20pmPerformanceMonitoring 6 }

     xldv20pmD3CurrentEntry OBJECT-TYPE
     -- info-VALUE:     -
     -- info-IMPL:      V2.0-> 
     -- info-VERCTRL:   -
        SYNTAX        Xldv20pmD3CurrentEntry
        ACCESS        not-accessible
        STATUS        mandatory
        DESCRIPTION
             " An entry describing the DS3 near-end and far-end Current
               Data Table . "
        INDEX { xldv20IfIndex,
                xldv20pmD3cIntervalType,
                xldv20pmD3cOAMLevel }
        ::= { xldv20pmD3CurrentTable 1 }

     Xldv20pmD3CurrentEntry ::=
        SEQUENCE {xldv20pmD3cIntervalType          Xldv20pmIntervalType,
                  xldv20pmD3cOAMLevel                     INTEGER,
                  xldv20pmD3cAdminState            Xldv20AdminState,
                  xldv20pmD3cSuspectFlag           Xldv20pmSuspectType,
                  xldv20pmD3cHistEntrySize                INTEGER,
                  xldv20pmD3cNrHistEntriesAvailable       INTEGER,
                  xldv20pmD3cElapsedTime                  INTEGER,
                  xldv20pmD3cThresholdLimitIndex          INTEGER,
                  xldv20pmD3cNeErroredSecondsCP           Counter,
                  xldv20pmD3cFeErroredSecondsCP           Counter,
                  xldv20pmD3cNeErroredSecondsPLCP         Counter,
                  xldv20pmD3cFeErroredSecondsPLCP         Counter,
                  xldv20pmD3cNeSeverelyErroredSecondsCP   Counter,
                  xldv20pmD3cFeSeverelyErroredSecondsCP   Counter,
                  xldv20pmD3cNeSeverelyErroredSecondsPLCP Counter,
                  xldv20pmD3cFeSeverelyErroredSecondsPLCP Counter,
                  xldv20pmD3cNeCodeViolationsP            Counter,
                  xldv20pmD3cNeCodeViolationsCP           Counter,
                  xldv20pmD3cFeCodeViolationsCP           Counter,
                  xldv20pmD3cNeCodeViolationsPLCP         Counter,
                  xldv20pmD3cFeCodeViolationsPLCP         Counter,
                  xldv20pmD3cNeUnavailableSeconds         Counter,
                  xldv20pmD3cFeUnavailableSeconds         Counter,
                  xldv20pmD3cNeUnavailableSecondsPLCP     Counter,
                  xldv20pmD3cFeUnavailableSecondsPLCP     Counter,
                  xldv20pmD3cNeSas                        Counter,
                  xldv20pmD3cFeSas                        Counter }

     xldv20pmD3cIntervalType OBJECT-TYPE
     -- info-VALUE:     min15(1), day(2)
     -- info-IMPL:      V2.0-> 
     -- info-VERCTRL:   -
        SYNTAX        Xldv20pmIntervalType
        ACCESS        read-only
        STATUS        mandatory
        DESCRIPTION
             " This type attribute is used to select between the
               15 min  or the day accumulation types. "
        ::= { xldv20pmD3CurrentEntry 1 }

     xldv20pmD3cOAMLevel OBJECT-TYPE
     -- info-VALUE:     1..3
     -- info-IMPL:      V2.0-> 
     -- info-VERCTRL:   -
        SYNTAX        INTEGER (1..3)
        ACCESS        read-only
        STATUS        mandatory
        DESCRIPTION
             " This attribute is used to select between the
               3 OAM levels f1 (1), f2 (2) and f3 (3) . "
        ::= { xldv20pmD3CurrentEntry 2 }

     xldv20pmD3cAdminState OBJECT-TYPE
     -- info-VALUE:     unlocked(1), locked(2)
     -- info-ROU:       GET db SET pm
     -- info-IMPL:      V2.0-> 
     -- info-VERCTRL:   -
        SYNTAX        Xldv20AdminState
        ACCESS        read-write
        STATUS        mandatory
        DESCRIPTION
             " This read-write attribute is used to activate (unlock)
               and deactivate (lock) the functions (incl. collection)
               performed by this managed entity.
               Note: the 15min  collection object must be activated,
                     before day collection can operate. "
        ::= { xldv20pmD3CurrentEntry 3 }

     xldv20pmD3cSuspectFlag OBJECT-TYPE
     -- info-VALUE:     reliable(1), suspect(2)
     -- info-ROU:       GET  db
     -- info-IMPL:      V2.0-> 
     -- info-VERCTRL:   -
        SYNTAX        Xldv20pmSuspectType
        ACCESS        read-only
        STATUS        mandatory
        DESCRIPTION
             " This read-only attribute will be set to indicate that
               troubles arose during an interval and that the counter
               values are suspect and incomplete. "
        ::= { xldv20pmD3CurrentEntry 4 }

     xldv20pmD3cHistEntrySize OBJECT-TYPE
     -- info-VALUE:     1..96
     -- info-IMPL:      V2.0-> 
     -- info-VERCTRL:   -
        SYNTAX        INTEGER (1..96)
        ACCESS        read-only
        STATUS        mandatory
        DESCRIPTION
             " This read-only attribute indicates the configured history size.
               The default value is 1 and means that at least one
               history entry is provided. "
        ::= { xldv20pmD3CurrentEntry 5 }

     xldv20pmD3cNrHistEntriesAvailable OBJECT-TYPE
     -- info-VALUE:     0..96
     -- info-ROU:       GET db
     -- info-IMPL:      V2.0-> 
     -- info-VERCTRL:   -
        SYNTAX        INTEGER (0..96)
        ACCESS        read-only
        STATUS        mandatory
        DESCRIPTION
             " This read-only attribute indicates how many history entries
               are already available.
               The range of values is between 0 and xldv20pmD3cHistEntrySize,
               thereby 0 means that this entry is not valid . "
        ::= { xldv20pmD3CurrentEntry 6 }

     xldv20pmD3cElapsedTime OBJECT-TYPE
     -- info-VALUE:     0..900 (sec) for min15
     -- info-VALUE:     0..1440 (min) for day
     -- info-ROU:       GET db
     -- info-IMPL:      V2.0-> 
     -- info-VERCTRL:   -
        SYNTAX        INTEGER (0..1440)
        ACCESS        read-only
        STATUS        mandatory
        DESCRIPTION
             " This read-only attribute represents the difference
               between the current time and the start of the present
               summary interval.
	       Units are seconds when 15 minute interval is selected 
	       or minutes for day interval.
               (Note: accurate to the sample time interval). "
        ::= { xldv20pmD3CurrentEntry 7 }

     xldv20pmD3cThresholdLimitIndex OBJECT-TYPE
     -- info-VALUE:     1..30
     -- info-ROU:       GET db  SET pm
     -- info-IMPL:      V2.0-> 
     -- info-VERCTRL:   -
        SYNTAX        INTEGER (1..30)
        ACCESS        read-write
        STATUS        mandatory
        DESCRIPTION
             " This read-write attribute provides an index to the
               ThresholdLimitTable managed entity that contains the
               threshold limits for the performance parameters reported
               by this managed entity.
               When the value of this attribute is set to 1, default
               threshold limits shall be used. These default values are
               not part of the threshold limit table but are hard coded
               in the application SW of PM.
               The range of values is [1,30]. "
        ::= { xldv20pmD3CurrentEntry 8 }

     xldv20pmD3cNeErroredSecondsCP OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a counter of Errored
               Seconds (ES) within the current interval or current day,
               the generation thereof is based on CP-bit parity. 
               Counter applicable for : d3n and F2 level only . "
        ::= { xldv20pmD3CurrentEntry 9 }

     xldv20pmD3cFeErroredSecondsCP OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a counter of Errored
               Seconds (ES) within the current 15 minute interval or current day,
               the generation thereof is based on CP-bit parity .
               Counter applicable for :  d3f and F2 level only . "
        ::= { xldv20pmD3CurrentEntry 10 }

     xldv20pmD3cNeErroredSecondsPLCP OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a counter of Errored
               Seconds on PLCP-bit parity within the current 15 minute
               interval or current day.
               Counter applicable for : d3n and F3 level only . "
        ::= { xldv20pmD3CurrentEntry 11 }

     xldv20pmD3cFeErroredSecondsPLCP OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a counter of Errored
               Seconds on PLCP-bit parity within the current 15 minute
               interval or current day.
               Counter applicable for : d3f and F3 level only . "
        ::= { xldv20pmD3CurrentEntry 12 }

     xldv20pmD3cNeSeverelyErroredSecondsCP OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a counter of
               Severely Errored Seconds (SES) within the current 15 minute
               interval or current day  based on CP-bit parity, the generation thereof
               is based on CP-bit parity.
               Counter applicable for : d3n and F2 level only . "
        ::= { xldv20pmD3CurrentEntry 13 }

     xldv20pmD3cFeSeverelyErroredSecondsCP OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a counter of
               Severely Errored Seconds (SES) within the current 15 minute
               interval or current day, the generation thereof
               is based on CP-bit parity .
               Counter applicable for : d3f and F2 level only . "
        ::= { xldv20pmD3CurrentEntry 14 }

     xldv20pmD3cNeSeverelyErroredSecondsPLCP OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a counter of
               Severely Errored Seconds (SES) within the current 15 minute
               interval or current day, the generation thereof
               is based on PLCP-bit parity .
               Counter applicable for : d3n and F3 level only . "
        ::= { xldv20pmD3CurrentEntry 15 }

     xldv20pmD3cFeSeverelyErroredSecondsPLCP OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a counter of
               Severely Errored Seconds (SES) within the current 15 minute
               interval or current day, the generation thereof
               is based on PLCP-bit parity .
               Counter applicable for : d3f and F3 level only . "
        ::= { xldv20pmD3CurrentEntry 16 }

     xldv20pmD3cNeCodeViolationsP OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a counter of
               Code Violations Errors (Count of P-bit parity errors)
               within the current 15 minute interval or current day.
               Counter applicable for : d3n and F2 level only . "
        ::= { xldv20pmD3CurrentEntry 17 }

     xldv20pmD3cNeCodeViolationsCP OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a counter of
               Code Violations Errors (Count of CP-bit parity errors)
               within the current 15 minute interval or current day. 
               Counter applicable for : d3n and F2 level only . "
        ::= { xldv20pmD3CurrentEntry 18 }

     xldv20pmD3cFeCodeViolationsCP OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a counter of
               Code Violations Errors (Count of CP-bit parity errors)
               within the current 15 minute interval or current day.
               Counter applicable for : d3f and F2 level only . "
        ::= { xldv20pmD3CurrentEntry 19 }

     xldv20pmD3cNeCodeViolationsPLCP OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a counter of
               Code Violations Errors (Count of PLCP frame Bit
               Interleaved Parity errors) within the current 15 minute
               interval or current day.
               Counter applicable for : d3n and F3 level only . "
        ::= { xldv20pmD3CurrentEntry 20 }

     xldv20pmD3cFeCodeViolationsPLCP OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a counter of
               Code Violations Errors (Count of PLCP frame Bit
               Interleaved Parity errors) within the current 15 minute
               interval or current day.
               Counter applicable for : d3f and F3 level only . "
        ::= { xldv20pmD3CurrentEntry 21 }

     xldv20pmD3cNeUnavailableSeconds OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a counter of
               Unavailable Seconds (UAS) within the current 15 minute
               interval or current day.
               Counter applicable for : d3n and F2 level only. "
        ::= { xldv20pmD3CurrentEntry 22 }

     xldv20pmD3cFeUnavailableSeconds OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a counter of
               Unavailable Seconds (UAS) within the current 15 minute
               interval or current day.
               Counter applicable for : d3f and F2 level only . "
        ::= { xldv20pmD3CurrentEntry 23 }

     xldv20pmD3cNeUnavailableSecondsPLCP OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a counter of
               Unavailable Seconds (UAS) within the current 15 minute
               interval or current day. The generation is based on PLCP-bit parity.
               Counter applicable for : d3n and F3 level only . "
        ::= { xldv20pmD3CurrentEntry 24 }

     xldv20pmD3cFeUnavailableSecondsPLCP OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a counter of
               Unavailable Seconds (UAS) within the current 15 minute
               interval or current day. The generation is based on PLCP-bit parity.
               Counter applicable for : d3f and F3 level only . "
        ::= { xldv20pmD3CurrentEntry 25 }

     xldv20pmD3cNeSas OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a counter of one
               second intervals containing one ore more Severely
               Errored Frame (SEF) defects or one or more Alarm
               Indication Signal (AIS) defects within the current 15 minute
               interval or current day.
               Counter applicable for : d3n and F2 level only . "
        ::= { xldv20pmD3CurrentEntry 26 }

     xldv20pmD3cFeSas OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a counter of one
               second intervals containing one ore more Severely
               Errored Frame (SEF) defects or one or more Alarm
               Indication Signal (AIS) defects within the current 15 minute
               interval or current day.
               Counter applicable for : d3f and F2 level only . "
        ::= { xldv20pmD3CurrentEntry 27 }


     -- --------------------------------------------------------------
     --           PMo  D S 3  H i s t o r y  D a t a  Table
     -- --------------------------------------------------------------

     xldv20pmD3HistoryTable OBJECT-TYPE
     -- info-IMPL:      V2.0-> 
     -- info-VERCTRL:   -
        SYNTAX        SEQUENCE OF Xldv20pmD3HistoryEntry
        ACCESS        not-accessible
        STATUS        mandatory
        DESCRIPTION
             " This table contains the entries for the PMo history
               objects at the near-end and far-end DS3 interfaces.
               It contains results that are overtaken from the
               D3CurrentTable PM-object at the end of a 15 min /day
               interval . "
        --DEFAULT next-function-async     fsnPmD3hEntryNext
        --DEFAULT get-function-async      fsnPmD3hEntryGet
        ::= { xldv20pmPerformanceMonitoring 7 }

     xldv20pmD3HistoryEntry OBJECT-TYPE
     -- info-IMPL:      V2.0-> 
     -- info-VERCTRL:   -
        SYNTAX        Xldv20pmD3HistoryEntry
        ACCESS        not-accessible
        STATUS        mandatory
        DESCRIPTION
             " An entry describing the DS3 near-end and far-end History
               Data Table . "
        INDEX { xldv20IfIndex,
                xldv20pmD3hIntervalType,
                xldv20pmD3hOAMLevel,
                xldv20pmD3hHistEntryNr }
        ::= { xldv20pmD3HistoryTable 1 }

     Xldv20pmD3HistoryEntry ::=
        SEQUENCE { xldv20pmD3hIntervalType         Xldv20pmIntervalType,
                   xldv20pmD3hOAMLevel                   INTEGER,
                   xldv20pmD3hHistEntryNr                INTEGER,
                   xldv20pmD3hSuspectFlag          Xldv20pmSuspectType,
                   xldv20pmD3hPeriodEndTime              INTEGER,
                   xldv20pmD3hNeErroredSecondsCP           Counter,
                   xldv20pmD3hFeErroredSecondsCP           Counter,
                   xldv20pmD3hNeErroredSecondsPLCP         Counter,
                   xldv20pmD3hFeErroredSecondsPLCP         Counter,
                   xldv20pmD3hNeSeverelyErroredSecondsCP   Counter,
                   xldv20pmD3hFeSeverelyErroredSecondsCP   Counter,
                   xldv20pmD3hNeSeverelyErroredSecondsPLCP Counter,
                   xldv20pmD3hFeSeverelyErroredSecondsPLCP Counter,
                   xldv20pmD3hNeCodeViolationsP            Counter,
                   xldv20pmD3hNeCodeViolationsCP           Counter,
                   xldv20pmD3hFeCodeViolationsCP           Counter,
                   xldv20pmD3hNeCodeViolationsPLCP         Counter,
                   xldv20pmD3hFeCodeViolationsPLCP         Counter,
                   xldv20pmD3hNeUnavailableSeconds         Counter,
                   xldv20pmD3hFeUnavailableSeconds         Counter,
                   xldv20pmD3hNeUnavailableSecondsPLCP     Counter,
                   xldv20pmD3hFeUnavailableSecondsPLCP     Counter,
                   xldv20pmD3hNeSas                        Counter,
                   xldv20pmD3hFeSas                        Counter }

     xldv20pmD3hIntervalType OBJECT-TYPE
     -- info-VALUE:     min15(1), day(2)
     -- info-IMPL:      V2.0-> 
     -- info-VERCTRL:   -
        SYNTAX        Xldv20pmIntervalType
        ACCESS        read-only
        STATUS        mandatory
        DESCRIPTION
             " This type attribute is used to select between the
               15 min  or the day accumulation types. "
        ::= { xldv20pmD3HistoryEntry 1 }

     xldv20pmD3hOAMLevel OBJECT-TYPE
     -- info-VALUE:     1..3
     -- info-IMPL:      V2.0-> 
     -- info-VERCTRL:   -
        SYNTAX        INTEGER (1..3)
        ACCESS        read-only
        STATUS        mandatory
        DESCRIPTION
             " This attribute is used to select between the
               3 OAM levels f1 (1), f2 (2) and f3 (3) . "
        ::= { xldv20pmD3HistoryEntry 2 }

     xldv20pmD3hHistEntryNr OBJECT-TYPE
     -- info-VALUE:     1..96
     -- info-IMPL:      V2.0-> 
     -- info-VERCTRL:   -
        SYNTAX        INTEGER (1..96)
        ACCESS        read-only
        STATUS        mandatory
        DESCRIPTION
             " This attribute is used as index to address a history entry.
             Entry 1 is the most recent, entry 96 is 24 hours ago.
             The range of values is between 1 and xldv20pmD3cHistEntrySize . " 
        ::= { xldv20pmD3HistoryEntry 3 }

     xldv20pmD3hSuspectFlag OBJECT-TYPE
     -- info-VALUE:     reliable(1), suspect(2)
     -- info-ROU:       GET  db
     -- info-IMPL:      V2.0-> 
     -- info-VERCTRL:   -
        SYNTAX        Xldv20pmSuspectType
        ACCESS        read-only
        STATUS        mandatory
        DESCRIPTION
             " This read-only attribute will be set to indicate that
               troubles arose during an interval and that the counter
               values are suspect and incomplete. "
        ::= { xldv20pmD3HistoryEntry 4 }

     xldv20pmD3hPeriodEndTime OBJECT-TYPE
     -- info-VALUE:     0..2147483647
     -- info-ROU:       GET  SET [db,pm]
     -- info-IMPL:      V2.0-> 
     -- info-VERCTRL:   -
        SYNTAX        INTEGER(0..2147483647)
        ACCESS        read-only
        STATUS        mandatory
        DESCRIPTION
             " This read-only attribute is a record of date/time at the
               end of an interval . "
        ::= { xldv20pmD3HistoryEntry 5 }

     xldv20pmD3hNeErroredSecondsCP OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a set of history
               counter of Errored Seconds (ES), the generation thereof
               is based on CP-bit parity for a 15min /day interval.
               Counter applicable for :  d3n and F2 level only . "
        ::= { xldv20pmD3HistoryEntry 6 }

     xldv20pmD3hFeErroredSecondsCP OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a set of history
               counter of Errored Seconds (ES), the generation thereof
               is based on CP-bit parity for a 15min /day interval.
               Counter applicable for : d3f and F2 level only . "
        ::= { xldv20pmD3HistoryEntry 7 }

     xldv20pmD3hNeErroredSecondsPLCP OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a set of history
               counter of Errored Seconds (ES) (One second interval in
               which Code Violations errors occure) for a 15min /day
               interval.
               Counter applicable for : d3n and F3 level only . "
        ::= { xldv20pmD3HistoryEntry 8 }

     xldv20pmD3hFeErroredSecondsPLCP OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a set of history
               counter of Errored Seconds (ES) (One second interval in
               which Code Violations errors occure) for a 15min /day
               interval.
               Counter applicable for : d3f and F3 level only . "
        ::= { xldv20pmD3HistoryEntry 9 }

     xldv20pmD3hNeSeverelyErroredSecondsCP OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a set of history
               counter of Severely Errored Seconds (ES), the generation
               thereof is based on CP-bit parity for a 15min /day
               interval.
               Counter applicable for : d3n and F2 level only . "
        ::= { xldv20pmD3HistoryEntry 10 }

     xldv20pmD3hFeSeverelyErroredSecondsCP OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a set of history
               counter of Severely Errored Seconds (ES), the generation
               thereof is based on CP-bit parity for a 15min /day
               interval.
               Counter applicable for : d3f and F2 level only . "
        ::= { xldv20pmD3HistoryEntry 11 }

     xldv20pmD3hNeSeverelyErroredSecondsPLCP OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a set of history
               counter of Severely Errored Seconds (SES) for a 15min /
               day interval.
               Counter applicable for : d3n and F3 level only . "
        ::= { xldv20pmD3HistoryEntry 12 }

     xldv20pmD3hFeSeverelyErroredSecondsPLCP OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a set of history
               counter of Severely Errored Seconds (SES) for a 15min /
               day interval.
               Counter applicable for : d3f and F3 level only . "
        ::= { xldv20pmD3HistoryEntry 13 }

     xldv20pmD3hNeCodeViolationsP OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a counter of
               Code Violations Errors (Count of P-bit parity errors)
               for a 15 min /day interval.
               Counter applicable for : d3n and F2 level only. "
        ::= { xldv20pmD3HistoryEntry 14 }

     xldv20pmD3hNeCodeViolationsCP OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a set of history
               counter of Code Violations Errors (Count of CP-bit
               parity errors) for a 15min /day interval.
               Counter applicable for : d3n and F2 level only . "
        ::= { xldv20pmD3HistoryEntry 15 }

     xldv20pmD3hFeCodeViolationsCP OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a set of history
               counter of Code Violations Errors (Count of CP-bit
               parity errors) for a 15min /day interval.
               Counter applicable for : d3f and F2 level only . "
        ::= { xldv20pmD3HistoryEntry 16 }

     xldv20pmD3hNeCodeViolationsPLCP OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a set of history
               counter of Code Violations Errors (Count of PLCP frame
               Bit Interleaved Parity errors) for a 15min /day
               interval.
               Counter applicable for : d3n and F3 level only . "
        ::= { xldv20pmD3HistoryEntry 17 }

     xldv20pmD3hFeCodeViolationsPLCP OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a set of history
               counter of Code Violations Errors (Count of PLCP frame
               Bit Interleaved Parity errors) for a 15min /day
               interval.
               Counter applicable for : d3f and F3 level only . "
        ::= { xldv20pmD3HistoryEntry 18 }

     xldv20pmD3hNeUnavailableSeconds OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a set of history
               counter of Unavailable Seconds (UAS) for a 15min /day
               interval.
               Counter applicable for : d3n and F2 level only . "
        ::= { xldv20pmD3HistoryEntry 19 }

     xldv20pmD3hFeUnavailableSeconds OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a set of history
               counter of Unavailable Seconds (UAS) for a 15min /day
               interval.
               Counter applicable for : d3f and F2 level only . "
        ::= { xldv20pmD3HistoryEntry 20 }

     xldv20pmD3hNeUnavailableSecondsPLCP OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a set of history
               counter of Unavailable Seconds (UAS) for a 15min /day
               interval.
               Counter applicable for : d3n and F3 level only . "
        ::= { xldv20pmD3HistoryEntry 21 }

     xldv20pmD3hFeUnavailableSecondsPLCP OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a set of history
               counter of Unavailable Seconds (UAS) for a 15min /day
               interval.
               Counter applicable for : d3f and F3 level only . "
        ::= { xldv20pmD3HistoryEntry 22 }

     xldv20pmD3hNeSas OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a set of history
               counter of one second intervals containing one ore more
               Severely Errored Frame (SEF) defects or one or more
               Alarm Indication Signal (AIS) defects for a 15min /day
               interval.
               Counter applicable for : d3n and F2 level only . "
        ::= { xldv20pmD3HistoryEntry 23 }

     xldv20pmD3hFeSas OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a set of history
               counter of one second intervals containing one ore more
               Severely Errored Frame (SEF) defects or one or more
               Alarm Indication Signal (AIS) defects for a 15min /day
               interval.
               Counter applicable for : d3f and F2 level only . "
        ::= { xldv20pmD3HistoryEntry 24 }


     -- --------------------------------------------------------------
     --          Pmo  S T M 1  C u r r e n t  D a t a  Table
     -- --------------------------------------------------------------

     xldv20pmS1CurrentTable OBJECT-TYPE
     -- info-IMPL:      V2.0-> 
        SYNTAX        SEQUENCE OF Xldv20pmS1CurrentEntry
        ACCESS        not-accessible
        STATUS        mandatory
        DESCRIPTION
             " This table contains the entries for the current 15 minute interval
               or the current day for STM1 near-end and far-end PPTPs.
               Note: Day PM collection uses the 15min  interval results . "
        --DEFAULT test-function-async     fsnPmS1cEntryTest
        --DEFAULT next-function-async     fsnPmS1cEntryNext
        --DEFAULT set-function-async      fsnPmS1cEntrySet
        --DEFAULT get-function-async      fsnPmS1cEntryGet
        ::= { xldv20pmPerformanceMonitoring 8 }

     xldv20pmS1CurrentEntry OBJECT-TYPE
     -- info-IMPL:      V2.0-> 
     -- info-VERCTRL:   -
        SYNTAX        Xldv20pmS1CurrentEntry
        ACCESS        not-accessible
        STATUS        mandatory
        DESCRIPTION
             " An entry describing the Stm1 Current Data Table . "
        INDEX { xldv20IfIndex,
                xldv20pmS1cIntervalType,
                xldv20pmS1cOAMLevel }
        ::= { xldv20pmS1CurrentTable 1 }

     Xldv20pmS1CurrentEntry ::=
        SEQUENCE { xldv20pmS1cIntervalType         Xldv20pmIntervalType,
                   xldv20pmS1cOAMLevel                 INTEGER,
                   xldv20pmS1cAdminState           Xldv20AdminState,
                   xldv20pmS1cSuspectFlag          Xldv20pmSuspectType,
                   xldv20pmS1cHistEntrySize            INTEGER,
                   xldv20pmS1cNrHistEntriesAvailable   INTEGER,
                   xldv20pmS1cElapsedTime              INTEGER,
                   xldv20pmS1cThresholdLimitIndex      INTEGER,
                   xldv20pmS1cNeErroredSeconds         Counter,
                   xldv20pmS1cFeErroredSeconds         Counter,
                   xldv20pmS1cNeSeverelyErroredSeconds Counter,
                   xldv20pmS1cFeSeverelyErroredSeconds Counter,
                   xldv20pmS1cNeBackgroundBlockErrors  Counter,
                   xldv20pmS1cFeBackgroundBlockErrors  Counter,
                   xldv20pmS1cNeUnavailableSeconds     Counter,
                   xldv20pmS1cFeUnavailableSeconds     Counter,
                   xldv20pmS1cNeOfsSeconds             Counter,
                   xldv20pmS1cNeAisSeconds             Counter,
                   xldv20pmS1cNeLosSeconds             Counter }

     xldv20pmS1cIntervalType OBJECT-TYPE
     -- info-VALUE:     min15(1), day(2)
     -- info-ROU:       GET  db
     -- info-IMPL:      V2.0-> 
     -- info-VERCTRL:   -
        SYNTAX        Xldv20pmIntervalType
        ACCESS        read-only
        STATUS        mandatory
        DESCRIPTION
             " This type attribute is used to select between the
               15 min  or the day accumulation types. "
        ::= { xldv20pmS1CurrentEntry 1 }

     xldv20pmS1cOAMLevel OBJECT-TYPE
     -- info-VALUE:     1..3
     -- info-ROU:       GET db
     -- info-IMPL:      V2.0-> 
     -- info-VERCTRL:   -
        SYNTAX        INTEGER (1..3)
        ACCESS        read-only
        STATUS        mandatory
        DESCRIPTION
             " This attribute is used to select between the
               3 OAM levels f1 (1), f2 (2) and f3 (3) . "
        ::= { xldv20pmS1CurrentEntry 2 }

     xldv20pmS1cAdminState OBJECT-TYPE
     -- info-VALUE:     unlocked(1), locked(2)
     -- info-ROU:       GET db  SET pm
     -- info-IMPL:      V2.0-> 
     -- info-VERCTRL:   -
        SYNTAX        Xldv20AdminState
        ACCESS        read-write
        STATUS        mandatory
        DESCRIPTION
             " This read-write attribute is used to activate (unlock)
               and deactivate (lock) the functions (incl. collection)
               performed by this managed entity.
               Note: the 15min  collection object must be activated,
                     before day collection can operate. "
        ::= { xldv20pmS1CurrentEntry 3 }

     xldv20pmS1cSuspectFlag OBJECT-TYPE
     -- info-VALUE:     reliable(1), suspect(2)
     -- info-ROU:       GET db
     -- info-IMPL:      V2.0-> 
     -- info-VERCTRL:   -
        SYNTAX        Xldv20pmSuspectType
        ACCESS        read-only
        STATUS        mandatory
        DESCRIPTION
             " This read-only attribute will be set to indicate that
               troubles arose during an interval and that the counter
               values are suspect and incomplete. "
        ::= { xldv20pmS1CurrentEntry 4 }

     xldv20pmS1cHistEntrySize OBJECT-TYPE
     -- info-VALUE:     1..96
     -- info-ROU:       GET db
     -- info-IMPL:      V2.0-> 
     -- info-VERCTRL:   -
        SYNTAX        INTEGER (1..96)
        ACCESS        read-only
        STATUS        mandatory
        DESCRIPTION
             " This read-only attribute indicates the configured history size.
               The default value is 1 and means that at least one
               history entry is provided. "
        ::= { xldv20pmS1CurrentEntry 5 }

     xldv20pmS1cNrHistEntriesAvailable OBJECT-TYPE
     -- info-VALUE:     0..96
     -- info-ROU:       GET db
     -- info-IMPL:      V2.0-> 
     -- info-VERCTRL:   -
        SYNTAX        INTEGER (0..96)
        ACCESS        read-only
        STATUS        mandatory
        DESCRIPTION
             " This read-only attribute indicates how many history entries
               are already available.
               The range of values is between 0 and xldv20pmS1cHistEntrySize,
               thereby 0 means that this entry is not valid . "
        ::= { xldv20pmS1CurrentEntry 6 }

     xldv20pmS1cElapsedTime OBJECT-TYPE
     -- info-VALUE:     0..900 (sec) for min15,
     -- info-VALUE:     0..1440 (min) for day
     -- info-ROU:       GET db
     -- info-IMPL:      V2.0-> 
     -- info-VERCTRL:   -
        SYNTAX        INTEGER(0..1440)
        ACCESS        read-only
        STATUS        mandatory
        DESCRIPTION
             " This read-only attribute represents the difference
               between the current time and the start of the present
               summary interval.
	       Units are seconds when 15 minute interval is selected 
	       or minutes for day interval.
               (Note: accurate to the sample time interval). "
        ::= { xldv20pmS1CurrentEntry 7 }

     xldv20pmS1cThresholdLimitIndex OBJECT-TYPE
     -- info-VALUE:     1..30
     -- info-ROU:       GET db  SET pm
     -- info-IMPL:      V2.0-> 
     -- info-VERCTRL:   -
        SYNTAX        INTEGER (1..30)
        ACCESS        read-write
        STATUS        mandatory
        DESCRIPTION
             " This read-write attribute provides an index to the
               ThresholdLimitTable managed entity that contains the
               threshold limits for the performance parameters reported
               by this managed entity.
               When the value of this attribute is set to 1, default
               threshold limits shall be used. These default values are
               not part of the threshold limit table but are hard coded
               in the application SW of PM. "
        ::= { xldv20pmS1CurrentEntry 8 }

     xldv20pmS1cNeErroredSeconds OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a counter of Errored
               Seconds (ES) within the current 15 minute interval or current day.
               Counter applicable for : s1n and F1, F2, F3 levels . "
        ::= { xldv20pmS1CurrentEntry 9 }

     xldv20pmS1cFeErroredSeconds OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a counter of Errored
               Seconds (ES) within the current 15 minute interval or current day.
               Counter applicable for : s1f and F2 and F3 levels . "
        ::= { xldv20pmS1CurrentEntry 10 }

     xldv20pmS1cNeSeverelyErroredSeconds OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a counter of
               Severely Errored Seconds (SES) within the current 15 minute
               interval or current day.
               Counter applicable for : s1n and F1, F2, F3 levels . "
        ::= { xldv20pmS1CurrentEntry 11 }

     xldv20pmS1cFeSeverelyErroredSeconds OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a counter of
               Severely Errored Seconds (SES) within the current 15 minute
               interval or current day.
               Counter applicable for : s1f and F2 and F3 levels . "
        ::= { xldv20pmS1CurrentEntry 12 }

     xldv20pmS1cNeBackgroundBlockErrors OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a counter for
               Background Block Errors (BBE) within the current 15 minute
               interval or current day.
               Counter applicable for : s1n and F1, F2, F3 levels . "
        ::= { xldv20pmS1CurrentEntry 13 }

     xldv20pmS1cFeBackgroundBlockErrors OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a counter for
               Background Block Errors (BBE) within the current 15 minute
               interval or current day.
               Counter applicable for : s1f and F2 and F3 levels . "
        ::= { xldv20pmS1CurrentEntry 14 }

     xldv20pmS1cNeUnavailableSeconds OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a counter of
               Unavailable Seconds (UAS) within the current 15 minute
               interval or current day.
               Counter applicable for : s1n and F1, F2, F3 levels . "
        ::= { xldv20pmS1CurrentEntry 15 }

     xldv20pmS1cFeUnavailableSeconds OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a counter of
               Unavailable Seconds (UAS) within the current 15 minute
               interval or current day.
               Counter applicable for : s1f and F2 and F3 levels . "
        ::= { xldv20pmS1CurrentEntry 16 }

     xldv20pmS1cNeOfsSeconds OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a counter of
               Errored Seconds on defect OFS within the current 15 minute
               interval or current day.
               Counter applicable for : s1n and level F1 . "
        ::= { xldv20pmS1CurrentEntry 17 }

     xldv20pmS1cNeAisSeconds OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a counter of
               errored Seconds on defect alarm indicatin signal AIS
               for a 15 min /day interval.
               Counter applicable for : s1n and F2  . "
        ::= { xldv20pmS1CurrentEntry 18 }

     xldv20pmS1cNeLosSeconds OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a counter of
               errored Seconds on defect LOS within the current 15 minute 
               interval or current day.
               Counter applicable for : s1n and level F1. "
        ::= { xldv20pmS1CurrentEntry 19 }


     -- --------------------------------------------------------------
     --        PMo  S T M 1  H i s t o r y  D a t a  Table
     -- --------------------------------------------------------------

     xldv20pmS1HistoryTable OBJECT-TYPE
     -- info-IMPL:      V2.0-> 
     -- info-VERCTRL:   -
        SYNTAX        SEQUENCE OF Xldv20pmS1HistoryEntry
        ACCESS        not-accessible
        STATUS        mandatory
        DESCRIPTION
             " This table contains the entries for the PMo objects of
               the 15 min /one day-history data collection results at
               the respective stm1 (s1n, s1f) drop area
               interfaces . "
        --DEFAULT next-function-async     fsnPmS1hEntryNext
        --DEFAULT get-function-async      fsnPmS1hEntryGet
        ::= { xldv20pmPerformanceMonitoring 9 }

     xldv20pmS1HistoryEntry OBJECT-TYPE
     -- info-IMPL:      V2.0-> 
     -- info-VERCTRL:   -
        SYNTAX        Xldv20pmS1HistoryEntry
        ACCESS        not-accessible
        STATUS        mandatory
        DESCRIPTION
             " An entry describing the S1 History Data Table . "
        INDEX { xldv20IfIndex,
                xldv20pmS1hIntervalType,
                xldv20pmS1hOAMLevel,
                xldv20pmS1hHistEntryNr }
        ::= { xldv20pmS1HistoryTable 1 }

     Xldv20pmS1HistoryEntry ::=
        SEQUENCE { xldv20pmS1hIntervalType        Xldv20pmIntervalType,
                   xldv20pmS1hOAMLevel                 INTEGER,
                   xldv20pmS1hHistEntryNr              INTEGER,
                   xldv20pmS1hSuspectFlag         Xldv20pmSuspectType,
                   xldv20pmS1hPeriodEndTime            INTEGER,
                   xldv20pmS1hNeErroredSeconds         Counter,
                   xldv20pmS1hFeErroredSeconds         Counter,
                   xldv20pmS1hNeSeverelyErroredSeconds Counter,
                   xldv20pmS1hFeSeverelyErroredSeconds Counter,
                   xldv20pmS1hNeBackgroundBlockErrors  Counter,
                   xldv20pmS1hFeBackgroundBlockErrors  Counter,
                   xldv20pmS1hNeUnavailableSeconds     Counter,
                   xldv20pmS1hFeUnavailableSeconds     Counter,
                   xldv20pmS1hNeOfsSeconds             Counter,
                   xldv20pmS1hNeAisSeconds             Counter,
                   xldv20pmS1hNeLosSeconds             Counter }

     xldv20pmS1hIntervalType OBJECT-TYPE
     -- info-VALUE:     min15(1), day(2)
     -- info-ROU:       GET db
     -- info-IMPL:      V2.0-> 
     -- info-VERCTRL:   -
        SYNTAX        Xldv20pmIntervalType
        ACCESS        read-only
        STATUS        mandatory
        DESCRIPTION
             " This type attribute is used to select between the
               15 min  or the day accumulation types. "
        ::= { xldv20pmS1HistoryEntry 1 }

     xldv20pmS1hOAMLevel OBJECT-TYPE
     -- info-VALUE:     1..3
     -- info-ROU:       GET db
     -- info-IMPL:      V2.0-> 
     -- info-VERCTRL:   -
        SYNTAX        INTEGER (1..3)
        ACCESS        read-only
        STATUS        mandatory
        DESCRIPTION
             " This attribute is used to select between the
               3 OAM levels f1 (1), f2 (2) and f3 (3) . "
        ::= { xldv20pmS1HistoryEntry 2 }

     xldv20pmS1hHistEntryNr OBJECT-TYPE
     -- info-VALUE:     1..96
     -- info-ROU:       GET db
     -- info-IMPL:      V2.0-> 
     -- info-VERCTRL:   -
        SYNTAX        INTEGER (1..96)
        ACCESS        read-only
        STATUS        mandatory
        DESCRIPTION
             " This attribute is used as index to address a history entry.
             Entry 1 is the most recent, entry 96 is 24 hours ago.
             The range of values is between 1 and xldv20pmCcHistEntrySize . " 
        ::= { xldv20pmS1HistoryEntry 3 }

     xldv20pmS1hSuspectFlag OBJECT-TYPE
     -- info-VALUE:     reliable(1), suspect(2)
     -- info-ROU:       GET db
     -- info-IMPL:      V2.0-> 
     -- info-VERCTRL:   -
        SYNTAX        Xldv20pmSuspectType
        ACCESS        read-only
        STATUS        mandatory
        DESCRIPTION
             " This read-only attribute will be set to indicate that
               troubles arose during an interval and that the counter
               values are suspect and incomplete. "
        ::= { xldv20pmS1HistoryEntry 4 }

     xldv20pmS1hPeriodEndTime OBJECT-TYPE
     -- info-VALUE:     0..2147483647
     -- info-ROU:       GET  db
     -- info-IMPL:      V2.0-> 
     -- info-VERCTRL:   -
        SYNTAX        INTEGER(0..2147483647)
        ACCESS        read-only
        STATUS        mandatory
        DESCRIPTION
             " Date/time at the end of the selected interval. "
        ::= { xldv20pmS1HistoryEntry 5 }

     xldv20pmS1hNeErroredSeconds OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a counter of Errored
               Seconds (ES) over a 15 min /day interval.
               Counter applicable for : s1n and F1, F2, F3 levels . "
        ::= { xldv20pmS1HistoryEntry 6 }

     xldv20pmS1hFeErroredSeconds OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a counter of Errored
               Seconds (ES) over a 15 min /day interval.
               Counter applicable for : s1f and F2 and F3 levels . "
        ::= { xldv20pmS1HistoryEntry 7 }

     xldv20pmS1hNeSeverelyErroredSeconds OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a counter of
               Severely Errored Seconds (SES) over a 15 min /day
               interval.
               Counter applicable for : s1n and F1, F2, F3 levels . "
        ::= { xldv20pmS1HistoryEntry 8 }

     xldv20pmS1hFeSeverelyErroredSeconds OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a counter of
               Severely Errored Seconds (SES) over a 15 min /day
               interval.
               Counter applicable for : s1f and F2 and F3 levels . "
        ::= { xldv20pmS1HistoryEntry 9 }

     xldv20pmS1hNeBackgroundBlockErrors OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a counter for
               Background Block Errors (BBE) over a 15 min /day
               interval.
               Counter applicable for : s1n and F1, F2, F3 levels . "
        ::= { xldv20pmS1HistoryEntry 10 }

     xldv20pmS1hFeBackgroundBlockErrors OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a counter for
               Background Block Errors (BBE) over a 15 min /day
               interval.
               Counter applicable for : s1f and F2 and F3 levels . "
        ::= { xldv20pmS1HistoryEntry 11 }

     xldv20pmS1hNeUnavailableSeconds OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a counter of
               Unavailable Seconds (UAS) for a 15 min /day interval.
               Counter applicable for : s1n and F1, F2, F3 levels . "
        ::= { xldv20pmS1HistoryEntry 12 }

     xldv20pmS1hFeUnavailableSeconds OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a counter of
               Unavailable Seconds (UAS) for a 15 min /day interval.
               Counter applicable for : s1f and F2 and F3 levels . "
        ::= { xldv20pmS1HistoryEntry 13 }

     xldv20pmS1hNeOfsSeconds OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a counter of
               Errored Seconds on defect OFS for a 15 min /day interval.
               Counter applicable for : s1n and level F1 . "
        ::= { xldv20pmS1HistoryEntry 14 }

     xldv20pmS1hNeAisSeconds OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a counter of
               errored Seconds on defect alarm indicatin signal AIS
               for a 15 min /day interval.
               Counter applicable for : s1n and level F2 . "
        ::= { xldv20pmS1HistoryEntry 15 }

     xldv20pmS1hNeLosSeconds OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a counter of
               errored Seconds on defect LOS for a 15 min /day interval.
               Counter applicable for : s1n and F1 . "
        ::= { xldv20pmS1HistoryEntry 16 }
     
     
     -- --------------------------------------------------------------
     --        PMo  o n  A T M   L a y e r                          
     --
     --             A t m  O b j e c t s  T a b l e
     -- ------------------------------------------------------------------
     --
     -- --------------------------------------------------------------
     --  PMo events 
     -- ------------------------------------------------------------------


     xldv20pmAtmObjectsTable OBJECT-TYPE
     -- info-IMPL:      V2.0-> 
     -- info-VERCTRL:   -
        SYNTAX        SEQUENCE OF Xldv20pmAtmObjectsEntry
        ACCESS        not-accessible
        STATUS        mandatory
        DESCRIPTION
             " This table contains the entries for the PMo objects 
               on ATM layer. Maximum of monitored connections is 128. "
        --DEFAULT test-function-async     fsnPmAoEntryTest
        --DEFAULT next-function-async     fsnPmAoEntryNext
        --DEFAULT set-function-async      fsnPmAoEntrySet
        --DEFAULT get-function-async      fsnPmAoEntryGet
        ::= { xldv20pmPerformanceMonitoring 10 }

     xldv20pmAtmObjectsEntry OBJECT-TYPE
     -- info-IMPL:      V2.0-> 
     -- info-VERCTRL:   -
        SYNTAX        Xldv20pmAtmObjectsEntry
        ACCESS        not-accessible
        STATUS        mandatory
        DESCRIPTION
             " An entry of the xldv20pmAtmObjectsTable. "
        INDEX { xldv20pmAoIndex }
        ::= { xldv20pmAtmObjectsTable 1 }

     Xldv20pmAtmObjectsEntry ::=
        SEQUENCE { xldv20pmAoIndex                    INTEGER ,
                   xldv20pmAoFlowType             Xldv20pmFlowType,
                   xldv20pmAoAdminState           Xldv20AdminState,
                   xldv20pmAoBlockSize            Xldv20pmBlockSizeType
                   }

     xldv20pmAoIndex OBJECT-TYPE
     -- info-VALUE:     1..128
     -- info-ROU:       GET  db
     -- info-IMPL:      V2.0-> 
     -- info-VERCTRL:   -
        SYNTAX        INTEGER (1..128)
        ACCESS        read-only
        STATUS        mandatory
        DESCRIPTION
             " Identifies an entry of the xldv20pmAtmObjectsTable. "
        ::= { xldv20pmAtmObjectsEntry 1 }
    
    xldv20pmAoFlowType OBJECT-TYPE
     -- info-VALUE:     f4Segment(1), f4EndToEnd(2)
     -- info-VALUE:     f5Segment(3), f5EndToEnd(4)
     -- info-ROU:       GET db  SET db
     -- info-IMPL:      V2.0-> 
     -- info-VERCTRL:   -
        SYNTAX        Xldv20pmFlowType
        ACCESS        read-only
        STATUS        mandatory
        DESCRIPTION
             " This attribute identifies the flow type :
               F4 (VP) or F5 (VC) segment or endToEnd flow. "
        ::= { xldv20pmAtmObjectsEntry 2 }
    
     xldv20pmAoAdminState OBJECT-TYPE
     -- info-VALUE:     unlocked(1), locked(2)
     -- info-ROU:       GET db  SET pm
     -- info-IMPL:      V2.0-> 
     -- info-VERCTRL:   -
        SYNTAX        Xldv20AdminState
        ACCESS        read-write
        STATUS        mandatory
        DESCRIPTION
             " This read-write attribute is used to activate (unlock)
               and deactivate (lock) the functions (incl. collection)
               performed by this managed entity.
               Note: the 15min  collection object must be activated,
                     before day collection can operate. "
        ::= { xldv20pmAtmObjectsEntry 3 }

     xldv20pmAoBlockSize OBJECT-TYPE
     -- info-VALUE:     128 (default), 256, 512, 1024
     -- info-ROU:       GET db  SET pm
     -- info-IMPL:      V2.0-> 
     -- info-VERCTRL:   -
        SYNTAX        Xldv20pmBlockSizeType
        ACCESS        read-write
        STATUS        mandatory
        DESCRIPTION
             " This is the number of user cells after which
               PMo cell is inserted. Default is 128. "
        ::= { xldv20pmAtmObjectsEntry 4 }

     -- --------------------------------------------------------------

     -- --------------------------------------------------------------
     --        PMo  o n  A T M   L a y e r                          
     --
     --             A t m  E n d p o i n t s  T a b l e
     -- --------------------------------------------------------------


     xldv20pmAtmEndpointsTable OBJECT-TYPE
     -- info-IMPL:      V2.0-> 
     -- info-VERCTRL:   -
        SYNTAX        SEQUENCE OF Xldv20pmAtmEndpointsEntry
        ACCESS        not-accessible
        STATUS        mandatory
        DESCRIPTION
             " This table contains the enpoints for PMo on Atm layer. "
        --DEFAULT next-function-async     fsnPmAeEntryNext
        --DEFAULT get-function-async      fsnPmAeEntryGet
        ::= { xldv20pmPerformanceMonitoring 11 }

     xldv20pmAtmEndpointsEntry OBJECT-TYPE
     -- info-IMPL:      V2.0-> 
     -- info-VERCTRL:   -
        SYNTAX        Xldv20pmAtmEndpointsEntry
        ACCESS        not-accessible
        STATUS        mandatory
        DESCRIPTION
             " An entry of xldv20pmAtmEndpointsTable. "
        INDEX { xldv20pmAoIndex,
                xldv20pmAeEndpointType }
        ::= { xldv20pmAtmEndpointsTable 1 }

     Xldv20pmAtmEndpointsEntry ::=
        SEQUENCE { xldv20pmAeEndpointType         Xldv20pmEndpointType,
                   xldv20pmAeConnectionIndex          INTEGER,
                   xldv20pmAeConnectionIndexType  Xldv20pmConnectionIndexType,
                   xldv20pmAeRole                 Xldv20pmRoleType,
                   xldv20pmAeFlowDirection        Xldv20FlowDirection }

     xldv20pmAeEndpointType OBJECT-TYPE
     -- info-VALUE:     source(1), sink(2)
     -- info-ROU:       GET  db
     -- info-IMPL:      V2.0-> 
     -- info-VERCTRL:   -
        SYNTAX        Xldv20pmEndpointType
        ACCESS        read-only
        STATUS        mandatory
        DESCRIPTION
             " Identifies the type of endpoint. "
        ::= { xldv20pmAtmEndpointsEntry 1 }
     
     xldv20pmAeConnectionIndex OBJECT-TYPE
     -- info-VALUE:     1..2048
     -- info-ROU:       GET  db
     -- info-IMPL:      V2.0-> 
     -- info-VERCTRL:   -
        SYNTAX        INTEGER (1..2048)
        ACCESS        read-only
        STATUS        mandatory
        DESCRIPTION
             " This attribute identifies the Vpl or Vcl cross connection
             where an endpoint object should be added. "
        ::= { xldv20pmAtmEndpointsEntry 2 }

    xldv20pmAeConnectionIndexType OBJECT-TYPE
     -- info-VALUE:     vplUni(1),vplNni(2),vclUni(3),vclNni(4)
     -- info-ROU:       GET db
     -- info-IMPL:      V2.0-> 
     -- info-VERCTRL:   -
        SYNTAX        Xldv20pmConnectionIndexType
        ACCESS        read-only
        STATUS        mandatory
        DESCRIPTION
             " This attribute identifies the type of connection index
             and the termination point where an endpoint should be added. "
        ::= { xldv20pmAtmEndpointsEntry 3 }
    
    xldv20pmAeRole OBJECT-TYPE
     -- info-VALUE:     analyseWithBackwardReporting(1),
     -- info-VALUE:     analyseWithoutBackwardReporting(2),
     -- info-VALUE:     generateWithCollect(3), generateWithoutCollect(4)}
     -- info-ROU:       GET db
     -- info-IMPL:      V2.0-> 
     -- info-VERCTRL:   -
        SYNTAX        Xldv20pmRoleType
        ACCESS        read-only
        STATUS        mandatory
        DESCRIPTION
             " The role of endpoint.
             'analyseWithBackwardReporting' (sink) means extracting
             forward monitoring (FM) OAM cells, sending back 
             backward reporting OAM cells and no data collection
             for current and history table.  
             'analyseWithoutBackwardReporting' (sink) means extracting
             FM cells and also collecting data.  
             'generateWithCollect' (source) means inserting FM cells,
             extracting backward reporting cells if they arrive 
             and collect data for current and history table.  
             'generateWithoutCollect' (source) means inserting FM cells
             but without collecting data.
             The CMU, the Ethernet part of the Twin NT can be 
             inserting and extracting points.  "
        ::= { xldv20pmAtmEndpointsEntry 4 }

    xldv20pmAeFlowDirection OBJECT-TYPE
     -- info-VALUE:     inwards(2), outwards(3)
     -- info-ROU:       GET db
     -- info-IMPL:      V2.0-> 
     -- info-VERCTRL:   -
        SYNTAX        Xldv20FlowDirection
        ACCESS        read-only
        STATUS        mandatory
        DESCRIPTION
             " This attribute identifies the flow direction.
               inwards means flow direction from outside (external interface)
               to cross connection.
               outwards means flow direction from inside to external interface. "
        ::= { xldv20pmAtmEndpointsEntry 5 }

     -- --------------------------------------------------------------
     --          PMo  A T M   C u r r e n t  Table
     -- --------------------------------------------------------------

     xldv20pmAtmCurrentTable OBJECT-TYPE
     -- info-IMPL:      V2.0-> 
        SYNTAX        SEQUENCE OF Xldv20pmAtmCurrentEntry
        ACCESS        not-accessible
        STATUS        mandatory
        DESCRIPTION
             " This table contains the entries for the the PMo objects
               for the current data of Pmo monitoring objects
               on ATM layer. 
               It includes attributes for performance parameters,
               collection interval is 15 minutes and one day . "
        --DEFAULT test-function-async     fsnPmAcEntryTest
        --DEFAULT next-function-async     fsnPmAcEntryNext
        --DEFAULT set-function-async      fsnPmAcEntrySet
        --DEFAULT get-function-async      fsnPmAcEntryGet
        ::= { xldv20pmPerformanceMonitoring 12 }

     xldv20pmAtmCurrentEntry OBJECT-TYPE
     -- info-IMPL:      V2.0-> 
     -- info-VERCTRL:   -
        SYNTAX        Xldv20pmAtmCurrentEntry
        ACCESS        not-accessible
        STATUS        mandatory
        DESCRIPTION
             " An entry describing the Atm Current Data Table . "
        INDEX { xldv20pmAoIndex,
                xldv20pmAcIntervalType }
        ::= { xldv20pmAtmCurrentTable 1 }

     Xldv20pmAtmCurrentEntry ::=
        SEQUENCE { xldv20pmAcIntervalType         Xldv20pmIntervalType,
                   xldv20pmAcAdminState           Xldv20AdminState,
                   xldv20pmAcSuspectFlag          Xldv20pmSuspectType,
                   xldv20pmAcHistEntrySize            INTEGER,
                   xldv20pmAcNrHistEntriesAvailable   INTEGER,
                   xldv20pmAcElapsedTime              INTEGER,
                   xldv20pmAcThresholdLimitIndex      INTEGER,
                   xldv20pmAcTransmittedUserCells     Counter,
                   xldv20pmAcLostUserCells            Counter,
                   xldv20pmAcMisinsertedUserCells     Counter }

     xldv20pmAcIntervalType OBJECT-TYPE
     -- info-VALUE:     min15(1), day(2)
     -- info-ROU:       GET  db
     -- info-IMPL:      V2.0-> 
     -- info-VERCTRL:   -
        SYNTAX        Xldv20pmIntervalType
        ACCESS        read-only
        STATUS        mandatory
        DESCRIPTION
             " This type attribute is used to select between the
               15 min  or the day accumulation types. "
        ::= { xldv20pmAtmCurrentEntry 1 }

     xldv20pmAcAdminState OBJECT-TYPE
     -- info-VALUE:     unlocked(1), locked(2)
     -- info-ROU:       GET db  SET pm
     -- info-IMPL:      V2.0-> 
     -- info-VERCTRL:   -
        SYNTAX        Xldv20AdminState
        ACCESS        read-write
        STATUS        mandatory
        DESCRIPTION
             " This read-write attribute is used to activate (unlock)
               and deactivate (lock) the functions (incl. collection)
               performed by this managed entity.
               Note: the 15min  collection object must be activated,
                     before day collection can operate. "
        ::= { xldv20pmAtmCurrentEntry 2 }

     xldv20pmAcSuspectFlag OBJECT-TYPE
     -- info-VALUE:     reliable(1), suspect(2)
     -- info-ROU:       GET db
     -- info-IMPL:      V2.0-> 
     -- info-VERCTRL:   -
        SYNTAX        Xldv20pmSuspectType
        ACCESS        read-only
        STATUS        mandatory
        DESCRIPTION
             " This read-only attribute will be set to indicate that
               troubles arose during an interval and that the counter
               values are suspect and incomplete. "
        ::= { xldv20pmAtmCurrentEntry 3 }

     xldv20pmAcHistEntrySize   OBJECT-TYPE
     -- info-VALUE:     1..96 (default 1)
     -- info-VALUE:     day counter : 1. min15 counter: 1..96
     -- info-ROU:       GET db  SET pm
     -- info-IMPL:      V2.0-> 
     -- info-VERCTRL:   -
        SYNTAX        INTEGER (1..96)
        ACCESS        read-only
        STATUS        mandatory
        DESCRIPTION
             " This is the configured size of history. "
        ::= { xldv20pmAtmCurrentEntry 4 }
     
     xldv20pmAcNrHistEntriesAvailable   OBJECT-TYPE
     -- info-VALUE:     day counter : 0,1.min15 counter: 0..96 (default 0)
     -- info-ROU:       GET db  SET pm
     -- info-IMPL:      V2.0-> 
     -- info-VERCTRL:   -
        SYNTAX        INTEGER (0..96)
        ACCESS        read-only
        STATUS        mandatory
        DESCRIPTION
             " This is the number of history entries which 
             are available in the history table. "
        ::= { xldv20pmAtmCurrentEntry 5 }
     
     xldv20pmAcElapsedTime OBJECT-TYPE
     -- info-VALUE:     0..900 (sec) for min15,
     -- info-VALUE:     0..1440 (min) for day
     -- info-ROU:       GET db
     -- info-IMPL:      V2.0-> 
     -- info-VERCTRL:   -
        SYNTAX        INTEGER(0..1440)
        ACCESS        read-only
        STATUS        mandatory
        DESCRIPTION
             " This read-only attribute represents the difference
               between the current time and the start of the present
               summary interval.
	       Units are seconds when 15 minute interval is selected 
	       or minutes for day interval.
               (Note: accurate to the sample time interval). "
        ::= { xldv20pmAtmCurrentEntry 6 }

     xldv20pmAcThresholdLimitIndex OBJECT-TYPE
     -- info-VALUE:     1..30
     -- info-ROU:       GET db  SET pm
     -- info-IMPL:      V2.0-> 
     -- info-VERCTRL:   -
        SYNTAX        INTEGER (1..30)
        ACCESS        read-write
        STATUS        mandatory
        DESCRIPTION
             " This read-write attribute provides an index to the
               ThresholdLimitTable managed entity that contains the
               threshold limits for the performance parameters reported
               by this managed entity.
               When the value of this attribute is set to 1, default
               threshold limits shall be used . "
        ::= { xldv20pmAtmCurrentEntry 7 }

     xldv20pmAcTransmittedUserCells OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a counter of
               transmitted user cells for a 15 min /day interval. "
        ::= { xldv20pmAtmCurrentEntry 8 }
     
     xldv20pmAcLostUserCells OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a counter of
               lost user cells for a 15 min /day interval. "
        ::= { xldv20pmAtmCurrentEntry 9 }

     xldv20pmAcMisinsertedUserCells OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a counter of
               Misinserted user cells for a 15 min /day interval. "
        ::= { xldv20pmAtmCurrentEntry 10 }

     -- --------------------------------------------------------------
     --          PMo  A T M   H I S T O R Y  Table
     -- --------------------------------------------------------------

     xldv20pmAtmHistoryTable OBJECT-TYPE
     -- info-IMPL:      V2.0-> 
     -- info-VERCTRL:   -
        SYNTAX        SEQUENCE OF Xldv20pmAtmHistoryEntry
        ACCESS        not-accessible
        STATUS        mandatory
        DESCRIPTION
             " This table contains the entries for the 15 min /one
             day-history data collection results for PMo objects 
             of  ATM layer. "
        --DEFAULT next-function-async     fsnPmAhEntryNext
        --DEFAULT get-function-async      fsnPmAhEntryGet
        ::= { xldv20pmPerformanceMonitoring 13 }

     xldv20pmAtmHistoryEntry OBJECT-TYPE
     -- info-IMPL:      V2.0-> 
     -- info-VERCTRL:   -
        SYNTAX        Xldv20pmAtmHistoryEntry
        ACCESS        not-accessible
        STATUS        mandatory
        DESCRIPTION
             " An entry describing the History Data Table for PMo on ATM
             layer. "
        INDEX { xldv20pmAoIndex,
                xldv20pmAhIntervalType,
                xldv20pmAhHistEntryNr }
        ::= { xldv20pmAtmHistoryTable 1 }

     Xldv20pmAtmHistoryEntry ::=
        SEQUENCE { xldv20pmAhIntervalType        Xldv20pmIntervalType,
                   xldv20pmAhHistEntryNr              INTEGER,
                   xldv20pmAhSuspectFlag         Xldv20pmSuspectType,
                   xldv20pmAhPeriodEndTime            INTEGER,
                   xldv20pmAhTransmittedUserCells     Counter,
                   xldv20pmAhLostUserCells            Counter,
                   xldv20pmAhMisinsertedUserCells     Counter }

     xldv20pmAhIntervalType OBJECT-TYPE
     -- info-VALUE:     min15(1), day(2)
     -- info-ROU:       GET db
     -- info-IMPL:      V2.0-> 
     -- info-VERCTRL:   -
        SYNTAX        Xldv20pmIntervalType
        ACCESS        read-only
        STATUS        mandatory
        DESCRIPTION
             " This type attribute is used to select between the
               15 min  or the day accumulation types. "
        ::= { xldv20pmAtmHistoryEntry 1 }

     xldv20pmAhHistEntryNr OBJECT-TYPE
     -- info-VALUE:     1..96
     -- info-ROU:       GET db
     -- info-IMPL:      V2.0-> 
     -- info-VERCTRL:   -
        SYNTAX        INTEGER (1..96)
        ACCESS        read-only
        STATUS        mandatory
        DESCRIPTION
             " This attribute is used as index to address a history entry.
             Entry 1 is the most recent, entry 96 is 24 hours ago.
             The range of values is between 1 and xldv20pmAcHistEntrySize . " 
        ::= { xldv20pmAtmHistoryEntry 2 }

     xldv20pmAhSuspectFlag OBJECT-TYPE
     -- info-VALUE:     reliable(1), suspect(2)
     -- info-ROU:       GET db
     -- info-IMPL:      V2.0-> 
     -- info-VERCTRL:   -
        SYNTAX        Xldv20pmSuspectType
        ACCESS        read-only
        STATUS        mandatory
        DESCRIPTION
             " This read-only attribute will be set to indicate that
               troubles arose during an interval and that the counter
               values are suspect and incomplete. "
        ::= { xldv20pmAtmHistoryEntry 3 }

     xldv20pmAhPeriodEndTime OBJECT-TYPE
     -- info-VALUE:     0..2147483647
     -- info-ROU:       GET  db
     -- info-IMPL:      V2.0-> 
     -- info-VERCTRL:   -
        SYNTAX        INTEGER(0..2147483647)
        ACCESS        read-only
        STATUS        mandatory
        DESCRIPTION
             " Date/time at the end of the selected interval. "
        ::= { xldv20pmAtmHistoryEntry 4 }

     xldv20pmAhTransmittedUserCells OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a counter of
               transmitted user cells for a 15 min /day interval. "
        ::= { xldv20pmAtmHistoryEntry 5 }
     
     xldv20pmAhLostUserCells OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a counter of
               lost user cells for a 15 min /day interval. "
        ::= { xldv20pmAtmHistoryEntry 6 }

     xldv20pmAhMisinsertedUserCells OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a counter of
               Misinserted user cells for a 15 min /day interval. "
        ::= { xldv20pmAtmHistoryEntry 7 }


     -- --------------------------------------------------------------
     --          PMo  The IMA Group Current Statistics subtree
     -- --------------------------------------------------------------
     --
     --
     -- The IMA Group Current Statistics subtree consists of a single table:
     -- the IMA Group Current Table. 
     -- 
     -- Selection of xldv20pmImaGroupIntervalType min15 :
     -- The entries contain the cumulative sum
     -- collected by each IMA group for the current 15 minute interval.
     -- 
     -- Selection of xldv20pmImaGroupIntervalType day  :
     -- The entries contain the cumulative sum
     -- of the various statistics collected by each IMA group for the 24 hour
     -- period preceding the current interval
     --

     xldv20pmImaGroupCurrentTable OBJECT-TYPE
     -- info-IMPL:      V2.0-> 
        SYNTAX        SEQUENCE OF Xldv20pmImaGroupCurrentEntry
        ACCESS        not-accessible
        STATUS        mandatory
        DESCRIPTION
             " This table contains the entries for the PMo objects
               for the current data of Pmo monitoring objects
               for IMA groups . 
               Collection interval is the current 15 minute and one the
               current day . "
        --DEFAULT test-function-async     fsnPmIgcEntryTest
        --DEFAULT next-function-async     fsnPmIgcEntryNext
        --DEFAULT set-function-async      fsnPmIgcEntrySet
        --DEFAULT get-function-async      fsnPmIgcEntryGet
        ::= { xldv20pmPerformanceMonitoring 14 }

     xldv20pmImaGroupCurrentEntry OBJECT-TYPE
     -- info-IMPL:      V2.0-> 
     -- info-VERCTRL:   -
        SYNTAX        Xldv20pmImaGroupCurrentEntry
        ACCESS        not-accessible
        STATUS        mandatory
        DESCRIPTION
             " An entry describing the current PMo data for ImaGroups. "
        INDEX { xldv20IfIndex,
                xldv20pmImaGroupCurrentIntervalType }
        ::= { xldv20pmImaGroupCurrentTable 1 }

     Xldv20pmImaGroupCurrentEntry ::=
        SEQUENCE { xldv20pmImaGroupCurrentIntervalType         Xldv20pmIntervalType,
                   xldv20pmImaGroupCurrentAdminState           Xldv20AdminState,
                   xldv20pmImaGroupCurrentSuspectFlag          Xldv20pmSuspectType,
                   xldv20pmImaGroupCurrentHistEntrySize            INTEGER,
                   xldv20pmImaGroupCurrentNrHistEntriesAvailable   INTEGER,
                   xldv20pmImaGroupCurrentElapsedTime              INTEGER,
                   xldv20pmImaGroupCurrentThresholdLimitIndex      INTEGER,
                   xldv20pmImaGroupCurrentUnavailSecs              Gauge,
                   xldv20pmImaGroupCurrentNeNumFailures            Gauge
                   }

     xldv20pmImaGroupCurrentIntervalType OBJECT-TYPE
     -- info-VALUE:     min15(1), day(2)
     -- info-ROU:       GET  db
     -- info-IMPL:      V2.0-> 
     -- info-VERCTRL:   -
        SYNTAX        Xldv20pmIntervalType
        ACCESS        read-only
        STATUS        mandatory
        DESCRIPTION
             " This type attribute is used to select between the
               15 min or the day accumulation types. "
        ::= { xldv20pmImaGroupCurrentEntry 1 }

     xldv20pmImaGroupCurrentAdminState OBJECT-TYPE
     -- info-VALUE:     unlocked(1), locked(2)
     -- info-ROU:       GET db  SET pm
     -- info-IMPL:      V2.0-> 
     -- info-VERCTRL:   -
        SYNTAX        Xldv20AdminState
        ACCESS        read-write
        STATUS        mandatory
        DESCRIPTION
             " This read-write attribute is used to activate (unlock)
               and deactivate (lock) the functions (incl. collection)
               performed by this managed entity.
               Note: the 15min  collection object must be activated,
                     before day collection can operate. "
        ::= { xldv20pmImaGroupCurrentEntry 2 }

     xldv20pmImaGroupCurrentSuspectFlag OBJECT-TYPE
     -- info-VALUE:     reliable(1), suspect(2)
     -- info-ROU:       GET db
     -- info-IMPL:      V2.0-> 
     -- info-VERCTRL:   -
        SYNTAX        Xldv20pmSuspectType
        ACCESS        read-only
        STATUS        mandatory
        DESCRIPTION
             " This read-only attribute will be set to indicate that
               troubles arose during an interval and that the counter
               values are suspect and incomplete. "
        ::= { xldv20pmImaGroupCurrentEntry 3 }

     xldv20pmImaGroupCurrentHistEntrySize   OBJECT-TYPE
     -- info-VALUE:     1..96 (default 1)
     -- info-VALUE:     day counter : 1. min15 counter: 1..96
     -- info-ROU:       GET db  SET pm
     -- info-IMPL:      V2.0-> 
     -- info-VERCTRL:   -
        SYNTAX        INTEGER (1..96)
        ACCESS        read-only
        STATUS        mandatory
        DESCRIPTION
             " This is the configured size of history. "
        ::= { xldv20pmImaGroupCurrentEntry 4 }
     
     xldv20pmImaGroupCurrentNrHistEntriesAvailable   OBJECT-TYPE
     -- info-VALUE:     day counter : 0,1.min15 counter: 0..96 (default 0)
     -- info-ROU:       GET db  SET pm
     -- info-IMPL:      V2.0-> 
     -- info-VERCTRL:   -
        SYNTAX        INTEGER (0..96)
        ACCESS        read-only
        STATUS        mandatory
        DESCRIPTION
             " This is the number of history entries which 
             are available in the history table. "
        ::= { xldv20pmImaGroupCurrentEntry 5 }
     
     xldv20pmImaGroupCurrentElapsedTime OBJECT-TYPE
     -- info-VALUE:     0..900 (sec) for min15,
     -- info-VALUE:     0..1440 (min) for day
     -- info-ROU:       GET db
     -- info-IMPL:      V2.0-> 
     -- info-VERCTRL:   -
        SYNTAX        INTEGER(0..1440)
        ACCESS        read-only
        STATUS        mandatory
        DESCRIPTION
             " This read-only attribute represents the difference
               between the current time and the start of the present
               summary interval.
	       Units are seconds when 15 minute interval is selected 
	       or minutes for day interval.
               (Note: accurate to the sample time interval). "
        ::= { xldv20pmImaGroupCurrentEntry 6 }

     xldv20pmImaGroupCurrentThresholdLimitIndex OBJECT-TYPE
     -- info-VALUE:     1..30
     -- info-ROU:       GET db  SET pm
     -- info-IMPL:      V2.0-> 
     -- info-VERCTRL:   -
        SYNTAX        INTEGER (1..30)
        ACCESS        read-write
        STATUS        mandatory
        DESCRIPTION
             " This read-write attribute provides an index to the
               ThresholdLimitTable managed entity that contains the
               threshold limits for the performance parameters reported
               by this managed entity.
               When the value of this attribute is set to 1, default
               threshold limits shall be used . "
        ::= { xldv20pmImaGroupCurrentEntry 7 }

     xldv20pmImaGroupCurrentUnavailSecs OBJECT-TYPE
     -- info-VALUE:     -
     -- info-ROU:       GET db
     -- info-IMPL:      V2.0-> 
     -- info-VERCTRL:   -
        SYNTAX        Gauge  
        ACCESS        read-only
        STATUS        mandatory
        DESCRIPTION
             " The counts of second intervals where the IMA group
               traffic state machine is down in the current
               for a 15 min /day interval. "
        ::= { xldv20pmImaGroupCurrentEntry 8 }

     xldv20pmImaGroupCurrentNeNumFailures OBJECT-TYPE
     -- info-VALUE:     -
     -- info-ROU:       GET db
     -- info-IMPL:      V2.0-> 
     -- info-VERCTRL:   -
        SYNTAX        Gauge 
        ACCESS        read-only
        STATUS        mandatory
        DESCRIPTION
             " The number of times a near-end group failure
               (config-Aborted, unsufficient-Links) has been reported 
               for a 15 min /day interval. "
        ::= { xldv20pmImaGroupCurrentEntry 9 }

     -- --------------------------------------------------------------
     --          PMo  I M A Group  H i s t o r y  subtree
     -- --------------------------------------------------------------

     -- This section combines the 
     -- the IMA Group Interval Statistics subtree and
     -- the IMA Group Total Statistics subtree.
     -- It consists of a single table:
     -- the IMA Group History Table.  
     -- 
     -- Selection the xldv20pmImaGroupHistoryIntervalType min15 :
     -- the entries contain various statistics
     -- collected by each IMA Group over the previous 24 hours of operation.
     --
     -- Selection the xldv20pmImaGroupHistoryIntervalType day :
     -- The entries contain the cumulative sum
     -- of the various statistics collected by each IMA Group for the 24 hour
     -- period preceding the current interval.
     --

     xldv20pmImaGroupHistoryTable OBJECT-TYPE
     -- info-IMPL:      V2.0-> 
     -- info-VERCTRL:   -
        SYNTAX        SEQUENCE OF Xldv20pmImaGroupHistoryEntry
        ACCESS        not-accessible
        STATUS        mandatory
        DESCRIPTION
             " This table contains the entries for the 15 min /one
             day-history data collection results for PMo objects 
             of  IMA Group interfaces. "
        --DEFAULT test-function-async     fsnPmIghEntryTest
        --DEFAULT next-function-async     fsnPmIghEntryNext
        --DEFAULT set-function-async      fsnPmIghEntrySet
        --DEFAULT get-function-async      fsnPmIghEntryGet
        ::= { xldv20pmPerformanceMonitoring 15 }

     xldv20pmImaGroupHistoryEntry OBJECT-TYPE
     -- info-IMPL:      V2.0-> 
     -- info-VERCTRL:   -
        SYNTAX        Xldv20pmImaGroupHistoryEntry
        ACCESS        not-accessible
        STATUS        mandatory
        DESCRIPTION
             " An entry describing the History Data Table for PMo 
             IMA groups. "
        INDEX { xldv20IfIndex,
                xldv20pmImaGroupHistoryIntervalType,
                xldv20pmImaGroupHistoryHistEntryNr }
        ::= { xldv20pmImaGroupHistoryTable 1 }

     Xldv20pmImaGroupHistoryEntry ::=
        SEQUENCE { xldv20pmImaGroupHistoryIntervalType    Xldv20pmIntervalType,
                   xldv20pmImaGroupHistoryHistEntryNr           INTEGER,
                   xldv20pmImaGroupHistorySuspectFlag     Xldv20pmSuspectType,
                   xldv20pmImaGroupHistoryPeriodEndTime         INTEGER,
                   xldv20pmImaGroupHistoryUnavailSecs           Gauge,
                   xldv20pmImaGroupHistoryNeNumFailures         Gauge
                 }

     xldv20pmImaGroupHistoryIntervalType OBJECT-TYPE
     -- info-VALUE:     min15(1), day(2)
     -- info-ROU:       GET db
     -- info-IMPL:      V2.0-> 
     -- info-VERCTRL:   -
        SYNTAX        Xldv20pmIntervalType
        ACCESS        read-only
        STATUS        mandatory
        DESCRIPTION
             " This type attribute is used to select between the
               15 min  or the day accumulation types. "
        ::= { xldv20pmImaGroupHistoryEntry 1 }

     xldv20pmImaGroupHistoryHistEntryNr OBJECT-TYPE
     -- info-VALUE:     1..96
     -- info-ROU:       GET db
     -- info-IMPL:      V2.0-> 
     -- info-VERCTRL:   -
        SYNTAX        INTEGER (1..96)
        ACCESS        read-only
        STATUS        mandatory
        DESCRIPTION
             " This attribute is used as index to address a history entry.
             Entry 1 is the most recent, entry 96 is 24 hours ago.
             The range of values is between 1 and xldv20pmImaGroupCurrentHistEntrySize . " 
        ::= { xldv20pmImaGroupHistoryEntry 2 }

     xldv20pmImaGroupHistorySuspectFlag OBJECT-TYPE
     -- info-VALUE:     reliable(1), suspect(2)
     -- info-ROU:       GET db
     -- info-IMPL:      V2.0-> 
     -- info-VERCTRL:   -
        SYNTAX        Xldv20pmSuspectType
        ACCESS        read-only
        STATUS        mandatory
        DESCRIPTION
             " This read-only attribute will be set to indicate that
               troubles arose during an interval and that the counter
               values are suspect and incomplete. "
        ::= { xldv20pmImaGroupHistoryEntry 3 }

     xldv20pmImaGroupHistoryPeriodEndTime OBJECT-TYPE
     -- info-VALUE:     0..2147483647
     -- info-ROU:       GET  db
     -- info-IMPL:      V2.0-> 
     -- info-VERCTRL:   -
        SYNTAX        INTEGER(0..2147483647)
        ACCESS        read-only
        STATUS        mandatory
        DESCRIPTION
             " Date/time at the end of the selected interval. "
        ::= { xldv20pmImaGroupHistoryEntry 4 }

     xldv20pmImaGroupHistoryUnavailSecs OBJECT-TYPE
     -- info-VALUE:     -
     -- info-ROU:       GET db
     -- info-IMPL:      V2.0-> 
     -- info-VERCTRL:   -
        SYNTAX        Gauge
        ACCESS        read-only
        STATUS        mandatory
        DESCRIPTION
        " The counts of second intervals where the IMA group
          traffic state machine is down in the current
          15 min /day interval. "
        ::= { xldv20pmImaGroupHistoryEntry 5 }
     
     xldv20pmImaGroupHistoryNeNumFailures OBJECT-TYPE
     -- info-VALUE:     -
     -- info-ROU:       GET db
     -- info-IMPL:      V2.0-> 
     -- info-VERCTRL:   -
        SYNTAX        Gauge
        ACCESS        read-only
        STATUS        mandatory
        DESCRIPTION
        " The number of times a near-end group failure
          (config-Aborted, unsufficient-Links) has been reported 
          for a previous 15 min interval or the previous day. "
        ::= { xldv20pmImaGroupHistoryEntry 6 }

     -- --------------------------------------------------------------
     --          PMo  I M A Link   C u r r e n t  Table
     -- --------------------------------------------------------------

     xldv20pmImaLinkCurrentTable OBJECT-TYPE
     -- info-IMPL:      V2.0->
        SYNTAX        SEQUENCE OF Xldv20pmImaLinkCurrentEntry
        ACCESS        not-accessible
        STATUS        mandatory
        DESCRIPTION
             " This table contains the entries for the the PMo objects
               for the current data of Pmo monitoring objects
               for IMA groups . 
               It includes attributes for performance parameters,
               collection interval is 15 minutes and one day . "
        --DEFAULT test-function-async     fsnPmIlcEntryTest
        --DEFAULT next-function-async     fsnPmIlcEntryNext
        --DEFAULT set-function-async      fsnPmIlcEntrySet
        --DEFAULT get-function-async      fsnPmIlcEntryGet
        ::= { xldv20pmPerformanceMonitoring 16 }

     xldv20pmImaLinkCurrentEntry OBJECT-TYPE
     -- info-IMPL:      V2.0-> 
     -- info-VERCTRL:   -
        SYNTAX        Xldv20pmImaLinkCurrentEntry
        ACCESS        not-accessible
        STATUS        mandatory
        DESCRIPTION
             " An entry describing the current PMo data for ImaLinks. "
        INDEX { xldv20IfIndex,
                xldv20pmImaLinkCurrentIntervalType }
        ::= { xldv20pmImaLinkCurrentTable 1 }

     Xldv20pmImaLinkCurrentEntry ::=
        SEQUENCE { xldv20pmImaLinkCurrentIntervalType         Xldv20pmIntervalType,
                   xldv20pmImaLinkCurrentAdminState           Xldv20AdminState,
                   xldv20pmImaLinkCurrentSuspectFlag          Xldv20pmSuspectType,
                   xldv20pmImaLinkCurrentHistEntrySize            INTEGER,
                   xldv20pmImaLinkCurrentNrHistEntriesAvailable   INTEGER,
                   xldv20pmImaLinkCurrentElapsedTime              INTEGER,
                   xldv20pmImaLinkCurrentThresholdLimitIndex      INTEGER,
                   xldv20pmImaLinkCurrentImaViolations            Gauge,
                   xldv20pmImaLinkCurrentOifAnomalies             Gauge,
                   xldv20pmImaLinkCurrentNeSevErroredSecs         Gauge,
                   xldv20pmImaLinkCurrentFeSevErroredSecs         Gauge,
                   xldv20pmImaLinkCurrentNeUnavailSecs            Gauge,
                   xldv20pmImaLinkCurrentFeUnavailSecs            Gauge,
                   xldv20pmImaLinkCurrentNeTxUnusableSecs         Gauge,
                   xldv20pmImaLinkCurrentNeRxUnusableSecs         Gauge,
                   xldv20pmImaLinkCurrentFeTxUnusableSecs         Gauge,
                   xldv20pmImaLinkCurrentFeRxUnusableSecs         Gauge,
                   xldv20pmImaLinkCurrentNeTxNumFailures          Gauge,
                   xldv20pmImaLinkCurrentNeRxNumFailures          Gauge
                 }

     xldv20pmImaLinkCurrentIntervalType OBJECT-TYPE
     -- info-VALUE:     min15(1), day(2)
     -- info-ROU:       GET  db
     -- info-IMPL:      V2.0-> 
     -- info-VERCTRL:   -
        SYNTAX        Xldv20pmIntervalType
        ACCESS        read-only
        STATUS        mandatory
        DESCRIPTION
             " This type attribute is used to select between the
               15 min  or the day accumulation types. "
        ::= { xldv20pmImaLinkCurrentEntry 1 }

     xldv20pmImaLinkCurrentAdminState OBJECT-TYPE
     -- info-VALUE:     unlocked(1), locked(2)
     -- info-ROU:       GET db  SET pm
     -- info-IMPL:      V2.0-> 
     -- info-VERCTRL:   -
        SYNTAX        Xldv20AdminState
        ACCESS        read-write
        STATUS        mandatory
        DESCRIPTION
             " This read-write attribute is used to activate (unlock)
               and deactivate (lock) the functions (incl. collection)
               performed by this managed entity.
               Note: the 15min  collection object must be activated,
                     before day collection can operate. "
        ::= { xldv20pmImaLinkCurrentEntry 2 }

     xldv20pmImaLinkCurrentSuspectFlag OBJECT-TYPE
     -- info-VALUE:     reliable(1), suspect(2)
     -- info-ROU:       GET db
     -- info-IMPL:      V2.0-> 
     -- info-VERCTRL:   -
        SYNTAX        Xldv20pmSuspectType
        ACCESS        read-only
        STATUS        mandatory
        DESCRIPTION
             " This read-only attribute will be set to indicate that
               troubles arose during an interval and that the counter
               values are suspect and incomplete. "
        ::= { xldv20pmImaLinkCurrentEntry 3 }

     xldv20pmImaLinkCurrentHistEntrySize   OBJECT-TYPE
     -- info-VALUE:     1..96 (default 1)
     -- info-VALUE:     day counter : 1. min15 counter: 1..96
     -- info-ROU:       GET db  SET pm
     -- info-IMPL:      V2.0-> 
     -- info-VERCTRL:   -
        SYNTAX        INTEGER (1..96)
        ACCESS        read-only
        STATUS        mandatory
        DESCRIPTION
             " This is the configured size of history. "
        ::= { xldv20pmImaLinkCurrentEntry 4 }
     
     xldv20pmImaLinkCurrentNrHistEntriesAvailable   OBJECT-TYPE
     -- info-VALUE:     day counter : 0,1.min15 counter: 0..96 (default 0)
     -- info-ROU:       GET db  SET pm
     -- info-IMPL:      V2.0-> 
     -- info-VERCTRL:   -
        SYNTAX        INTEGER (0..96)
        ACCESS        read-only
        STATUS        mandatory
        DESCRIPTION
             " This is the number of history entries which 
             are available in the history table. "
        ::= { xldv20pmImaLinkCurrentEntry 5 }
     
     xldv20pmImaLinkCurrentElapsedTime OBJECT-TYPE
     -- info-VALUE:     0..900 (sec) for min15,
     -- info-VALUE:     0..1440 (min) for day
     -- info-ROU:       GET db
     -- info-IMPL:      V2.0-> 
     -- info-VERCTRL:   -
        SYNTAX        INTEGER(0..1440)
        ACCESS        read-only
        STATUS        mandatory
        DESCRIPTION
             " This read-only attribute represents the difference
               between the current time and the start of the present
               summary interval.
	       Units are seconds when 15 minute interval is selected 
	       or minutes for day interval.
               (Note: accurate to the sample time interval). "
        ::= { xldv20pmImaLinkCurrentEntry 6 }

     xldv20pmImaLinkCurrentThresholdLimitIndex OBJECT-TYPE
     -- info-VALUE:     1..30
     -- info-ROU:       GET db  SET pm
     -- info-IMPL:      V2.0-> 
     -- info-VERCTRL:   -
        SYNTAX        INTEGER (1..30)
        ACCESS        read-write
        STATUS        mandatory
        DESCRIPTION
             " This read-write attribute provides an index to the
               ThresholdLimitTable managed entity that contains the
               threshold limits for the performance parameters reported
               by this managed entity.
               When the value of this attribute is set to 1, default
               threshold limits shall be used . "
        ::= { xldv20pmImaLinkCurrentEntry 7 }

     xldv20pmImaLinkCurrentImaViolations OBJECT-TYPE
     -- info-VALUE:     
     -- info-ROU:       GET db
     -- info-IMPL:      V2.0->
     -- info-VERCTRL:   -
        SYNTAX        Gauge
        ACCESS        read-only
        STATUS        mandatory
        DESCRIPTION
        "ICP violations: count of errored, invalid or missing ICP cells,
        except during SES-IMA or UAS-IMA conditions, in the current
        15 minute interval.
        ATM Forum IMA v1.1, (R-125) and (O-26) in Section 12.2.2.2
        on page 77. "
      ::= { xldv20pmImaLinkCurrentEntry 8 }

     xldv20pmImaLinkCurrentOifAnomalies OBJECT-TYPE
     -- info-VALUE:     
     -- info-ROU:       GET db
     -- info-IMPL:      V2.0->
     -- info-VERCTRL:   -
        SYNTAX        Gauge
        ACCESS        read-only
        STATUS        mandatory
        DESCRIPTION
        "The number of OIF anomalies, except during SES-IMA or UAS-IMA
        conditions, at the near-end in the current 15 minute interval.
        This is an optional attribute.
        ATM Forum IMA v1.1, (O-20) and (O-26) in Section 12.2.2.2
        on page 77"
      ::= { xldv20pmImaLinkCurrentEntry 9 }

     xldv20pmImaLinkCurrentNeSevErroredSecs OBJECT-TYPE
     -- info-VALUE:     
     -- info-ROU:       GET db
     -- info-IMPL:      V2.0->
     -- info-VERCTRL:   -
        SYNTAX        Gauge
        ACCESS        read-only
        STATUS        mandatory
        DESCRIPTION
        "Count of one second intervals containing >= 30% of the ICP cells
        counted as IV-IMAs, or one or more link defects (e.g., LOS, OOF/LOF,
        AIS, or LCD), LIF defects, or LODS defects, except during UAS-IMA
        condition, in the current 15 minute interval.
        ATM Forum IMA v1.1, (R-126) and (O-26) in Section 12.2.2.2
        on page 77"
      ::= { xldv20pmImaLinkCurrentEntry 10 }

     xldv20pmImaLinkCurrentFeSevErroredSecs OBJECT-TYPE
     -- info-VALUE:     
     -- info-ROU:       GET db
     -- info-IMPL:      V2.0->
     -- info-VERCTRL:   -
        SYNTAX        Gauge
        ACCESS        read-only
        STATUS        mandatory
        DESCRIPTION
         "Count of unavailable seconds at near-end in the current 15 minute
          interval: unavailability begins at the onset of 10 contiguous
          SES-IMA and ends at the onset of 10 contiguous seconds with no
          SES-IMA.
          ATM Forum IMA v1.1, (R-128) and (O-26) in Section 12.2.2.2 on page 77"
      ::= { xldv20pmImaLinkCurrentEntry 11 }

     xldv20pmImaLinkCurrentNeUnavailSecs OBJECT-TYPE
     -- info-VALUE:     
     -- info-ROU:       GET db
     -- info-IMPL:      V2.0->
     -- info-VERCTRL:   -
        SYNTAX        Gauge
        ACCESS        read-only
        STATUS        mandatory
        DESCRIPTION
        "Count of unavailable seconds at near-end in the current 15 minute
        interval: unavailability begins at the onset of 10 contiguous
        SES-IMA-FE and ends at the onset of 10 contiguous seconds with no
        SES-IMA-FE.
        ATM Forum IMA v1.1, (R-129) and (O-26) in Section 12.2.2.2
        on page 77 . "
      ::= { xldv20pmImaLinkCurrentEntry 12 }

     xldv20pmImaLinkCurrentFeUnavailSecs OBJECT-TYPE
     -- info-VALUE:     
     -- info-ROU:       GET db
     -- info-IMPL:      V2.0->
     -- info-VERCTRL:   -
        SYNTAX        Gauge
        ACCESS        read-only
        STATUS        mandatory
        DESCRIPTION
        "Count of unavailable seconds at far-end in the current 15 minute
        interval: unavailability begins at the onset of 10 contiguous
        SES-IMA-FE and ends at the onset of 10 contiguous seconds with no
        SES-IMA-FE.
        ATM Forum IMA v1.1, (R-129) and (O-26) in Section 12.2.2.2
        on page 77 . "
      ::= { xldv20pmImaLinkCurrentEntry 13 }

     xldv20pmImaLinkCurrentNeTxUnusableSecs OBJECT-TYPE
     -- info-VALUE:     
     -- info-ROU:       GET db
     -- info-IMPL:      V2.0->
     -- info-VERCTRL:   -
        SYNTAX        Gauge
        ACCESS        read-only
        STATUS        mandatory
        DESCRIPTION
        "Tx Unusable seconds: count of Unusable seconds at the near-end
        Tx LSM in the current 15 minute interval.
        ATM Forum IMA v1.1, (R-130) and (O-26) in Section 12.2.2.2
        on page 77. "
      ::= { xldv20pmImaLinkCurrentEntry 14 }

     xldv20pmImaLinkCurrentNeRxUnusableSecs OBJECT-TYPE
     -- info-VALUE:     
     -- info-ROU:       GET db
     -- info-IMPL:      V2.0->
     -- info-VERCTRL:   -
        SYNTAX        Gauge
        ACCESS        read-only
        STATUS        mandatory
        DESCRIPTION
        "Rx Unusable seconds: count of Unusable seconds at the near-end
        Rx LSM in the current 15 minute interval.
        ATM Forum IMA v1.1, (R-131) and (O-26) in Section 12.2.2.2
        on page 77. "
      ::= { xldv20pmImaLinkCurrentEntry 15 }

     xldv20pmImaLinkCurrentFeTxUnusableSecs OBJECT-TYPE
     -- info-VALUE:     
     -- info-ROU:       GET db
     -- info-IMPL:      V2.0->
     -- info-VERCTRL:   -
        SYNTAX        Gauge
        ACCESS        read-only
        STATUS        mandatory
        DESCRIPTION
        "Tx Unusable seconds: count of Unusable seconds at the far-end
        Tx LSM in the current 15 minute interval.
        ATM Forum IMA v1.1, (R-132) and (O-26) in Section 12.2.2.2
        on page 77. "
      ::= { xldv20pmImaLinkCurrentEntry 16 }

     xldv20pmImaLinkCurrentFeRxUnusableSecs OBJECT-TYPE
     -- info-VALUE:     
     -- info-ROU:       GET db
     -- info-IMPL:      V2.0->
     -- info-VERCTRL:   -
        SYNTAX        Gauge
        ACCESS        read-only
        STATUS        mandatory
        DESCRIPTION
        "Rx Unusable seconds: count of Unusable seconds at the far-end
        Rx LSM in the current 15 minute interval.
        ATM Forum IMA v1.1, (R-133) and (O-26) in Section 12.2.2.2
        on page 77. "
      ::= { xldv20pmImaLinkCurrentEntry 17 }

     xldv20pmImaLinkCurrentNeTxNumFailures OBJECT-TYPE
     -- info-VALUE:     
     -- info-ROU:       GET db
     -- info-IMPL:      V2.0->
     -- info-VERCTRL:   -
        SYNTAX        Gauge
        ACCESS        read-only
        STATUS        mandatory
        DESCRIPTION
        "The number of times a near-end transmit failure alarm condition
        has been entered on this link (i.e., some form of implementation
        specific transmit fault) in the current 15 minute interval.
        ATM Forum IMA v1.1, (R-134) and (O-26) in Section 12.2.2.2
        on page 77"
     ::= { xldv20pmImaLinkCurrentEntry 18 }

     xldv20pmImaLinkCurrentNeRxNumFailures OBJECT-TYPE
     -- info-VALUE:     
     -- info-ROU:       GET db
     -- info-IMPL:      V2.0->
     -- info-VERCTRL:   -
        SYNTAX        Gauge
        ACCESS        read-only
        STATUS        mandatory
        DESCRIPTION
        "The number of times a near-end receive failure alarm condition
        has been entered on this link (i.e., LIF, LODS, RFI-IMA, Mis-Connected,
        or some form of implementation specific receive fault)
        in the current 15 minute interval.
        ATM Forum IMA v1.1, (R-135) and (O-26) in Section 12.2.2.2
        on page 77"
     ::= { xldv20pmImaLinkCurrentEntry 19 }

     -- --------------------------------------------------------------
     --          PMo  I M A Link  H i s t o r y  subtree
     -- --------------------------------------------------------------
     -- This section combines the 
     -- the IMA Link Interval Statistics subtree and
     -- the IMA Link Total Statistics subtree.
     -- It consists of a single table:
     -- the IMA Link History Table.  
     -- 
     -- Selection the xldv20pmIntervalType min15 :
     -- the entries contain various statistics
     -- collected by each IMA link over the previous 24 hours of operation.
     --
     -- Selection the xldv20pmIntervalType day :
     -- The entries contain the cumulative sum
     -- of the various statistics collected by each IMA link for the 24 hour
     -- period preceding the current interval.
     --

     xldv20pmImaLinkHistoryTable OBJECT-TYPE
     -- info-IMPL:      V2.0->
     -- info-VERCTRL:   -
        SYNTAX        SEQUENCE OF Xldv20pmImaLinkHistoryEntry
        ACCESS        not-accessible
        STATUS        mandatory
        DESCRIPTION
             " This table contains the entries for the 15 min /one
             day-history data collection results for PMo objects 
             of  IMA Link interfaces. "
        --DEFAULT next-function-async     fsnPmIlhEntryNext
        --DEFAULT get-function-async      fsnPmIlhEntryGet
        ::= { xldv20pmPerformanceMonitoring 17 }

     xldv20pmImaLinkHistoryEntry OBJECT-TYPE
     -- info-IMPL:      V2.0->
     -- info-VERCTRL:   -
        SYNTAX        Xldv20pmImaLinkHistoryEntry
        ACCESS        not-accessible
        STATUS        mandatory
        DESCRIPTION
             " An entry describing the History Data Table for PMo 
             IMA groups. "
        INDEX { xldv20IfIndex,
                xldv20pmImaLinkHistoryIntervalType,
                xldv20pmImaLinkHistoryHistEntryNr }
        ::= { xldv20pmImaLinkHistoryTable 1 }

     Xldv20pmImaLinkHistoryEntry ::=
        SEQUENCE { xldv20pmImaLinkHistoryIntervalType    Xldv20pmIntervalType,
                   xldv20pmImaLinkHistoryHistEntryNr           INTEGER,
                   xldv20pmImaLinkHistorySuspectFlag     Xldv20pmSuspectType,
                   xldv20pmImaLinkHistoryPeriodEndTime         INTEGER,
                   xldv20pmImaLinkHistoryImaViolations            Gauge,
                   xldv20pmImaLinkHistoryOifAnomalies             Gauge,
                   xldv20pmImaLinkHistoryNeSevErroredSecs         Gauge,
                   xldv20pmImaLinkHistoryFeSevErroredSecs         Gauge,
                   xldv20pmImaLinkHistoryNeUnavailSecs            Gauge,
                   xldv20pmImaLinkHistoryFeUnavailSecs            Gauge,
                   xldv20pmImaLinkHistoryNeTxUnusableSecs         Gauge,
                   xldv20pmImaLinkHistoryNeRxUnusableSecs         Gauge,
                   xldv20pmImaLinkHistoryFeTxUnusableSecs         Gauge,
                   xldv20pmImaLinkHistoryFeRxUnusableSecs         Gauge,
                   xldv20pmImaLinkHistoryNeTxNumFailures          Gauge,
                   xldv20pmImaLinkHistoryNeRxNumFailures          Gauge
                 }

     xldv20pmImaLinkHistoryIntervalType OBJECT-TYPE
     -- info-VALUE:     min15(1), day(2)
     -- info-ROU:       GET db
     -- info-IMPL:      V2.0->
     -- info-VERCTRL:   -
        SYNTAX        Xldv20pmIntervalType
        ACCESS        read-only
        STATUS        mandatory
        DESCRIPTION
             " This type attribute is used to select between the
               15 min  or the day accumulation types. "
        ::= { xldv20pmImaLinkHistoryEntry 1 }

     xldv20pmImaLinkHistoryHistEntryNr OBJECT-TYPE
     -- info-VALUE:     1..96
     -- info-ROU:       GET db
     -- info-IMPL:      V2.0->
     -- info-VERCTRL:   -
        SYNTAX        INTEGER (1..96)
        ACCESS        read-only
        STATUS        mandatory
        DESCRIPTION
             " This attribute is used as index to address a history entry.
             Entry 1 is the most recent, entry 96 is 24 hours ago.
             The range of values is between 1 and xldv20pmImaLinkCurrentHistEntrySize . " 
        ::= { xldv20pmImaLinkHistoryEntry 2 }

     xldv20pmImaLinkHistorySuspectFlag OBJECT-TYPE
     -- info-VALUE:     reliable(1), suspect(2)
     -- info-ROU:       GET db
     -- info-IMPL:      V2.0->
     -- info-VERCTRL:   -
        SYNTAX        Xldv20pmSuspectType
        ACCESS        read-only
        STATUS        mandatory
        DESCRIPTION
             " This read-only attribute will be set to indicate that
               troubles arose during an interval and that the counter
               values are suspect and incomplete. "
        ::= { xldv20pmImaLinkHistoryEntry 3 }

     xldv20pmImaLinkHistoryPeriodEndTime OBJECT-TYPE
     -- info-VALUE:     0..2147483647
     -- info-ROU:       GET  db
     -- info-IMPL:      V2.0->
     -- info-VERCTRL:   -
        SYNTAX        INTEGER(0..2147483647)
        ACCESS        read-only
        STATUS        mandatory
        DESCRIPTION
             " Date/time at the end of the selected interval. "
        ::= { xldv20pmImaLinkHistoryEntry 4 }

     xldv20pmImaLinkHistoryImaViolations OBJECT-TYPE
     -- info-VALUE:     
     -- info-ROU:       GET db
     -- info-IMPL:      V2.0->
     -- info-VERCTRL:   -
        SYNTAX        Gauge
        ACCESS        read-only
        STATUS        mandatory
        DESCRIPTION
        "ICP violations: count of errored, invalid or missing ICP cells,
        except during SES-IMA or UAS-IMA conditions, 
        in one of the previous 96, individual 15 minute, intervals
        or the previous day.
        ATM Forum IMA v1.1, (R-125) and (O-26) in Section 12.2.2.2
        on page 77. "
      ::= { xldv20pmImaLinkHistoryEntry 5 }

     xldv20pmImaLinkHistoryOifAnomalies OBJECT-TYPE
     -- info-VALUE:     
     -- info-ROU:       GET db
     -- info-IMPL:      V2.0->
     -- info-VERCTRL:   -
        SYNTAX        Gauge
        ACCESS        read-only
        STATUS        mandatory
        DESCRIPTION
        "The number of OIF anomalies, except during SES-IMA or UAS-IMA
        conditions, at the near-end in one of the previous 96,
        individual 15 minute, intervals or the previous day.
        This is an optional attribute.
        ATM Forum IMA v1.1, (O-20) and (O-26) in Section 12.2.2.2
        on page 77"
      ::= { xldv20pmImaLinkHistoryEntry 6 }

     xldv20pmImaLinkHistoryNeSevErroredSecs OBJECT-TYPE
     -- info-VALUE:     
     -- info-ROU:       GET db
     -- info-IMPL:      V2.0->
     -- info-VERCTRL:   -
        SYNTAX        Gauge
        ACCESS        read-only
        STATUS        mandatory
        DESCRIPTION
        "Count of one second intervals containing >= 30% of the ICP cells
        counted as IV-IMAs, or one or more link defects (e.g., LOS, OOF/LOF,
        AIS, or LCD), LIF defects, or LODS defects, except during UAS-IMA
        condition, in one of the previous 96, individual 15 minute, intervals
        or the previous day.
        ATM Forum IMA v1.1, (R-126) and (O-26) in Section 12.2.2.2
        on page 77"
      ::= { xldv20pmImaLinkHistoryEntry 7 }

     xldv20pmImaLinkHistoryFeSevErroredSecs OBJECT-TYPE
     -- info-VALUE:     
     -- info-ROU:       GET db
     -- info-IMPL:      V2.0->
     -- info-VERCTRL:   -
        SYNTAX        Gauge
        ACCESS        read-only
        STATUS        mandatory
        DESCRIPTION
         "Count of unavailable seconds at near-end 
          in one of the previous 96, individual 15 minute, intervals
          or the previous day.
          Unavailability begins at the onset of 10 contiguous
          SES-IMA and ends at the onset of 10 contiguous seconds with no
          SES-IMA.
          ATM Forum IMA v1.1, (R-127) and (O-26) in Section 12.2.2.2 on page 77"
      ::= { xldv20pmImaLinkHistoryEntry 8 }

     xldv20pmImaLinkHistoryNeUnavailSecs OBJECT-TYPE
     -- info-VALUE:     
     -- info-ROU:       GET db
     -- info-IMPL:      V2.0->
     -- info-VERCTRL:   -
        SYNTAX        Gauge
        ACCESS        read-only
        STATUS        mandatory
        DESCRIPTION
        "Count of unavailable seconds at near-end
        in one of the previous 96, individual 15 minute, intervals
        or the previous day.
        Unavailability begins at the onset of 10 contiguous
        SES-IMA and ends at the onset of 10 contiguous seconds with no
        SES-IMA.
        ATM Forum IMA v1.1, (R-128) and (O-26) in Section 12.2.2.2
        on page 77 . "
      ::= { xldv20pmImaLinkHistoryEntry 9 }

     xldv20pmImaLinkHistoryFeUnavailSecs OBJECT-TYPE
     -- info-VALUE:     
     -- info-ROU:       GET db
     -- info-IMPL:      V2.0->
     -- info-VERCTRL:   -
        SYNTAX        Gauge
        ACCESS        read-only
        STATUS        mandatory
        DESCRIPTION
        "Count of unavailable seconds at far-end 
        in one of the previous 96, individual 15 minute, intervals
        or the previous day.
        Unavailability begins at the onset of 10 contiguous
        SES-IMA-FE and ends at the onset of 10 contiguous seconds with no
        SES-IMA-FE.
        ATM Forum IMA v1.1, (R-129) and (O-26) in Section 12.2.2.2
        on page 77 . "
      ::= { xldv20pmImaLinkHistoryEntry 10 }

     xldv20pmImaLinkHistoryNeTxUnusableSecs OBJECT-TYPE
     -- info-VALUE:     
     -- info-ROU:       GET db
     -- info-IMPL:      V2.0->
     -- info-VERCTRL:   -
        SYNTAX        Gauge
        ACCESS        read-only
        STATUS        mandatory
        DESCRIPTION
        "Tx Unusable seconds: count of Unusable seconds at the near-end
        Tx LSM in one of the previous 96, individual 15 minute, intervals
        or the previous day.
        ATM Forum IMA v1.1, (R-130) and (O-26) in Section 12.2.2.2
        on page 77. "
      ::= { xldv20pmImaLinkHistoryEntry 11 }

     xldv20pmImaLinkHistoryNeRxUnusableSecs OBJECT-TYPE
     -- info-VALUE:     
     -- info-ROU:       GET db
     -- info-IMPL:      V2.0->
     -- info-VERCTRL:   -
        SYNTAX        Gauge
        ACCESS        read-only
        STATUS        mandatory
        DESCRIPTION
        "Rx Unusable seconds: count of Unusable seconds at the near-end
        Rx LSM in one of the previous 96, individual 15 minute, intervals
        or the previous day.
        ATM Forum IMA v1.1, (R-131) and (O-26) in Section 12.2.2.2
        on page 77. "
      ::= { xldv20pmImaLinkHistoryEntry 12 }

     xldv20pmImaLinkHistoryFeTxUnusableSecs OBJECT-TYPE
     -- info-VALUE:     
     -- info-ROU:       GET db
     -- info-IMPL:      V2.0->
     -- info-VERCTRL:   -
        SYNTAX        Gauge
        ACCESS        read-only
        STATUS        mandatory
        DESCRIPTION
        "Tx Unusable seconds: count of Unusable seconds at the far-end
        Tx LSM in one of the previous 96, individual 15 minute, intervals
        or the previous day.
        ATM Forum IMA v1.1, (R-132) and (O-26) in Section 12.2.2.2
        on page 77. "
      ::= { xldv20pmImaLinkHistoryEntry 13 }

     xldv20pmImaLinkHistoryFeRxUnusableSecs OBJECT-TYPE
     -- info-VALUE:     
     -- info-ROU:       GET db
     -- info-IMPL:      V2.0->
     -- info-VERCTRL:   -
        SYNTAX        Gauge
        ACCESS        read-only
        STATUS        mandatory
        DESCRIPTION
        "Rx Unusable seconds: count of Unusable seconds at the far-end
        Rx LSM in one of the previous 96, individual 15 minute, intervals
        or the previous day.
        ATM Forum IMA v1.1, (R-133) and (O-26) in Section 12.2.2.2
        on page 77. "
      ::= { xldv20pmImaLinkHistoryEntry 14 }

     xldv20pmImaLinkHistoryNeTxNumFailures OBJECT-TYPE
     -- info-VALUE:     
     -- info-ROU:       GET db
     -- info-IMPL:      V2.0->
     -- info-VERCTRL:   -
        SYNTAX        Gauge
        ACCESS        read-only
        STATUS        mandatory
        DESCRIPTION
        "The number of times a near-end transmit failure alarm condition
        has been entered on this link (i.e., some form of implementation
        specific transmit fault) in one of the previous 96,
        individual 15 minute, intervals or the previous day.
        ATM Forum IMA v1.1, (R-134) and (O-26) in Section 12.2.2.2
        on page 77"
     ::= { xldv20pmImaLinkHistoryEntry 15 }

     xldv20pmImaLinkHistoryNeRxNumFailures OBJECT-TYPE
     -- info-VALUE:     
     -- info-ROU:       GET db
     -- info-IMPL:      V2.0->
     -- info-VERCTRL:   -
        SYNTAX        Gauge
        ACCESS        read-only
        STATUS        mandatory
        DESCRIPTION
        "The number of times a near-end receive failure alarm condition
        has been entered on this link (i.e., LIF, LODS, RFI-IMA, Mis-Connected,
        or some form of implementation specific receive fault)
        in one of the previous 96, individual 15 minute, intervals
        or the previous day.
        ATM Forum IMA v1.1, (R-135) and (O-26) in Section 12.2.2.2
        on page 77"
     ::= { xldv20pmImaLinkHistoryEntry 16 }

     -- ==============================================================
     --         P r o t o c o l   M o n i t o r i n g  (PrM)
     --                         g r o u p
     -- ==============================================================

     -- --------------------------------------------------------------
     --    PrM  T C - A d a p t o r  C u r r e n t  D a t a  Table
     -- --------------------------------------------------------------

     xldv20pmTcaPrMCurrentTable OBJECT-TYPE
     -- info-IMPL:      V2.0-> 
     -- info-VERCTRL:   -
        SYNTAX        SEQUENCE OF Xldv20pmTcaPrMCurrentEntry
        ACCESS        not-accessible
        STATUS        mandatory
        DESCRIPTION
             " This table contains the entries for the PrM object at
               the following tca layer locations:
                - STM1 interface (in downstream direction)
                - STS3-c interface (in downstream direction)
                - E3 interface (in downstream direction)
                - DS3 interface (in downstream direction)
                - SU_AD16 interfaces (in upstream stream direction).
               PrM also possible at IMA groups.
               It includes attributes for performance parameters,
               collection interval is 15 min /one day . "
        --DEFAULT test-function-async     fsnTcEntryTest
        --DEFAULT next-function-async     fsnTcEntryNext
        --DEFAULT set-function-async      fsnTcEntrySet
        --DEFAULT get-function-async      fsnTcEntryGet
        ::= { xldv20pmProtocolMonitoring 1 }

     xldv20pmTcaPrMCurrentEntry OBJECT-TYPE
     -- info-IMPL:      V2.0-> 
     -- info-VERCTRL:   -
        SYNTAX        Xldv20pmTcaPrMCurrentEntry
        ACCESS        not-accessible
        STATUS        mandatory
        DESCRIPTION
             " An entry describing the TC-Adaptor Current Data Table
               . "
        INDEX { xldv20IfIndex,
                xldv20pmTcIntervalType }
        ::= { xldv20pmTcaPrMCurrentTable 1 }

     Xldv20pmTcaPrMCurrentEntry ::=
        SEQUENCE { xldv20pmTcIntervalType     Xldv20pmIntervalType,
                   xldv20pmTcAdminState       Xldv20AdminState,
                   xldv20pmTcSuspectFlag      Xldv20pmSuspectType,
                   xldv20pmTcHistEntrySize            INTEGER,
                   xldv20pmTcNrHistEntriesAvailable   INTEGER,
                   xldv20pmTcElapsedTime              INTEGER,
                   xldv20pmTcThresholdLimitIndex      INTEGER,
                   xldv20pmTcDiscardedCells           Counter }

     xldv20pmTcIntervalType OBJECT-TYPE
     -- info-VALUE:     min15(1), day(2)
     -- info-ROU:       GET db
     -- info-IMPL:      V2.0-> 
     -- info-VERCTRL:   -
        SYNTAX        Xldv20pmIntervalType
        ACCESS        read-only
        STATUS        mandatory
        DESCRIPTION
             " This nac type attribute is used to select between the
               15 min  or the day accumulation types. "
        ::= { xldv20pmTcaPrMCurrentEntry 1 }

     xldv20pmTcAdminState OBJECT-TYPE
     -- info-VALUE:     unlocked(1), locked(2)
     -- info-ROU:       GET db  SET pm
     -- info-IMPL:      V2.0-> 
     -- info-VERCTRL:   -
        SYNTAX        Xldv20AdminState
        ACCESS        read-write
        STATUS        mandatory
        DESCRIPTION
             " This read-write attribute is used to activate (unlock)
               and deactivate (lock) the functions (incl. collection)
               performed by this managed entity.
               Note: the 15min  collection object must be activated,
                     before day collection can operate. "
        ::= { xldv20pmTcaPrMCurrentEntry 2 }

     xldv20pmTcSuspectFlag OBJECT-TYPE
     -- info-VALUE:     reliable(1), suspect(2)
     -- info-ROU:       GET db
     -- info-IMPL:      V2.0-> 
     -- info-VERCTRL:   -
        SYNTAX        Xldv20pmSuspectType
        ACCESS        read-only
        STATUS        mandatory
        DESCRIPTION
             " This read-only attribute will be set to indicate that
               troubles arose during an interval and that the counter
               values are suspect and incomplete. "
        ::= { xldv20pmTcaPrMCurrentEntry 3 }

     xldv20pmTcHistEntrySize OBJECT-TYPE
     -- info-VALUE:     1..96
     -- info-ROU:       GET db
     -- info-IMPL:      V2.0-> 
     -- info-VERCTRL:   -
        SYNTAX        INTEGER (1..96)
        ACCESS        read-only
        STATUS        mandatory
        DESCRIPTION
             " This read-only attribute indicates the number of 15min 
               history entries configured for the particular interface.
               The default value is 1 and means that at least one 
               history entry is provided. "
        ::= { xldv20pmTcaPrMCurrentEntry 4 }

     xldv20pmTcNrHistEntriesAvailable OBJECT-TYPE
     -- info-VALUE:     0..96
     -- info-ROU:       GET db
     -- info-IMPL:      V2.0-> 
     -- info-VERCTRL:   -
        SYNTAX        INTEGER (0..96)
        ACCESS        read-only
        STATUS        mandatory
        DESCRIPTION
             " This read-only attribute indicates how many HistEntries
               are already available.
               The range of values is between 0 and xldv20pmTcHistEntrySize,
               thereby 0 means that this entry is not valid . "
        ::= { xldv20pmTcaPrMCurrentEntry 5 }

     xldv20pmTcElapsedTime OBJECT-TYPE
     -- info-VALUE:     0..900 (sec) for min15,
     -- info-VALUE:     0..1440 (min) for day
     -- info-ROU:       GET db
     -- info-IMPL:      V2.0-> 
     -- info-VERCTRL:   -
        SYNTAX        INTEGER (0..1440)
        ACCESS        read-only
        STATUS        mandatory
        DESCRIPTION
             " This read-only attribute represents the difference
               between the current time and the start of the present
               summary interval.
	       Units are seconds when 15 minute interval is selected 
	       or minutes for day interval.
               (Note: accurate to the sample time interval). "
        ::= { xldv20pmTcaPrMCurrentEntry 6 }

     xldv20pmTcThresholdLimitIndex OBJECT-TYPE
     -- info-VALUE:     1..30
     -- info-ROU:       GET db  SET pm
     -- info-IMPL:      V2.0-> 
     -- info-VERCTRL:   -
        SYNTAX        INTEGER (1..30)
        ACCESS        read-write
        STATUS        mandatory
        DESCRIPTION
             " This read-write attribute provides an index to the
               ThresholdLimitTable managed entity that contains the
               threshold limits for the performance parameters reported
               by this managed entity.
               When the value of this attribute is set to 1, default
               threshold limits shall be used. These default values are
               not part of the threshold limit table but are hard coded
               in the application SW of PM. "
        ::= { xldv20pmTcaPrMCurrentEntry 7 }

     xldv20pmTcDiscardedCells OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a counter of the
               number of ATM cells discarded at this interface, due to
               a HEC violation, since the start of this interval . "
        ::= { xldv20pmTcaPrMCurrentEntry 8 }


     -- --------------------------------------------------------------
     --    PrM  T C - A d a p t o r  H i s t o r y  D a t a  Table
     -- --------------------------------------------------------------

     xldv20pmTcaPrMHistoryTable OBJECT-TYPE
     -- info-IMPL:      V2.0-> 
     -- info-VERCTRL:   -
        SYNTAX        SEQUENCE OF Xldv20pmTcaPrMHistoryEntry
        ACCESS        not-accessible
        STATUS        mandatory
        DESCRIPTION
             " This table contains the entries for the PrM history
               object at the different tca layer locations. It contains
               results that are overtaken from the TcaPrMCurrentTable
               PM-object at the end of a 15 min /day interval . "
        --DEFAULT next-function-async     fsnThEntryNext
        --DEFAULT get-function-async      fsnThEntryGet
        ::= { xldv20pmProtocolMonitoring 2 }

     xldv20pmTcaPrMHistoryEntry OBJECT-TYPE
     -- info-ROU:       GET  SET [db,pm]
     -- info-IMPL:      V2.0-> 
     -- info-VERCTRL:   -
        SYNTAX        Xldv20pmTcaPrMHistoryEntry
        ACCESS        not-accessible
        STATUS        mandatory
        DESCRIPTION
             " An entry describing the TC-Adaptor History Data Table
               . "
        INDEX { xldv20IfIndex,
                xldv20pmThIntervalType,
                xldv20pmThHistEntryNr }
        ::= { xldv20pmTcaPrMHistoryTable 1 }

     Xldv20pmTcaPrMHistoryEntry ::=
        SEQUENCE { xldv20pmThIntervalType     Xldv20pmIntervalType,
                   xldv20pmThHistEntryNr      INTEGER,
                   xldv20pmThSuspectFlag      Xldv20pmSuspectType,
                   xldv20pmThPeriodEndTime    INTEGER,
                   xldv20pmThDiscardedCells   Counter }

     xldv20pmThIntervalType OBJECT-TYPE
     -- info-VALUE:     min15(1), day(2)
     -- info-ROU:       GET db
     -- info-IMPL:      V2.0-> 
     -- info-VERCTRL:   -
        SYNTAX        Xldv20pmIntervalType
        ACCESS        read-only
        STATUS        mandatory
        DESCRIPTION
             " This type attribute is used to select between the
               15 min  or the day accumulation types. "
        ::= { xldv20pmTcaPrMHistoryEntry 1 }

     xldv20pmThHistEntryNr OBJECT-TYPE
     -- info-VALUE:     1..96
     -- info-ROU:       GET db
     -- info-IMPL:      V2.0-> 
     -- info-VERCTRL:   -
        SYNTAX        INTEGER (1..96)
        ACCESS        read-only
        STATUS        mandatory
        DESCRIPTION
             " This attribute is used as index to address a history entry.
             Entry 1 is the most recent, entry 96 is 24 hours ago.
             The range of values is between 1 and xldv20pmTcHistEntrySize. " 
        ::= { xldv20pmTcaPrMHistoryEntry 2 }

     xldv20pmThSuspectFlag OBJECT-TYPE
     -- info-VALUE:     reliable(1), suspect(2)
     -- info-ROU:       GET db
     -- info-IMPL:      V2.0-> 
     -- info-VERCTRL:   -
        SYNTAX        Xldv20pmSuspectType
        ACCESS        read-only
        STATUS        mandatory
        DESCRIPTION
             " This read-only attribute will be set to indicate that
               troubles arose during an interval and that the counter
               values are suspect and incomplete. "
        ::= { xldv20pmTcaPrMHistoryEntry 3 }

     xldv20pmThPeriodEndTime OBJECT-TYPE
     -- info-VALUE:     0..2147483647
     -- info-ROU:       GET  db
     -- info-IMPL:      V2.0-> 
     -- info-VERCTRL:   -
        SYNTAX        INTEGER(0..2147483647)
        ACCESS        read-only
        STATUS        mandatory
        DESCRIPTION
             " This read-only attribute is a record of date/time at the
               end of an interval . "
        ::= { xldv20pmTcaPrMHistoryEntry 4 }

     xldv20pmThDiscardedCells OBJECT-TYPE
     -- info-VALUE:     -
     -- info-ROU:       GET db
     -- info-IMPL:      V2.0-> 
     -- info-VERCTRL:   -
        SYNTAX        Counter
        ACCESS        read-only
        STATUS        mandatory
        DESCRIPTION
             " This read-only attribute represents a set of history
               counter of the number of ATM cells discarded at this
               interface, due to a HEC violation, since the start of
               this interval . "
        ::= { xldv20pmTcaPrMHistoryEntry 5 }


     -- ==============================================================
     --          P e r f o r m a n c e   M a n a g e m e n t
     --              T h r e s h o l d i n g   g r o u p
     -- ==============================================================

     -- --------------------------------------------------------------
     --           Thresholding Table for PM on Physical layer
     --           (all Interfaces)
     -- --------------------------------------------------------------

     xldv20pmThresholdLimitTable OBJECT-TYPE
     -- info-IMPL:      V2.0-> 
     -- info-VERCTRL:   -
        SYNTAX        SEQUENCE OF Xldv20pmThresholdLimitEntry
        ACCESS        not-accessible
        STATUS        mandatory
        DESCRIPTION
             " The threshold limit table for all interface. 
               This table associates threshold limit index/PM counter
               pairs with threshold limit values for a 15 minutes
               interval. Entries with same threshold limit index
               belong to the same threshold limit profile.
               Each of the following TC-adaptor types are available
               and can be configured: adc, s1n, s3n, d3n, e3n.
               A crossing of a threshold limit leads to a 
               threshold crossing alert. "
        --DEFAULT test-function-async     fsnPmThlEntryTest
        --DEFAULT next-function-async     fsnPmThlEntryNext
        --DEFAULT set-function-async      fsnPmThlEntrySet
        --DEFAULT get-function-async      fsnPmThlEntryGet
        ::= { xldv20pmThresholding 1 }

     xldv20pmThresholdLimitEntry OBJECT-TYPE
     -- info-IMPL:      V2.0-> 
     -- info-VERCTRL:   -
        SYNTAX        Xldv20pmThresholdLimitEntry
        ACCESS        not-accessible
        STATUS        mandatory
        DESCRIPTION
             " An entry describing the threshold limit information . "
        INDEX { xldv20pmThlThresholdLimitIndex }
        ::= { xldv20pmThresholdLimitTable 1 }

     Xldv20pmThresholdLimitEntry ::=
        SEQUENCE { xldv20pmThlThresholdLimitIndex          INTEGER,
            xldv20pmThlNeBackgroundBlockErrors             INTEGER, -- s1f, adc, e3n
            xldv20pmThlNeCodeViolations                    INTEGER, -- s3n
            xldv20pmThlNeCodeViolationsCP                  INTEGER, -- d3n
            xldv20pmThlNeCodeViolationsP                   INTEGER, -- d3n
            xldv20pmThlNeCodeViolationsPLCP                INTEGER, -- d3n
            xldv20pmThlNeErroredSeconds                    INTEGER, -- adc, e3n
            xldv20pmThlNeErroredSecondsCP                  INTEGER, -- d3n
            xldv20pmThlNeErroredSecondsPLCP                INTEGER, -- d3n
            xldv20pmThlNeSas                               INTEGER, -- d3n
            xldv20pmThlNeSeverelyErroredFrameSeconds       INTEGER, -- s3n
            xldv20pmThlNeSeverelyErroredSeconds            INTEGER, -- s1n, s3n, adc, e3n
            xldv20pmThlNeSeverelyErroredSecondsCP          INTEGER, -- d3n
            xldv20pmThlNeSeverelyErroredSecondsPLCP        INTEGER, -- d3n
            xldv20pmThlNeUnavailableSeconds                INTEGER, -- s1n, s3n, d3n, adc, e3n
            xldv20pmThlNeUnavailableSecondsPLCP            INTEGER, -- s3n
            xldv20pmThlNeAisSeconds                        INTEGER, -- s1n
            xldv20pmThlNeOfsSeconds                        INTEGER, -- s1n
            xldv20pmThlNeLosSeconds                        INTEGER, -- s1n
            xldv20pmThlFeBackgroundBlockErrors             INTEGER, -- s1f, adc, e3f
            xldv20pmThlFeCodeViolations                    INTEGER, -- s3f
            xldv20pmThlFeCodeViolationsCP                  INTEGER, -- d3f
            xldv20pmThlFeCodeViolationsPLCP                INTEGER, -- d3f
            xldv20pmThlFeErroredSeconds                    INTEGER, -- s1f, s3f, adr, e3f
            xldv20pmThlFeErroredSecondsCP                  INTEGER, -- d3f
            xldv20pmThlFeErroredSecondsPLCP                INTEGER, -- d3f
            xldv20pmThlFeSas                               INTEGER, -- d3f
            xldv20pmThlFeSeverelyErroredSeconds            INTEGER, -- s1f, s3f, adr, e3f
            xldv20pmThlFeSeverelyErroredSecondsCP          INTEGER, -- d3f
            xldv20pmThlFeSeverelyErroredSecondsPLCP        INTEGER, -- d3f
            xldv20pmThlFeUnavailableSeconds                INTEGER, -- s1f, s3f, adr, e3f
            xldv20pmThlFeUnavailableSecondsPLCP            INTEGER, -- d3f
            xldv20pmThlDiscardedCells                      INTEGER, -- tca
            xldv20pmThlImaGroupUnavailSecs                 INTEGER, -- IMA group
            xldv20pmThlImaGroupNeNumFailures               INTEGER, -- IMA group
            xldv20pmThlImaLinkImaViolations                INTEGER, -- IMA link
            xldv20pmThlImaLinkOifAnomalies                 INTEGER, -- IMA link
            xldv20pmThlImaLinkNeSevErroredSecs             INTEGER, -- IMA link
            xldv20pmThlImaLinkFeSevErroredSecs             INTEGER, -- IMA link
            xldv20pmThlImaLinkNeUnavailSecs                INTEGER, -- IMA link
            xldv20pmThlImaLinkFeUnavailSecs                INTEGER, -- IMA link
            xldv20pmThlImaLinkNeTxUnusableSecs             INTEGER, -- IMA link
            xldv20pmThlImaLinkNeRxUnusableSecs             INTEGER, -- IMA link
            xldv20pmThlImaLinkFeTxUnusableSecs             INTEGER, -- IMA link
            xldv20pmThlImaLinkFeRxUnusableSecs             INTEGER, -- IMA link
            xldv20pmThlImaLinkNeTxNumFailures              INTEGER, -- IMA link
            xldv20pmThlImaLinkNeRxNumFailures              INTEGER -- IMA link
                   }

     xldv20pmThlThresholdLimitIndex OBJECT-TYPE
     -- info-VALUE:     1..30
     -- info-ROU:       GET  db
     -- info-IMPL:      V2.0-> 
     -- info-VERCTRL:   -
        SYNTAX        INTEGER (1..30)
        ACCESS        read-only
        STATUS        mandatory
        DESCRIPTION
             " This read-only attribute selects a profile out of the
               threshold limit table . "
        ::= { xldv20pmThresholdLimitEntry 1 }

     xldv20pmThlNeBackgroundBlockErrors OBJECT-TYPE
     -- info-VALUE:     0..2147483647
     -- info-ROU:       GET  db SET pm
     -- info-IMPL:      V2.0-> 
     -- info-VERCTRL:   -
        SYNTAX        INTEGER (0..2147483647)
        ACCESS        read-write
        STATUS        mandatory
        DESCRIPTION
             " This read-write attribute selects the threshold limit value
               of the counter in the current threshold limit profile. "
        ::= { xldv20pmThresholdLimitEntry 2 }

     xldv20pmThlNeCodeViolations OBJECT-TYPE
     -- info-VALUE:     0..2147483647
     -- info-ROU:       GET  db SET pm
     -- info-IMPL:      V2.0-> 
     -- info-VERCTRL:   -
        SYNTAX        INTEGER (0..2147483647)
        ACCESS        read-write
        STATUS        mandatory
        DESCRIPTION
             " This read-write attribute selects the threshold limit value
               of the counter in the current threshold limit profile. "
        ::= { xldv20pmThresholdLimitEntry 3 }

     xldv20pmThlNeCodeViolationsCP OBJECT-TYPE
     -- info-VALUE:     0..2147483647
     -- info-ROU:       GET  db SET pm
     -- info-IMPL:      V2.0-> 
     -- info-VERCTRL:   -
        SYNTAX        INTEGER (0..2147483647)
        ACCESS        read-write
        STATUS        mandatory
        DESCRIPTION
             " This read-write attribute selects the threshold limit value
               of the counter in the current threshold limit profile. "
        ::= { xldv20pmThresholdLimitEntry 4 }
     
     xldv20pmThlNeCodeViolationsP OBJECT-TYPE
     -- info-VALUE:     0..2147483647
     -- info-ROU:       GET  db SET pm
     -- info-IMPL:      V2.0-> 
     -- info-VERCTRL:   -
        SYNTAX        INTEGER (0..2147483647)
        ACCESS        read-write
        STATUS        mandatory
        DESCRIPTION
             " This read-write attribute selects the threshold limit value
               of the counter in the current threshold limit profile. "
        ::= { xldv20pmThresholdLimitEntry 5 }

     xldv20pmThlNeCodeViolationsPLCP OBJECT-TYPE
     -- info-VALUE:     0..2147483647
     -- info-ROU:       GET  db SET pm
     -- info-IMPL:      V2.0-> 
     -- info-VERCTRL:   -
        SYNTAX        INTEGER (0..2147483647)
        ACCESS        read-write
        STATUS        mandatory
        DESCRIPTION
             " This read-write attribute selects the threshold limit value
               of the counter in the current threshold limit profile. "
        ::= { xldv20pmThresholdLimitEntry 6 }

     xldv20pmThlNeErroredSeconds OBJECT-TYPE
     -- info-VALUE:     0..86400
     -- info-ROU:       GET  db SET pm
     -- info-IMPL:      V2.0-> 
     -- info-VERCTRL:   -
        SYNTAX        INTEGER (0..86400)
        ACCESS        read-write
        STATUS        mandatory
        DESCRIPTION
             " This read-write attribute selects the threshold limit value
               of the counter in the current threshold limit profile. "
        ::= { xldv20pmThresholdLimitEntry 7 }

     xldv20pmThlNeErroredSecondsCP OBJECT-TYPE
     -- info-VALUE:     0..86400
     -- info-ROU:       GET  db SET pm
     -- info-IMPL:      V2.0-> 
     -- info-VERCTRL:   -
        SYNTAX        INTEGER (0..86400)
        ACCESS        read-write
        STATUS        mandatory
        DESCRIPTION
             " This read-write attribute selects the threshold limit value
               of the counter in the current threshold limit profile. "
        ::= { xldv20pmThresholdLimitEntry 8 }

     xldv20pmThlNeErroredSecondsPLCP OBJECT-TYPE
     -- info-VALUE:     0..86400
     -- info-ROU:       GET  db SET pm
     -- info-IMPL:      V2.0-> 
     -- info-VERCTRL:   -
        SYNTAX        INTEGER (0..86400)
        ACCESS        read-write
        STATUS        mandatory
        DESCRIPTION
             " This read-write attribute selects the threshold limit value
               of the counter in the current threshold limit profile. "
        ::= { xldv20pmThresholdLimitEntry 9 }

     xldv20pmThlNeSas OBJECT-TYPE
     -- info-VALUE:     0..86400
     -- info-ROU:       GET  db SET pm
     -- info-IMPL:      V2.0-> 
     -- info-VERCTRL:   -
        SYNTAX        INTEGER (0..86400)
        ACCESS        read-write
        STATUS        mandatory
        DESCRIPTION
             " This read-write attribute selects the threshold limit value
               of the counter in the current threshold limit profile. "
        ::= { xldv20pmThresholdLimitEntry 10 }

     xldv20pmThlNeSeverelyErroredFrameSeconds OBJECT-TYPE
     -- info-VALUE:     0..86400
     -- info-ROU:       GET  db SET pm
     -- info-IMPL:      V2.0-> 
     -- info-VERCTRL:   -
        SYNTAX        INTEGER (0..86400)
        ACCESS        read-write
        STATUS        mandatory
        DESCRIPTION
             " This read-write attribute selects the threshold limit value
               of the counter in the current threshold limit profile. "
        ::= { xldv20pmThresholdLimitEntry 11 }

     xldv20pmThlNeSeverelyErroredSeconds OBJECT-TYPE
     -- info-VALUE:     0..86400
     -- info-ROU:       GET  db SET pm
     -- info-IMPL:      V2.0-> 
     -- info-VERCTRL:   -
        SYNTAX        INTEGER (0..86400)
        ACCESS        read-write
        STATUS        mandatory
        DESCRIPTION
             " This read-write attribute selects the threshold limit value
               of the counter in the current threshold limit profile. "
        ::= { xldv20pmThresholdLimitEntry 12 }

     xldv20pmThlNeSeverelyErroredSecondsCP OBJECT-TYPE
     -- info-VALUE:     0..86400
     -- info-ROU:       GET  db SET pm
     -- info-IMPL:      V2.0-> 
     -- info-VERCTRL:   -
        SYNTAX        INTEGER (0..86400)
        ACCESS        read-write
        STATUS        mandatory
        DESCRIPTION
             " This read-write attribute selects the threshold limit value
               of the counter in the current threshold limit profile. "
        ::= { xldv20pmThresholdLimitEntry 13 }

     xldv20pmThlNeSeverelyErroredSecondsPLCP OBJECT-TYPE
     -- info-VALUE:     0..86400
     -- info-ROU:       GET  db SET pm
     -- info-IMPL:      V2.0-> 
     -- info-VERCTRL:   -
        SYNTAX        INTEGER (0..86400)
        ACCESS        read-write
        STATUS        mandatory
        DESCRIPTION
             " This read-write attribute selects the threshold limit value
               of the counter in the current threshold limit profile. "
        ::= { xldv20pmThresholdLimitEntry 14 }
        
     xldv20pmThlNeUnavailableSeconds OBJECT-TYPE
     -- info-VALUE:     0..86400
     -- info-ROU:       GET  db SET pm
     -- info-IMPL:      V2.0-> 
     -- info-VERCTRL:   -
        SYNTAX        INTEGER (0..86400)
        ACCESS        read-write
        STATUS        mandatory
        DESCRIPTION
             " This read-write attribute selects the threshold limit value
               of the counter in the current threshold limit profile. "
        ::= { xldv20pmThresholdLimitEntry 15 }

     xldv20pmThlNeUnavailableSecondsPLCP OBJECT-TYPE
     -- info-VALUE:     0..86400
     -- info-ROU:       GET  db SET pm
     -- info-IMPL:      V2.0-> 
     -- info-VERCTRL:   -
        SYNTAX        INTEGER (0..86400)
        ACCESS        read-write
        STATUS        mandatory
        DESCRIPTION
             " This read-write attribute selects the threshold limit value
               of the counter in the current threshold limit profile. "
        ::= { xldv20pmThresholdLimitEntry 16 }

     xldv20pmThlNeAisSeconds OBJECT-TYPE
     -- info-VALUE:     0..86400
     -- info-ROU:       GET  db SET pm
     -- info-IMPL:      V2.0-> 
     -- info-VERCTRL:   -
        SYNTAX        INTEGER (0..86400)
        ACCESS        read-write
        STATUS        mandatory
        DESCRIPTION
             " This read-write attribute selects the threshold limit value
               of the counter in the current threshold limit profile. "
        ::= { xldv20pmThresholdLimitEntry 17 }

     xldv20pmThlNeOfsSeconds OBJECT-TYPE
     -- info-VALUE:     0..86400
     -- info-ROU:       GET  db SET pm
     -- info-IMPL:      V2.0-> 
     -- info-VERCTRL:   -
        SYNTAX        INTEGER (0..86400)
        ACCESS        read-write
        STATUS        mandatory
        DESCRIPTION
             " This read-write attribute selects the threshold limit value
               of the counter in the current threshold limit profile. "
        ::= { xldv20pmThresholdLimitEntry 18 }

     xldv20pmThlNeLosSeconds OBJECT-TYPE
     -- info-VALUE:     0..86400
     -- info-ROU:       GET  db SET pm
     -- info-IMPL:      V2.0-> 
     -- info-VERCTRL:   -
        SYNTAX        INTEGER (0..86400)
        ACCESS        read-write
        STATUS        mandatory
        DESCRIPTION
             " This read-write attribute selects the threshold limit value
               of the counter in the current threshold limit profile. "
        ::= { xldv20pmThresholdLimitEntry 19 }

     xldv20pmThlFeBackgroundBlockErrors OBJECT-TYPE
     -- info-VALUE:     0..2147483647
     -- info-ROU:       GET  db SET pm
     -- info-IMPL:      V2.0-> 
     -- info-VERCTRL:   -
        SYNTAX        INTEGER (0..2147483647)
        ACCESS        read-write
        STATUS        mandatory
        DESCRIPTION
             " This read-write attribute selects the threshold limit value
               of the counter in the current threshold limit profile. "
        ::= { xldv20pmThresholdLimitEntry 20 }

     xldv20pmThlFeCodeViolations OBJECT-TYPE
     -- info-VALUE:     0..2147483647
     -- info-ROU:       GET  db SET pm
     -- info-IMPL:      V2.0-> 
     -- info-VERCTRL:   -
        SYNTAX        INTEGER (0..2147483647)
        ACCESS        read-write
        STATUS        mandatory
        DESCRIPTION
             " This read-write attribute selects the threshold limit value
               of the counter in the current threshold limit profile. "
        ::= { xldv20pmThresholdLimitEntry 21 }

     xldv20pmThlFeCodeViolationsCP OBJECT-TYPE
     -- info-VALUE:     0..2147483647
     -- info-ROU:       GET  db SET pm
     -- info-IMPL:      V2.0-> 
     -- info-VERCTRL:   -
        SYNTAX        INTEGER (0..2147483647)
        ACCESS        read-write
        STATUS        mandatory
        DESCRIPTION
             " This read-write attribute selects the threshold limit value
               of the counter in the current threshold limit profile. "
        ::= { xldv20pmThresholdLimitEntry 22 }

     xldv20pmThlFeCodeViolationsPLCP OBJECT-TYPE
     -- info-VALUE:     0..2147483647
     -- info-ROU:       GET  db SET pm
     -- info-IMPL:      V2.0-> 
     -- info-VERCTRL:   -
        SYNTAX        INTEGER (0..2147483647)
        ACCESS        read-write
        STATUS        mandatory
        DESCRIPTION
             " This read-write attribute selects the threshold limit value
               of the counter in the current threshold limit profile. "
        ::= { xldv20pmThresholdLimitEntry 23 }

     xldv20pmThlFeErroredSeconds OBJECT-TYPE
     -- info-VALUE:     0..86400
     -- info-ROU:       GET  db SET pm
     -- info-IMPL:      V2.0-> 
     -- info-VERCTRL:   -
        SYNTAX        INTEGER (0..86400)
        ACCESS        read-write
        STATUS        mandatory
        DESCRIPTION
             " This read-write attribute selects the threshold limit value
               of the counter in the current threshold limit profile. "
        ::= { xldv20pmThresholdLimitEntry 24 }

     xldv20pmThlFeErroredSecondsCP OBJECT-TYPE
     -- info-VALUE:     0..86400
     -- info-ROU:       GET  db SET pm
     -- info-IMPL:      V2.0-> 
     -- info-VERCTRL:   -
        SYNTAX        INTEGER (0..86400)
        ACCESS        read-write
        STATUS        mandatory
        DESCRIPTION
             " This read-write attribute selects the threshold limit value
               of the counter in the current threshold limit profile. "
        ::= { xldv20pmThresholdLimitEntry 25 }

     xldv20pmThlFeErroredSecondsPLCP OBJECT-TYPE
     -- info-VALUE:     0..86400
     -- info-ROU:       GET  db SET pm
     -- info-IMPL:      V2.0-> 
     -- info-VERCTRL:   -
        SYNTAX        INTEGER (0..86400)
        ACCESS        read-write
        STATUS        mandatory
        DESCRIPTION
             " This read-write attribute selects the threshold limit value
               of the counter in the current threshold limit profile. "
        ::= { xldv20pmThresholdLimitEntry 26 }

     xldv20pmThlFeSas OBJECT-TYPE
     -- info-VALUE:     0..86400
     -- info-ROU:       GET  db SET pm
     -- info-IMPL:      V2.0-> 
     -- info-VERCTRL:   -
        SYNTAX        INTEGER (0..86400)
        ACCESS        read-write
        STATUS        mandatory
        DESCRIPTION
             " This read-write attribute selects the threshold limit value
               of the counter in the current threshold limit profile. "
        ::= { xldv20pmThresholdLimitEntry 27 }

     xldv20pmThlFeSeverelyErroredSeconds OBJECT-TYPE
     -- info-VALUE:     0..86400
     -- info-ROU:       GET  db SET pm
     -- info-IMPL:      V2.0-> 
     -- info-VERCTRL:   -
        SYNTAX        INTEGER (0..86400)
        ACCESS        read-write
        STATUS        mandatory
        DESCRIPTION
             " This read-write attribute selects the threshold limit value
               of the counter in the current threshold limit profile. "
        ::= { xldv20pmThresholdLimitEntry 28 }

     xldv20pmThlFeSeverelyErroredSecondsCP OBJECT-TYPE
     -- info-VALUE:     0..86400
     -- info-ROU:       GET  db SET pm
     -- info-IMPL:      V2.0-> 
     -- info-VERCTRL:   -
        SYNTAX        INTEGER (0..86400)
        ACCESS        read-write
        STATUS        mandatory
        DESCRIPTION
             " This read-write attribute selects the threshold limit value
               of the counter in the current threshold limit profile. "
        ::= { xldv20pmThresholdLimitEntry 29 }

     xldv20pmThlFeSeverelyErroredSecondsPLCP OBJECT-TYPE
     -- info-VALUE:     0..86400
     -- info-ROU:       GET  db SET pm
     -- info-IMPL:      V2.0-> 
     -- info-VERCTRL:   -
        SYNTAX        INTEGER (0..86400)
        ACCESS        read-write
        STATUS        mandatory
        DESCRIPTION
             " This read-write attribute selects the threshold limit value
               of the counter in the current threshold limit profile. "
        ::= { xldv20pmThresholdLimitEntry 30 }

     xldv20pmThlFeUnavailableSeconds OBJECT-TYPE
     -- info-VALUE:     0..86400
     -- info-ROU:       GET  db SET pm
     -- info-IMPL:      V2.0-> 
     -- info-VERCTRL:   -
        SYNTAX        INTEGER (0..86400)
        ACCESS        read-write
        STATUS        mandatory
        DESCRIPTION
             " This read-write attribute selects the threshold limit value
               of the counter in the current threshold limit profile. "
        ::= { xldv20pmThresholdLimitEntry 31 }

     xldv20pmThlFeUnavailableSecondsPLCP OBJECT-TYPE
     -- info-VALUE:     0..86400
     -- info-ROU:       GET  db SET pm
     -- info-IMPL:      V2.0-> 
     -- info-VERCTRL:   -
        SYNTAX        INTEGER (0..86400)
        ACCESS        read-write
        STATUS        mandatory
        DESCRIPTION
             " This read-write attribute selects the threshold limit value
               of the counter in the current threshold limit profile. "
        ::= { xldv20pmThresholdLimitEntry 32 }
        
     xldv20pmThlDiscardedCells OBJECT-TYPE
     -- info-VALUE:     0..2147483647
     -- info-ROU:       GET  db SET pm
     -- info-IMPL:      V2.0-> 
     -- info-VERCTRL:   -
        SYNTAX        INTEGER (0..2147483647)
        ACCESS        read-write
        STATUS        mandatory
        DESCRIPTION
             " This read-write attribute selects the threshold limit value
               of the counter in the current threshold limit profile. "
        ::= { xldv20pmThresholdLimitEntry 33 }

     xldv20pmThlImaGroupUnavailSecs OBJECT-TYPE
     -- info-VALUE:     0..2147483647
     -- info-ROU:       GET  db SET pm
     -- info-IMPL:      V2.0-> 
     -- info-VERCTRL:   -
        SYNTAX        INTEGER (0..2147483647)
        ACCESS        read-write
        STATUS        mandatory
        DESCRIPTION
             " This read-write attribute selects the threshold limit value
               of the counter in the current threshold limit profile.  "
        ::= { xldv20pmThresholdLimitEntry 34 }

     xldv20pmThlImaGroupNeNumFailures OBJECT-TYPE
     -- info-VALUE:     0..2147483647
     -- info-ROU:       GET  db SET pm
     -- info-IMPL:      V2.0-> 
     -- info-VERCTRL:   -
        SYNTAX        INTEGER (0..2147483647)
        ACCESS        read-write
        STATUS        mandatory
        DESCRIPTION
             " This read-write attribute selects the threshold limit value
               of the counter in the current threshold limit profile.  "
        ::= { xldv20pmThresholdLimitEntry 35 }

     xldv20pmThlImaLinkImaViolations OBJECT-TYPE
     -- info-VALUE:     0..2147483647
     -- info-ROU:       GET  db SET pm
     -- info-IMPL:      V2.0-> 
     -- info-VERCTRL:   -
        SYNTAX        INTEGER (0..2147483647)
        ACCESS        read-write
        STATUS        mandatory
        DESCRIPTION
             " This read-write attribute selects the threshold limit value
               of the counter in the current threshold limit profile.  "
        ::= { xldv20pmThresholdLimitEntry 36 }

     xldv20pmThlImaLinkOifAnomalies OBJECT-TYPE
     -- info-VALUE:     0..2147483647
     -- info-ROU:       GET  db SET pm
     -- info-IMPL:      V2.0-> 
     -- info-VERCTRL:   -
        SYNTAX        INTEGER (0..2147483647)
        ACCESS        read-write
        STATUS        mandatory
        DESCRIPTION
             " This read-write attribute selects the threshold limit value
               of the counter in the current threshold limit profile.  "
        ::= { xldv20pmThresholdLimitEntry 37 }

     xldv20pmThlImaLinkNeSevErroredSecs OBJECT-TYPE
     -- info-VALUE:     0..2147483647
     -- info-ROU:       GET  db SET pm
     -- info-IMPL:      V2.0-> 
     -- info-VERCTRL:   -
        SYNTAX        INTEGER (0..2147483647)
        ACCESS        read-write
        STATUS        mandatory
        DESCRIPTION
             " This read-write attribute selects the threshold limit value
               of the counter in the current threshold limit profile.  "
        ::= { xldv20pmThresholdLimitEntry 38 }

     xldv20pmThlImaLinkFeSevErroredSecs OBJECT-TYPE
     -- info-VALUE:     0..2147483647
     -- info-ROU:       GET  db SET pm
     -- info-IMPL:      V2.0-> 
     -- info-VERCTRL:   -
        SYNTAX        INTEGER (0..2147483647)
        ACCESS        read-write
        STATUS        mandatory
        DESCRIPTION
             " This read-write attribute selects the threshold limit value
               of the counter in the current threshold limit profile.  "
        ::= { xldv20pmThresholdLimitEntry 39 }

     xldv20pmThlImaLinkNeUnavailSecs OBJECT-TYPE
     -- info-VALUE:     0..2147483647
     -- info-ROU:       GET  db SET pm
     -- info-IMPL:      V2.0-> 
     -- info-VERCTRL:   -
        SYNTAX        INTEGER (0..2147483647)
        ACCESS        read-write
        STATUS        mandatory
        DESCRIPTION
             " This read-write attribute selects the threshold limit value
               of the counter in the current threshold limit profile.  "
        ::= { xldv20pmThresholdLimitEntry 40 }

     xldv20pmThlImaLinkFeUnavailSecs OBJECT-TYPE
     -- info-VALUE:     0..2147483647
     -- info-ROU:       GET  db SET pm
     -- info-IMPL:      V2.0-> 
     -- info-VERCTRL:   -
        SYNTAX        INTEGER (0..2147483647)
        ACCESS        read-write
        STATUS        mandatory
        DESCRIPTION
             " This read-write attribute selects the threshold limit value
               of the counter in the current threshold limit profile.  "
        ::= { xldv20pmThresholdLimitEntry 41 }

     xldv20pmThlImaLinkNeTxUnusableSecs OBJECT-TYPE
     -- info-VALUE:     0..2147483647
     -- info-ROU:       GET  db SET pm
     -- info-IMPL:      V2.0-> 
     -- info-VERCTRL:   -
        SYNTAX        INTEGER (0..2147483647)
        ACCESS        read-write
        STATUS        mandatory
        DESCRIPTION
             " This read-write attribute selects the threshold limit value
               of the counter in the current threshold limit profile.  "
        ::= { xldv20pmThresholdLimitEntry 42 }

     xldv20pmThlImaLinkNeRxUnusableSecs OBJECT-TYPE
     -- info-VALUE:     0..2147483647
     -- info-ROU:       GET  db SET pm
     -- info-IMPL:      V2.0-> 
     -- info-VERCTRL:   -
        SYNTAX        INTEGER (0..2147483647)
        ACCESS        read-write
        STATUS        mandatory
        DESCRIPTION
             " This read-write attribute selects the threshold limit value
               of the counter in the current threshold limit profile.  "
        ::= { xldv20pmThresholdLimitEntry 43 }

     xldv20pmThlImaLinkFeTxUnusableSecs OBJECT-TYPE
     -- info-VALUE:     0..2147483647
     -- info-ROU:       GET  db SET pm
     -- info-IMPL:      V2.0-> 
     -- info-VERCTRL:   -
        SYNTAX        INTEGER (0..2147483647)
        ACCESS        read-write
        STATUS        mandatory
        DESCRIPTION
             " This read-write attribute selects the threshold limit value
               of the counter in the current threshold limit profile.  "
        ::= { xldv20pmThresholdLimitEntry 44 }

     xldv20pmThlImaLinkFeRxUnusableSecs OBJECT-TYPE
     -- info-VALUE:     0..2147483647
     -- info-ROU:       GET  db SET pm
     -- info-IMPL:      V2.0-> 
     -- info-VERCTRL:   -
        SYNTAX        INTEGER (0..2147483647)
        ACCESS        read-write
        STATUS        mandatory
        DESCRIPTION
             " This read-write attribute selects the threshold limit value
               of the counter in the current threshold limit profile.  "
        ::= { xldv20pmThresholdLimitEntry 45 }

     xldv20pmThlImaLinkNeTxNumFailures OBJECT-TYPE
     -- info-VALUE:     0..2147483647
     -- info-ROU:       GET  db SET pm
     -- info-IMPL:      V2.0-> 
     -- info-VERCTRL:   -
        SYNTAX        INTEGER (0..2147483647)
        ACCESS        read-write
        STATUS        mandatory
        DESCRIPTION
             " This read-write attribute selects the threshold limit value
               of the counter in the current threshold limit profile.  "
        ::= { xldv20pmThresholdLimitEntry 46 }

     xldv20pmThlImaLinkNeRxNumFailures OBJECT-TYPE
     -- info-VALUE:     0..2147483647
     -- info-ROU:       GET  db SET pm
     -- info-IMPL:      V2.0-> 
     -- info-VERCTRL:   -
        SYNTAX        INTEGER (0..2147483647)
        ACCESS        read-write
        STATUS        mandatory
        DESCRIPTION
             " This read-write attribute selects the threshold limit value
               of the counter in the current threshold limit profile.  "
        ::= { xldv20pmThresholdLimitEntry 47 }

     -- --------------------------------------------------------------
     --           Thresholding Table for PM on ATM layer
     -- --------------------------------------------------------------

     xldv20pmAtmThresholdLimitTable OBJECT-TYPE
     -- info-IMPL:      V2.0-> 
     -- info-VERCTRL:   -
        SYNTAX        SEQUENCE OF Xldv20pmAtmThresholdLimitEntry
        ACCESS        not-accessible
        STATUS        mandatory
        DESCRIPTION
             " The threshold limit table for all interface. 
               This table associates threshold limit index/PM counter
               pairs with threshold limit values for a 15 minutes
               interval. Entries with same threshold limit index
               belong to the same threshold limit profile.
               A crossing of a threshold limit leads to a 
               threshold crossing alert. "
        --DEFAULT test-function-async     fsnPmAtlEntryTest
        --DEFAULT next-function-async     fsnPmAtlEntryNext
        --DEFAULT set-function-async      fsnPmAtlEntrySet
        --DEFAULT get-function-async      fsnPmAtlEntryGet
        ::= { xldv20pmThresholding 2 }

     xldv20pmAtmThresholdLimitEntry OBJECT-TYPE
     -- info-IMPL:      V2.0-> 
     -- info-VERCTRL:   -
        SYNTAX        Xldv20pmAtmThresholdLimitEntry
        ACCESS        not-accessible
        STATUS        mandatory
        DESCRIPTION
             " An entry describing the threshold limit information . "
        INDEX { xldv20pmAtlThresholdLimitIndex }
        ::= { xldv20pmAtmThresholdLimitTable 1 }

     Xldv20pmAtmThresholdLimitEntry ::=
        SEQUENCE { xldv20pmAtlThresholdLimitIndex      INTEGER,
                   xldv20pmAtlTransmittedUserCells     Unsigned32,
                   xldv20pmAtlLostUserCells            Unsigned32,
                   xldv20pmAtlMisinsertedUserCells     Unsigned32
		   }

     xldv20pmAtlThresholdLimitIndex OBJECT-TYPE
     -- info-VALUE:     1..30
     -- info-ROU:       GET  db
     -- info-IMPL:      V2.0-> 
     -- info-VERCTRL:   -
        SYNTAX        INTEGER (1..30)
        ACCESS        read-only
        STATUS        mandatory
        DESCRIPTION
             " This read-only attribute selects a profile out of the
               threshold limit table of PM on ATM layer. "
        ::= { xldv20pmAtmThresholdLimitEntry 1 }

     xldv20pmAtlTransmittedUserCells OBJECT-TYPE
     -- info-VALUE:     
     -- info-ROU:       GET db SET pm
     -- info-IMPL:      V2.0-> 
     -- info-VERCTRL:   
        SYNTAX        Unsigned32
        ACCESS        read-write
        STATUS        mandatory
        DESCRIPTION
             " This read-write attribute selects the threshold limit value
               of the counter in the current threshold limit profile. "
        ::= { xldv20pmAtmThresholdLimitEntry 2 }

     xldv20pmAtlLostUserCells OBJECT-TYPE
     -- info-VALUE:     
     -- info-ROU:       GET db SET pm
     -- info-IMPL:      V2.0-> 
     -- info-VERCTRL:   
        SYNTAX        Unsigned32
        ACCESS        read-write
        STATUS        mandatory
        DESCRIPTION
             " This read-write attribute selects the threshold limit value
               of the counter in the current threshold limit profile. "
        ::= { xldv20pmAtmThresholdLimitEntry 3 }

     xldv20pmAtlMisinsertedUserCells OBJECT-TYPE
     -- info-VALUE:     
     -- info-ROU:       GET db SET pm
     -- info-IMPL:      V2.0-> 
     -- info-VERCTRL:   
        SYNTAX        Unsigned32
        ACCESS        read-write
        STATUS        mandatory
        DESCRIPTION
             " This read-write attribute selects the threshold limit value
               of the counter in the current threshold limit profile. "
        ::= { xldv20pmAtmThresholdLimitEntry 4 }

     -- ==============================================================
     --          P e r f o r m a n c e   M a n a g e m e n t
     --                      T r a p   g r o u p
     -- ==============================================================

     xldv20pmTrapVars OBJECT IDENTIFIER ::= { xldv20pmTraps 1 }
     -- info-IMPL:      V2.0-> 


     -- --------------------------------------------------------------
     --            t r a p   v a r i a b l e s   g r o u p
     -- --------------------------------------------------------------

     xldv20pmTvIfIndex OBJECT-TYPE
     -- info-VALUE:     -
     -- info-IMPL:      V2.0-> 
        SYNTAX        Unsigned16
        ACCESS        not-accessible
        STATUS        mandatory
        DESCRIPTION
             " The interface index of the reporting PM object. "
        ::= { xldv20pmTrapVars 1 }

     xldv20pmTvPmType OBJECT-TYPE
     -- info-VALUE:    s1F1PMo(1), s1F2PMo(2),
     -- info-VALUE:    s1F3PMo(3), s3F1PMo(4), s3F2PMo(5),
     -- info-VALUE:    s3F3PMo(6), d3F2PMo(7), d3F3PMo(8),
     -- info-VALUE:    e3F3PMo(9), adcF3PMo(10),
     -- info-VALUE:    s1PrM(11), s3PrM(12), e3PrM(13),
     -- info-VALUE:    d3PrM(14), adcPrM(15),
     -- info-VALUE:    e1ImaPrM(16), d1ImaPrM(17),
     -- info-VALUE:    e1ImaPMo(18), d1ImaPMo(19),
     -- info-VALUE:    atmImaPMo(20)
     -- info-IMPL:     V2.0-> 
        SYNTAX        Xldv20pmType
        ACCESS        not-accessible
        STATUS        mandatory
        DESCRIPTION
             " Specifies the reporting PM object and OAM level. "
        ::= { xldv20pmTrapVars 2 }

     xldv20pmTvPmCounter OBJECT-TYPE
     -- info-VALUE:     neBackgroundBlockErrors
     -- info-VALUE:     neCodeViolations
     -- info-VALUE:     neCodeViolationsCP
     -- info-VALUE:     neCodeViolationsP
     -- info-VALUE:     neCodeViolationsPLCP
     -- info-VALUE:     neErroredSeconds
     -- info-VALUE:     neErroredSecondsCP
     -- info-VALUE:     neErroredSecondsPLCP
     -- info-VALUE:     neSeverelyErroredFrameSeconds
     -- info-VALUE:     neSeverelyErroredSeconds
     -- info-VALUE:     neSeverelyErroredSecondsCP
     -- info-VALUE:     neSeverelyErroredSecondsPLCP
     -- info-VALUE:     neUnavailableSeconds
     -- info-VALUE:     neUnavailableSecondsPLCP
     -- info-VALUE:     neAisSeconds
     -- info-VALUE:     neOfsSeconds
     -- info-VALUE:     neLosSeconds
     -- info-VALUE:     feBackgroundBlockErrors
     -- info-VALUE:     feCodeViolations
     -- info-VALUE:     feCodeViolationsCP
     -- info-VALUE:     feCodeViolationsPLCP
     -- info-VALUE:     feErroredSeconds
     -- info-VALUE:     feErroredSecondsCP
     -- info-VALUE:     feErroredSecondsPLCP
     -- info-VALUE:     feSas
     -- info-VALUE:     feSeverelyErroredSeconds
     -- info-VALUE:     feSeverelyErroredSecondsCP
     -- info-VALUE:     feSeverelyErroredSecondsPLCP
     -- info-VALUE:     feUnavailableSeconds
     -- info-VALUE:     feUnavailableSecondsPLCP
     -- info-VALUE:     discardedCells
     -- info-VALUE:     imaGroupUnavailSecs
     -- info-VALUE:     imaGroupNeNumFailures
     -- info-VALUE:     imaLinkImaViolations
     -- info-VALUE:     imaLinkOifAnomalies
     -- info-VALUE:     imaLinkNeSevErroredSecs
     -- info-VALUE:     imaLinkFeSevErroredSecs
     -- info-VALUE:     imaLinkNeUnavailSecs
     -- info-VALUE:     imaLinkFeUnavailSecs
     -- info-VALUE:     imaLinkNeTxUnusableSecs
     -- info-VALUE:     imaLinkNeRxUnusableSecs
     -- info-VALUE:     imaLinkFeTxUnusableSecs
     -- info-VALUE:     imaLinkFeRxUnusableSecs
     -- info-VALUE:     imaLinkNeTxNumFailures
     -- info-VALUE:     imaLinkNeRxNumFailures
     -- info-IMPL:      V2.0-> 
        SYNTAX        Xldv20pmCounterName
        ACCESS        not-accessible
        STATUS        mandatory
        DESCRIPTION
             " Identifies the PM counter. "
        ::= { xldv20pmTrapVars 3 }

     xldv20pmTvCurrentCounterValue OBJECT-TYPE
     -- info-VALUE:     -
     -- info-IMPL:      V2.0-> 
        SYNTAX        Counter
        ACCESS        not-accessible
        STATUS        mandatory
        DESCRIPTION
             " The actual counter value at detection. "
        ::= { xldv20pmTrapVars 4 }

     xldv20pmTvCurrentCounterLimit OBJECT-TYPE
     -- info-VALUE:     -
     -- info-IMPL:      V2.0-> 
        SYNTAX        Counter
        ACCESS        not-accessible
        STATUS        mandatory
        DESCRIPTION
             " The current value of threshold limit. "
        ::= { xldv20pmTrapVars 5 }

     xldv20pmTvAtmPmCounter OBJECT-TYPE
     -- info-VALUE:     -
     -- info-IMPL:      V2.0-> 
        SYNTAX        Xldv20pmAtmCounterType
        ACCESS        not-accessible
        STATUS        mandatory
        DESCRIPTION
             " Identifies the performance parameter. "
        ::= { xldv20pmTrapVars 6 }

     xldv20pmTvAtmObjectIndex OBJECT-TYPE
     -- info-VALUE:     -
     -- info-IMPL:      V2.0-> 
        SYNTAX        Unsigned16
        ACCESS        not-accessible
        STATUS        mandatory
        DESCRIPTION
             "Identifies the AtmPm object. "
        ::= { xldv20pmTrapVars 7 }

     xldv20pmTvEndpointType OBJECT-TYPE
     -- info-VALUE:     -
     -- info-IMPL:      V2.0-> 
        SYNTAX        Xldv20pmEndpointType
        ACCESS        not-accessible
        STATUS        mandatory
        DESCRIPTION
             "Identifies the type of endpoint. "
        ::= { xldv20pmTrapVars 8 }

     xldv20pmTvIntervalType OBJECT-TYPE
     -- info-VALUE:     -
     -- info-IMPL:      V2.0-> 
        SYNTAX        Xldv20pmIntervalType
        ACCESS        not-accessible
        STATUS        mandatory
        DESCRIPTION
             "Identifies the type of interval. "
        ::= { xldv20pmTrapVars 9 }


     -- --------------------------------------------------------------
     --                t r a p   t y p e s   g r o u p
     --                f o r  P M  o n  P h y s i c a l  L a y e r 
     -- --------------------------------------------------------------

     xldv20pmTrapTypes OBJECT IDENTIFIER ::= { xldv20pmTraps 2 }
     -- info-IMPL:      V2.0-> 

     xldv20pmTrThresholdCrossingAlert TRAP-TYPE
     -- info-TRAPTYPE:  event
     -- info-TRAPID:    200
     -- info-IMPL:      V2.0-> 
        ENTERPRISE xldv20Traps
        VARIABLES { xldv20TvTimeAndDate,
                    xldv20pmTvIfIndex,
                    xldv20pmTvPmType,
                    xldv20pmTvPmCounter,
                    xldv20pmTvIntervalType,
                    xldv20pmTvCurrentCounterValue,
                    xldv20pmTvCurrentCounterLimit }
        DESCRIPTION
             " Threshold crossing alert for PM on physical layer. "
        ::= 200


     -- --------------------------------------------------------------
     --                t r a p   t y p e s   g r o u p
     --                f o r  P M  o n  A T M  L a y e r 
     -- --------------------------------------------------------------

     xldv20pmTrAtmThresholdCrossingAlert TRAP-TYPE
     -- info-TRAPTYPE:  event
     -- info-TRAPID:    300
     -- info-IMPL:      V2.0-> 
        ENTERPRISE xldv20Traps 
        VARIABLES { xldv20TvTimeAndDate,
                    xldv20pmTvAtmObjectIndex,
                    xldv20pmTvAtmPmCounter,
                    xldv20pmTvIntervalType,
                    xldv20pmTvCurrentCounterValue,
                    xldv20pmTvCurrentCounterLimit
		    }
        DESCRIPTION
             " Threshold crossing alert for PM on ATM layer . "
        ::= 300


     xldv20pmTrAtmObjectCreation TRAP-TYPE
     -- info-TRAPTYPE:  event
     -- info-TRAPID:    302
     -- info-IMPL:      V2.0-> 
        ENTERPRISE xldv20Traps 
        VARIABLES { xldv20TvTimeAndDate,
                    xldv20pmTvAtmObjectIndex
		    }
        DESCRIPTION
             " An Atm object is created. "
        ::= 302
     
     xldv20pmTrAtmObjectDeletion TRAP-TYPE
     -- info-TRAPTYPE:  event
     -- info-TRAPID:    303
     -- info-IMPL:      V2.0-> 
        ENTERPRISE xldv20Traps 
        VARIABLES { xldv20TvTimeAndDate,
                    xldv20pmTvAtmObjectIndex
		    }
        DESCRIPTION
             " An Atm object is deleted. "
        ::= 303

     xldv20pmTrAtmEndpointObjectCreation TRAP-TYPE
     -- info-TRAPTYPE:  event
     -- info-TRAPID:    304
     -- info-IMPL:      V2.0-> 
        ENTERPRISE xldv20Traps 
        VARIABLES { xldv20TvTimeAndDate,
                    xldv20pmTvAtmObjectIndex,
                    xldv20pmTvEndpointType
		    }
        DESCRIPTION
             " An Atm endpoint object is created. "
        ::= 304
     
     xldv20pmTrAtmEndpointObjectDeletion TRAP-TYPE
     -- info-TRAPTYPE:  event
     -- info-TRAPID:    305
     -- info-IMPL:      V2.0-> 
        ENTERPRISE xldv20Traps 
        VARIABLES { xldv20TvTimeAndDate,
                    xldv20pmTvAtmObjectIndex,
                    xldv20pmTvEndpointType
		    }
        DESCRIPTION
             " An Atm endpoint object is deleted. "
        ::= 305
END
