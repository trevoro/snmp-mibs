-- 3COM NMC MIB 
-- MIB File Generated on 14-Dec-1998 at 16:10:10

NMC-MIB DEFINITIONS ::= BEGIN

IMPORTS
   enterprises,
   experimental,
   IpAddress,
   TimeTicks,
   Gauge,
   Counter
      FROM RFC1155-SMI
   DisplayString
      FROM RFC1213-MIB
   OBJECT-TYPE
      FROM RFC-1212;


usr OBJECT IDENTIFIER ::= { enterprises 429 }

nas OBJECT IDENTIFIER ::= { usr 1 }

nmc OBJECT IDENTIFIER ::= { nas 2 }

-- The NAS Network Management Card Configuration Group.

nmcCfg OBJECT IDENTIFIER ::= { nmc 1 }

nmcCfgSystemTime OBJECT-TYPE
SYNTAX DisplayString (SIZE(0..8))
ACCESS read-write
STATUS mandatory
DESCRIPTION
"This parameter is used to set and read the current time as 
kept by the NMC's real-time clock.  It should be set to the 
local time in the place where the chassis is physically 
located.  The real-time clock has the capability of 
maintaining correct time for short durations without power."
::= { nmcCfg 1 }

nmcCfgSystemDate OBJECT-TYPE
SYNTAX DisplayString (SIZE(0..8))
ACCESS read-write
STATUS mandatory
DESCRIPTION
"This parameter is used to set and read the current date as 
kept by the NMC's real-time clock.  It should be set to the 
local date where the chassis is physically located."
::= { nmcCfg 2 }

nmcGmtime OBJECT-TYPE
SYNTAX INTEGER
ACCESS read-only
STATUS mandatory
DESCRIPTION
"This object reflects the current time in Greenwich Mean 
Time (GMT).  The value of this object is sent in USR's 
enterprise specific SNMP trap messages for use by the 
receiving Management Stations."
::= { nmcCfg 3 }

nmcTimezone OBJECT-TYPE
SYNTAX INTEGER{
  easternUSA-gmtMinus5(1),
  centralUSA-gmtMinus6(2),
  mountainUSA-gmtMinus7(3),
  pacificUSA-gmtMinus8(4),
  gmtMinus9(5),
  gmtMinus10(6),
  gmtMinus11(7),
  gmtMinus12(8),
  gmtPlus12(9),
  gmtPlus11(10),
  gmtPlus10(11),
  gmtPlus9(12),
  gmtPlus8(13),
  gmtPlus7(14),
  gmtPlus6(15),
  gmtPlus5(16),
  gmtPlus4(17),
  gmtPlus3(18),
  gmtPlus2(19),
  gmtPlus1(20),
  gmt(21),
  gmtMinus1(22),
  gmtMinus2(23),
  gmtMinus3(24),
  gmtMinus4(25),
  newfoundland-gmtMinus3-30(26),
  tehran-gmtPlus3-30(27),
  kabul-gmtPlus4-30(28),
  bombay-gmtPlus5-30(29),
  adelaide-gmtPlus9-30(30)
}
ACCESS read-write
STATUS mandatory
DESCRIPTION
"This object should be set to reflect the timezone in which 
the chassis is physically located.  It is used in the 
conversion from local time to Greenwich Mean Time (GMT).  
The timezones are named for the number of hours by which 
GMT differs from local time.
Default=gmtPlus0(21)."
::= { nmcCfg 4 }

nmcCfgAuthFailTrapEnable OBJECT-TYPE
SYNTAX INTEGER{
  enable(1),
  disable(2)
}
ACCESS read-write
STATUS mandatory
DESCRIPTION
"This object indicates whether or not the SNMP Proxy Agent 
running in the Network Management Card is to send a trap 
upon reception of an SNMP message that was not properly 
authenticated.  MIB-I and II require a mechanism for 
enabling/disabling generation of this trap."
::= { nmcCfg 5 }

nmcDaySavingTime OBJECT-TYPE
SYNTAX INTEGER{
  enable(1),
  disable(2)
}
ACCESS read-write
STATUS mandatory
DESCRIPTION
"The value of this object determines whether or not the NMC 
will honor daylight savings time when converting from local 
time to Greenwich Mean Time (GMT)."
::= { nmcCfg 6 }

nmcCfgWanDialOutPhoneNum OBJECT-TYPE
SYNTAX DisplayString (SIZE(0..39))
ACCESS read-write
STATUS mandatory
DESCRIPTION
"This is the phone number that the NMC will use to dial a 
modem that is connected to the WAN port if there is no 
existing connection when the NMC tries to send and IP 
datagram out that port."
::= { nmcCfg 7 }

nmcCfgAtString OBJECT-TYPE
SYNTAX DisplayString (SIZE(0..39))
ACCESS read-write
STATUS mandatory
DESCRIPTION
"This object is the user defined AT string that will be used 
to configure a modem connected to the NMC's WAN port if the 
NMC needs to dial out to make a connection."
::= { nmcCfg 8 }

nmcPowerUpAutoCfgEnable OBJECT-TYPE
SYNTAX INTEGER{
  enable(1),
  disable(2)
}
ACCESS read-write
STATUS mandatory
DESCRIPTION
"This parameter defines whether or not to automatically 
configure cards when they are inserted into the chassis or 
when the chassis is powered on.  If set to do the 
autoconfigure, the values used to configure the cards will 
be those that were last saved to the NMC's NVRAM.  For 
cards that do not match the values in NVRAM, those cards 
will be configured with default values."
::= { nmcCfg 9 }

nmcCfgNumWanRetries OBJECT-TYPE
SYNTAX INTEGER (0..20)
ACCESS read-write
STATUS mandatory
DESCRIPTION
"This will specify the number of attempts to be made by 
port_write_task() to send the packet out of the WAN port 
while doing a dial up connection. The default is 0 which 
means the number of retries is disabled and it will keep 
trying to transmit the same packet for ever until it 
succeeds."
::= { nmcCfg 10 }

nmcCfgWanRetryPause OBJECT-TYPE
SYNTAX INTEGER (5..120)
ACCESS read-write
STATUS mandatory
DESCRIPTION
"The amount of time in seconds that the NMC will pause 
between attempts to transmit a packet. The default value 
for this object is 30."
::= { nmcCfg 11 }

nmcCfgWanRetrySuspendTime OBJECT-TYPE
SYNTAX INTEGER (5..300)
ACCESS read-write
STATUS mandatory
DESCRIPTION
"The Time period in seconds for which the WAN port should 
suspend its attempts to send out the packet. This time 
period applies when the number of failures has reached a 
configured maximum. It may resume its retries after the 
time period."
::= { nmcCfg 12 }

nmcCfgNumFailBefSuspend OBJECT-TYPE
SYNTAX INTEGER (0..50)
ACCESS read-write
STATUS mandatory
DESCRIPTION
"The number of connection failures to allow before 
suspending retries."
::= { nmcCfg 13 }

nmcCfgLogSrvrSelect OBJECT-TYPE
SYNTAX INTEGER{
  primary(1),
  secondary(2),
  none(3),
  third(4),
  fourth(5),
  fifth(6),
  sixth(7),
  seventh(8),
  eighth(9)
}
ACCESS read-only
STATUS mandatory
DESCRIPTION
"The server selection for event logging.
Default=none(3)."
::= { nmcCfg 14 }

nmcCfgLogPriSrvrAddr OBJECT-TYPE
SYNTAX IpAddress
ACCESS read-write
STATUS mandatory
DESCRIPTION
"The primary logging server's IP address."
::= { nmcCfg 15 }

nmcCfgLogSecSrvrAddr OBJECT-TYPE
SYNTAX IpAddress
ACCESS read-write
STATUS mandatory
DESCRIPTION
"The secondary logging server's IP address."
::= { nmcCfg 16 }

nmcCfgLogUdpPortNum OBJECT-TYPE
SYNTAX INTEGER (0..65535)
ACCESS read-write
STATUS mandatory
DESCRIPTION
"The logging server's UDP port number.
Default=1646."
::= { nmcCfg 17 }

nmcCfgLogRetryCnt OBJECT-TYPE
SYNTAX INTEGER (0..20)
ACCESS read-write
STATUS mandatory
DESCRIPTION
"The NMC logging client transmission retry 
count.
Default=3."
::= { nmcCfg 18 }

nmcCfgLogCallStatGrpSel OBJECT-TYPE
SYNTAX INTEGER{
  none(1),
  group2(2),
  group3(3),
  group4(4),
  group23(5),
  group24(6),
  group34(7),
  group234(8),
  group5(9),
  group25(10),
  group35(11),
  group45(12),
  group235(13),
  group245(14),
  group345(15),
  group2345(16)
}
ACCESS read-write
STATUS mandatory
DESCRIPTION
"The optional call statistics groups included in log 
messages.  Groups are Usage(1), Data Transfer(2), 
Performance(3), Operating Mode(4) and RMMIE(5). Group 1 is 
always sent. Groups 2-5 are optional.
Default = none(1)."
::= { nmcCfg 19 }

nmcCfgLogMD5Calc OBJECT-TYPE
SYNTAX INTEGER{
  enable(1),
  disable(2)
}
ACCESS read-write
STATUS optional
DESCRIPTION
"This Optional Object will indicate to the accounting Client 
whether to calculate MD5 for accounting request message or 
not. default=disable."
::= { nmcCfg 20 }

nmcCfgTFTPTimeout OBJECT-TYPE
SYNTAX INTEGER (1..30)
ACCESS read-write
STATUS mandatory
DESCRIPTION
"This object will be used to set up the timeout for the TFTP 
retries.  The default would be 12 sec and the maximum 
allowed timeout would be 30 sec."
::= { nmcCfg 21 }

nmcCfgDnsPriSrvrAddr OBJECT-TYPE
SYNTAX IpAddress
ACCESS read-write
STATUS mandatory
DESCRIPTION
"The primary DNS server's IP address."
::= { nmcCfg 22 }

nmcCfgDnsSecSrvrAddr OBJECT-TYPE
SYNTAX IpAddress
ACCESS read-write
STATUS mandatory
DESCRIPTION
"The secondary DNS server's IP address."
::= { nmcCfg 23 }

nmcCfgLog3SrvrAddr OBJECT-TYPE
SYNTAX IpAddress
ACCESS read-write
STATUS mandatory
DESCRIPTION
"The third backup logging server IP address to use."
::= { nmcCfg 24 }

nmcCfgLog4SrvrAddr OBJECT-TYPE
SYNTAX IpAddress
ACCESS read-write
STATUS mandatory
DESCRIPTION
"The fourth backup logging server IP address to use."
::= { nmcCfg 25 }

nmcCfgLog5SrvrAddr OBJECT-TYPE
SYNTAX IpAddress
ACCESS read-write
STATUS mandatory
DESCRIPTION
"The fifth backup logging server IP address to use."
::= { nmcCfg 26 }

nmcCfgLog6SrvrAddr OBJECT-TYPE
SYNTAX IpAddress
ACCESS read-write
STATUS mandatory
DESCRIPTION
"The sixth backup logging server IP address to use."
::= { nmcCfg 27 }

nmcCfgLog7SrvrAddr OBJECT-TYPE
SYNTAX IpAddress
ACCESS read-write
STATUS mandatory
DESCRIPTION
"The seventh backup logging server IP address to use."
::= { nmcCfg 28 }

nmcCfgLog8SrvrAddr OBJECT-TYPE
SYNTAX IpAddress
ACCESS read-write
STATUS mandatory
DESCRIPTION
"The eighth backup logging server IP address to use."
::= { nmcCfg 29 }

nmcCfgLogSrvrName OBJECT-TYPE
SYNTAX DisplayString (SIZE(0..80))
ACCESS read-write
STATUS mandatory
DESCRIPTION
"The host name of the logging server. Used to resolve 
logging server IP addresses through DNS query requests from 
the resolver."
::= { nmcCfg 30 }

nmcCfgDnsRetryCnt OBJECT-TYPE
SYNTAX INTEGER (0..20)
ACCESS read-write
STATUS mandatory
DESCRIPTION
"The maximum number of retries that will be attempted to 
query a DNS before trying the secondary DNS."
::= { nmcCfg 31 }

nmcCfgDnsUdpPortNum OBJECT-TYPE
SYNTAX INTEGER (0..65535)
ACCESS read-write
STATUS mandatory
DESCRIPTION
"The logging server's UDP port number.
Default=53."
::= { nmcCfg 32 }

nmcCfgDnsSrvrSelect OBJECT-TYPE
SYNTAX INTEGER{
  none(1),
  primary(2),
  secondary(3)
}
ACCESS read-only
STATUS mandatory
DESCRIPTION
"The server selection for DNS.
Default=none(1)."
::= { nmcCfg 33 }

nmcCfgLogDnsEna OBJECT-TYPE
SYNTAX INTEGER{
  enable(1),
  disable(2)
}
ACCESS read-write
STATUS mandatory
DESCRIPTION
"Indicates whether logging server host address DNS 
resolution is enabled or disabled. Disabled, the logging 
server addresses are taken from the log server address 
objects."
::= { nmcCfg 34 }

nmcCfgLogStatusInterval OBJECT-TYPE
SYNTAX INTEGER (10..65535)
ACCESS read-write
STATUS mandatory
DESCRIPTION
"This value defines the interval in seconds between 
Status-Server requests for a failed RADIUS Accounting 
server connection.
Default=30."
::= { nmcCfg 35 }

nmcCfgDnsSrvrFailure OBJECT-TYPE
SYNTAX INTEGER{
  none(1),
  other(2),
  commFailure(3),
  invalidEntry(4)
}
ACCESS read-only
STATUS mandatory
DESCRIPTION
"This value defines the failure reason for last failure of 
DNS resolver query."
::= { nmcCfg 36 }

nmcCfgLogSrvrFailure OBJECT-TYPE
SYNTAX INTEGER{
  none(1),
  other(2),
  commFailure(3),
  invalidResponse(4),
  disabledServer(5)
}
ACCESS read-only
STATUS mandatory
DESCRIPTION
"This value defines the failure reason for the last failure 
of RADIUS accounting server access."
::= { nmcCfg 37 }

nmcCfgSessionIDNewFmt OBJECT-TYPE
SYNTAX INTEGER{
  disable(1),
  enable(2)
}
ACCESS read-write
STATUS optional
DESCRIPTION
"This Object is used to Enable/Disable the New Session ID 
Format. Default is Disable."
::= { nmcCfg 38 }

-- The NAS Network Management Card Status Group.

nmcStat OBJECT IDENTIFIER ::= { nmc 2 }

nmcStatStatus OBJECT-TYPE
SYNTAX INTEGER{
  other(1),
  ok(2),
  nonCriticalFailure(3)
}
ACCESS read-only
STATUS mandatory
DESCRIPTION
"This object will indicate the general status or health of 
the Network Management Card."
::= { nmcStat 1 }

nmcStatDramInstalled OBJECT-TYPE
SYNTAX INTEGER
ACCESS read-only
STATUS mandatory
DESCRIPTION
"This object indicates the amount of dynamic RAM currently 
installed on the Network Management Card.  The units for 
this value are kilobytes."
::= { nmcStat 2 }

nmcStatNVRAMInstalled OBJECT-TYPE
SYNTAX INTEGER
ACCESS read-only
STATUS mandatory
DESCRIPTION
"This object indicates the amount of non-volatile RAM 
currently installed on the Network Management Card.  The 
units for this value are kilobytes."
::= { nmcStat 3 }

nmcStatEventId OBJECT-TYPE
SYNTAX INTEGER
ACCESS read-only
STATUS mandatory
DESCRIPTION
"This value increments once for each network management 
event detected by the NMC.  It is used to correlate SNMP 
traps with events that occured in the system."
::= { nmcStat 4 }

nmcStatTemperature OBJECT-TYPE
SYNTAX INTEGER
ACCESS read-only
STATUS optional
DESCRIPTION
"This object reflects the current temperature in the NAS 
chassis, as detected by the NMC.  The value of this object 
indicates the temperature in degree Celcius."
::= { nmcStat 5 }

nmcStatPowerUpTstFailures OBJECT-TYPE
SYNTAX Counter
ACCESS read-only
STATUS mandatory
DESCRIPTION
"This object contains the number of power up tests which 
failed during the power up of the NMC card."
::= { nmcStat 6 }

nmcStatPowerUpTstFailBMap OBJECT-TYPE
SYNTAX INTEGER
ACCESS read-only
STATUS mandatory
DESCRIPTION
"This object defines a bit map which contains a one in the 
postion that indicates a power up test failure.  The number 
returned is an integer that represents which power up 
test(s) that have failed. (e.g. a return value of three 
would mean power up tests 1 & 2 failed since bits 00000011 
in the least significant byte would be set.)"
::= { nmcStat 7 }

nmcStatTestResult OBJECT-TYPE
SYNTAX INTEGER
ACCESS read-only
STATUS mandatory
DESCRIPTION
"This object contains the bit mapped result of the request 
to perform a self test.  A non zero value indicates that 
there has been one or more self test failures."
::= { nmcStat 8 }

nmcStatCompSwVer OBJECT-TYPE
SYNTAX DisplayString (SIZE(0..9))
ACCESS read-only
STATUS mandatory
DESCRIPTION
"This object contains the software compatibility version."
::= { nmcStat 9 }

nmcStatPktBusClkSrc OBJECT-TYPE
SYNTAX INTEGER{
  notApplicable(1),
  backplaneActive(2),
  backplaneActive1ClkFail(3),
  nmcActive(4)
}
ACCESS read-only
STATUS optional
DESCRIPTION
"The source of the backplane packet bus clock."
::= { nmcStat 10 }

nmcStatNmcPktBusClk OBJECT-TYPE
SYNTAX INTEGER{
  notApplicable(1),
  available(2),
  active(3),
  failed(4)
}
ACCESS read-only
STATUS optional
DESCRIPTION
"The NMC's packet bus  clock status."
::= { nmcStat 11 }

nmcStatRedLed OBJECT-TYPE
SYNTAX INTEGER{
  none(1),
  chassisTemperatureHigh(2),
  chassisFanFailure(3),
  voltageWarningforPSU(4),
  failureofPSU(5),
  managementBusFailure(6),
  interfaceCardFailure(7),
  incompatibleTokenRingNIC(8)
}
ACCESS read-only
STATUS optional
DESCRIPTION
"This Object will return the Reason why the Hub Status LED 
is RED."
::= { nmcStat 12 }

nmcAuxIn1Sts OBJECT-TYPE
SYNTAX INTEGER{
  portOpen(1),
  portClosed(2),
  portNotApplicable(3)
}
ACCESS read-only
STATUS mandatory
DESCRIPTION
"This Object shows status of Aux Input port1."
::= { nmcStat 13 }

nmcAuxIn2Sts OBJECT-TYPE
SYNTAX INTEGER{
  portOpen(1),
  portClosed(2),
  portNotApplicable(3)
}
ACCESS read-only
STATUS mandatory
DESCRIPTION
"This Object shows status of Aux Input port2."
::= { nmcStat 14 }

nmcAuxOut1Sts OBJECT-TYPE
SYNTAX INTEGER{
  portOpen(1),
  portClosed(2),
  portNotApplicable(3)
}
ACCESS read-only
STATUS mandatory
DESCRIPTION
"This Object shows status of Aux Output port1."
::= { nmcStat 15 }

nmcAuxOut2Sts OBJECT-TYPE
SYNTAX INTEGER{
  portOpen(1),
  portClosed(2),
  portNotApplicable(3)
}
ACCESS read-only
STATUS mandatory
DESCRIPTION
"This Object shows status of Aux Output port2."
::= { nmcStat 16 }

-- The NAS Network Management Card Trap Group.

nmcTrap OBJECT IDENTIFIER ::= { nmc 3 }

nmcTrapSequenceNumber OBJECT-TYPE
SYNTAX INTEGER
ACCESS read-only
STATUS mandatory
DESCRIPTION
"This object increments every time a trap is generated by 
the NMC.  This object is sent in the var-bind list of each 
trap and can be used by management stations to detect when 
a trap has been lost."
::= { nmcTrap 1 }

nmcTrapDestTable OBJECT-TYPE
SYNTAX SEQUENCE OF NmcTrapDestEntry
ACCESS not-accessible
STATUS mandatory
DESCRIPTION
"This table defines the places to which traps are to be 
sent.  These places may refer to management consoles, or 
other alarm collection processes."
::= { nmcTrap 2 }

nmcTrapDestEntry OBJECT-TYPE
SYNTAX NmcTrapDestEntry
ACCESS not-accessible
STATUS mandatory
DESCRIPTION
"There is an entry in this table for each destination to 
which the NMC is to send SNMP traps."
INDEX { nmcTrapDestIP }
::= { nmcTrapDestTable 1 }

NmcTrapDestEntry ::=
SEQUENCE {
nmcTrapDestIP
    IpAddress,
nmcTrapDestCommunity
    OCTET STRING,
nmcTrapDestDescr
    DisplayString
}

nmcTrapDestIP OBJECT-TYPE
SYNTAX IpAddress
ACCESS read-only
STATUS mandatory
DESCRIPTION
"This object identifies the IP address to be used for 
sending traps to the destination identified by 
nmcTrapDestDescr."
::= { nmcTrapDestEntry 1 }

nmcTrapDestCommunity OBJECT-TYPE
SYNTAX OCTET STRING (SIZE(0..31))
ACCESS read-write
STATUS mandatory
DESCRIPTION
"This object identifies the community string to be used when 
sending traps to the destination identified by 
nmcTrapDestDescr."
::= { nmcTrapDestEntry 2 }

nmcTrapDestDescr OBJECT-TYPE
SYNTAX DisplayString (SIZE(0..24))
ACCESS read-write
STATUS mandatory
DESCRIPTION
"This object contains a plain text description of the trap 
destination to which this entry pertains."
::= { nmcTrapDestEntry 3 }

nmcArTrapId OBJECT-TYPE
SYNTAX INTEGER (0..127)
ACCESS read-only
STATUS optional
DESCRIPTION
"A single user defined value can be configured through 
AutoResponse script MIB objects to be sent to the 
management stations when a NMC AutoResponse SNMP TRAP 
occurs."
::= { nmcTrap 3 }

-- The NAS Network Management Card Command Group.

nmcCmd OBJECT IDENTIFIER ::= { nmc 4 }

nmcCmdMgtStationId OBJECT-TYPE
SYNTAX OCTET STRING (SIZE(0..8))
ACCESS read-write
STATUS mandatory
DESCRIPTION
"This object is a generic read-write variable that a 
Management Station (MS) can use to guarantee that the 
results from a given command are the results of a command 
issued by that specific MS.  Each MS must SET a unique 
value to this object when doing commands and GET the value 
of this object together with ds0CmdReqId and ds0CmdResult 
to detect interference from other MSs."
::= { nmcCmd 1 }

nmcCmdReqId OBJECT-TYPE
SYNTAX INTEGER
ACCESS read-write
STATUS mandatory
DESCRIPTION
"This object contains the value of the request-id field in 
the SNMP PDU which invoked the current or most recent 
command or test on this Network Management Card.  If the 
request-id is unknown or undefined, this object contains 
the value zero."
::= { nmcCmd 2 }

nmcCmdFunction OBJECT-TYPE
SYNTAX INTEGER{
  noCommand(1),
  saveToNvram(2),
  restoreFromDefaults(3),
  restoreFromNvram(4),
  nonDisruptSelfTest(5),
  softwareReset(6),
  saveUiParmsToEEPROM(7),
  restoreNmcFromDefaults(8),
  restoreNmcFromNvram(9),
  bulkFileUpload(10),
  bulkFileDownload(11),
  openAuxOutputPort1(12),
  openAuxOutputPort2(13),
  closeAuxOutputPort1(14),
  closeAuxOutputPort2(15)
}
ACCESS read-write
STATUS mandatory
DESCRIPTION
"This object contains the value which decsribe the command 
which is being invoked."
::= { nmcCmd 3 }

nmcCmdForce OBJECT-TYPE
SYNTAX INTEGER{
  noForce(1),
  force(2)
}
ACCESS read-write
STATUS mandatory
DESCRIPTION
"In some cases, the Network Managment Card may be in a state 
such that certain commands could adversely affect 
operations.  In such cases, a command request with this 
object not present or set to noForce will result in a 
warning.  If the operator elects to ignore such warnings, 
this object can be set to force in a subsequent issue of 
the command to cause the command to be carried out 
regardless of its potentially hazzardous effects."
::= { nmcCmd 4 }

nmcCmdParam OBJECT-TYPE
SYNTAX OCTET STRING (SIZE(0..24))
ACCESS read-write
STATUS mandatory
DESCRIPTION
"This object contains parameters that are specific to the 
particular command being issued.  In some cases, there will 
be no additional parameters required."
::= { nmcCmd 5 }

nmcCmdResult OBJECT-TYPE
SYNTAX INTEGER{
  none(1),
  success(2),
  inProgress(3),
  notSupported(4),
  unAbleToRun(5),
  aborted(6),
  failed(7)
}
ACCESS read-only
STATUS mandatory
DESCRIPTION
"This object contains the result of the most recently 
requested command or test, or the value none(1) if no 
commands have been requested since the last reset."
::= { nmcCmd 6 }

nmcCmdCode OBJECT-TYPE
SYNTAX INTEGER{
  noError(1),
  unable(2),
  unrecognizedData(5),
  unrecognizedCommand(6),
  slotEmpty(8),
  unsupportedCommand(20),
  testFailed(25),
  nvramAccessConflict(27),
  erasingFlashError(63),
  badCRC(72),
  pendingSoftwareDownload(73),
  erasingFlash(81),
  fileTransferTimedOut(86),
  unrecognizedFile(88),
  fileTransferInProgress(93),
  pendingFileTransfer(115)
}
ACCESS read-only
STATUS mandatory
DESCRIPTION
"The value of this object upon command completion indicates 
a further description of what went wrong if the command was 
unsuccessful.  In the case of tests, a bit mapped result of 
each of the sub-tests performed appears in the 
nmcStatTestResult object."
::= { nmcCmd 7 }

-- The NAS Network Management Card HUB Security Group

nmcHs OBJECT IDENTIFIER ::= { nmc 6 }

nmcHsDialInOutNamePrompt OBJECT-TYPE
SYNTAX DisplayString (SIZE(0..80))
ACCESS read-write
STATUS optional
DESCRIPTION
"This is the first prompt that appears when users establish 
a connection with a security modem.  It should serve to 
identify the system and prompt users to enter their name."
::= { nmcHs 1 }

nmcHsDialInOutPsswdPrompt OBJECT-TYPE
SYNTAX DisplayString (SIZE(0..80))
ACCESS read-write
STATUS optional
DESCRIPTION
"This prompt appears after a valid response has been made to 
the previous prompt (i.e., name string followed by CR/LF), 
and prompts users to enter their password."
::= { nmcHs 2 }

nmcHsDialBackNamePrompt OBJECT-TYPE
SYNTAX DisplayString (SIZE(0..80))
ACCESS read-write
STATUS optional
DESCRIPTION
"This prompt only appears when users are configured for dial 
back security (to either a stored or entered number).  It 
is also only issued when the Request Login Validation on 
Dial-Back field is enabled for the user in the RADIUS user 
database.  This prompt should be different than the name 
prompt used when users first log into the system."
::= { nmcHs 3 }

nmcHsDialBackPsswdPrompt OBJECT-TYPE
SYNTAX DisplayString (SIZE(0..80))
ACCESS read-write
STATUS optional
DESCRIPTION
"This prompt appears after a valid response to the prior 
prompt, and prompts users to enter their password."
::= { nmcHs 4 }

nmcHsDialBackPhonePrompt OBJECT-TYPE
SYNTAX DisplayString (SIZE(0..80))
ACCESS read-write
STATUS optional
DESCRIPTION
"This prompt only appears if you have configured the user 
for dial back entered mode in the RADIUS user database.  It 
prompts the user to enter the phone number at which the 
system can call them back."
::= { nmcHs 5 }

nmcHsDialBackPendPrompt OBJECT-TYPE
SYNTAX DisplayString (SIZE(0..80))
ACCESS read-write
STATUS optional
DESCRIPTION
"This message only appears if you configure users for a dial 
back mode (to either a stored or entered number) in the 
RADIUS user database.  It confirms to users that they have 
logged in successfully, and lets them know that the system 
has reserved a modem to call them back."
::= { nmcHs 6 }

nmcHsMdmSelectPrompt OBJECT-TYPE
SYNTAX DisplayString (SIZE(0..80))
ACCESS read-write
STATUS optional
DESCRIPTION
"This message only appears if a user is configured for dial 
back in the RADIUS database and that this record has the 
Request Dial Back Modem Selection field enabled.  The 
system displays a list of allowed dial back modems that 
have been entered for this user.  Users must enter the 
number that appears on the menu next to their choice."
::= { nmcHs 7 }

nmcHsLoginFailedMsg OBJECT-TYPE
SYNTAX DisplayString (SIZE(0..80))
ACCESS read-write
STATUS optional
DESCRIPTION
"This message appears when users fail to enter a valid 
name/password combination."
::= { nmcHs 8 }

nmcHsPhoneRestrictPrompt OBJECT-TYPE
SYNTAX DisplayString (SIZE(0..80))
ACCESS read-write
STATUS optional
DESCRIPTION
"This message appears when users are prompted for a dial 
back phone number and the entered number violates the 
allowed numbers specified in the Call Restriction List."
::= { nmcHs 9 }

nmcHsInvalidMdmSelecMsg OBJECT-TYPE
SYNTAX DisplayString (SIZE(0..80))
ACCESS read-write
STATUS optional
DESCRIPTION
"This message appears when users configured for dial back 
with the Request Dial-Back Modem Selection field enabled, 
select a modem to which they are not allowed access (as 
specified in the list of allowed Dial-Back modems)."
::= { nmcHs 10 }

nmcHsNoMdnsAvailMsg OBJECT-TYPE
SYNTAX DisplayString (SIZE(0..80))
ACCESS read-write
STATUS optional
DESCRIPTION
"This message appears when the system is unable to reserve a 
modem for dial-back that was either selected by the user or 
defined in it's list of Allowed Dial Back modems."
::= { nmcHs 11 }

nmcHsConnectSuccessMsg OBJECT-TYPE
SYNTAX DisplayString (SIZE(0..80))
ACCESS read-write
STATUS optional
DESCRIPTION
"This message confirms that users have successfully 
compleated their login and may proceed with either their 
dial-in or dial-out call."
::= { nmcHs 12 }

nmcHsNewPasswordPrompt OBJECT-TYPE
SYNTAX DisplayString (SIZE(0..80))
ACCESS read-write
STATUS optional
DESCRIPTION
"This prompt only appears when a users password has expired. 
 It is issued once for the new password and then again for 
re-issue of the new password."
::= { nmcHs 13 }

nmcHsChangePasswordMsg OBJECT-TYPE
SYNTAX DisplayString (SIZE(0..80))
ACCESS read-write
STATUS optional
DESCRIPTION
"This message appears during name/password authentication 
when the user's password has expired.  This message is 
immediately followed by the enter new password prompt."
::= { nmcHs 14 }

nmcHsPromptRspTimeout OBJECT-TYPE
SYNTAX INTEGER (10..255)
ACCESS read-write
STATUS optional
DESCRIPTION
"This value represents the number of seconds in which users 
must respond to each prompt.  Users failing to respond 
within the specified time are disconnected, and a Dial 
Security login failure trap is generated.  Any login 
failures of this type also apply to the user blacklist 
function if a valid user name has been entered.  This field 
takes precidence over the modem's inactivity timer during a 
security login.  The default for this object is 
30(seconds)."
::= { nmcHs 15 }

nmcHsPromptRspAttempts OBJECT-TYPE
SYNTAX INTEGER (1..16)
ACCESS read-write
STATUS optional
DESCRIPTION
"This value represents the number of tries the user is 
allowed per prompt during any one security session.  If 
this number is reached, the call is terminated.  For the 
purposes of retry limiting, the user name and password are 
treated as a single prompt.  This means that if a valid 
name and an invalid password are entered, the failure is 
counted against both the Prompt Response Attempt Limit and 
the Failed Logins Before Blacklist.  The default for this 
object is 1."
::= { nmcHs 16 }

nmcHsPromptRspEchoEna OBJECT-TYPE
SYNTAX INTEGER{
  disable(1),
  enable(2)
}
ACCESS read-write
STATUS optional
DESCRIPTION
"When enabled, this option instructs the NMC to echo the 
user's typed responses back to the users screen.  Password 
responses are echoed as 'X's.  The default for this option 
is disabled."
::= { nmcHs 17 }

nmcHsDialBackDelay OBJECT-TYPE
SYNTAX INTEGER (1..100)
ACCESS read-write
STATUS optional
DESCRIPTION
"This object defines the number of seconds to wait between 
successive dial back attempts; i.e., the time the NMC waits 
before attempting the next dial back when it was unable to 
connect.  The default is 30 seconds."
::= { nmcHs 18 }

nmcHsDialBackAttempts OBJECT-TYPE
SYNTAX INTEGER (1..100)
ACCESS read-write
STATUS optional
DESCRIPTION
"This object defines the number of times that the NMC will 
attempt to dial back a dial in user configured for dial 
back when successive dial back attempts fail.  The default 
for this object is one. "
::= { nmcHs 19 }

nmcHsSecuritySrvrAddr OBJECT-TYPE
SYNTAX IpAddress
ACCESS read-write
STATUS mandatory
DESCRIPTION
"This object identifies the IP address of the Primary RADIUS 
security server where the NMC RADIUS client sends requests."
::= { nmcHs 20 }

nmcHsSecuritySrvrPort OBJECT-TYPE
SYNTAX INTEGER (0..65535)
ACCESS read-write
STATUS mandatory
DESCRIPTION
"This object identifies the UDP port where the NMC's RADIUS 
client issues requests to the RADIUS security server.  The 
default port is 1645."
::= { nmcHs 21 }

nmcHsSecuritySrvrRetries OBJECT-TYPE
SYNTAX INTEGER (0..3)
ACCESS read-write
STATUS mandatory
DESCRIPTION
"This object identifies the number of retries that the NMC's 
RADIUS client will preform when attempting to send requests 
to a RADIUS security server. The default retry number is 1."
::= { nmcHs 22 }

nmcHsMdmAttemptLimit OBJECT-TYPE
SYNTAX INTEGER (1..16)
ACCESS read-write
STATUS mandatory
DESCRIPTION
"This value represents the number of times an attempt can be 
made to login on any one modem without success.  If this 
value is exceeded and the mdmLoginAttemptLimExceeded trap 
has been enabled, then the mdmLoginAttemptLimExceeded trap 
is generated.  Default = 3."
::= { nmcHs 23 }

nmcHsServerUnavailable OBJECT-TYPE
SYNTAX INTEGER{
  denyCall(1),
  allowCall(2)
}
ACCESS read-write
STATUS mandatory
DESCRIPTION
"This option specifies whether to deny or allow a call when 
a dial security server is unreachable.
Default = 
denyCall(1)."
::= { nmcHs 24 }

nmcHsServerSelect OBJECT-TYPE
SYNTAX INTEGER{
  primary(1),
  secondary(2),
  none(3),
  third(4),
  fourth(5),
  fifth(6),
  sixth(7),
  seventh(8),
  eighth(9)
}
ACCESS read-only
STATUS mandatory
DESCRIPTION
"Server Selection for RADIUS Security. Default=none(3)."
::= { nmcHs 25 }

nmcHsSecondarySrvrAddr OBJECT-TYPE
SYNTAX IpAddress
ACCESS read-write
STATUS mandatory
DESCRIPTION
"This object identifies the IP address of the Secondary 
RADIUS Security Server."
::= { nmcHs 26 }

nmcHsDiPasswdEnaDis OBJECT-TYPE
SYNTAX INTEGER{
  enable(1),
  disable(2)
}
ACCESS read-write
STATUS optional
DESCRIPTION
"This Optional Object will Enable/Disable PASSWORD prompt 
for Dial-In Hub Security.  Default is Enable(1)."
::= { nmcHs 27 }

nmcHsSecurity3SrvrAddr OBJECT-TYPE
SYNTAX IpAddress
ACCESS read-write
STATUS mandatory
DESCRIPTION
"This object identifies the IP address of the 3rd RADIUS 
Security backup server."
::= { nmcHs 28 }

nmcHsSecurity4SrvrAddr OBJECT-TYPE
SYNTAX IpAddress
ACCESS read-write
STATUS mandatory
DESCRIPTION
"This object identifies the IP address of the 4th RADIUS 
Security backup server."
::= { nmcHs 29 }

nmcHsSecurity5SrvrAddr OBJECT-TYPE
SYNTAX IpAddress
ACCESS read-write
STATUS mandatory
DESCRIPTION
"This object identifies the IP address of the 5th RADIUS 
Security backup server."
::= { nmcHs 30 }

nmcHsSecurity6SrvrAddr OBJECT-TYPE
SYNTAX IpAddress
ACCESS read-write
STATUS mandatory
DESCRIPTION
"This object identifies the IP address of the 6th RADIUS 
Security backup server."
::= { nmcHs 31 }

nmcHsSecurity7SrvrAddr OBJECT-TYPE
SYNTAX IpAddress
ACCESS read-write
STATUS mandatory
DESCRIPTION
"This object identifies the IP address of the 7th RADIUS 
Security backup server."
::= { nmcHs 32 }

nmcHsSecurity8SrvrAddr OBJECT-TYPE
SYNTAX IpAddress
ACCESS read-write
STATUS mandatory
DESCRIPTION
"This object identifies the IP address of the 8th RADIUS 
Security backup server."
::= { nmcHs 33 }

nmcHsSecuritySrvrName OBJECT-TYPE
SYNTAX DisplayString (SIZE(0..80))
ACCESS read-write
STATUS mandatory
DESCRIPTION
"Identifies the host name of the RADIUS Security server used 
to resolve IP addresses through DNS queries." 
::= { nmcHs 34 }

nmcHsSecuritySrvrDnsEna OBJECT-TYPE
SYNTAX INTEGER{
  enable(1),
  disable(2)
}
ACCESS read-write
STATUS mandatory
DESCRIPTION
"Indicates RADIUS Security server IP addresses are resolved 
through DNS queries. If disabled, the Security server 
address objects are used.
Default=disabled"
::= { nmcHs 35 }

nmcHsSecurityStatusInt OBJECT-TYPE
SYNTAX INTEGER (10..65535)
ACCESS read-write
STATUS mandatory
DESCRIPTION
"This value defines the interval in seconds between 
Status-Server requests for a failed RADIUS Security server 
connection.
Default=30."
::= { nmcHs 36 }

nmcHsSecurityFailure OBJECT-TYPE
SYNTAX INTEGER{
  none(1),
  other(2),
  commFailure(3),
  invalidResponse(4),
  disabledServer(5)
}
ACCESS read-only
STATUS mandatory
DESCRIPTION
"This value defines the failure reason for the last failure 
of RADIUS Security server access."
::= { nmcHs 37 }

-- The NAS Network Management Card Security Trap Enable Group.

nmcTe OBJECT IDENTIFIER ::= { nmc 7 }

nmcTeDialOutLoginFail OBJECT-TYPE
SYNTAX INTEGER{
  enableTrap(1),
  disableAll(2),
  enableLog(3),
  enableAll(4)
}
ACCESS read-write
STATUS optional
DESCRIPTION
"Enable/disable for the trap generated when a dial out login 
security session has failed."
::= { nmcTe 1 }

nmcTeDialInLoginFail OBJECT-TYPE
SYNTAX INTEGER{
  enableTrap(1),
  disableAll(2),
  enableLog(3),
  enableAll(4)
}
ACCESS read-write
STATUS optional
DESCRIPTION
"Enable/disable for the trap generated when a dial in login 
security session has failed."
::= { nmcTe 2 }

nmcTeDialOutRestrictNum OBJECT-TYPE
SYNTAX INTEGER{
  enableTrap(1),
  disableAll(2),
  enableLog(3),
  enableAll(4)
}
ACCESS read-write
STATUS optional
DESCRIPTION
"Enable/disable for the trap generated when a dial out 
security session has failed as a result of attempting to 
dial a restricted phone number."
::= { nmcTe 3 }

nmcTeDialBackRestrictNum OBJECT-TYPE
SYNTAX INTEGER{
  enableTrap(1),
  disableAll(2),
  enableLog(3),
  enableAll(4)
}
ACCESS read-write
STATUS optional
DESCRIPTION
"Enable/disable for the trap generated when a dial back 
security session has failed as a result of attempting to 
dial a restricted phone number."
::= { nmcTe 4 }

nmcTeUserBlacklist OBJECT-TYPE
SYNTAX INTEGER{
  enableTrap(1),
  disableAll(2),
  enableLog(3),
  enableAll(4)
}
ACCESS read-write
STATUS optional
DESCRIPTION
"Enable/disable for the trap generated when a security user 
has reached their final failed login attempt number and is 
now being blacklisted."
::= { nmcTe 5 }

nmcTeUserBlacklistLogin OBJECT-TYPE
SYNTAX INTEGER{
  enableTrap(1),
  disableAll(2),
  enableLog(3),
  enableAll(4)
}
ACCESS read-write
STATUS optional
DESCRIPTION
"Enable/disable for the trap generated when a security login 
attempt by a currently blacklisted user has occurred."
::= { nmcTe 6 }

nmcTeRespAttmptLimExceed OBJECT-TYPE
SYNTAX INTEGER{
  enableTrap(1),
  disableAll(2),
  enableLog(3),
  enableAll(4)
}
ACCESS read-write
STATUS optional
DESCRIPTION
"Enable/disable for the trap generated when a security user 
has failed to issue a valid response to a particular 
security prompt before the configured limit."
::= { nmcTe 7 }

nmcTeLoginAttmptLimExceed OBJECT-TYPE
SYNTAX INTEGER{
  enableTrap(1),
  disableAll(2),
  enableLog(3),
  enableAll(4)
}
ACCESS read-write
STATUS optional
DESCRIPTION
"Enable/disable for the trap generated when a security 
session has failed because the indicated user does not 
appear in the security user database."
::= { nmcTe 8 }

nmcTeLogSrvrLoss OBJECT-TYPE
SYNTAX INTEGER{
  enable(1),
  disable(2)
}
ACCESS read-write
STATUS mandatory
DESCRIPTION
"Enable/disable for the trap generated when communication 
with a logging server has been lost."
::= { nmcTe 9 }

nmcTeSecSrvrLoss OBJECT-TYPE
SYNTAX INTEGER{
  enable(1),
  disable(2)
}
ACCESS read-write
STATUS mandatory
DESCRIPTION
"Enable/disable for the trap generated when communication 
with a security server has been lost."
::= { nmcTe 10 }

nmcTeSinglePbClockFail OBJECT-TYPE
SYNTAX INTEGER{
  enable(1),
  disable(2)
}
ACCESS read-write
STATUS mandatory
DESCRIPTION
"Enable/disable for the trap generated when the NMC detects 
that there is a packet bus clock failure in a single 
slot.
Default=enable(1)."
::= { nmcTe 11 }

nmcTePbClockSwitch OBJECT-TYPE
SYNTAX INTEGER{
  enable(1),
  disable(2)
}
ACCESS read-write
STATUS mandatory
DESCRIPTION
"Enable/disable for the trap generated when the NMC detects 
that there is a packet bus clock failure in multiple slots 
and the NMC has assumed the role of clock 
master.
Default=enable(1)."
::= { nmcTe 12 }

nmcTePbClockFail OBJECT-TYPE
SYNTAX INTEGER{
  enable(1),
  disable(2)
}
ACCESS read-write
STATUS mandatory
DESCRIPTION
"Enable/disable for the trap generated when the NMC detects 
that the packet bus clock on the NMC daughter board pcb has 
failed.  Check status of nmcStatPktBusClkSrc to determine 
if the NMC was acting as clock master.
Default=enable(1)."
::= { nmcTe 13 }

nmcTeDnsSrvrLoss OBJECT-TYPE
SYNTAX INTEGER{
  enable(1),
  disable(2)
}
ACCESS read-write
STATUS mandatory
DESCRIPTION
"Enable/disable for the trap generated when communication 
with the primary and secondary DNS server has been lost."
::= { nmcTe 14 }

nmcTeNtpSrvrLoss OBJECT-TYPE
SYNTAX INTEGER{
  enable(1),
  disable(2)
}
ACCESS read-write
STATUS mandatory
DESCRIPTION
"Enable/disable for the trap generated when communication 
with all NTP servers has failed."
::= { nmcTe 15 }

nmcTeNtpSrvrRestore OBJECT-TYPE
SYNTAX INTEGER{
  enable(1),
  disable(2)
}
ACCESS read-write
STATUS mandatory
DESCRIPTION
"Enable/disable for the trap generated when communication 
with the NTP server has been restored."
::= { nmcTe 16 }

nmcTeNtpSrvrDegraded OBJECT-TYPE
SYNTAX INTEGER{
  enable(1),
  disable(2)
}
ACCESS read-write
STATUS mandatory
DESCRIPTION
"Enable/disable for the trap generated when communication 
with the primary NTP server has failed, but the secondary 
has been restored."
::= { nmcTe 17 }

nmcTeDnsSrvrRestore OBJECT-TYPE
SYNTAX INTEGER{
  enable(1),
  disable(2)
}
ACCESS read-write
STATUS mandatory
DESCRIPTION
"Enable/disable for the trap generated when communication 
with the primary DNS server has been 
restored.
Default=disable."
::= { nmcTe 18 }

nmcTeDnsSrvrDegraded OBJECT-TYPE
SYNTAX INTEGER{
  enable(1),
  disable(2)
}
ACCESS read-write
STATUS mandatory
DESCRIPTION
"Enable/disable for the trap generated when communication 
with the primary DNS server has failed, but the secondary 
DNS server is operational.
Default=disabled."
::= { nmcTe 19 }

nmcTeLogSrvrRestore OBJECT-TYPE
SYNTAX INTEGER{
  enable(1),
  disable(2)
}
ACCESS read-write
STATUS mandatory
DESCRIPTION
"Enable/disable for the trap generated when communication 
with a logging server has been restored."
::= { nmcTe 20 }

nmcTeLogSrvrGroupOper OBJECT-TYPE
SYNTAX INTEGER{
  enable(1),
  disable(2)
}
ACCESS read-write
STATUS mandatory
DESCRIPTION
"Enable/disable for the trap generated when the 
communication with the group of logging servers is 
operational with the primary server in service."
::= { nmcTe 21 }

nmcTeLogSrvrGroupDegr OBJECT-TYPE
SYNTAX INTEGER{
  enable(1),
  disable(2)
}
ACCESS read-write
STATUS mandatory
DESCRIPTION
"Enable/disable from the trap generated when the 
communication with the group of logging servers has 
degraded with a non-primary server in service."
::= { nmcTe 22 }

nmcTeLogSrvrGroupNonOp OBJECT-TYPE
SYNTAX INTEGER{
  enable(1),
  disable(2)
}
ACCESS read-write
STATUS mandatory
DESCRIPTION
"Enable/disable for the trap generated when the 
communication with the group of logging servers is 
non-operational."
::= { nmcTe 23 }

nmcTeSecSrvrRestore OBJECT-TYPE
SYNTAX INTEGER{
  enable(1),
  disable(2)
}
ACCESS read-write
STATUS mandatory
DESCRIPTION
"Enable/disable for the trap generated when communication 
with the RADIUS Security server has been 
restored.
Default=disabled"
::= { nmcTe 24 }

nmcTeSecSrvrGroupOper OBJECT-TYPE
SYNTAX INTEGER{
  enable(1),
  disable(2)
}
ACCESS read-write
STATUS mandatory
DESCRIPTION
"Enable/disable for the trap generated when communication to 
the RADIUS Security server group becomes 
operational.
Default=disabled"
::= { nmcTe 25 }

nmcTeSecSrvrGroupDegr OBJECT-TYPE
SYNTAX INTEGER{
  enable(1),
  disable(2)
}
ACCESS read-write
STATUS mandatory
DESCRIPTION
"Enable/disable for the trap generated when communication to 
the RADIUS Security server group becomes degraded because 
of failure to contact primary server.
Default=disabled"
::= { nmcTe 26 }

nmcTeSecSrvrGroupNonOp OBJECT-TYPE
SYNTAX INTEGER{
  enable(1),
  disable(2)
}
ACCESS read-write
STATUS mandatory
DESCRIPTION
"Enable/disable for the trap generated when communication to 
the RADIUS Security server group becomes non-operational 
because of failure to contact any Security 
servers.
Default=disabled"
::= { nmcTe 27 }

nmcUiCfg OBJECT IDENTIFIER ::= { nmc 8 }

nmcUiCfgLanIPAddr OBJECT-TYPE
SYNTAX IpAddress
ACCESS read-write
STATUS mandatory
DESCRIPTION
"This contains the IP address of the LAN interface."
::= { nmcUiCfg 1 }

nmcUiCfgLanSubnetMask OBJECT-TYPE
SYNTAX IpAddress
ACCESS read-write
STATUS mandatory
DESCRIPTION
"This specifies the subnet mask for LAN interface."
::= { nmcUiCfg 2 }

nmcUiCfgWanIPAddr OBJECT-TYPE
SYNTAX IpAddress
ACCESS read-write
STATUS mandatory
DESCRIPTION
"This specifies the IP address for the WAN interface."
::= { nmcUiCfg 3 }

nmcUiCfgWanSubnetMask OBJECT-TYPE
SYNTAX IpAddress
ACCESS read-write
STATUS mandatory
DESCRIPTION
"This specifies the Subnet mask for the WAN interface."
::= { nmcUiCfg 4 }

nmcUiCfgDefaultGwyIP OBJECT-TYPE
SYNTAX IpAddress
ACCESS read-write
STATUS mandatory
DESCRIPTION
"This specifies the address of the Gateway to which the IP 
will forward those packets whose net ID does not match the 
net ID of either interface."
::= { nmcUiCfg 5 }

nmcUiCfgLocalTrIeeeAddr OBJECT-TYPE
SYNTAX OCTET STRING (SIZE(6..6))
ACCESS read-write
STATUS mandatory
DESCRIPTION
"This gives the IEEE physical address of the Token Ring 
interface."
::= { nmcUiCfg 6 }

nmcUiCfgPrivateString OBJECT-TYPE
SYNTAX DisplayString (SIZE(0..32))
ACCESS write-only
STATUS mandatory
DESCRIPTION
"This specifies the SNMP read-write community 
string.
Default='private'."
::= { nmcUiCfg 7 }

nmcUiCfgLanIfEnable OBJECT-TYPE
SYNTAX INTEGER{
  enable(1),
  disable(2)
}
ACCESS read-write
STATUS optional
DESCRIPTION
"This parameter controls the enable/disable of the LAN 
interface."
::= { nmcUiCfg 8 }

nmcUiCfgPublicString OBJECT-TYPE
SYNTAX DisplayString (SIZE(0..32))
ACCESS write-only
STATUS mandatory
DESCRIPTION
"This specifies the SNMP read-only community 
string.
Default='public'."
::= { nmcUiCfg 9 }

nmcUiCfgRouteEnable OBJECT-TYPE
SYNTAX INTEGER{
  enable(1),
  disable(2)
}
ACCESS read-write
STATUS optional
DESCRIPTION
"This Parameter controls the ability of the NMC to route 
traffic between it's LAN and SLIP interfaces, Default = 
enable(1)."
::= { nmcUiCfg 10 }

nmcUiCfgUiSlipCfg OBJECT-TYPE
SYNTAX INTEGER{
  uiport(1),
  slipport(2)
}
ACCESS read-write
STATUS optional
DESCRIPTION
"This is used to configure the UI port as SLIP or UI. 
Default=UI."
::= { nmcUiCfg 11 }

nmcUiCfgWan2IpAddr OBJECT-TYPE
SYNTAX IpAddress
ACCESS read-write
STATUS mandatory
DESCRIPTION
"This contains the IP address of second SLIP port."
::= { nmcUiCfg 12 }

nmcUiCfgWan2SubnetMask OBJECT-TYPE
SYNTAX IpAddress
ACCESS read-write
STATUS mandatory
DESCRIPTION
"This contains SubnetMask for Second Slip port."
::= { nmcUiCfg 13 }

nmcUiCfgInactiveTime OBJECT-TYPE
SYNTAX INTEGER (0..1440)
ACCESS read-write
STATUS optional
DESCRIPTION
"This parameter is in minutes it is used as an Inactivity 
time on the UI port. The Default is 3 minutes and 0 minutes 
disables the feature."
::= { nmcUiCfg 14 }

nmcUiCfgPassword OBJECT-TYPE
SYNTAX INTEGER{
  enable(1),
  disable(2)
}
ACCESS read-write
STATUS optional
DESCRIPTION
"This parameter is used to Enable or Disable the PASSWORD 
protection for UI functions. Default = disabled."
::= { nmcUiCfg 15 }

-- The NAS Network Management Card Authorized Access Group.

nmcAuth OBJECT IDENTIFIER ::= { nmc 9 }

nmcAuthAccTable OBJECT-TYPE
SYNTAX SEQUENCE OF NmcAuthAccEntry
ACCESS not-accessible
STATUS mandatory
DESCRIPTION
"This table defines which management stations are allowed 
access to the NMC."
::= { nmcAuth 1 }

nmcAuthAccEntry OBJECT-TYPE
SYNTAX NmcAuthAccEntry
ACCESS not-accessible
STATUS mandatory
DESCRIPTION
"There is an entry for each management station allowd access 
to the NMC."
INDEX { nmcAuthAccIpAddr }
::= { nmcAuthAccTable 1 }

NmcAuthAccEntry ::=
SEQUENCE {
nmcAuthAccIpAddr
    IpAddress,
nmcAuthAccNetMask
    IpAddress,
nmcAuthAccDescr
    DisplayString
}

nmcAuthAccIpAddr OBJECT-TYPE
SYNTAX IpAddress
ACCESS read-only
STATUS mandatory
DESCRIPTION
"This is the IP address of the station allowed access to the 
NMC."
::= { nmcAuthAccEntry 1 }

nmcAuthAccNetMask OBJECT-TYPE
SYNTAX IpAddress
ACCESS read-write
STATUS mandatory
DESCRIPTION
"This is the network mask of the station allowed access to 
the NMC."
::= { nmcAuthAccEntry 2 }

nmcAuthAccDescr OBJECT-TYPE
SYNTAX DisplayString (SIZE(0..24))
ACCESS read-write
STATUS mandatory
DESCRIPTION
"This is the description of the station allowed access to 
the NMC."
::= { nmcAuthAccEntry 3 }

-- The NAS Network Management Card Network Time Protocol Group.

nmcNtp OBJECT IDENTIFIER ::= { nmc 10 }

nmcNtpSrvrPrimAddr OBJECT-TYPE
SYNTAX IpAddress
ACCESS read-write
STATUS mandatory
DESCRIPTION
"The primary NTP server's IP address."
::= { nmcNtp 1 }

nmcNtpSrvrSecdAddr OBJECT-TYPE
SYNTAX IpAddress
ACCESS read-write
STATUS mandatory
DESCRIPTION
"The secondary NTP server's IP address. This server is only 
accessed when responses from the primary have failed."
::= { nmcNtp 2 }

nmcNtpSyncInterval OBJECT-TYPE
SYNTAX INTEGER (600..86400)
ACCESS read-write
STATUS mandatory
DESCRIPTION
"The synchronization interval between successive NTP 
requests in seconds."
::= { nmcNtp 3 }

nmcNtpOperationalMode OBJECT-TYPE
SYNTAX INTEGER{
  disabled(1),
  unicast(2)
}
ACCESS read-write
STATUS mandatory
DESCRIPTION
"The operational mode of the NTP client. In unicast mode, 
the NTP requests the current time from the primary NTP and 
uses the secondary NTP as a backup."
::= { nmcNtp 4 }

nmcNtpLastSyncTime OBJECT-TYPE
SYNTAX INTEGER
ACCESS read-only
STATUS mandatory
DESCRIPTION
"The time since the last successful NTP synchronization in 
seconds."
::= { nmcNtp 5 }

nmcNtpLastSyncServer OBJECT-TYPE
SYNTAX INTEGER{
  none(1),
  primary(2),
  secondary(3)
}
ACCESS read-only
STATUS mandatory
DESCRIPTION
"The last NTP server used to successfully synchronize time."
::= { nmcNtp 6 }

nmcNtpLastFailedTime OBJECT-TYPE
SYNTAX INTEGER
ACCESS read-only
STATUS mandatory
DESCRIPTION
"The time since the last failed NTP synchronization attempt 
in seconds."
::= { nmcNtp 7 }

nmcNtpLastFailedServer OBJECT-TYPE
SYNTAX INTEGER{
  none(1),
  primary(2),
  secondary(3)
}
ACCESS read-only
STATUS mandatory
DESCRIPTION
"The last NTP server used in a failed attempt to synchronize 
time."
::= { nmcNtp 8 }

END
