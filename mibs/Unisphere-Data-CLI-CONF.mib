-- *****************************************************************************
-- Unisphere-Data-CLI-CONF
--
-- SNMP Agent Capabilities definitions for the CLI MIB.
--
-- Copyright (c) 2001 Unisphere Networks, Inc.  All rights reserved.
-- *****************************************************************************

Unisphere-Data-CLI-CONF DEFINITIONS ::= BEGIN

IMPORTS
    MODULE-IDENTITY
        FROM SNMPv2-SMI
    AGENT-CAPABILITIES
        FROM SNMPv2-CONF
    usDataAgents
        FROM Unisphere-Data-Agents
    usdCliGroup,
    usdCliSecurityAlertGroup,
    usdCliSecurityTrapGroup
        FROM Unisphere-Data-CLI-MIB;

usdCliAgent MODULE-IDENTITY
    LAST-UPDATED "200103272230Z"  -- 27-Mar-01 05:30 PM EST
    ORGANIZATION "Unisphere Networks, Inc."
    CONTACT-INFO
        "       Unisphere Networks, Inc.
        Postal: 10 Technology Park Drive
                Westford, MA  01886
                USA
        Tel:    +1 978 589 5800
        E-mail: mib@UnisphereNetworks.com"
    DESCRIPTION
        "The agent capabilities definitions for the CLI Security Management
        component of the SNMP agent in the Unisphere Routing Switch family of
        products."
    -- Revision History
    REVISION    "200103272230Z"  -- 27-Mar-01 05:30 PM EST  - RX 3.2
    DESCRIPTION
        "The initial release of this management information module."
    ::= { usDataAgents 6 }

usdCliAgentV1 AGENT-CAPABILITIES
    PRODUCT-RELEASE
        "Version 1 of the CLI Security Management component of the Unisphere
        Routing Switch SNMP agent.  This version of the CLI Security Management
        component is supported in the Unisphere RX 1.3 and subsequent system
        releases."
    STATUS      current
    DESCRIPTION
        "The MIB supported by the SNMP agent for the CLI Security Management
        application in the Unisphere Routing Switch."

    SUPPORTS        Unisphere-Data-CLI-MIB
        INCLUDES  { usdCliGroup,
                    usdCliSecurityAlertGroup,
                    usdCliSecurityTrapGroup }

    ::= { usdCliAgent 1 }

END
