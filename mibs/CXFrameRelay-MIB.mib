CXFrameRelay-MIB DEFINITIONS ::= BEGIN

--#CURRENT-VERSION 6  

IMPORTS
   Counter, TimeTicks      FROM RFC1155-SMI
   OBJECT-TYPE     FROM RFC-1212
   TRAP-TYPE               FROM RFC-1215
   cxFrameRelay,SapIndex,Alias
          FROM CXProduct-SMI
   cxModuleHwPhysSlot      FROM CXModuleHardware-MIB;

-- Proprietary Data Types

DLCI    ::=     INTEGER (1..1022)



--  Service Access Point Configuration Table

--  The table describing:
--      parameters required to configure a frame relay module service access 
--      point
--      statistics available for monitoring any frame relay module service 
--      access point
--      parameters required to configure traps at frame relay module service 
--      access points


frpSapTable OBJECT-TYPE
   SYNTAX  SEQUENCE OF FrpSapEntry
   ACCESS  not-accessible
   STATUS  mandatory
   DESCRIPTION
"A table containing configuration information about each frame relay 
module service access point."
   REFERENCE
     "Draft American National Standard T1.617-1991, Annex D"
   ::= { cxFrameRelay 1 }


   frpSapEntry OBJECT-TYPE
     SYNTAX  FrpSapEntry
     ACCESS  not-accessible
     STATUS  mandatory
     DESCRIPTION
"The parameters for a particular frame relay module service access point."
     INDEX { frpSapNumber }
     ::= { frpSapTable 1 }

     FrpSapEntry ::=
     SEQUENCE {
        frpSapNumber                            SapIndex,
        frpSapRowStatus                 INTEGER,
        frpSapAlias                             Alias,
        frpSapCompanionAlias                    Alias,
        frpSapType                              INTEGER,
        frpSapAddressLength                     INTEGER,
        frpSapMaxSupportedVCs           INTEGER,
        frpSapVCBase                            INTEGER,
        frpSapOutCongestionManagement   INTEGER,
        frpSapResourceAllocation                INTEGER,
        frpSapLinkManagement            INTEGER,
        frpSapInterfaceType                     INTEGER,
        frpSapPollingInterval                   INTEGER,
        frpSapPollingVerification               INTEGER,
        frpSapFullEnquiryInterval               INTEGER,
        frpSapErrorThreshold                    INTEGER,
        frpSapMonitoredEvents                   INTEGER,   
        frpSapMode                              INTEGER,
        frpSapPrioQueue1HitRatio                INTEGER,
        frpSapPrioQueue2HitRatio                INTEGER,
        frpSapPrioQueue3HitRatio                INTEGER,
        frpSapPrioQueue4HitRatio                INTEGER,
        frpSapDialEntry                         INTEGER,
        frpSapFilterBitMap                      INTEGER,
        frpSapLmiFlavor                         INTEGER,
        frpSapGenerator                         INTEGER,
        frpSapGeneratorDlciNumber               DLCI,
        frpSapGeneratorFrameSize                INTEGER,
        frpSapGeneratorNumberOfFrames           INTEGER,
        frpSapGeneratorInterFrameDelay          INTEGER,
        frpSapBillingTimer                      INTEGER,
        frpSapSdLmMessageInterval               INTEGER,
        frpSapSdLmActiveTimer                   INTEGER,
        frpSaptrapTrap1                         INTEGER,
        frpSapControl                           INTEGER,
        frpSapControlStats                      INTEGER,
        frpSapstatLinkManagementState           INTEGER,
        frpSapstatCurrentLinkManagementType     INTEGER,
        frpSapstatTxDataFrames                  Counter,
        frpSapstatRxDataFrames                  Counter,
        frpSapstatTxDataOctets                  Counter,
        frpSapstatRxDataOctets                  Counter,
        frpSapstatTxLmiFrames                   Counter,
        frpSapstatRxLmiFrames                   Counter,
        frpSapstatTxQueuedDiscards              Counter,
        frpSapstatRxCIRExceededDiscards         Counter,
        frpSapstatRxSysCongestionDiscards       Counter,
        frpSapstatRxUnavailInboundDiscards      Counter,
        frpSapstatRxUnavailOutboundDiscards     Counter,
        frpSapstatRxInvalidVCDiscards           Counter,
        frpSapstatRxBadStatusDiscards           Counter,
        frpSapstatRxMiscellaneousDiscards       Counter,
        frpSapstatRxCIRExceeds                  Counter,
        frpSapstatRxShortFrameDiscards          Counter,
        frpSapstatLmiInvalidFieldDiscards       Counter,
        frpSapstatLmiInvalidSequenceDiscards    Counter,
        frpSapstatLmiTimeouts                   Counter,
        frpSapstatLmiInvalidStatusDiscards      Counter,
        frpSapstatLmiInvalidStatusEnqDiscards   Counter,
        frpSapstatLmiInvalidUpdStatusDiscards   Counter
        }


 
   frpSapNumber OBJECT-TYPE
     SYNTAX  SapIndex
     ACCESS  read-only
     STATUS  mandatory
     DESCRIPTION
"Indicates the row containing objects for configuring (or monitoring) a 
SAP that is associated with another SAP either in the Bit-Oriented 
Protocol (BOP) Driver, B-Channel Manager (BCM) (CX900 only), SMDS/ATM Data 
Exchange Interface (SDXI/ADXI) (CX1000 only), Frame Relay Interface Module 
(FRIM), Gateway Mux/Frame Relay Module (GMF), or Gateway Frame Relay/Frame 
Relay (GFF) (CX1000 only) software layer.

Options:
1 - 7: (CX900's BOP- or BCM-related lower SAPs)

1 - 16: (CX1000's BOP- or DXI-related lower SAPs)

17 - 32: (CX1000's GFF-related lower SAPs)

40: (GMF-related upper SAP)

41: (FRIM-related upper SAP)

Default Value: none"

     ::= { frpSapEntry 1 }


   frpSapRowStatus OBJECT-TYPE
     SYNTAX  INTEGER {
          invalid         (1),
          valid           (2)
          }
     ACCESS  read-write
     STATUS  mandatory
     DESCRIPTION
"Determines the status of the objects in a table row.

Options:
invalid (1): Row is deleted from the table immediately, however values are 
still in effect until the next reset. 

valid (2): Use this value to add a new row to the table, or modify an 
existing row.

Default Value: none

Configuration Changed: administrative "
     ::= { frpSapEntry 2 }


   frpSapAlias OBJECT-TYPE
     SYNTAX  Alias
     ACCESS  read-write
     STATUS  mandatory
     DESCRIPTION
"Determines the textual name identifying this SAP.

Range of Values:
CX1000: 0 - 35 alphanumeric characters beginning with a non-numeric character

CX900: 0 - 16 alphanumeric characters beginning with a non-numeric character


Default Value: 
frsap1 (for frpSapNumber 1) 

frsap2 (for frpSapNumber 2) 

frsap3 (for frpSapNumber 3) 

frsap4 (for frpSapNumber 4) 

frsap5 (for frpSapNumber 5)

frsap6 (for frpSapNumber 6) 

frsap7 (for frpSapNumber 7) 

frsap8 (for frpSapNumber 8) 

frsap9 (for frpSapNumber 9) 

frsap10 (for frpSapNumber 10) 

frsap11 (for frpSapNumber 11) 

frsap12 (for frpSapNumber 12) 

frsap13 (for frpSapNumber 13) 

frsap14 (for frpSapNumber 14) 

frsap15 (for frpSapNumber 15) 

frsap16 (for frpSapNumber 16) 

frsap17 (for frpSapNumber 17) 

frsap18 (for frpSapNumber 18) 

frsap19 (for frpSapNumber 19) 

frsap20 (for frpSapNumber 20) 

frsap21 (for frpSapNumber 21) 

frsap22 (for frpSapNumber 22) 

frsap23 (for frpSapNumber 23) 

frsap24 (for frpSapNumber 24) 

frsap25 (for frpSapNumber 25) 

frsap26 (for frpSapNumber 26) 

frsap27 (for frpSapNumber 27) 

frsap28 (for frpSapNumber 28) 

frsap29 (for frpSapNumber 29) 

frsap30 (for frpSapNumber 30) 

frsap31 (for frpSapNumber 31) 

frsap32 (for frpSapNumber 32) 

frsap40 (for frpSapNumber 40)

frsap41 (for frpSapNumber 41)

Configuration Changed: administrative "
     ::= { frpSapEntry 3 }


   frpSapCompanionAlias OBJECT-TYPE
     SYNTAX  Alias
     ACCESS  read-write
     STATUS  mandatory
     DESCRIPTION
"Determines the textual name identifying this SAP's companion SAP in 
either the Frame Relay Interface Module, the Bit-Oriented Protocol (BOP) 
Driver, the SMDS/ATM Data Exchange Interface (SDXI/ADXI) (CX1000), the 
Gateway MUX/ Frame Relay (GMF), or the Gateway Frame Relay/Frame Relay 
(GFF) (CX1000) software layer.

Range of Values:

CX1000: 0 - 35 alphanumeric characters beginning with a non-numeric character 

CX900: 0-16 alphanumeric characters beginning with a non-numeric character 

Default Value:
FrPort.11-FrPort.71 (locked for CX900's frpSapNumber 1-7)

bopsap1-16 (for CX1000's frpSapNumber 1-16)

gffsap17-32 (for CX1000's frpSapNumber 17-32)

undefined (for frpSapNumber 40-41)

Configuration Changed: administrative "
     ::= { frpSapEntry 4 }


   frpSapType OBJECT-TYPE
     SYNTAX  INTEGER {
            lower               (1),
          upper           (2)
          }
     ACCESS  read-write
     STATUS  mandatory
     DESCRIPTION
"Determines this SAP's type.

Options:
lower (1): SAP is a lower type (leads to a physical port, or to an 
intervening SAP in the SMDS/ATM Data Exchange Interface software layer 
(CX1000 only), or to a SAP in the Gateway Frame Relay/Frame Relay software 
layer) (CX1000 only).

upper (2): SAP is a upper type (leads to a logical port in Frame Relay 
Interface Module or Gateway MUX/Frame Relay software layer.

Default Value: none

Configuration Changed: administrative "
     ::= { frpSapEntry 5 }


   frpSapAddressLength OBJECT-TYPE
     SYNTAX  INTEGER {
          two-octets      (2),
          three-octets    (3),
          four-octets     (4)
          }
     ACCESS  read-write
     STATUS  mandatory
     DESCRIPTION
"Determines the address length in octets that will be used for DLCIs. This 
length includes control data for Q.922 format. This object is meaningful 
only if 'frpSapType' for this SAP is set to 'lower'.

Options:
two-octets (2): two octets

three-octets (3): three octets (for future use)

four-octets (4): four octets (for future use)

Default Value: two-octets (2)

Configuration Changed: administrative "
     REFERENCE
        "Draft American National Standard T1.618-1991,
Section 3.2"
     DEFVAL { two-octets }
     ::= { frpSapEntry 6 }



--   The next two objects have been become obsolete!  In order to support 
--   older versions of the SunNet Manager with newer FR600 softwares, it is 
--   mandatory that an error NEVER be returned when an SNMP request attempts 
--   to "set" or "get" their values.
--    Note however, that their values will never update!!!

   frpSapMaxSupportedVCs OBJECT-TYPE
     SYNTAX  INTEGER (1..1022)
     ACCESS  read-write
     STATUS  deprecated
     DESCRIPTION
"Determines the maximum number of virtual circuits allowed for this SAP. 
Changing this maximum number no longer takes effect; the system now 
manages it dynamically. This object remains in the Frame Relay MIB to 
support older software that interacts with this MIB object.

Range of Values: 1 - 1,022 (locked at 1,022)

Default Value: 1,022"
     ::= { frpSapEntry 7 }


   frpSapVCBase OBJECT-TYPE
     SYNTAX  INTEGER (1..1022)
     ACCESS  read-write
     STATUS  deprecated
     DESCRIPTION
"Determines the base value used for virtual circuit numbering at this SAP. 
Changing this base value no longer takes effect; the system now manages it 
dynamically. This object remains in the Frame Relay MIB to support older 
software (revision 2.0 and earlier) that interacts with this MIB object.

Range of Values: 1 - 1,022 (locked at 1)

Default Value: 1"
     ::= { frpSapEntry 8 }



   frpSapOutCongestionManagement OBJECT-TYPE
     SYNTAX  INTEGER {
          disabled        (1),
          enabled (2)
          }
     ACCESS  read-write
     STATUS  mandatory
     DESCRIPTION
"Determines whether outbound congestion management has been enabled for 
this SAP. If enabled, congestion management techniques control the data 
flow out the SAP.

Options:
disabled (1): congestion management is disabled

enabled (2): congestion management is enabled

Default Value: disabled (1)

Configuration Changed: operative "
     DEFVAL { disabled }
     ::= { frpSapEntry 9 }


   frpSapResourceAllocation OBJECT-TYPE
     SYNTAX  INTEGER (1..99)
     ACCESS  read-write
     STATUS  mandatory
     DESCRIPTION
"Determines the virtual resources available to this SAP at any time as a 
percentage of total system resources.

Range of Values: 1 - 99

Default Value: 80

Configuration Changed: operative "
     DEFVAL { 80 }
     ::= { frpSapEntry 10 }


   frpSapLinkManagement OBJECT-TYPE
     SYNTAX  INTEGER {
          none                    (1),
          frameRelayForum         (2),
          ansiAnnexD              (3),
          ccittAnnexA             (4),
          dama1                   (5),
          dama2                   (6),
          auto                    (7)
          }
     ACCESS  read-write
     STATUS  mandatory
     DESCRIPTION
"Determines the link management standard for the Frame Relay interface. 
This object is meaningful only if object frpSapType for this SAP is set to 
'lower'.

Options:
none (1): no link management

frameRelayForum (2): Frame Relay Forum

ansiAnnexD (3): ANSI T1.617 Annex D

ccittAnnexA (4): CCITT Q.933 Annex A

dama1 (5): DAMA management on DLCI 990, same port

dama2 (6): DAMA management on DLCI 990, port 3

auto (7): auto discover which link management standard being used by UNI network.
          It can be set only if the object frpSapInterfaceType is uniUser.

Default Value: none

Configuration Changed: administrative "
     DEFVAL { none }
     ::= { frpSapEntry 11 }


   frpSapInterfaceType OBJECT-TYPE
     SYNTAX  INTEGER {
          uniUser (1),
          uniNetwork      (2),
          nni             (3)
          }
     ACCESS  read-write
     STATUS  mandatory
     DESCRIPTION
"Determines the signalling behavior of the SAP. This object is meaningful 
only if object frpSapType for this SAP is set to 'lower'.

Options:
uniUser (1): UNI User

uniNetwork (2): UNI Network

nni (3): NNI

Default Value: uniUser (1)

Configuration Changed: administrative "
     DEFVAL { uniUser }
     ::= { frpSapEntry 12 }


   frpSapPollingInterval OBJECT-TYPE
     SYNTAX  INTEGER (5..30)
     ACCESS  read-write
     STATUS  mandatory
     DESCRIPTION
"Determines the interval in seconds between successive 'Status Enquiry' 
messages initiated on the user side of a UNI (user to network interface). 
This object is meaningful only if object frpSapType for this SAP is set to 
'lower'.

Range of Values: 5 - 30

Default Value: 10

Configuration Changed: administrative "
     REFERENCE
        "Draft American National Standard T1.617-1991,
Section D.7 Timer 
        T391"
     DEFVAL { 10 }
     ::= { frpSapEntry 13 }


   frpSapPollingVerification OBJECT-TYPE
     SYNTAX           INTEGER (5..30)
     ACCESS           read-write
     STATUS  mandatory
     DESCRIPTION
"Determines the permitted interval in seconds between transmission of a 
'Status' and reception of a 'Status Enquiry' on the network side of the 
UNI (user to network interface). This object is meaningful only if object 
frpSapType for this SAP is set to 'lower'.

Range of Values: 5 - 30

Default Value: 15

Configuration Changed: administrative "
     REFERENCE
        "Draft American National Standard T1.617-1991,
Section D.7 Timer 
        T392"
     DEFVAL { 15 }
     ::= { frpSapEntry 14 }


   frpSapFullEnquiryInterval OBJECT-TYPE
     SYNTAX  INTEGER (1..255)
     ACCESS  read-write
     STATUS  mandatory
     DESCRIPTION
"Determines the number of 'Status Enquiry' intervals that must pass before 
a 'Full Status Enquiry' message can be issued at the user side of the UNI 
(user to network interface). This object is meaningful only if object 
frpSapType for this SAP is set to 'lower'.

Range of Values: 1 - 255

Default Value: 6

Configuration Changed: administrative "
     REFERENCE
        "Draft American National Standard T1.617-1991,
Section D.7 Counter 
        N391"
     DEFVAL { 6 }
     ::= { frpSapEntry 15 }



   frpSapErrorThreshold OBJECT-TYPE
     SYNTAX  INTEGER (1..10)
     ACCESS  read-write
     STATUS  mandatory
     DESCRIPTION
"Determines the number of unanswered 'Status Enquiry' messages that can 
occur within the interval defined in object frpSapMonitoredEvents before 
the user side of the UNI (user to network interface) declares the 
interface to be down. The value of frpSapErrorThreshold must not be 
greater than the value of frpSapMonitoredEvents. This object is meaningful 
only if object frpSapType for this SAP is set to 'lower'.

OR

Determines the number of timeouts that can occur within the interval 
defined in frpSapMonitoredEvents as result of not receiving a 'Status 
Enquiry' from a user before the network side of the UNI (user to network 
interface) declares the interface to be down. This object is meaningful 
only if object frpSapType for this SAP is set to 'lower'.

Range of Values: 1-10

Default Value: 3

Configuration Changed: administrative "
     REFERENCE
        "Draft American National Standard T1.617-1991,
Section D.5.1 & D.7 
        Counter N392"
     DEFVAL { 3 }
     ::= { frpSapEntry 16 }


   frpSapMonitoredEvents OBJECT-TYPE
     SYNTAX  INTEGER (1..10)
     ACCESS  read-write
     STATUS  mandatory
     DESCRIPTION
"Determines the number of polling intervals that will be monitored at any 
one time for unanswered messages, unreceived messages, or messages 
received in error. This period must pass without frpSapErrorThreshold 
being exceeded before an interface can be brought up after being brought 
down because unanswered messages, unreceived messages, or messages 
received in error exceeded frpSapErrorThreshold. The value of 
frpSapMonitoredEvents must be greater than the value of 
frpSapErrorThreshold. This object is meaningful only if object frpSapType 
for this SAP is set to 'lower'.

Range of Values: 1 - 10

Default Value: 4

Configuration Changed: administrative "
     REFERENCE
        "Draft American National Standard T1.617-1991,
Section D.5.2 & D.7 
        Counter N393"
     DEFVAL { 4 }
     ::= { frpSapEntry 17 }

   frpSapMode OBJECT-TYPE
     SYNTAX  INTEGER {
          frameRelay          (1),
          transparent         (2),
          frameRelayAtmNIwf   (3)   
          }
     ACCESS  read-write
     STATUS  mandatory
     DESCRIPTION
"Determines whether data passing through this SAP will be encapsulated.

OR

Determines this SAP will network interwork with ATM.

Options:
frameRelay (1): mode is Frame Relay (data received/transmitted encapsulated)

transparent (2): mode is transparent (data received/transmitted unencapsulated)

frameRelayAtmNIwf(3): mode is FrameRelay/ATM Network Interworking. When a SAP is created or 
                      changed to this mode, a row in frpAtmNISapTable will be 
                      automatically created with this SAP number as index. When a
                      SAP is deleted or changed from this mode, the correspondant 
                      row in frpAtmNISapTable will also be deleted.
                      

Default Value: frameRelay (1)

Configuration Changed: administrative "
     DEFVAL { frameRelay }
     ::= { frpSapEntry 18 }


   frpSapPrioQueue1HitRatio     OBJECT-TYPE
     SYNTAX  INTEGER
     ACCESS  read-write
     STATUS  mandatory
     DESCRIPTION
"Determines how frequently the queue for outbound traffic with very high 
priority is checked compared to queues having outbound traffic with high, 
medium or low priorities.

Note: Unless set to zero, this value forms part of a frequency ratio that 
includes values assigned to these other queue priorities. Associated 
queues are checked in proportion to assigned values (frequency ratio 
method). If set to zero, this queue priority's associated queue is checked 
only if queue priorities of all other queues have been set to zero and 
only if queues with higher priorities are empty (absolute priority 
method).

Range of Values: 0 - 255

Default Value: 0

Configuration Changed: administrative "
     DEFVAL {0}
     ::= { frpSapEntry 19 }


   frpSapPrioQueue2HitRatio     OBJECT-TYPE
     SYNTAX  INTEGER
     ACCESS  read-write
     STATUS  mandatory
     DESCRIPTION
"Determines how frequently the queue for outbound traffic with high 
priority is checked compared to queues having outbound traffic with very 
high, medium or low priorities.

Note: Unless set to zero, this value forms part of a frequency ratio that 
includes values assigned to these other queue priorities. Associated 
queues are checked in proportion to assigned values (frequency ratio 
method). If set to zero, this queue priority's associated queue is checked 
only if queue priorities of all other queues have been set to zero and 
only if queues with higher priorities are empty (absolute priority 
method).

Range of Values: 0 - 255

Default Value: 0

Configuration Changed: administrative "
     DEFVAL {0}
     ::= { frpSapEntry 20 }


   frpSapPrioQueue3HitRatio     OBJECT-TYPE
     SYNTAX  INTEGER
     ACCESS  read-write
     STATUS  mandatory
     DESCRIPTION
"Determines how frequently the queue for outbound traffic with medium 
priority is checked compared to queues having outbound traffic with very 
high, high or low priorities.

Note: Unless set to zero, this value forms part of a frequency ratio that 
includes values assigned to these other queue priorities. Associated 
queues are checked in proportion to assigned values (frequency ratio 
method). If set to zero, this queue priority's associated queue is checked 
only if queue priorities of all other queues have been set to zero and 
only if queues with higher priorities are empty (absolute priority 
method).

Range of Values: 0 - 255

Default Value: 0

Configuration Changed: administrative "
      DEFVAL {0}
     ::= { frpSapEntry 21 }


   frpSapPrioQueue4HitRatio     OBJECT-TYPE
     SYNTAX  INTEGER
     ACCESS  read-write
     STATUS  mandatory
     DESCRIPTION
"Determines how frequently the queue for outbound traffic with low 
priority is checked compared to queues having outbound traffic with very 
high, high or medium priorities.

Note: Unless set to zero, this value forms part of a frequency ratio that 
includes values assigned to these other queue priorities. Associated 
queues are checked in proportion to assigned values (frequency ratio 
method). If set to zero, this queue priority's associated queue is checked 
only if queue priorities of all other queues have been set to zero and 
only if queues with higher priorities are empty (absolute priority 
method).

Range of Values: 0 - 255

Default Value: 0

Configuration Changed: administrative "
      DEFVAL {0}
     ::= { frpSapEntry 22 }


   frpSapDialEntry     OBJECT-TYPE
     SYNTAX  INTEGER (0..255)
     ACCESS  read-write
     STATUS  mandatory
     DESCRIPTION
"Determines the entry of the Dial table containing information that this 
SAP will use to perform its dialup function.

Range of Values: 0 - 255

Default Value: 0 (dialup function not supported)

Configuration Changed: administrative "
      DEFVAL {0}
     ::= { frpSapEntry 23 }



   frpSapFilterBitMap     OBJECT-TYPE
     SYNTAX  INTEGER (0..65535)
     ACCESS  read-write
     STATUS  mandatory
     DESCRIPTION
"A bit map of 2 bytes that determines the type of frame.

Range of Values: 0 - 65535

Default Value: 0 (do not filter any type of frame)

Configuration Changed: administrative "
      DEFVAL {0}
   --#STARTING-VERSION 3
     ::= { frpSapEntry 24 }

   frpSapLmiFlavor OBJECT-TYPE
     SYNTAX  INTEGER {
          other       (1),
          strict      (2),
          tolerant    (3)
          }
     ACCESS  read-write
     STATUS  mandatory
     DESCRIPTION
"Determines optional behavior for the Link Management.  This object
is required due to the variety of requirement from Frame Relay 
certification agency.  The Sprint certification for example requires 
this object to be set to 'strict'.  Configuring other (1) is 
equivalent in our implementation as a value of strict (2).

Options:
other (1): depending on implementation.

strict (2): duplication of fields, DLCI IE out of sequence, ... are considered
            errors.

tolerant (3): the software is more permissive in its error handling.

Default Value: tolerant (3)

Configuration Changed: operative "
     DEFVAL { tolerant }
   --#STARTING-VERSION 4
     ::= { frpSapEntry 25 }


-- gap (15) for future parameters
--      1 used for "frpSapMode"
--      4 used for "frpSapPrioQueue1HitRatio" ... 
--      "frpSapPrioQueue4HitRatio".
--      1 used for "frpSapDialEntry"
--      1 used for "frpSapFilterBitMap"
--      1 used for "frpSapLmiFlavor"
   


   frpSapGenerator OBJECT-TYPE
     SYNTAX  INTEGER {
          disabled        (1),
          enabled (2),
          retrigger       (3)
          }
     ACCESS  read-write
     STATUS  mandatory
      DESCRIPTION
"Determines whether this SAP generates for diagnostic purposes the number 
of frames set by object frpSapGeneratorNumberOfFrames of a size set in 
'frpSapGeneratorFrameSize' to be inserted in frpSapGeneratorDlciNumber.

Options:
disabled (1): frame generator is disabled for the circuit specified at 
this SAP

enabled (2): frame generator is enabled after a system reset to generate a 
sequence of frames for the circuit specified at this SAP.

retrigger (3): frame generator is enabled immediately to generate a 
sequence of frames for the circuit specified at this SAP.

Default Value: disabled

Configuration Changed: operative "
      DEFVAL { disabled }
     ::= { frpSapEntry 33 }


   frpSapGeneratorDlciNumber OBJECT-TYPE
     SYNTAX  DLCI
     ACCESS  read-write
     STATUS  mandatory
      DESCRIPTION
"Determines the DLCI (Data Link Connection Identifier) to be used for each 
frame generated for this SAP.

Range of Values: 1 - 1,022

Default Value: 16

Configuration Changed: operative "
     DEFVAL { 16 }
     ::= { frpSapEntry 34 }


   frpSapGeneratorFrameSize OBJECT-TYPE
     SYNTAX  INTEGER (32..4096)
     ACCESS  read-write
     STATUS  mandatory
     DESCRIPTION
"Determines the size of each frame generated for this SAP.

Range of Values: 32 - 4096

Default Value: 32

Configuration Changed: operative "
     DEFVAL { 32 }
     ::= { frpSapEntry 35 }


   frpSapGeneratorNumberOfFrames OBJECT-TYPE
     SYNTAX  INTEGER (1..200)
     ACCESS  read-write
     STATUS  mandatory
     DESCRIPTION
"Determines the number of frames to be generated for this SAP.

Range of Values: 1 - 200 (200=continuous)

Default Value: 1

Configuration Changed: operative "
     DEFVAL { 1 }
     ::= { frpSapEntry 36 }


   frpSapGeneratorInterFrameDelay OBJECT-TYPE
     SYNTAX  INTEGER (50..60000)
     ACCESS  read-write
     STATUS  mandatory
     DESCRIPTION
"Determines the time in milliseconds that must pass between frames 
generated for this SAP.

Range of Values: 50 - 60,000

Default Value: 50

Configuration Changed: operative "
     DEFVAL { 50 }
     ::= { frpSapEntry 37 }


   frpSapBillingTimer OBJECT-TYPE
     SYNTAX  INTEGER (1..525600)
     ACCESS  read-write
     STATUS  mandatory
     DESCRIPTION
"Determines the time in minutes that must pass before generating an 
frpPvcBillingStats trap for each circuit whose frpCircuittrapTrap2 object 
has been enabled. Unless retriggered with frpSapControl, this timer must 
expire before a change in its value can take effect.

Range of Values: 1 - 525,600

Default Value: 1440

Configuration Changed: operative "
     DEFVAL { 1440 }
     ::= { frpSapEntry 38 }

   frpSapSdLmMessageInterval    OBJECT-TYPE
     SYNTAX  INTEGER (10..65535)
     ACCESS  read-write
     STATUS  obsolete
     DESCRIPTION
"Determines the time in milliseconds that must pass between successive 
connection management messages that report the same event. This object is 
meaningful only if frpSapLinkManagement for this SAP is set to DAMA1 or DAMA2.

Range of Values: 10 - 65,535

Default Value: 50

Configuration Changed: operative "
     DEFVAL { 50 }
     --#ENDING-VERSION 6
     ::= { frpSapEntry 39 }

   frpSapSdLmActiveTimer   OBJECT-TYPE
     SYNTAX  INTEGER (10..65535)
     ACCESS  read-write
     STATUS  obsolete
     DESCRIPTION
"Determines the number of milliseconds that an inactive virtual circuit 
can continue to be seen in an active state before being changed to an idle 
state. This object is meaningful only if frpSapLinkManagement for this SAP 
is set to DAMA1 or DAMA2.

Range of Values: 10 - 65,535

Default Value: 1,000

Configuration Changed: operative "
     DEFVAL { 1000 }
     --#ENDING-VERSION 6
     ::= { frpSapEntry 40 }



-- gap (11) for future parameters
--      1 already used up for "frpSapGeneratorInterFrameDelay"
--      1 already used up for "frpSapBillingTimer"
--      1 already used up for "frpSapSdLmMessageInterval"
--      1 already used up for "frpSapSdLmActiveTimer"


   frpSaptrapTrap1 OBJECT-TYPE
     SYNTAX  INTEGER {
          disabled        (1),
          enabled (2)
          }
     ACCESS  read-write
     STATUS  mandatory
     DESCRIPTION
"Determines whether this SAP produces the frpSapInterfaceStatusChange trap 
whose accumulated value can be retrieved by an SNMP-compliant network 
management device.

Options:
disabled (1): SAP does not produce an interface status change

enabled (2): SAP produces an interface status change trap

Default Value: disabled (1)

Configuration Changed: operative "
   DEFVAL { disabled }
     ::= { frpSapEntry 48 }


-- gap (6) for future traps and write-controls
--      1 already used up for "frpSapControl"
--      1 already used up for "frpSapControlStats"


   frpSapControl OBJECT-TYPE
     SYNTAX  INTEGER {
          retriggerBillingTimer   (1)
          }
     ACCESS  write-only
     STATUS  mandatory
     DESCRIPTION
"Cancels and resets a SAP's frpSapBillingTime'.

Options:
retriggerBillingTimer (1): retriggers billing timer at this SAP

Default Value: none

Configuration Changed: operative "
     ::= { frpSapEntry 53 }


   frpSapControlStats OBJECT-TYPE
     SYNTAX  INTEGER {
          clearSapStats           (1),
          clearAllCircuitStats    (2)
          }
     ACCESS  write-only
     STATUS  mandatory
     DESCRIPTION
"Controls the handling of statistics for this SAP.

Options:
clearSapStats (1): clears all statistics at this SAP

clearAllCircuitStats (2): clears statistics of all circuits associated 
with this SAP

Default Value: none

Configuration Changed: operative "
     ::= { frpSapEntry 54 }


   frpSapstatLinkManagementState OBJECT-TYPE
     SYNTAX  INTEGER {
          linkDown        (1),
          linkUp          (2)
          }
     ACCESS  read-only
     STATUS  mandatory
     DESCRIPTION
"Indicates the state of link management at this SAP.

Options:
linkDown (1): link management is down

linkUp (2): link management (and link itself) is up

Default Value: none"
     ::= { frpSapEntry 55 }

   frpSapstatCurrentLinkManagementType OBJECT-TYPE
     SYNTAX  INTEGER  {
             none                 (1),
             frameRelayForum      (2),
             ansiAnnexD           (3),
             ccittAnnexA          (4),
             dama1                (5),
             dama2                (6),
             discovering          (7)
             }
     ACCESS  read-only
     STATUS  mandatory
     DESCRIPTION
"Indicate the link management standard being used. 

none (1): no link management

frameRelayForum (2): Frame Relay Forum

ansiAnnexD (3): ANSI T1.617 Annex D

ccittAnnexA (4): CCITT Q.933 Annex A

dama1 (5): DAMA management on DLCI 999, same port

dama2 (6): DAMA management on DLCI 999, port 3

discovering (7):  on the process to detect which Link Management Standard being used 
                  The value is meaningful only if frpSapLinkManagement
                  is configured to auto(7),

Default Value: none"
--#STARTING-VERSION 2
     ::= { frpSapEntry 56 }


-- gap (5) for future states


   frpSapstatTxDataFrames OBJECT-TYPE
     SYNTAX  Counter
     ACCESS  read-only
     STATUS  mandatory
     DESCRIPTION
"Indicates the number of data frames sent from this SAP across all virtual 
circuits since the last power up.

Range of Values: 0 - 4,294,967,295

Default Value: none"
     ::= { frpSapEntry  61 }


   frpSapstatRxDataFrames OBJECT-TYPE
     SYNTAX  Counter
     ACCESS  read-only
     STATUS  mandatory
     DESCRIPTION
"Indicates the number of data frames received at this SAP across all 
virtual circuits since the last power up.

Range of Values: 0 - 4,294,967,295

Default Value: none"
     ::= { frpSapEntry 62 }


   frpSapstatTxDataOctets OBJECT-TYPE
     SYNTAX  Counter
     ACCESS  read-only
     STATUS  mandatory
     DESCRIPTION
"Indicates the number of data octets sent from this SAP across all virtual 
circuits since the last power up.

Range of Values: 0 - 4,294,967,295

Default Value: none"
     ::= { frpSapEntry 63 }


   frpSapstatRxDataOctets OBJECT-TYPE
     SYNTAX  Counter
     ACCESS  read-only
     STATUS  mandatory
     DESCRIPTION
"Indicates the number of data octets received at this SAP across all 
virtual circuits since the last power up.

Range of Values: 0-4,294,967,295

Default Value: none"
     ::= { frpSapEntry 64 }


   frpSapstatTxLmiFrames OBJECT-TYPE
     SYNTAX  Counter
     ACCESS  read-only
     STATUS  mandatory
     DESCRIPTION
"Indicates the number of link management interface frames sent from this 
SAP. This object is meaningful only if frpSapType for this SAP is set to 
'lower'.

Range of Values: 0 - 4,294,967,295

Default Value: none"
     ::= { frpSapEntry 65 }


   frpSapstatRxLmiFrames OBJECT-TYPE
     SYNTAX  Counter
     ACCESS  read-only
     STATUS  mandatory
     DESCRIPTION
"Indicates the number of link management interface frames received at this 
SAP. This object is meaningful only if object frpSapType for this SAP is 
set to 'lower'.

Range of Values: 0 - 4,294,967,295

Default Value: none"
     ::= { frpSapEntry  66 }


   frpSapstatTxQueuedDiscards OBJECT-TYPE
     SYNTAX  Counter
     ACCESS  read-only
     STATUS  mandatory
     DESCRIPTION
"Indicates the number of outbound data frames discarded at this SAP due to 
interface congestion, circuit unavailability (status down), or unspecified 
routing (circuit deleted or never added).

Range of Values: 0 - 65,535

Default Value: none"
     ::= { frpSapEntry 67 }


-- gap (11) for future transmit type statistics


   frpSapstatRxCIRExceededDiscards OBJECT-TYPE
     SYNTAX  Counter
     ACCESS  read-only
     STATUS  mandatory
     DESCRIPTION
"Indicates the number of data frames received and then discarded at this 
SAP across all virtual circuits because the combined value of 
frpCircuitCommittedBurst and frpCircuitExcessBurst has been exceeded.

Range of Values: 0 - 65,535

Default Value: none"
     ::= { frpSapEntry 79 }


   frpSapstatRxSysCongestionDiscards OBJECT-TYPE
     SYNTAX  Counter
     ACCESS  read-only
     STATUS  mandatory
     DESCRIPTION
"Indicates the number of data frames received and then discarded at this 
SAP across all virtual circuits due to system congestion.

Range of Values: 0 - 65,535

Default Value: none"
     ::= { frpSapEntry 80 }


   frpSapstatRxUnavailInboundDiscards OBJECT-TYPE
     SYNTAX  Counter
     ACCESS  read-only
     STATUS  mandatory
     DESCRIPTION
"Indicates the number of data frames received and then discarded at this 
SAP across all virtual circuits due to unavailability of an inbound 
virtual circuit.

Range of Values: 0 - 65,535

Default Value: none"
     ::= { frpSapEntry 81 }


   frpSapstatRxUnavailOutboundDiscards OBJECT-TYPE
     SYNTAX  Counter
     ACCESS  read-only
     STATUS  mandatory
     DESCRIPTION
"Indicates the number of data frames received and then discarded at this 
SAP across all virtual circuits due to unavailability of an outbound 
virtual circuit or to no routing specified.

Range of Values: 0 - 65,535

Default Value: none"
     ::= { frpSapEntry 82 }


   frpSapstatRxInvalidVCDiscards OBJECT-TYPE
     SYNTAX  Counter
     ACCESS  read-only
     STATUS  mandatory
     DESCRIPTION
"Indicates the number of data frames received and then discarded at this 
SAP across all virtual circuits due to an invalid DLCI.

Range of Values: 0 - 65,535

Default Value: none"
     ::= { frpSapEntry 83 }


   frpSapstatRxBadStatusDiscards OBJECT-TYPE
     SYNTAX  Counter
     ACCESS  read-only
     STATUS  mandatory
     DESCRIPTION
"Indicates the number of data frames received and then discarded at this 
SAP across all virtual circuits due to invalid status specification within 
frames passed from the Bit-Oriented Protocol (BOP) Driver, the SMDS/ATM 
Data Exchange Interface (SDXI/ADXI) (CX1000 only), the Gateway Frame 
Relay/Frame Relay (CX1000 only), or B-Channel Manager (CX900 only) 
software layer.

Range of Values: 0 - 65,535

Default Value: none"
     ::= { frpSapEntry 84 }


   frpSapstatRxMiscellaneousDiscards OBJECT-TYPE
     SYNTAX  Counter
     ACCESS  read-only
     STATUS  mandatory
     DESCRIPTION
"Indicates the number of data frames received and then discarded at this 
SAP across all virtual circuits due to any invalid condition not specified 
by other discard type objects.

Range of Values: 0 - 65,535

Default Value: none"
     ::= { frpSapEntry 85 }


   frpSapstatRxCIRExceeds OBJECT-TYPE
     SYNTAX  Counter
     ACCESS  read-only
     STATUS  mandatory
     DESCRIPTION
"Indicates the number of times the combined value of 
frpCircuitCommittedBurst and frpCircuitExcessBurst has been exceeded in a 
'Tc' window at the inbound side of all virtual circuits of this SAP.

Note: A 'Tc' window is a time slice determined by dividing 
frpCircuitCommittedBurst by frpCircuitCommittedInformationRate.

Range of Values: 0 - 65,535

Default Value: none"
     ::= { frpSapEntry 86 }


   frpSapstatRxShortFrameDiscards OBJECT-TYPE
     SYNTAX  Counter
     ACCESS  read-only
     STATUS  mandatory
     DESCRIPTION
"Indicates the total number of short frames discarded at this SAP since 
power-up.

Note: A frame is short if it has less than two bytes for the header and 
one byte for user data when in Frame Relay mode, or if it has less than 
one byte when in Transparent mode.

Range of Values: 0 - 65,535

Default Value: none"
     ::= { frpSapEntry 87 }


-- gap (10) for future receive type statistics
--      1 already used up for "frpSapstatRxShortFrameDiscards"


   frpSapstatLmiInvalidFieldDiscards OBJECT-TYPE
     SYNTAX  Counter
     ACCESS  read-only
     STATUS  mandatory
     DESCRIPTION
"Indicates the number of link management frames received at this SAP that 
contained an invalid field and were consequently discarded. This object is 
meaningful only if object frpSapType for this SAP is set to 'lower'.

Range of Values: 0 - 65,535

Default Value: none"
     ::= { frpSapEntry 97 }


   frpSapstatLmiInvalidSequenceDiscards OBJECT-TYPE
     SYNTAX  Counter
     ACCESS  read-only
     STATUS  mandatory
     DESCRIPTION
"Indicates the number of link management frames received at this SAP that 
contained an unexpected Receive Sequence Number and were consequently 
discarded. This object is meaningful only if object frpSapType for this 
SAP is set to 'lower'.

Range of Values: 0 - 65,535

Default Value: none"
     ::= { frpSapEntry 98 }


   frpSapstatLmiTimeouts OBJECT-TYPE
     SYNTAX  Counter
     ACCESS  read-only
     STATUS  mandatory
     DESCRIPTION
"Indicates the number of times a link management frame was not received at 
this SAP within the expected time. This object is meaningful only if 
object frpSapType for this SAP is set to 'lower'.

Range of Values: 0 - 65,535

Default Value: none"
     ::= { frpSapEntry 99 }


   frpSapstatLmiInvalidStatusDiscards OBJECT-TYPE
     SYNTAX  Counter
     ACCESS  read-only
     STATUS  mandatory
     DESCRIPTION
"Indicates the number of invalid 'Status' management frames received at 
this SAP and subsequently discarded. This object is meaningful only if 
object frpSapType for this SAP is set to 'lower'.

Range of Values: 0 - 65,535

Default Value: none"
     ::= { frpSapEntry 100 }


   frpSapstatLmiInvalidStatusEnqDiscards OBJECT-TYPE
     SYNTAX  Counter
     ACCESS  read-only
     STATUS  mandatory
     DESCRIPTION
"Indicates the number of invalid 'Status Enquiry' management frames 
received at this SAP and subsequently discarded. This object is meaningful 
only if object frpSapType for this SAP is set to 'lower'.

Range of Values: 0 - 65,535

Default Value: none"
     ::= { frpSapEntry 101 }


   frpSapstatLmiInvalidUpdStatusDiscards OBJECT-TYPE
     SYNTAX  Counter
     ACCESS  read-only
     STATUS  mandatory
     DESCRIPTION
"Indicates the number of invalid 'Update Status' management frames 
received at this SAP and subsequently discarded. This object is meaningful 
only if object frpSapType for this SAP is set to 'lower'.

Range of Values: 0 - 65,535

Default Value: none"
     ::= { frpSapEntry 102 }




--  Virtual Circuit Configuration Table

--  The table describing:
--      parameters required to configure a virtual circuit at a frame relay 
--      service access point
--
--      statistics available for monitoring any virtual circuit at any frame 
--      relay module service access point
--
--      parameters required to configure virtual circuits traps at a frame 
--      relay service access point
--
--      parameters required to configure a route between any two virtual 
--      circuits at any frame relay module service access points

frpCircuitTable OBJECT-TYPE
   SYNTAX  SEQUENCE OF FrpCircuitEntry
   ACCESS  not-accessible
   STATUS  mandatory
   DESCRIPTION
"A table containing configuration information about virtual circuits at 
frame relay module service access points."
   ::= { cxFrameRelay 2 }


   frpCircuitEntry OBJECT-TYPE
     SYNTAX  FrpCircuitEntry
     ACCESS  not-accessible
     STATUS  mandatory
     DESCRIPTION
"The parameters for a particular virtual circuit at a specified frame 
relay module service access point."
     INDEX { frpCircuitSapNumber, frpCircuitDlci }
     ::= { frpCircuitTable 1 }


   FrpCircuitEntry ::=
     SEQUENCE {
        frpCircuitSapNumber                     SapIndex,
        frpCircuitDlci                          DLCI,
        frpCircuitRowStatus                     INTEGER,
        frpCircuitPriorityLevel                 INTEGER,
        frpCircuitCommittedBurst                INTEGER,
        frpCircuitExcessBurst                   INTEGER,
        frpCircuitCommittedInformationRate      INTEGER,
        frpCircuitCIRManagement                 INTEGER,
        frpCircuitMultiProtEncaps               INTEGER,
        frpCircuitHighPriorityBurst             INTEGER,
        frpCircuitLowPriorityBurst              INTEGER,
        frpCircuitFragmentationSize             INTEGER,
        frpCircuitAlias                         Alias,
        frpCircuitCompanionSapNumber            INTEGER,
        frpCircuitCompanionDlci                 INTEGER,
        frpCircuitAlternateSapNumber            INTEGER,
        frpCircuitAlternateDlci                 INTEGER,
        frpCircuitMulticastGroupId              INTEGER,
        frpCircuitMulticastType                 INTEGER,
        frpCircuitCompressionPort               INTEGER,
        frpCircuitExpressService                INTEGER,
        frpCircuittrapTrap1                     INTEGER,
        frpCircuittrapTrap2                     INTEGER,
        frpCircuitControlStats                  INTEGER,
        frpCircuitstatReportedState             INTEGER,
        frpCircuitstatRouteState                INTEGER,
        frpCircuitstatAlternateRouteState       INTEGER,
        frpCircuitstatLocalCreationTime         TimeTicks,
        frpCircuitstatRemoteCreationTime        TimeTicks,
        frpCircuitstatTxFrames                  Counter,
        frpCircuitstatRxFrames                  Counter,
        frpCircuitstatTxOctets                  Counter,
        frpCircuitstatRxOctets                  Counter,
        frpCircuitstatTxFECNs                   Counter,
        frpCircuitstatRxFECNs                   Counter,
        frpCircuitstatTxBECNs                   Counter,
        frpCircuitstatRxBECNs                   Counter,
        frpCircuitstatTxQueuedDiscards          Counter,
        frpCircuitstatRxCIRExceededDiscards     Counter,
        frpCircuitstatRxSysCongestionDiscards   Counter,
        frpCircuitstatRxUnavailInboundDiscards  Counter,
        frpCircuitstatRxUnavailOutboundDiscards Counter,
        frpCircuitstatRxCIRExceeds              Counter,
        frpCircuitstatFragmentationFailures     Counter,
        frpCircuitstatDeFragmentationFailures   Counter
        }


   frpCircuitSapNumber OBJECT-TYPE
     SYNTAX  SapIndex
     ACCESS  read-only
     STATUS  mandatory
     DESCRIPTION
"Indicates the row containing objects for configuring (or monitoring) one 
of 1,022 possible circuits of a SAP that is associated with another SAP 
either in the Bit-Oriented Protocol (BOP) Driver, B-Channel Manager (BCM) 
(CX900 only), SMDS/ATM Data Exchange Interface (SDXI/ADXI) (CX1000 only), 
Frame Relay Interface Module (FRIM), Gateway Mux/Frame Relay Module (GMF), 
or Gateway Frame Relay/Frame Relay (GFF) (CX1000 only) software layer.

Options:
1-7: (CX900's BOP- or BCM-related lower SAPs)

1-16: (CX1000's BOP- or DXI-related lower SAPs)

17-32: (CX1000's GFF-related lower SAPs)

40: (GMF-related upper SAP)

41: (FRIM-related upper SAP)

Default Value: none"
     ::= { frpCircuitEntry 1 }


   frpCircuitDlci OBJECT-TYPE
     SYNTAX  DLCI
     ACCESS  read-only
     STATUS  mandatory
     DESCRIPTION
"Indicates the virtual circuit's DLCI (Data Link Connection Identifier) 
for a particular SAP.

Note: A given SAP can have up to 1,022 virtual circuits associated with 
it, subject to system memory; each DLCI associated with a given SAP must 
be unique; DLCIs associated with a PX 600 in the same CX1000 chassis must 
be numbered 600 or greater.

Range of Values: 1 - 1,022

Default Value: none"
     ::= { frpCircuitEntry 2 }


   frpCircuitRowStatus OBJECT-TYPE
     SYNTAX  INTEGER {
          invalid         (1),
          valid           (2)
          }
     ACCESS  read-write
     STATUS  mandatory
     DESCRIPTION
"Determines whether this SAP/DLCI association, and any circuit linked with 
it, is to be deleted in the Frame Relay software layer.

Options:
invalid (1): Row is deleted from the table immediately, however values are 
still in effect until the next reset. 

valid (2): Use this value to add a new row to the table, or modify an 
existing row.

Default Value: valid (2)

Configuration Changed: operative "
     ::= { frpCircuitEntry 3 }


   frpCircuitPriorityLevel OBJECT-TYPE
     SYNTAX  INTEGER {       veryHigh        (1),
          high            (2),
          medium          (3),
          low             (4)
          }
     ACCESS  read-write
     STATUS  mandatory
     DESCRIPTION
"Determines the priority level assigned to this virtual circuit.

Note: Very high priority is reserved for for delay-sensitive traffic 
such as voice or fax. Higher priority traffic takes precedence over lower 
priority traffic.

Options:
veryHigh (1): circuit has very high priority

high (2): circuit has high priority

medium (3): circuit has medium priority

low (4): circuit has low priority

Default Value: medium (3)

Configuration Changed: operative "
     DEFVAL { medium }
     ::= { frpCircuitEntry 4 }


   frpCircuitCommittedBurst OBJECT-TYPE
     SYNTAX  INTEGER
     ACCESS  read-write
     STATUS  mandatory
     DESCRIPTION
"Determines the maximum number of inbound data bits that the Frame Relay 
module commits to transfer under normal conditions within an established 
measurement interval.

Range of Values: 0 - 2,048,000

Default Value: 0

Configuration Changed: operative "
     REFERENCE
        "Draft American National Standard T1.617-1991,
Section 6.5.19"
     DEFVAL { 0 }
     ::= { frpCircuitEntry 5 }


   frpCircuitExcessBurst OBJECT-TYPE
     SYNTAX  INTEGER
     ACCESS  read-write
     STATUS  mandatory
     DESCRIPTION
"Determines the maximum number of uncommitted inbound data bits that the 
Frame Relay module will attempt to transfer within an established 
measurement interval.

Range of Values: 0 - 512,000

Default Value: 0

Configuration Changed: operative "
     REFERENCE
        "Draft American National Standard T1.617-1991,
Section 6.5.19"
     DEFVAL { 0 }
     ::= { frpCircuitEntry 6 }


   frpCircuitCommittedInformationRate OBJECT-TYPE
     SYNTAX  INTEGER
     ACCESS  read-write
     STATUS  mandatory
     DESCRIPTION
"Determines the average inbound 'Frame Relay Information Field' bits 
transferred per second in one direction across the user side of a Frame 
Relay module during an established measurement interval.

Range of Values: 0 - 2,048,000

Default Value: none

Note: This value must be equal to or less than object 
frpCircuitCommittedBurst.

Configuration Changed: operative "
     REFERENCE
        "Draft American National Standard T1.617-1991,
Section 6.5.19"
     DEFVAL { 0 }  -- the default value is no commitment.
     ::= { frpCircuitEntry 7 }


   frpCircuitCIRManagement OBJECT-TYPE
     SYNTAX  INTEGER {
          disabled         (1),
          enabled-inbound  (2),
          monitor-inbound  (3),
          enabled-outbound (4)
          }
     ACCESS  read-write
     STATUS  mandatory
     DESCRIPTION
"Determines whether CIR management is enabled for this virtual circuit.

Note: If CIR management is enabled, frpCircuitCommittedBurst, 
frpCircuitExcessBurst and frpCircuitCommittedInformationRate are used 
to control the information flow rate at inbound/outbound of the virtual 
circuit. If CIR management is enabled only for monitoring, these objects 
are used to gather statistics regarding information flow rate.

Options:
disabled (1): congestion management is disabled

enabled-inbound (2): CIR management is enabled at inbound

monitor-inbound (3): CIR management is enabled at inbound for monitoring only

enabled-outbound (4): CIR management is enabled at outbound

Default Value: disabled (1)

Configuration Changed: operative "
     DEFVAL { disabled }
     ::= { frpCircuitEntry 8 }


   frpCircuitMultiProtEncaps OBJECT-TYPE
     SYNTAX  INTEGER {
          disabled        (1),
          enabled (2)
          }
     ACCESS  read-write
     STATUS  mandatory
     DESCRIPTION
"Determines whether traffic on this virtual circuit receives a 
multiprotocol encapsulation header when outbound, and is stripped of this 
header when inbound, as specified in Frame Relay Forum's FRF.3 (Final) 
('Multiprotocol Encapsulation Implementation Agreement') and the Network 
Working Group's RFC 1490 ('Multiprotocol Interconnect over Frame Relay').

Note: If this traffic does not pass through the Frame Relay module's FRIM 
software, it will move across this circuit transparently (i.e. without 
gaining or losing an encapsulation header).

Options:
disabled (1): multiprotocol encapsulation is disabled

enabled (2): multiprotocol encapsulation is enabled

Default Value: disabled (1)

Configuration Changed: administrative "
     DEFVAL { disabled }
     ::= { frpCircuitEntry 9 }


   frpCircuitHighPriorityBurst   OBJECT-TYPE
     SYNTAX  INTEGER
     ACCESS  read-write
     STATUS  mandatory
     DESCRIPTION
"Determines the maximum number of uncommitted inbound data bits exceeding 
frpCircuitExcessBurst and having very high priority that the Frame Relay 
module will attempt to transfer within an established measurement 
interval.

NOTE: The higher this value, the greater the chance for system congestion.

Range of Values: 0 - 512,000

Default Value: 0

Configuration Changed: operative "
     DEFVAL { 0 }
     ::= { frpCircuitEntry 10 }


    frpCircuitLowPriorityBurst   OBJECT-TYPE
     SYNTAX  INTEGER
     ACCESS  read-write
     STATUS  mandatory
     DESCRIPTION
"Determines the maximum number of inbound data bits having very high, 
high, or medium priority that the Frame Relay module commits to transfer 
within an established measurement interval.

NOTE: The higher this value, the greater the chance that low priority 
traffic will be discarded. This value cannot be greater than the value set 
in frpCircuitCommittedBurst.

Range of Values: 0 - 512,000

Default Value: 0

Configuration Changed: operative "
     DEFVAL { 0 }
     ::= { frpCircuitEntry 11 }


    frpCircuitFragmentationSize   OBJECT-TYPE
     SYNTAX  INTEGER
     ACCESS  read-write
     STATUS  mandatory
     DESCRIPTION
"Determines whether fragmentation is enabled (>0), and if so, the maximum 
size permitted per fragment. Fragmentation occurs when the frame size 
(including DLCI header) exceeds the value specified for this parameter. 
The frame is then fragmentation into smaller fragments, each with a 
maximum size specified by this parameter.

Note: This object only applies to circuits which are configured for 
Multi-Protocol Encapsulation (MPE) support (frpCircuitMultiProtEncaps = 
'enabled'), and which are associated with a sap of type 'lower' 
(frpSapType = 'lower').

Range of Values: 0, 64 - 1024

Default Value: 0

Configuration Changed: operative "
     DEFVAL { 0 }
     ::= { frpCircuitEntry 18 }


-- gap (10) for future parameters
--      1 already used up for "frpCircuitMultiProtEncaps"
--      2 already used up for "frpCircuitHighPriorityBurst" and 
--     "frpCircuitLowPriorityBurst"
--      1 already used up for "frpCircuitFragmentationSize"

   frpCircuitAlias      OBJECT-TYPE 
          SYNTAX  Alias          
     ACCESS  read-write
          STATUS  mandatory
          DESCRIPTION
"Determines the textual name uniquely identifying this virtual circuit's 
destination across the Frame Relay network.

Note: This alias is required for managing card sets in remote CX1000s; 
otherwise, it is optional. Specifying an alias consumes memory that might 
otherwise support a larger number of virtual circuits.

Range of Values:
0-35 alphanumeric characters beginning with a non-numeric 
character (CX1000)

0-16 alphanumeric characters beginning with a 
non-numeric character (CX900)

Default Value: none

Configuration Changed: operative "
   ::= { frpCircuitEntry 19 }


   frpCircuitCompanionSapNumber OBJECT-TYPE
          SYNTAX  INTEGER
     ACCESS  read-write
     STATUS  mandatory
     DESCRIPTION
"Indicates the companion SAP in the Frame Relay software layer involved, 
together with 'frpCircuitCompanionDlci', in establishing one of 1,022 
possible virtual circuits for this SAP.

Options:
1-7: (CX900's BOP- or BCM-related lower SAPs)

1-16: (CX1000's BOP- or DXI-related lower SAPs)

17-32: (CX1000's GFF-related lower SAPs)

40: (GMF-related upper SAP)

41: (FRIM-related upper SAP)

Default Value: none

Configuration Changed: operative "
     DEFVAL { 0 }
     ::= { frpCircuitEntry 20 }


   frpCircuitCompanionDlci OBJECT-TYPE
     SYNTAX  INTEGER
     ACCESS  read-write
     STATUS  mandatory
     DESCRIPTION
"Indicates the virtual circuit's DLCI (Data Link Connection Identifier) 
for the companion SAP.

Range of Values: 1 - 1,022

Default Value: none

Configuration Changed: operative "
     DEFVAL { 0 }
     ::= { frpCircuitEntry 21 }


   frpCircuitAlternateSapNumber OBJECT-TYPE
     SYNTAX  INTEGER
     ACCESS  read-write
     STATUS  mandatory
     DESCRIPTION
"Indicates an alternative companion SAP in the Frame Relay software layer 
involved, together with 'frpCircuitAlternativeDlci', in establishing one 
of 1,022 possible secondary virtual circuits for this SAP.

Options:
1-7: (CX900's BOP- or BCM-related lower SAPs)

1-16: (CX1000's BOP- or DXI-related lower SAPs)

17-32: (CX1000's GFF-related lower SAPs)

40: (GMF-related upper SAP)

41: (FRIM-related upper SAP)

Default Value: none

Configuration Changed: operative "
     DEFVAL { 0 }
     ::= { frpCircuitEntry 22 }


   frpCircuitAlternateDlci OBJECT-TYPE
     SYNTAX  INTEGER
     ACCESS  read-write
     STATUS  mandatory
     DESCRIPTION
"Indicates the virtual circuit's DLCI (Data Link Connection Identifier) 
for the alternative companion SAP.

Range of Values: 1-1,022

Default Value: none

Configuration Changed: operative "
     DEFVAL { 0 }
     ::= { frpCircuitEntry 23 }


   frpCircuitMulticastGroupId      OBJECT-TYPE
     SYNTAX  INTEGER  (0..255)
     ACCESS  read-only
     STATUS  mandatory
     DESCRIPTION
"Indicates the identifier of a multicast group to which the virtual 
circuit belongs.

Range of Values: 0 - 255 (0=not in group)

Default Value: 0"
     DEFVAL { 0 }
     ::= { frpCircuitEntry 24 }


   frpCircuitMulticastType    OBJECT-TYPE
     SYNTAX  INTEGER {
          noMulticastAssociation  (1),
          rootOneWay              (2),
          leafOneWay              (3),
          rootTwoWay              (4),
          leafTwoWay              (5),
          rootNWay                (6),
          rootTwoWaySinglePass    (7),
          leafTwoWaySinglePass    (8)
           }
     ACCESS  read-only
     STATUS  mandatory
     DESCRIPTION
"Determines member and service types of this virtual circuit when part of 
a multicast group.

Options:
noMulticastAssociation (1): PVC is not part of multicast group

rootOneWay (2): PVC is a root member whose multicast server sends frames 
received from this root member only to route partners of the multicast 
group's active leaf members (one-way multicast service)

leafOneWay (3): PVC is a leaf member that cannot receive a root member's 
frames from a multicast server (one-way multicast service)

rootTwoWay (4): PVC is a root member whose multicast server sends frames 
received from this root member to this multicast group's active leaf 
members; the multicast server also sends frames received from any active 
leaf member to the root member (two-way multicast service)

leafTwoWay (5): PVC is a leaf member whose multicast server sends frames 
received from this leaf member to this multicast group's root member 
(two-way multicast service)

rootNWay (6): PVC is a root member whose multicast server sends frames 
received from this root member to this multicast group's other active root 
members; the multicast server also sends frames received from any other 
active root member to all other active root members (N-way multicast 
service)

rootTwoWaySinglePass (7): PVC is a root member whose multicast server sends
frames received from this root member to this multicast group's first active
leaf members found only; the multicast server also sends frames received 
from any active leaf member to the root member (two-way multicast service)

leafTwoWaySinglePass (8): PVC is a leaf member whose multicast server sends 
frames received from this leaf member to this multicast group's root member 
(two-way multicast service)

Default Value: noMulticastAssociation (1)"
     DEFVAL { noMulticastAssociation  }
     ::= { frpCircuitEntry 25 }

   frpCircuitCompressionPort OBJECT-TYPE
     SYNTAX  INTEGER
     ACCESS  read-write
     STATUS  mandatory
     DESCRIPTION
"Determines whether compression is used on this DLCI. A value of 0 
indicates that compression is disabled.

When compression is enabled (i.e., this object has a non-zero value), the 
value given is an index that links this DLCI with a compression port. This 
index is the value of the compressPortNumber object in the compressEntry. 
The number of the compression port is memory-dependant.

Range of Values: 0 (no compression) to 64

Default Value: 0 

Configuration Changed: administrative"
     DEFVAL { 0 }
     ::= { frpCircuitEntry 26 }

   frpCircuitExpressService OBJECT-TYPE
     SYNTAX  INTEGER {
          disabled   (1),
          enabled    (2)
          }
     ACCESS  read-write
     STATUS  mandatory
     DESCRIPTION
"Determines whether this Frame Relay circuit provide express
services.

Options:
disabled (1): circuit does not provide express service

enabled (2): circuit provides express service

Default Value: enabled (2)

Configuration Changed: administrative"
     DEFVAL { enabled }
--#STARTING-VERSION 2
     ::= { frpCircuitEntry 27 }


-- gap (10) for future parameters
--      2 already used up for "frpCircuitAlternateSapNumber" & 
--     "frpCircuitAlternateDlci"
--      2 already used up for "frpCircuitMulticastGroupId"  &  
--     "frpCircuitMulticastType"
--      1 already used up for "frpCircuitCompressionPort"
--      1 already used up for "frpCircuitExpressService"


   frpCircuittrapTrap1 OBJECT-TYPE
     SYNTAX  INTEGER {
          disabled        (1),
          enabled (2)
          }
     ACCESS  read-write
     STATUS  mandatory
     DESCRIPTION
"Determines whether this SAP produces the frpPvcReportedStatusChange 
trap whose accumulated value can be retrieved by an SNMP-compliant network 
management device.

Options:
disabled (1): SAP does not produce a PVC status change trap

enabled (2): SAP produces a PVC status change trap

Default Value: disabled (1)

Configuration Changed: operative "
     DEFVAL { disabled }
     ::= { frpCircuitEntry 32 }


   frpCircuittrapTrap2 OBJECT-TYPE
     SYNTAX  INTEGER {
          disabled        (1),
          enabled (2)
          }
     ACCESS  read-write
     STATUS  mandatory
     DESCRIPTION
"Determines whether this SAP produces the frpPvcBillingStats trap whose 
accumulated value can be retrieved by an SNMP-compliant network management 
device.

Options:
disabled (1): SAP does not produce a billing statistics trap

enabled (2): SAP produces a billing statistics trap

Default Value: disabled (1)

Configuration Changed: operative "
     DEFVAL { disabled }
     ::= { frpCircuitEntry 33 }


-- gap (7) for future traps and write-only controls
--      1 already used up for "frpCircuittrapTrap2"
--      1 already used up for "frpCircuitControlStats"


   frpCircuitControlStats OBJECT-TYPE
     SYNTAX  INTEGER {
          clearCircuitStats       (1)
          }
     ACCESS  write-only
     STATUS  mandatory
     DESCRIPTION
"Clears accumulated statistics for this circuit.

Options:
clearCircuitStats (1): clears circuit statistics

Default Value: none

Configuration Changed: operative "
     ::= { frpCircuitEntry 39 }


   frpCircuitstatReportedState OBJECT-TYPE
     SYNTAX  INTEGER {
          notReported             (1),
          reportedActive  (2),
          reportedInactive        (3)
          }
     ACCESS  read-only
     STATUS  mandatory
     DESCRIPTION
"Indicates the virtual circuit's current state as reported to this SAP by 
link management. If the virtual circuit is associated with a SAP whose 
frpSapType is set to 'upper', or a SAP whose'frpSapType is set to 
'lower' SAP) and whose frpSapInterfaceType is set to 'uniNetwork', then 
this object will always read 'reportedActive'.

Options:
notReported (1): circuit's state has not been reported

reportedActive (2): circuit's state has been reported as active

reportedInactive (3): circuit's state has been reported as inactive

Default Value: notReported (1)"
     DEFVAL { notReported }
     ::= { frpCircuitEntry 40 }


   frpCircuitstatRouteState OBJECT-TYPE
     SYNTAX  INTEGER {
          noRoute         (1),
          routeNotOperational     (2),
          routeOperational        (3)
          }
     ACCESS  read-only
     STATUS  mandatory
     DESCRIPTION
"Indicates the current state of the virtual circuit's primary route or 
pathway.

Options:
noRoute (1): virtual circuit has no associated pathway

routeNotOperational (2): pathway of virtual circuit is not operational

routeOperational (3): pathway of virtual circuit is operational

Default Value: noRoute (1)"
     DEFVAL { noRoute }
     ::= { frpCircuitEntry 41 }


   frpCircuitstatAlternateRouteState OBJECT-TYPE
     SYNTAX  INTEGER {
          noRoute         (1),
          routeNotOperational     (2),
          routeOperational        (3),
          alternateCircuit        (4)
          }
     ACCESS  read-only
     STATUS  mandatory
     DESCRIPTION
"Indicates the current state of the virtual circuit's alternate route or 
pathway.

Options:
noRoute (1): Virtual circuit has no associated alternate pathway

routeNotOperational (2): Alternate pathway of virtual circuit is not 
operational

routeOperational (3): Alternate pathway of virtual circuit is operational

alternateCircuit (4): This virtual circuit is an alternate circuit

Default Value: noRoute (1)"
     DEFVAL { noRoute }
     ::= { frpCircuitEntry 42 }


-- gap (5) for future states
--      1 already used up for "frpCircuitAlternate Route State"


   frpCircuitstatLocalCreationTime OBJECT-TYPE
     SYNTAX  TimeTicks
     ACCESS  read-only
     STATUS  mandatory
     DESCRIPTION
"Indicates the system clock's time at which this circuit was created in 
the Frame Relay software layer.

Range of Values: system-generated

Default Value: none"
     ::= { frpCircuitEntry 47 }


   frpCircuitstatRemoteCreationTime OBJECT-TYPE
     SYNTAX  TimeTicks
     ACCESS  read-only
     STATUS  mandatory
     DESCRIPTION
"Indicates the system clock's time at which this circuit, created as a 
result of its configuration in the Frame Relay software layer, was 
reported to the user by the network as 'new'.

Range of Values: system-generated

Default Value: none"
     ::= { frpCircuitEntry 48 }


   frpCircuitstatTxFrames OBJECT-TYPE
     SYNTAX  Counter
     ACCESS  read-only
     STATUS  mandatory
     DESCRIPTION
"Indicates the number of frames sent on this virtual circuit since its 
creation.

Range of Values: 0-4,294,967,295

Default Value: none"
     ::= { frpCircuitEntry 49 }


   frpCircuitstatRxFrames OBJECT-TYPE
     SYNTAX  Counter
     ACCESS  read-only
     STATUS  mandatory
     DESCRIPTION
"Indicates the number of frames received on this virtual circuit since its 
creation.

Range of Values: 0 - 4,294,967,295

Default Value: none"
     ::= { frpCircuitEntry 50 }


   frpCircuitstatTxOctets OBJECT-TYPE
     SYNTAX  Counter
     ACCESS  read-only
     STATUS  mandatory
     DESCRIPTION
"Indicates the number of octets sent on this virtual circuit since its 
creation.

Range of Values: 0 - 4,294,967,295

Default Value: none"
     ::= { frpCircuitEntry 51 }


   frpCircuitstatRxOctets OBJECT-TYPE
     SYNTAX  Counter
     ACCESS  read-only
     STATUS  mandatory
     DESCRIPTION
"Indicates the number of octets received on this virtual circuit since its 
creation.

Range of Values: 0 - 4,294,967,295

Default Value: none"
     ::= { frpCircuitEntry 52 }


   frpCircuitstatTxFECNs OBJECT-TYPE
     SYNTAX  Counter
     ACCESS  read-only
     STATUS  mandatory
     DESCRIPTION
"Indicates the number of frames sent on this virtual circuit since its 
creation whose FECN bit revealed forward congestion.

Range of Values: 0 - 65,535

Default Value: none"
     REFERENCE
        "Draft American National Standard T1.618-1991,
Section 3.3.3"
     ::= { frpCircuitEntry 53 }


   frpCircuitstatRxFECNs OBJECT-TYPE
     SYNTAX  Counter
     ACCESS  read-only
     STATUS  mandatory
     DESCRIPTION
"Indicates the number of frames received on this virtual circuit since its 
creation whose FECN bit revealed forward congestion.

Range of Values: 0 - 65,535

Default Value: none"
     REFERENCE
        "Draft American National Standard T1.618-1991,
Section 3.3.3"
     ::= { frpCircuitEntry 54 }


   frpCircuitstatTxBECNs OBJECT-TYPE
     SYNTAX  Counter
     ACCESS  read-only
     STATUS  mandatory
     DESCRIPTION
"Indicates the number of frames sent on this virtual circuit since its 
creation whose BECN bit revealed backward congestion.

Range of Values: 0 - 65,535

Default Value: none"
     REFERENCE
        "Draft American National Standard T1.618-1991,
Section 3.3.4"
     ::= { frpCircuitEntry 55 }


   frpCircuitstatRxBECNs OBJECT-TYPE
     SYNTAX  Counter
     ACCESS  read-only
     STATUS  mandatory
     DESCRIPTION
"Indicates the number of frames received on this virtual circuit since its 
creation whose BECN bit revealed backward congestion.

Range of Values: 0 - 65,535

Default Value: none"
     REFERENCE
        "Draft American National Standard T1.618-1991,
Section 3.3.4"
     ::= { frpCircuitEntry 56 }


-- gap (6) for future transmit & receive type statistics


   frpCircuitstatTxQueuedDiscards OBJECT-TYPE
     SYNTAX  Counter
     ACCESS  read-only
     STATUS  mandatory
     DESCRIPTION
"Indicates the number of outbound data frames discarded on this virtual 
circuit due to interface congestion, circuit unavailability (status down), 
or unspecified routing (circuit deleted or never added).

Range of Values: 0 - 65,535

Default Value: none"
     ::= { frpCircuitEntry 63 }


-- gap (6) for future transmit type parameters


   frpCircuitstatRxCIRExceededDiscards OBJECT-TYPE
     SYNTAX  Counter
     ACCESS  read-only
     STATUS  mandatory
     DESCRIPTION
"Indicates the number of data frames received and then discarded on this 
virtual circuit because the combined value of frpCircuitCommittedBurst 
and frpCircuitExcessBurst has been exceeded.

Range of Values: 0 - 65,535

Default Value: none"
     ::= { frpCircuitEntry 70 }


   frpCircuitstatRxSysCongestionDiscards OBJECT-TYPE
     SYNTAX  Counter
     ACCESS  read-only
     STATUS  mandatory
     DESCRIPTION
"Indicates the number of data frames received and then discarded on this 
virtual circuit due to system congestion.

Range of Values: 0 - 65,535

Default Value: none"
     ::= { frpCircuitEntry 71 }


   frpCircuitstatRxUnavailInboundDiscards OBJECT-TYPE
     SYNTAX  Counter
     ACCESS  read-only
     STATUS  mandatory
     DESCRIPTION
"Indicates the number of data frames received and then discarded on this 
virtual circuit because it was unavailable.

Range of Values: 0 - 65,535

Default Value: none"
     ::= { frpCircuitEntry 72 }


   frpCircuitstatRxUnavailOutboundDiscards OBJECT-TYPE
     SYNTAX  Counter
     ACCESS  read-only
     STATUS  mandatory
     DESCRIPTION
"Indicates the number of data frames received and then discarded at this 
virtual circuit because the outbound virtual circuit was unavailable.

Range of Values: 0 - 65,535

Default Value: none"
     ::= { frpCircuitEntry 73 }


   frpCircuitstatRxCIRExceeds OBJECT-TYPE
     SYNTAX  Counter
     ACCESS  read-only
     STATUS  mandatory
     DESCRIPTION
"Indicates the number of times the combined value of 
frpCircuitCommittedBurst and frpCircuitExcessBurst has been exceeded 
in a 'Tc' window at the inbound side of this virtual circuit.

NOTE: A 'Tc' window is a timeslice determined by dividing 
frpCircuitCommittedBurst by frpCircuitCommittedInformationRate.

Range of Values: 0 - 65,535

Default Value: none"
     ::= { frpCircuitEntry 74 }


   frpCircuitstatFragmentationFailures OBJECT-TYPE
     SYNTAX  Counter
     ACCESS  read-only
     STATUS  mandatory
     DESCRIPTION
"Indicates the number of times frame fragmentation failed.

Range of Values: 0 - 65,535

Default Value: none"
     ::= { frpCircuitEntry 75 }


   frpCircuitstatDeFragmentationFailures OBJECT-TYPE
     SYNTAX  Counter
     ACCESS  read-only
     STATUS  mandatory
     DESCRIPTION
"Indicates the number of times frame reassembly failed.

Range of Values: 0 - 65,535

Default Value: none"
     ::= { frpCircuitEntry 76 }


-- Frame Relay Reported Pvcs Table

--    The table used to look-up all reported pvcs and their status, as 
--    reported by the network to the frame relay service access point 
--    configured as a user side of a user-to-network interface 
--    (frpSapInterfaceType = "uniUser") which supports some form of link 
--    management procedures (frpSapLinkManagement -SYMBOL 185 \f 
--    "Symbol"- "none").
--    All status reported by this table are as of the last "full status" 
--    link management frame received from the uni-network side.


frpReportedPvcTable OBJECT-TYPE
   SYNTAX  SEQUENCE OF FrpReportedPvcEntry
   ACCESS  not-accessible
   STATUS  mandatory
 	  		 DESCRIPTION ""
   ::= { cxFrameRelay 3 }


   frpReportedPvcEntry OBJECT-TYPE
     SYNTAX  FrpReportedPvcEntry
     ACCESS  not-accessible
     STATUS  mandatory
 	  		 DESCRIPTION ""
     INDEX { frpReportedPvcSapNumber }
     ::= { frpReportedPvcTable 1 }



   FrpReportedPvcEntry ::=
     SEQUENCE {
        frpReportedPvcSapNumber         SapIndex,
        frpReportedPvcDlci                      DLCI,
        frpReportedPvcLocallyConfigured         INTEGER,
        frpReportedPvcStatus                    INTEGER
        }


   frpReportedPvcSapNumber OBJECT-TYPE
     SYNTAX  SapIndex
     ACCESS  read-only
     STATUS  mandatory
     DESCRIPTION
"Indicates the row containing objects for monitoring a particular lower 
SAP.

Options:
1-7 (CX900's BOP- or BCM-related lower SAPs)

1-16 (CX1000's BOP- or DXI-related lower SAPs)

17-32 (CX1000's GFF-related lower SAPs)

Default Value: none"
     ::= { frpReportedPvcEntry 1 }


   frpReportedPvcDlci OBJECT-TYPE
     SYNTAX  DLCI
     ACCESS  read-only
     STATUS  mandatory
     DESCRIPTION
"Indicates the virtual circuit's DLCI (Data Link Connection Identifier) 
for a particular SAP.

Range of Values: 1 - 1,022

Default Value: none"

     ::= { frpReportedPvcEntry 2 }


   frpReportedPvcLocallyConfigured OBJECT-TYPE
     SYNTAX  INTEGER {
          no              (1),
          yes             (2)
          }
     ACCESS  read-only
     STATUS  mandatory
     DESCRIPTION
"Indicates whether the virtual circuit is actually configured in the Frame 
Relay software layer.

Options:
no (1): virtual circuit is not configured

yes (2): virtual circuit is configured

Default Value: none"
     ::= { frpReportedPvcEntry 3 }


   frpReportedPvcStatus OBJECT-TYPE
     SYNTAX  INTEGER {
          inactive        (1),
          active          (2)
          }
     ACCESS  read-only
     STATUS  mandatory
     DESCRIPTION
"Indicates the status of the virtual circuit as reported by the network.

Options:
inactive (1): virtual circuit is not active

active (2): virtual circuit is active

Default Value: none"
     ::= { frpReportedPvcEntry 4 }



-- Frame Relay Muticast services
--    The table used to configure the multicast service.


frpMulticastTable OBJECT-TYPE
   SYNTAX  SEQUENCE OF FrpMulticastEntry
   ACCESS  not-accessible
   STATUS  mandatory
   DESCRIPTION
"A table containing the members of multicast service groups." 
   ::= { cxFrameRelay 4 }

   
   frpMulticastEntry OBJECT-TYPE
     SYNTAX  FrpMulticastEntry
     ACCESS  not-accessible
     STATUS  mandatory
     DESCRIPTION
     "A member of a multicast service group" 
     INDEX { frpMulticastGroupId, 
      frpMulticastSapNumber,
      frpMulticastDlci                }
     ::= { frpMulticastTable 1 }



   FrpMulticastEntry ::=
     SEQUENCE {
   frpMulticastGroupId     INTEGER,  
   frpMulticastSapNumber   SapIndex,
   frpMulticastDlci        DLCI,
   frpMulticastRowStatus   INTEGER,
   frpMulticastMemberType  INTEGER,
   frpMulticastServiceType INTEGER,
   frpMulticastMemberStatus        INTEGER
        }

     frpMulticastGroupId     OBJECT-TYPE
     SYNTAX  INTEGER (1..255)
     ACCESS  read-only
     STATUS  mandatory
     DESCRIPTION
"Indicates the identifier of a multicast group to which this virtual 
circuit belongs.

Range of Values: 1-255

Default Value: none"
     ::= { frpMulticastEntry 1 }


   frpMulticastSapNumber   OBJECT-TYPE
     SYNTAX  SapIndex
     ACCESS  read-only
     STATUS  mandatory
     DESCRIPTION
"Indicates the SAP of a multicast group's virtual circuit whose objects 
are to be configured (or monitored).

Options:
1-7: (CX900's BOP- or BCM-related lower SAPs)

1-16: (CX1000's BOP- or DXI-related lower SAPs)

41: (FRIM-related upper SAP)

Default Value: none"
     ::= { frpMulticastEntry 2 } 


   frpMulticastDlci        OBJECT-TYPE
     SYNTAX  DLCI
     ACCESS  read-only
     STATUS  mandatory
     DESCRIPTION
"Indicates the DLCI (Data Link Connection Identifier) associated with the 
SAP of a multicast group's virtual circuit.

Range of Values: 1 - 1,022

Default Value: none"
     ::= { frpMulticastEntry 3 }


   frpMulticastRowStatus    OBJECT-TYPE
     SYNTAX  INTEGER {
          invalid (1),
          valid    (2)
          }
     ACCESS  read-write
     STATUS  mandatory
     DESCRIPTION
"Determines whether this virtual circuit is to be deleted from this 
multicast group.

Options:
invalid (1): Row is deleted from the table immediately, however values are 
still in effect until the next reset. 

valid (2): Use this value to add a new row to the table, or modify an 
existing row.

Default Value: none

Configuration Changed: operative "
     ::= { frpMulticastEntry 4 }


   frpMulticastMemberType   OBJECT-TYPE
     SYNTAX  INTEGER {
          root    (1),
          leaf    (2)
          }
     ACCESS  read-write
     STATUS  mandatory
     DESCRIPTION
"Determines whether this virtual circuit is a root member that multicasts 
traffic or a leaf member that cannot multicast traffic.

Options:
root (1): PVC is root member (MDLCI)

leaf (2): PVC is leaf member

Default Value: none

NOTE: If a member type has been specified, it cannot be modified but must 
instead be deleted and specified again.

Configuration Changed: operative "
     ::= { frpMulticastEntry 5 }


   frpMulticastServiceType  OBJECT-TYPE
     SYNTAX  INTEGER {
          oneWay          (1),
          twoWay          (2),
          nWay            (3),
          twoWaySinglePass(4)
          }
     ACCESS  read-write
     STATUS  mandatory
     DESCRIPTION
"Determines whether the multicast server of a virtual circuit provides 
one-way, two-way, N-way, or special two-way single pass multicast service.

Options:
oneWay (1): multicast server sends frames received from a multicast 
group's root member to route partners of its active leaf members (one-way 
multicast service).

twoWay (2): multicast server sends frames received from a multicast 
group's root member to its active leaf members; multicast server also 
sends frames received from any active leaf member to the root member 
(two-way multicast service).

nWay (3): multicast server sends frames received from a multicast group's 
root member to other active root members in that group; multicast server 
also sends frames received from any other active root member to all other 
active root members (N-way multicast service).

twoWaySinglePass (4): multicast server sends frames received from the
multicast group's root member to only first active leaf member found within
all leaf members in that group; multicast server also sends frames received
from any active leaf member to the root member (two-way multicast service).

Default Value: none

NOTE: If a service has been specified, it cannot be modified but must 
instead be deleted and specified again.

Configuration Changed: operative "
     ::= { frpMulticastEntry 6 }


   frpMulticastMemberStatus         OBJECT-TYPE
     SYNTAX  INTEGER {
          inactive        (1),
          active  (2)
          }
     ACCESS  read-only
     STATUS  mandatory
     DESCRIPTION
"Indicates whether this virtual circuit is active or inactive in the 
multicast group.

Options:
inactive (1): PVC is not active in multicast group

active (2): PVC is active in multicast group

Default Value: none"
     ::= { frpMulticastEntry 7 }

frpMibLevel OBJECT-TYPE
   SYNTAX  INTEGER
   ACCESS  read-only
   STATUS  mandatory
   DESCRIPTION
"Used to determine current MIB module release supported
by the agent. Object is in decimal."
   DEFVAL { 0 }
   --#STARTING-VERSION 1
   ::= { cxFrameRelay 5 }


-- Service access point related traps

frpSapInterfaceStatusChange TRAP-TYPE
   ENTERPRISE      cxFrameRelay
   VARIABLES               {       cxModuleHwPhysSlot,
          frpSapNumber,
          frpSapstatLinkManagementState
          }
   DESCRIPTION
"Indicates that the link management currently in use at the service access 
point has changed state. It has toggled between any of the states defined 
in object frpSapstatLinkManagementState."
   ::= 1



-- Virtual circuit related traps

frpPvcReportedStatusChange TRAP-TYPE
   ENTERPRISE      cxFrameRelay
   VARIABLES               {       cxModuleHwPhysSlot,
          frpCircuitSapNumber,
          frpCircuitDlci,
          frpCircuitstatReportedState
          }
 	  		 DESCRIPTION ""
   ::= 2


frpPvcBillingStats TRAP-TYPE
   ENTERPRISE      cxFrameRelay
   VARIABLES               {       cxModuleHwPhysSlot,
          frpCircuitSapNumber,
          frpCircuitDlci,
          frpCircuitstatTxFrames,
          frpCircuitstatRxFrames,
          frpCircuitstatTxOctets,
          frpCircuitstatRxOctets
          }
 	  		 DESCRIPTION ""
   ::= 3

END
