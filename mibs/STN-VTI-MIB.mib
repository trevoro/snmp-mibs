-- *****************************************************************
--
-- stn-vti.mib:  
--      Spring Tide Networks Network Virtual Tunnel Interface 
--                         (VTI) MIB File
--
--
--      Copyright (c) 2000 by Spring Tide Networks, Inc.
--                      ALL RIGHTS RESERVED       
--
-- *****************************************************************

-- MIB Object definitions for Spring Tide VTI

STN-VTI-MIB DEFINITIONS ::= BEGIN

    IMPORTS
        MODULE-IDENTITY,
        OBJECT-TYPE, 
        IpAddress,
        Integer32
                FROM SNMPv2-SMI

        DisplayString
                FROM SNMPv2-TC

        MODULE-COMPLIANCE
                FROM SNMPv2-CONF

        InterfaceIndex
                FROM IF-MIB

        stnRouterVTI
                FROM STN-ROUTER-MIB

        stnNotification
                FROM SPRING-TIDE-NETWORKS-SMI;


    stnVti MODULE-IDENTITY
        LAST-UPDATED    "0011270000Z"
        ORGANIZATION    "Spring Tide Networks"
        CONTACT-INFO
                "
                Spring Tide Networks, Inc.
                Customer Service

                Postal: 3 Clock Tower Place
                        Suite 200
                        Maynard, MA 01754 USA
                Tel:    +1 978 298 2000
                Email:  custserv@springtidenet.com
                "
        DESCRIPTION     "This MIB module describes managed objects of
                         Spring Tide Networks Virtual Tunnel Interface."
        ::= { stnRouterVTI 1 }


--
-- Top Level STN VTI MIB Objects
--

    stnVtiObjects       OBJECT IDENTIFIER ::= {stnVti 1}
    
--
-- STN VTI Table
--   One entry for each VTI defined in the system.
--
    stnVtiTable OBJECT-TYPE
        SYNTAX          SEQUENCE OF StnVtiEntry
        MAX-ACCESS      not-accessible
        STATUS          current
        DESCRIPTION     "A list of VTI  entries."
        ::= { stnVtiObjects 1 }
 
    stnVtiEntry OBJECT-TYPE
        SYNTAX          StnVtiEntry
        MAX-ACCESS      not-accessible
        STATUS          current
        DESCRIPTION     "Entry contains information about a particular VTI ."
        INDEX           { stnVtiIfIndex }
        ::= { stnVtiTable 1 }
 
    StnVtiEntry ::= SEQUENCE {
        stnVtiIfIndex                     InterfaceIndex,
        stnVtiViId                        Integer32,
        stnVtiName                        DisplayString,
        stnVtiPolicy                      DisplayString,
        stnVtiState                       INTEGER,
        stnVtiLastError                   Integer32,
        stnVtiProxyTunnelSerialNum        Integer32,
        stnVtiMTU                         Integer32,
        stnVtiSpeed                       Integer32,
        stnVtiL2MuxIdx                    InterfaceIndex
    }

    stnVtiIfIndex OBJECT-TYPE
        SYNTAX          InterfaceIndex
        MAX-ACCESS      read-only
        STATUS          current
        DESCRIPTION     "The ifIndex of the VTI Layer 2 Interface."
        ::= { stnVtiEntry 1 }

    stnVtiViId OBJECT-TYPE
        SYNTAX          Integer32
        MAX-ACCESS      read-only
        STATUS          current
        DESCRIPTION     "The instance of the configuration record corresponding
                         to this VTI."
        ::= { stnVtiEntry 2 }

    stnVtiName OBJECT-TYPE
        SYNTAX          DisplayString (SIZE (1..32))
        MAX-ACCESS      read-only
        STATUS          current
        DESCRIPTION     "The name configured for this VTI."
        ::= { stnVtiEntry 3 }

    stnVtiPolicy OBJECT-TYPE
        SYNTAX          DisplayString (SIZE (1..32))
        MAX-ACCESS      read-only
        STATUS          current
        DESCRIPTION     "The name of the policy configured for this VTI."
        ::= { stnVtiEntry 4 }

    stnVtiState OBJECT-TYPE
        SYNTAX          INTEGER {
                          up(1),
                          down(2)
                        }
        MAX-ACCESS      read-only
        STATUS          current
        DESCRIPTION     "The current registration state of the VTI. A value of 
                         up indicates that the VTI is registered for a tunnel.
                         A value of down indicates that the VTI is waiting for 
                         a tunnel to be assigned."
        ::= { stnVtiEntry 5 }

    stnVtiLastError OBJECT-TYPE
        SYNTAX          Integer32
        MAX-ACCESS      read-only
        STATUS          current
        DESCRIPTION     "Error code indicating the last error that occured on 
                         the interface"
        ::= { stnVtiEntry 6 }

    stnVtiProxyTunnelSerialNum OBJECT-TYPE
        SYNTAX          Integer32
        MAX-ACCESS      read-only
        STATUS          current
        DESCRIPTION     "Serial number of proxy tunnel associated with this 
                         VTI."
        ::= { stnVtiEntry 7 }

    stnVtiMTU OBJECT-TYPE
        SYNTAX          Integer32
        MAX-ACCESS      read-only
        STATUS          current
        DESCRIPTION     " The Maximum Transfer Unit of this VTI."
        ::= { stnVtiEntry 8 }

    stnVtiSpeed OBJECT-TYPE
        SYNTAX          Integer32
        MAX-ACCESS      read-only
        STATUS          current
        DESCRIPTION     " The interface speed of this VTI."
        ::= { stnVtiEntry 9 }

    stnVtiL2MuxIdx OBJECT-TYPE
        SYNTAX          InterfaceIndex
        MAX-ACCESS      read-only
        STATUS          current
        DESCRIPTION     "The interface index of of the L2MUX associated 
                        with this VTI."
        ::= { stnVtiEntry 10 }

END
