MPSLA DEFINITIONS ::= BEGIN

-- TITLE:	Maipu Vxworks System Objects


IMPORTS
	DisplayString, TruthValue,RowStatus,PhysAddress, TEXTUAL-CONVENTION 
    					FROM SNMPv2-TC
	IpAddress, NOTIFICATION-TYPE,MODULE-IDENTITY, OBJECT-TYPE, Integer32, Unsigned32
					FROM SNMPv2-SMI  	
	mpMgmt,mpTrapObject FROM MAIPU-SMI;  
	

EnabledStatus ::= TEXTUAL-CONVENTION 
    STATUS      current 
    DESCRIPTION 
        "A simple status value for the object." 
    SYNTAX      INTEGER { enabled(1), disabled(2) } 

mpTrap	OBJECT-IDENTITY
	STATUS	current
	DESCRIPTION
		"Private trap properties."
	::= { mpTrapObject 1 }
	
mpTrapClass	OBJECT-TYPE
	SYNTAX	INTEGER {
--				critical(1),
--				major(2),
--				minor(3),
--				information(4),
--				warning(5)
				emergencies(1),
				alerts(2),
				critical(3),
				errors(4),
				warnings(5),
				notifications(6),
				informational(7),
				debugging(8)
					}
	MAX-ACCESS	read-only
	STATUS	current
	DESCRIPTION
		"The class of the Traps."
	::= { mpTrap 1 }	
	
mpTrapDescr	OBJECT-TYPE
	SYNTAX	DisplayString
	MAX-ACCESS	read-only
	STATUS	current
	DESCRIPTION
		"Describe the reason of the trap."
	::= { mpTrap 2 }
	
mpTrapType	OBJECT-TYPE
	SYNTAX	INTEGER {
				system(1),
				interface(2),
				other(3)
					}
	MAX-ACCESS	read-only
	STATUS	current
	DESCRIPTION
		"The type of each trap,show the category."
	::= { mpTrap 3 }
	
mpTraps	OBJECT-IDENTITY
	STATUS	current
	DESCRIPTION
		"All the successor object identifiers of maipu.traps are the 
		same as those of maipu.products, which represent the source
		device type of traps. When maipu Agent send out traps, it 
		should set the 'enterprise' field to an OID which indicates the 
		device type, so that when a NMS receive the trap, it could 
		lookup such field to identify different device.
       
       		For example: 'Specific' = 1 in a trap package may represent 
       		different meaning in different kinds of device, if 'enterprise' 
       		= 1.3.6.1.4.1.5651.2.6.1, then NMS could know that it is sent 
       		from a MP9400, so the trap means 'Modem card power-on'."
	::= { mpTrapObject 2 }
	


mpSla         OBJECT-IDENTITY    --2008.9.11 分配人：吴飞，申请人：申 杰， SLA
	STATUS	current
	DESCRIPTION
		"Subtree for SLA."
	::= { mpTraps 62 }
	



mpios                  OBJECT IDENTIFIER ::= { mpMgmt 20 }

iosSystem              OBJECT IDENTIFIER ::= { mpios 1 }

iosObjects             OBJECT IDENTIFIER ::= { iosSystem 1 }

 

sysSLA                 MODULE-IDENTITY

                      LAST-UPDATED "0809171056Z"

                      ORGANIZATION "Maipu  Communication Technology Co. LTD."
                      CONTACT-INFO "Maipu  Communication Technology Co. LTD."

                          DESCRIPTION
                              "Node for System SLA subtree."

                          ::= { iosObjects  201 }



sysSlaGbl  		OBJECT IDENTIFIER ::= { sysSLA 1 }

sysSlaCtrl          	OBJECT-TYPE
                    		SYNTAX  EnabledStatus
                    		MAX-ACCESS  read-write
                    		STATUS  current
                    		DESCRIPTION
                    			"RTR global switch
                    			 enable(2)-enable RTR module
                    			 disable(2)-no RTR module"
                    		::= { sysSlaGbl  1 }

sysSlaResponder     	OBJECT-TYPE
                    		SYNTAX  TruthValue
                    		MAX-ACCESS  read-write
                    		STATUS  current
                    		DESCRIPTION
                    			"Rtr Responder
                    			 TRUE(1)-Rtr Responder
                    			 False(2)-no Rtr Responder
                    			 on valid in jitter entity now"
                    		::= { sysSlaGbl  2 }


sysSlaNotUsedEntityId	OBJECT-TYPE
                    		SYNTAX  INTEGER(1..2000)
                    		MAX-ACCESS  read-only
                    		STATUS  current
                    		DESCRIPTION
                    			"The entity id that not in use"
                    		::= { sysSlaGbl  3 }

sysSlaNotUsedScheId	OBJECT-TYPE
                    		SYNTAX  INTEGER(1..2000)
                    		MAX-ACCESS  read-only
                    		STATUS  current
                    		DESCRIPTION
                    			"The schedule id that not in use"
                    		::= { sysSlaGbl  4 }



------------------------------------------------------------------------------
sysSlaEntityMgt 	OBJECT IDENTIFIER ::= { sysSLA 2 }

sysSlaEntityTable   	OBJECT-TYPE
                    		SYNTAX  SEQUENCE OF   SysSlaEntityEntry   
                    		MAX-ACCESS  not-accessible
                    		STATUS  current
                    		DESCRIPTION
                    			"Rtr entity table,config or view information about Rtr entity"
                    		::= { sysSlaEntityMgt 100 }

sysSlaEntityEntry   	OBJECT-TYPE
                    		SYNTAX  SysSlaEntityEntry   
                    		MAX-ACCESS  not-accessible
                    		STATUS  current
                    		DESCRIPTION
                    			"Rtr entity,config or view information about Rtr entity"
                    		INDEX  { rtrEntityId }
                    		::= { sysSlaEntityTable  1 }

SysSlaEntityEntry   	::= SEQUENCE {
                    			slaEntityId            INTEGER,
                    			slaEntityName          DisplayString,
                    			slaEntityType          INTEGER,
                    			slaEntityRowStatus     RowStatus
                    	             }


slaEntityId         	OBJECT-TYPE
                    		SYNTAX  INTEGER(1..2000)
                    		MAX-ACCESS  read-write
                    		STATUS  current
                    		DESCRIPTION
                    			"Rtr entity Id,index"
                    		::= { sysSlaEntityEntry 1 }

slaEntityName       	OBJECT-TYPE
                    		SYNTAX  DisplayString(SIZE(0..40))
                    		MAX-ACCESS  read-only
                    		STATUS  current
                    		DESCRIPTION
                    			"rtr entity name,araised aumatically,read-only"
                    		::= { sysSlaEntityEntry 2 }

slaEntityType       	OBJECT-TYPE
                    		SYNTAX  INTEGER {
                    			         icmpEcho(1),
                    			          jitter(2),
                    			          flowStatistics(3),
						  udpecho(4),
					          icmpPathJit(5),
						  icmpPathEcho(6)
                    			        }
                    		MAX-ACCESS  read-write
                    		STATUS  current
                    		DESCRIPTION
                    			"rtr entity,inlcuding icmpEcho,jitter,flow statistics,udpecho,icmp path echo,icmp path jitter"
                    		::= { sysSlaEntityEntry 3 }



slaEntityRowStatus  	OBJECT-TYPE
                    		SYNTAX  RowStatus
                    		MAX-ACCESS  read-write
                    		STATUS  current
                    		DESCRIPTION
                    			"rtr entity row status"
                    		::= { sysSlaEntityEntry 4 }


------------------------------------------------------------------------------
sysSlaGroupMgt      	OBJECT IDENTIFIER ::= { sysSLA 3 }

sysSlaGroupTable    	OBJECT-TYPE
                    		SYNTAX  SEQUENCE OF   SysSlaGroupEntry    
                    		MAX-ACCESS  not-accessible
                    		STATUS  current
                    		DESCRIPTION
                    			"Rtr group table"
                    		::= { sysSlaGroupMgt      100 }

sysSlaGroupEntry    	OBJECT-TYPE
                    		SYNTAX  SysSlaGroupEntry    
                    		MAX-ACCESS  not-accessible
                    		STATUS  current
                    		DESCRIPTION
                    			"Rtr group entity"
                    		INDEX  { slaGroupId }
                    		::= { sysSlaGroupTable    1 }

SysSlaGroupEntry    	::= SEQUENCE {
                    			slaGroupId             INTEGER,
                    			slaGroupName           DisplayString,
                    			slaGroupInterval       INTEGER,
                    			slaGroupEntityMembers   DisplayString,
                    			slaGroupRowStatus      RowStatus
                    	             }


slaGroupId          	OBJECT-TYPE
                    		SYNTAX  INTEGER(1..2000)
                    		MAX-ACCESS  read-write
                    		STATUS  current
                    		DESCRIPTION
                    			"rtr group id,index"
                    		::= { sysSlaGroupEntry    1 }

slaGroupName        	OBJECT-TYPE
                    		SYNTAX  DisplayString(SIZE(0..40))
                    		MAX-ACCESS  read-only
                    		STATUS  current
                    		DESCRIPTION
                    			"rtr group name,araised aumatically, read-only"
                    		::= { sysSlaGroupEntry    2 }

slaGroupInterval    	OBJECT-TYPE
                    		SYNTAX  INTEGER(0..10000)
                    		MAX-ACCESS  read-write
                    		STATUS  current
                    		DESCRIPTION
                    			"rtr group interval, seconds"
                    		::= { sysSlaGroupEntry    3 }

slaGroupEntityMembers	OBJECT-TYPE
                    		SYNTAX  DisplayString(SIZE(0..255))
                    		MAX-ACCESS  read-write
                    		STATUS  current
                    		DESCRIPTION
                    			"RTR group members，string type：
                    			 1，3，10-20，50
                    			 string length no more than 255, separated by comma,no space in the string。"
                    		::= { sysSlaGroupEntry    4 }

slaGroupRowStatus   	OBJECT-TYPE
                    		SYNTAX  RowStatus
                    		MAX-ACCESS  read-write
                    		STATUS  current
                    		DESCRIPTION
                    			"rtr group table row status"
                    		::= { sysSlaGroupEntry    5 }


------------------------------------------------------------------------------
sysSlaScheduleMgt   	OBJECT IDENTIFIER ::= { sysSLA 4 }

sysSlaScheduleTable 	OBJECT-TYPE
                    		SYNTAX  SEQUENCE OF   SysSlaScheduleEntry 
                    		MAX-ACCESS  not-accessible
                    		STATUS  current
                    		DESCRIPTION
                    			"rtr schedule table"
                    		::= { sysSlaScheduleMgt   100 }

sysSlaScheduleEntry 	OBJECT-TYPE
                    		SYNTAX  SysSlaScheduleEntry 
                    		MAX-ACCESS  not-accessible
                    		STATUS  current
                    		DESCRIPTION
                    			"rtr schedule table entry"
                    		INDEX  { slaScheduleId }
                    		::= { sysSlaScheduleTable 1 }

SysSlaScheduleEntry 	::= SEQUENCE {
                    			slaScheduleId          Unsigned32,
                    			slaScheduleType        INTEGER,
                    			slaScheduleObjId       INTEGER,
                    			slaScheduleStartTimeFlag    INTEGER,
                    			slaScheduleAfterTime    DisplayString,
                    			slaScheduleStartTime    DisplayString,
                    			slaScheduleAgeOut      Unsigned32,
                    			slaScheduleLifeFlag    INTEGER,
                    			slaScheduleLifeTime    Unsigned32,
                    			slaScheduleRepeat      Unsigned32,
                    			slaScheduleInterval    Unsigned32,
                    			slaScheduleRowStatus   RowStatus
                    	             }


slaScheduleId       	OBJECT-TYPE
                    		SYNTAX  Unsigned32
                    		MAX-ACCESS  read-write
                    		STATUS  current
                    		DESCRIPTION
                    			"rtr schedule Id,index"
                    		::= { sysSlaScheduleEntry   1 }

slaScheduleType     	OBJECT-TYPE
                    		SYNTAX  INTEGER {
                    			         entity(1),
                    			          group(2)
                    			        }
                    		MAX-ACCESS  read-write
                    		STATUS  current
                    		DESCRIPTION
                    			"rtr schedule type"
                    		::= { sysSlaScheduleEntry   2 }

slaScheduleObjId    	OBJECT-TYPE
                    		SYNTAX  INTEGER(1..2000)
                    		MAX-ACCESS  read-write
                    		STATUS  current
                    		DESCRIPTION
                    			"id of rtrschedule object which means rtr group or entity."
                    		::= { sysSlaScheduleEntry   3 }

slaScheduleStartTimeFlag	OBJECT-TYPE
                    		SYNTAX  INTEGER {
                    			         startNow(1),
                    			          afterTime(2),
                    			          startTime(3)
                    			        }
                    		MAX-ACCESS  read-write
                    		STATUS  current
                    		DESCRIPTION
                    			"RTR schedule start time.
                    			 startNow;
                    			 afterTime;
                    			 startTime-start at the given time"
                    		::= { sysSlaScheduleEntry   4 }

slaScheduleAfterTime		OBJECT-TYPE
				SYNTAX  DisplayString(SIZE(0..12))
                    		MAX-ACCESS  read-write
                    		STATUS  current
                    		DESCRIPTION
                    			"RTR schedule given time.
                    			 type string：
                    			 HH:MM:SS
                    			 valid when sysRtrScheduleFlag is afterTime."
                    		::= { sysSlaScheduleEntry   5 }

slaScheduleStartTime	OBJECT-TYPE
                    		SYNTAX  DisplayString(SIZE(0..40))
                    		MAX-ACCESS  read-write
                    		STATUS  current
                    		DESCRIPTION
                    			"RTR schedule given time.
                    			 type string：
                    			 HH:MM:SS,mm,dd,yyyy
                    			 valid when sysRtrScheduleFlag is startTime."
                    		::= { sysSlaScheduleEntry   6 }

slaScheduleAgeOut   	OBJECT-TYPE
                    		SYNTAX  Unsigned32(1..4294967295)
                    		MAX-ACCESS  read-write
                    		STATUS  current
                    		DESCRIPTION
                    			"rtr schedule ageout time in second."
                    		::= { sysSlaScheduleEntry   7 }

slaScheduleLifeFlag 	OBJECT-TYPE
                    		SYNTAX  INTEGER {
                    			         forever(1),
                    			          repeatAndDie(2)
                    			        }
                    		MAX-ACCESS  read-write
                    		STATUS  current
                    		DESCRIPTION
                    			"rtr schedule's life 
                    			 forever,if config, no need to config lifetime and repeat times
                    			 repeatAndDie,if config, need to config lifetime and repeat times"
                    		::= { sysSlaScheduleEntry   8 }

slaScheduleLifeTime 	OBJECT-TYPE
                    		SYNTAX  Unsigned32(1..2147483647)
                    		MAX-ACCESS  read-write
                    		STATUS  current
                    		DESCRIPTION
                    			"rtr schedule's lieftime in second,
                    			valid only when rtrScheduleLifeFlag is repeatAndDie."
                    		::= { sysSlaScheduleEntry   9 }

slaScheduleRepeat   	OBJECT-TYPE
                    		SYNTAX  Unsigned32(1..2147483647)
                    		MAX-ACCESS  read-write
                    		STATUS  current
                    		DESCRIPTION
                    			"rtr schedule's repeat times,
					valid only when rtrScheduleLifeFlag is repeatAndDie."
                    		::= { sysSlaScheduleEntry   10 }

slaScheduleInterval 	OBJECT-TYPE
                    		SYNTAX  Unsigned32(1..2147483647)
                    		MAX-ACCESS  read-only
                    		STATUS  current
                    		DESCRIPTION
                    			"rtr schedule interval in second"
                    		::= { sysSlaScheduleEntry   11 }

slaScheduleRowStatus	OBJECT-TYPE
                    		SYNTAX  RowStatus
                    		MAX-ACCESS  read-write
                    		STATUS  current
                    		DESCRIPTION
                    			"rtr schedule row status"
                    		::= { sysSlaScheduleEntry   12 }


------------------------------------------------------------------------------
sysSlaIcmpEchoMgt   	OBJECT IDENTIFIER ::= { sysSLA 5 }

sysSlaIcmpEchoTable 	OBJECT-TYPE
                    		SYNTAX  SEQUENCE OF   SysSlaIcmpEchoEntry 
                    		MAX-ACCESS  not-accessible
                    		STATUS  current
                    		DESCRIPTION
                    			"RTR ICMP entity table"
                    		::= { sysSlaIcmpEchoMgt   100 }

sysSlaIcmpEchoEntry 	OBJECT-TYPE
                    		SYNTAX  SysSlaIcmpEchoEntry 
                    		MAX-ACCESS  not-accessible
                    		STATUS  current
                    		DESCRIPTION
                    			"RTR ICMP entity entry"
                    		INDEX  { slaIcmpEchoTableEntityId    }
                    		::= { sysSlaIcmpEchoTable 1 }

SysSlaIcmpEchoEntry 	::= SEQUENCE {
                    			slaIcmpEchoTableEntityId	INTEGER,
                    			slaIcmpEchoTargetIp    IpAddress,
                    			slaIcmpEchoPktNum      Unsigned32,
                    			slaIcmpEchoPktLen      INTEGER,
                    			slaIcmpEchoTimeout     INTEGER,
                    			slaIcmpEchoSchInterval	Unsigned32,
                    			slaIcmpEchoExtendFlag   TruthValue,
                    			slaIcmpEchoVrfName     DisplayString,
                    			slaIcmpEchoSourceIp    IpAddress,
                    			slaIcmpEchoTos         INTEGER,
                    			slaIcmpEchoSetDf       TruthValue,
                    			slaIcmpEchoVerifyData   TruthValue,
					slaIcmpEchoHistorySize  INTEGER,
					slaIcmpEchoPeriods	INTEGER,
					slaIcmpEchoAlarmType	INTEGER,
					slaIcmpEchoAlarmType	INTEGER,
					slaIcmpEchoIsScheduling	TruthValue,
                    			slaIcmpEchoRowStatus   RowStatus
                    	             }


slaIcmpEchoTableEntityId	OBJECT-TYPE
                    		SYNTAX  INTEGER(1..2000)
                    		MAX-ACCESS  read-write
                    		STATUS  current
                    		DESCRIPTION
                    			"ICMP entity ID,index"
                    		::= { sysSlaIcmpEchoEntry 1 }

slaIcmpEchoTargetIp 	OBJECT-TYPE
                    		SYNTAX  IpAddress
                    		MAX-ACCESS  read-write
                    		STATUS  current
                    		DESCRIPTION
                    			"ICMPECHO(ping) destination address"
                    		::= { sysSlaIcmpEchoEntry 2 }

slaIcmpEchoPktNum   	OBJECT-TYPE
                    		SYNTAX  Unsigned32(1..200000000)
                    		MAX-ACCESS  read-write
                    		STATUS  current
                    		DESCRIPTION
                    			"ICMP PING send packets number,default 1.
                    			pkt-num * timeout must be less than schedule interval"
                    		::= { sysSlaIcmpEchoEntry 3 }

slaIcmpEchoPktLen   	OBJECT-TYPE
                    		SYNTAX  INTEGER(36..18024)
                    		MAX-ACCESS  read-write
                    		STATUS  current
                    		DESCRIPTION
                    			"ICMP PING send packets size,default 70."
                    		::= { sysSlaIcmpEchoEntry 4 }

slaIcmpEchoTimeout  	OBJECT-TYPE
                    		SYNTAX  INTEGER(1..3600)
                    		MAX-ACCESS  read-write
                    		STATUS  current
                    		DESCRIPTION
                    			"ICMP ping reply timeout in seconds,default 2 seconds.
                    			pkt-num * timeout must be less than schedule interval"
                    		::= { sysSlaIcmpEchoEntry 5 }

slaIcmpEchoSchInterval 	OBJECT-TYPE
                    			SYNTAX  Unsigned32(1..2147483647)
                    			MAX-ACCESS  read-write
                    			STATUS  current
                    			DESCRIPTION
                    				"IcmpEcho interval in seconds,default 12 seconds.
                    				schedule interval must be larger than timout * pkt-num"
                    			::= { sysSlaIcmpEchoEntry 6 }
                    		
slaIcmpEchoExtendFlag	OBJECT-TYPE
                    		SYNTAX  TruthValue
                    		MAX-ACCESS  read-write
                    		STATUS  current
                    		DESCRIPTION
                    			"ICMP extern ping flag,
                    			have set Tos,verify data,DF,sourceIp and vrf or yet."
                    		::= { sysSlaIcmpEchoEntry 7 }

slaIcmpEchoVrfName  	OBJECT-TYPE
                    		SYNTAX  DisplayString(SIZE(0..40))
                    		MAX-ACCESS  read-write
                    		STATUS  current
                    		DESCRIPTION
                    			"vrfname type string,
                    			valid only rtrIcmpEchoExtendFlag is TRUE,default global."
                    		::= { sysSlaIcmpEchoEntry 8 }

slaIcmpEchoSourceIp 	OBJECT-TYPE
                    		SYNTAX  IpAddress
                    		MAX-ACCESS  read-write
                    		STATUS  current
                    		DESCRIPTION
                    			"ICMP source IP address,
					valid only rtrIcmpEchoExtendFlag is TRUE."
                    		::= { sysSlaIcmpEchoEntry 9 }

slaIcmpEchoTos      	OBJECT-TYPE
                    		SYNTAX  INTEGER(0..255)
                    		MAX-ACCESS  read-write
                    		STATUS  current
                    		DESCRIPTION
                    			"ICMP TOS value,
					valid only rtrIcmpEchoExtendFlag is TRUE,default 0."
                    		::= { sysSlaIcmpEchoEntry 10 }

slaIcmpEchoSetDf    	OBJECT-TYPE
                    		SYNTAX  TruthValue
                    		MAX-ACCESS  read-write
                    		STATUS  current
                    		DESCRIPTION
                    			"ICMP pakcet DF bit,
                    			valid only rtrIcmpEchoExtendFlag is TRUE,default TRUE."
                    		::= { sysSlaIcmpEchoEntry 11 }

slaIcmpEchoVerifyData	OBJECT-TYPE
                    		SYNTAX  TruthValue
                    		MAX-ACCESS  read-write
                    		STATUS  current
                    		DESCRIPTION
                    			"ICMP verifay data flag,
                    			valid only rtrIcmpEchoExtendFlag is TRUE,default FALSE."
                    		::= { sysSlaIcmpEchoEntry 12 }

slaIcmpEchoHistorySize  OBJECT-TYPE
                    		SYNTAX  INTEGER(0..255)
                    		MAX-ACCESS  read-write
                    		STATUS  current
                    		DESCRIPTION
                    			"ICMPECHO entity 's history size,default 1."
                    		::= { sysSlaIcmpEchoEntry 13 }

slaIcmpEchoPeriods	OBJECT-TYPE
                    		SYNTAX  INTEGER(0..500)
                    		MAX-ACCESS  read-write
                    		STATUS  current
                    		DESCRIPTION
                    			"periods,default 1."
                    		::= { sysSlaIcmpEchoEntry 14 }

slaIcmpEchoAlarmType		OBJECT-TYPE
				SYNTAX  INTEGER {
                    			        log(1),
                    			        trap(2),
						logAndTrap(3),
						noLogAndtrap(4) 
                    			        }
                    		MAX-ACCESS  read-write
                    		STATUS  current
                    		DESCRIPTION
                    			"RTR entity alarm type。
                    			 log－log message
                    			 trap－snmp trap
					 logAndTrap-log message and snmp trap
					 noLogAndtrap-no log message and no snmp trap,default."
                    		::= { sysSlaIcmpEchoEntry 15 }

slaIcmpEchoIsScheduling		OBJECT-TYPE
                    		SYNTAX  TruthValue
                    		MAX-ACCESS  read-write
                    		STATUS  current
                    		DESCRIPTION
                    			"TRUE(1)-in scheduling
					 FALSE(2)-not in scheduling"
                    		::= { sysSlaIcmpEchoEntry 16 }



slaIcmpEchoRowStatus	OBJECT-TYPE
                    		SYNTAX  RowStatus
                    		MAX-ACCESS  read-write
                    		STATUS  current
                    		DESCRIPTION
                    			"ICMP row status"
                    		::= { sysSlaIcmpEchoEntry 17 }
------------------------------------------------------------------------------
sysSlaIcmpEchoHistoryTable 	OBJECT-TYPE
                    		SYNTAX  SEQUENCE OF   SysSlaIcmpEchoHistoryEntry 
                    		MAX-ACCESS  not-accessible
                    		STATUS  current
                    		DESCRIPTION
                    			"RTR ICMP entity history table"
                    		::= { sysSlaIcmpEchoMgt 200 }

sysSlaIcmpEchoHistoryEntry 	OBJECT-TYPE
                    		SYNTAX  SysSlaIcmpEchoHistoryEntry 
                    		MAX-ACCESS  not-accessible
                    		STATUS  current
                    		DESCRIPTION
                    			"RTR ICMP entity entry"
                    		INDEX  { slaIcmpEchoHisTableEntityId , slaIcmpechoHistoryIndex }
                    		::= { sysSlaIcmpEchoHistoryTable 1 }

SysSlaIcmpEchoHistoryEntry 	::= SEQUENCE {
					slaIcmpEchoHisTableEntityId		   INTEGER,
                    			slaIcmpEchoHistoryIndex    INTEGER,
                    			slaIcmpEchoRtt    	   INTEGER,
					slaIcmpEchoPktLoss    	   INTEGER,
					slaIcmpEchoTime		   DisplayString,    
					slaIcmpEchoTableRowStatus	   RowStatus
                    	             }
slaIcmpEchoHisTableEntityId		OBJECT-TYPE
                    		SYNTAX  INTEGER(1..2000)
                    		MAX-ACCESS  read-write
                    		STATUS  current
                    		DESCRIPTION
                    			"ICMP entity id,index"
                    		::= { sysSlaIcmpEchoHistoryEntry 1 }

slaIcmpEchoHistoryIndex    	OBJECT-TYPE
                    		SYNTAX  INTEGER(1..500)
                    		MAX-ACCESS  read-write
                    		STATUS  current
                    		DESCRIPTION
                    			"ICMP entity history index"
                    		::= { sysSlaIcmpEchoHistoryEntry 2 }

slaIcmpEchoRtt			OBJECT-TYPE
				SYNTAX  INTEGER(0..5000)
				MAX-ACCESS  read-write
				STATUS  current
				DESCRIPTION
					"ICMP entity rtt"
				::= { sysSlaIcmpEchoHistoryEntry 3}

slaIcmpEchoPktLoss		OBJECT-TYPE
				SYNTAX  INTEGER(0..200000000)
				MAX-ACCESS  read-write
				STATUS  current
				DESCRIPTION
					"ICMP entity pkt loss "
				::= { sysSlaIcmpEchoHistoryEntry  4}

slaIcmpEchoTime			OBJECT-TYPE
				SYNTAX  DisplayString(SIZE(0..39))
				MAX-ACCESS  read-write
				STATUS  current
				DESCRIPTION
					"recorded time"
				::= { sysSlaIcmpEchoHistoryEntry  5}

slaIcmpEchoTableRowStatus		OBJECT-TYPE
                    		SYNTAX  RowStatus
                    		MAX-ACCESS  read-write
                    		STATUS  current
                    		DESCRIPTION
                    			"ICMP row status"
                    		::= { sysSlaIcmpEchoHistoryEntry 6 }


------------------------------------------------------------------------------
sysSlaJitterMgt     	OBJECT IDENTIFIER ::= { sysSLA 6 }

sysSlaJitterTable   	OBJECT-TYPE
                    		SYNTAX  SEQUENCE OF   SysSlaJitterEntry   
                    		MAX-ACCESS  not-accessible
                    		STATUS  current
                    		DESCRIPTION
                    			"RTR JITTER entity table"
                    		::= { sysSlaJitterMgt     100 }

sysSlaJitterEntry   	OBJECT-TYPE
                    		SYNTAX  SysSlaJitterEntry   
                    		MAX-ACCESS  not-accessible
                    		STATUS  current
                    		DESCRIPTION
                    			"RTR JITTER entity entry"
                    		INDEX  { slaJitterTableEntityId }
                    		::= { sysSlaJitterTable   1 }

SysSlaJitterEntry   	::= SEQUENCE {
                    			slaJitterTableEntityId 		INTEGER,
                    			slaJitterState			INTEGER,
                    			slaJitterTargetIp		IpAddress,
                    			slaJitterTargetPort		INTEGER,
                    			slaJitterCodec			INTEGER,
                    			slaJitterPktLen			INTEGER,
                    			slaJitterPktNum			INTEGER,
                    			slaJitterPktInterval		INTEGER,
                    			slaJitterSchInterval		INTEGER,
                    			slaJitterSourceIp		IpAddress,
                    			slaJitterSourcePort		INTEGER,
                    			slaJitterTimeout		INTEGER,
                    			slaJitterVrfName		DisplayString,
                    			slaJitterTos			INTEGER,
					slaJitterHistorySize		INTEGER,
					slaJitterPeriods		INTEGER,
					slaJitterAlarmType		INTEGER,
                    			slaJitterTableRowStatus		RowStatus
                    	             }


slaJitterTableEntityId 		OBJECT-TYPE
                    		SYNTAX  INTEGER(1..2000)
                    		MAX-ACCESS  read-write
                    		STATUS  current
                    		DESCRIPTION
                    			"JITTER entity id,index"
                    		::= { sysSlaJitterEntry 1 }
                    		
slaJitterState          OBJECT-TYPE
							SYNTAX	INTEGER	{
								init(1),
								pend(2),
								request(3),
								transmit(4),
								halt(5),
								finished(6)
									}
							MAX-ACCESS  read-only
                    		STATUS  current
                    		DESCRIPTION
                    		"JITTE entity：1－init，2－pend,
                    		                 3－send request，4-send packets，
                    		                 5-halt, 6－finish"
							::= { sysSlaJitterEntry 2 }
							
slaJitterTargetIp   	OBJECT-TYPE
                    		SYNTAX  IpAddress
                    		MAX-ACCESS  read-write
                    		STATUS  current
                    		DESCRIPTION
                    			"JITTER responder destination ip address"
                    		::= { sysSlaJitterEntry 3 }

slaJitterTargetPort 	OBJECT-TYPE
                    		SYNTAX  INTEGER(1..65535)
                    		MAX-ACCESS  read-write
                    		STATUS  current
                    		DESCRIPTION
                    			"JITTER responder destination port"
                    		::= { sysSlaJitterEntry 4 }

slaJitterCodec      	OBJECT-TYPE
                    		SYNTAX  INTEGER {
                    			         g711MULAW(1),
                    			          g711ALAW(2),
                    			          g729A(3),
                    			          userDefined(4),
                    			          invalid(5)
                    			        }
                    		MAX-ACCESS  read-write
                    		STATUS  current
                    		DESCRIPTION
                    			"JITTER codec type,including:
                    			1 G711MULAW,2 G711ALAW,3  G729A,4 USER_DEFINED
                    			5 UNKOWN"
                    		::= { sysSlaJitterEntry 5 }

slaJitterPktLen     	OBJECT-TYPE
                    		SYNTAX  INTEGER(16..1500)
                    		MAX-ACCESS  read-write
                    		STATUS  current
                    		DESCRIPTION
                    			"JITTER codec packet length,
                    			read-writable when rtrJitterCodec is USER_DEFINED 
                    			else read-only
					type:byte."
                    		::= { sysSlaJitterEntry 6 }

slaJitterPktNum     	OBJECT-TYPE
                    		SYNTAX  INTEGER(1..6000)
                    		MAX-ACCESS  read-write
                    		STATUS  current
                    		DESCRIPTION
                    			"JITTER codec packet number,
                    			read-writable when rtrJitterCodec is USER_DEFINED
                    			else read-only.
                    			pkt-num * pkt-interval must be less than timeout"
                    		::= { sysSlaJitterEntry 7 }

slaJitterPktInterval	OBJECT-TYPE
                    		SYNTAX  INTEGER(20..6000)
                    		MAX-ACCESS  read-write
                    		STATUS  current
                    		DESCRIPTION
                    			"JITTER codec packet send interval,
                    			read-writable when rtrJitterCodec is USER_DEFINED,default 20 ms.
                    			else read-only,
                    			type:ms.
                    			pkt-num * pkt-interval must be less than timeout"
                    		::= { sysSlaJitterEntry 8 }

slaJitterSchInterval 	OBJECT-TYPE
                    		SYNTAX  INTEGER(1..2147483647)
                    		MAX-ACCESS  read-write
                    		STATUS  current
                    		DESCRIPTION
                    			"Jitter schedule interval,
                    			read-writable when rtrJitterCodec is USER_DEFINED,default 6s.
                    			else read-only,
                    			type:s.
                    			schedule interval must be larger than timeout"
                    		::= { sysSlaJitterEntry 9 }
                    			
slaJitterSourceIp   	OBJECT-TYPE
                    		SYNTAX  IpAddress
                    		MAX-ACCESS  read-write
                    		STATUS  current
                    		DESCRIPTION
                    			"JITTER source IP address"
                    		::= { sysSlaJitterEntry 10 }

slaJitterSourcePort 	OBJECT-TYPE
                    		SYNTAX  INTEGER(1..65535)
                    		MAX-ACCESS  read-write
                    		STATUS  current
                    		DESCRIPTION
                    			"JITTER source port"
                    		::= { sysSlaJitterEntry 11 }

slaJitterTimeout    	OBJECT-TYPE
                    		SYNTAX  INTEGER(0..604800000)
                    		MAX-ACCESS  read-write
                    		STATUS  current
                    		DESCRIPTION
                    			"JITTER timeout value,type:ms,default 5000,
                    			notice,schedule interval must be larger than timeout"
                    		::= { sysSlaJitterEntry 12 }

slaJitterVrfName    	OBJECT-TYPE
                    		SYNTAX  DisplayString(SIZE(0..40))
                    		MAX-ACCESS  read-write
                    		STATUS  current
                    		DESCRIPTION
                    			"JITTER vrf string,default global."
                    		::= { sysSlaJitterEntry 13 }

slaJitterTos        	OBJECT-TYPE
                    		SYNTAX  INTEGER(0..255)
                    		MAX-ACCESS  read-write
                    		STATUS  current
                    		DESCRIPTION
                    			"JITTER pakcet TOS value,default 0."
                    		::= { sysSlaJitterEntry 14 }

slaJitterHistorySize		OBJECT-TYPE
                    		SYNTAX  INTEGER(0..255)
                    		MAX-ACCESS  read-write
                    		STATUS  current
                    		DESCRIPTION
                    			"JITTER entity's history size,default 1."
                    		::= { sysSlaJitterEntry 15 }

slaJitterPeriods		OBJECT-TYPE
                    		SYNTAX  INTEGER(0..500)
                    		MAX-ACCESS  read-write
                    		STATUS  current
                    		DESCRIPTION
                    			"periods,default 1."
                    		::= { sysSlaJitterEntry 16 }

slaJitterAlarmType		OBJECT-TYPE
			SYNTAX  INTEGER {
                    			        log(1),
                    			        trap(2),
						logAndTrap(3),
						noLogAndtrap(4) 
                    			        }
                    		MAX-ACCESS  read-write
                    		STATUS  current
                    		DESCRIPTION
                    			"RTR entity alarm type。
                    			 log(1)－log message
                    			 trap(2)－snmp trap
					 logAndTrap(3)-log message and snmp trap
					 noLogAndtrap(4)-no log message and no snmp trap,default."
                    		::= { sysSlaJitterEntry  17 }

slaJitterTableRowStatus		OBJECT-TYPE
                    		SYNTAX  RowStatus
                    		MAX-ACCESS  read-write
                    		STATUS  current
                    		DESCRIPTION
                    			"JITTER row status"
                    		::= { sysSlaJitterEntry 18 }

-------------------------------------------------------------------------------

sysSlaJitterHistoryTable 	OBJECT-TYPE
                    		SYNTAX  SEQUENCE OF   SysSlaJitterHistoryEntry   
                    		MAX-ACCESS  not-accessible
                    		STATUS  current
                    		DESCRIPTION
                    			"RTR JITTER history table"
                    		::= { sysSlaJitterMgt 200 }

sysSlaJitterHistoryEntry   	OBJECT-TYPE
                    		SYNTAX  SysSlaJitterHistoryEntry   
                    		MAX-ACCESS  not-accessible
                    		STATUS  current
                    		DESCRIPTION
                    			"RTR JITTER entity entry"
                    		INDEX  { slaJitterHisTableEntityId ,slaJitterHistoryIndex }
                    		::= { sysSlaJitterHistoryTable 1 }

SysSlaJitterHistoryEntry   	::= SEQUENCE {
					slaJitterHisTableEntityId		INTEGER,
					slaJitterHistoryIndex  INTEGER,
                    			slaJitterRtt           INTEGER,
                    			slaJitterPktLossSd     INTEGER,
                    			slaJitterPktLossDs     INTEGER,
                    			slaJitterSd            INTEGER,
                    			slaJitterDs            INTEGER,
                    			slaJitterDelaySd       INTEGER,
                    			slaJitterDelayDs       INTEGER,
                    			slaJitterIcpif         INTEGER,
                    			slaJitterMos           INTEGER,
					slaJitterTime	       DisplayString,
                    			slaJitterHisTableRowStatus     RowStatus
                    	             }
slaJitterHisTableEntityId			OBJECT-TYPE
                    		SYNTAX  INTEGER(1..2000)
                    		MAX-ACCESS  read-write
                    		STATUS  current
                    		DESCRIPTION
                    			"JITTER entity id, index"
                    		::= { sysSlaJitterHistoryEntry   1 }
                    		

slaJitterHistoryIndex   	OBJECT-TYPE
                    		SYNTAX  INTEGER(1..255)
                    		MAX-ACCESS  read-write
                    		STATUS  current
                    		DESCRIPTION
                    			"JITTER history index"
                    		::= { sysSlaJitterHistoryEntry   2 }
                    		
slaJitterRtt     		OBJECT-TYPE
                    		SYNTAX  INTEGER
                    		MAX-ACCESS  read-only
                    		STATUS  current
                    		DESCRIPTION
                    			"JITTER round-trip-time value in ms"
                    		::= { sysSlaJitterHistoryEntry   3 }


slaJitterPktLossSd  		OBJECT-TYPE
                    		SYNTAX  INTEGER
                    		MAX-ACCESS  read-only
                    		STATUS  current
                    		DESCRIPTION
                    			"JITTER total lossed pakcets which send by the source "
                    		::= { sysSlaJitterHistoryEntry   4 }

slaJitterPktLossDs  		OBJECT-TYPE
                    		SYNTAX  INTEGER
                    		MAX-ACCESS  read-only
                    		STATUS  current
                    		DESCRIPTION
                    			"JITTER total loss pakcets which send by the target"
                    		::= { sysSlaJitterHistoryEntry   5 }

slaJitterSd		      	OBJECT-TYPE
                    		SYNTAX  INTEGER
                    		MAX-ACCESS  read-only
                    		STATUS  current
                    		DESCRIPTION
                    			"JITTER destination to source jitter in millisecond"
                    		::= { sysSlaJitterHistoryEntry   6 }

slaJitterDs             	OBJECT-TYPE
                    		SYNTAX  INTEGER
                    		MAX-ACCESS  read-only
                    		STATUS  current
                    		DESCRIPTION
                    			"JITTER source to destination jitter in millisecond"
                    		::= { sysSlaJitterHistoryEntry   7 }

slaJitterDelaySd 	 	OBJECT-TYPE
                    		SYNTAX  INTEGER
                    		MAX-ACCESS  read-only
                    		STATUS  current
                    		DESCRIPTION
                    			"JITTER maximal destination to source delay in millisecond"
                    		::= { sysSlaJitterHistoryEntry   8 }

slaJitterDelayDs	 	OBJECT-TYPE
                    		SYNTAX  INTEGER
                    		MAX-ACCESS  read-only
                    		STATUS  current
                    		DESCRIPTION
                    			"JITTER maximal source to destination delay in millisecond"
                    		::= { sysSlaJitterHistoryEntry   9 }

slaJitterIcpif		   	OBJECT-TYPE
                    		SYNTAX  INTEGER
                    		MAX-ACCESS  read-only
                    		STATUS  current
                    		DESCRIPTION
                    			"JITTER icpif"
                    		::= { sysSlaJitterHistoryEntry   10 }

slaJitterMos		     	OBJECT-TYPE
                    		SYNTAX  INTEGER
                    		MAX-ACCESS  read-only
                    		STATUS  current
                    		DESCRIPTION
                    			"JITTER MOS"
                    		::= { sysSlaJitterHistoryEntry   11 }


slaJitterTime		     	OBJECT-TYPE
                    		SYNTAX  DisplayString(SIZE(0..40))
                    		MAX-ACCESS  read-only
                    		STATUS  current
                    		DESCRIPTION
                    			"recorded time"
                    		::= { sysSlaJitterHistoryEntry   12 }

slaJitterHisTableRowStatus     		OBJECT-TYPE
                    		SYNTAX  RowStatus
                    		MAX-ACCESS  read-write
                    		STATUS  current
                    		DESCRIPTION
                    			"JITTER history row status"
                    		::= { sysSlaJitterHistoryEntry   13 }


------------------------------------------------------------------------------

sysSlaUdpEchoMgt     	OBJECT IDENTIFIER ::= { sysSLA 7 }

sysSlaUdpEchoTable   	OBJECT-TYPE
                    		SYNTAX  SEQUENCE OF   SysSlaUdpEchoEntry   
                    		MAX-ACCESS  not-accessible
                    		STATUS  current
                    		DESCRIPTION
                    			"RTR UDPECHO entity table"
                    		::= { sysSlaUdpEchoMgt     100 }

sysSlaUdpEchoEntry   	OBJECT-TYPE
                    		SYNTAX  SysSlaUdpEchoEntry   
                    		MAX-ACCESS  not-accessible
                    		STATUS  current
                    		DESCRIPTION
                    			"RTR UDPECHO entity entry"
                    		INDEX  { slaUdpEchoTableEntityId  }
                    		::= { sysSlaUdpEchoTable   1 }

SysSlaUdpEchoEntry   	::= SEQUENCE {
                    			slaUdpEchoTableEntityId 		INTEGER,
                    			slaUdpEchoState         	INTEGER,
                    			slaUdpEchoTargetIp      	IpAddress,
                    			slaUdpEchoTargetPort    	Unsigned32,
                    			slaUdpEchoPktLen        	INTEGER,
                    			slaUdpEchoSchInterval   	Unsigned32,
                    			slaUdpEchoSourceIp      	IpAddress,
                    			slaUdpEchoSourcePort    	Unsigned32,
                    			slaUdpEchoTimeout       	Unsigned32,
                    			slaUdpEchoVrfName       	DisplayString,
                    			slaUdpEchoTos           	INTEGER,
					slaUdpEchoHistorySize		INTEGER,
					slaUdpEchoPeriods		INTEGER,
					slaUdpEchoAlarmType		INTEGER,
                      			slaUdpEchoTableRowStatus     	RowStatus
                    	             }


slaUdpEchoTableEntityId 	OBJECT-TYPE
                    		SYNTAX  INTEGER(1..2000)
                    		MAX-ACCESS  read-write
                    		STATUS  current
                    		DESCRIPTION
                    			"UDPECHO entity id,index"
                    		::= { sysSlaUdpEchoEntry   1 }
                    		
slaUdpEchoState          OBJECT-TYPE
				SYNTAX	INTEGER	{
					init(1),
					pend(2),
					request(3),
					transmit(4),
					halt(5),
					finished(6)
						}
				MAX-ACCESS  read-only
                    		STATUS  current
                    		DESCRIPTION
                    		"UDPECHO entity：1－init，2－pend，
                    		                 3－send request，4-send packets，5-halt,
                    		                 6－finish"
				::= { sysSlaUdpEchoEntry   2 }
							
slaUdpEchoTargetIp   	OBJECT-TYPE
                    		SYNTAX  IpAddress
                    		MAX-ACCESS  read-write
                    		STATUS  current
                    		DESCRIPTION
                    			"UDPECHO responder destination ip address"
                    		::= { sysSlaUdpEchoEntry   3 }

slaUdpEchoTargetPort 	OBJECT-TYPE
                    		SYNTAX  Unsigned32(1..65535)
                    		MAX-ACCESS  read-write
                    		STATUS  current
                    		DESCRIPTION
                    			"UDPECHO responder destination port"
                    		::= { sysSlaUdpEchoEntry   4 }


slaUdpEchoPktLen     	OBJECT-TYPE
                    		SYNTAX  INTEGER(4..1500)
                    		MAX-ACCESS  read-write
                    		STATUS  current
                    		DESCRIPTION
                    			"UDPECHO packet length,default 16."
                    		::= { sysSlaUdpEchoEntry   5 }


slaUdpEchoSchInterval 	OBJECT-TYPE
                    		SYNTAX  Unsigned32(1..65535)
                    		MAX-ACCESS  read-write
                    		STATUS  current
                    		DESCRIPTION
                    			"UDPECHO schedule interval in milliseconds,default 6.
                   			type:s.
                   			schedule interval must be larger than timeout"
                    		::= { sysSlaUdpEchoEntry   6 }
                    			
slaUdpEchoSourceIp   	OBJECT-TYPE
                    		SYNTAX  IpAddress
                    		MAX-ACCESS  read-write
                    		STATUS  current
                    		DESCRIPTION
                    			"UDPECHO source IP address"
                    		::= { sysSlaUdpEchoEntry   7 }

slaUdpEchoSourcePort 	OBJECT-TYPE
                    		SYNTAX  Unsigned32(1..65535)
                    		MAX-ACCESS  read-write
                    		STATUS  current
                    		DESCRIPTION
                    			"UDPECHO source port"
                    		::= { sysSlaUdpEchoEntry   8 }

slaUdpEchoTimeout    	OBJECT-TYPE
                    		SYNTAX  Unsigned32(0..604800000)
                    		MAX-ACCESS  read-write
                    		STATUS  current
                    		DESCRIPTION
                    			"UDPECHO timeout value,type:ms,default 5000.
                    			schedule interval must be larger than timeout"
                    		::= { sysSlaUdpEchoEntry   9 }

slaUdpEchoVrfName    	OBJECT-TYPE
                    		SYNTAX  DisplayString(SIZE(0..40))
                    		MAX-ACCESS  read-write
                    		STATUS  current
                    		DESCRIPTION
                    			"UDPECHO vrf string,default global."
                    		::= { sysSlaUdpEchoEntry   10 }

slaUdpEchoTos        		OBJECT-TYPE
                    		SYNTAX  INTEGER(0..255)
                    		MAX-ACCESS  read-write
                    		STATUS  current
                    		DESCRIPTION
                    			"UDPECHO pakcet TOS value,default 0."
                    		::= { sysSlaUdpEchoEntry   11 }


slaUdpEchoHistorySize		OBJECT-TYPE
                    		SYNTAX  INTEGER(0..255)
                    		MAX-ACCESS  read-write
                    		STATUS  current
                    		DESCRIPTION
                    			"UDPECHO entity's history size,defualt 1."
                    		::= { sysSlaUdpEchoEntry   12 }

slaUdpEchoPeriods		OBJECT-TYPE
                    		SYNTAX  INTEGER(0..500)
                    		MAX-ACCESS  read-write
                    		STATUS  current
                    		DESCRIPTION
                    			"periods,default 1."
                    		::= { sysSlaUdpEchoEntry   13 }

slaUdpEchoAlarmType		OBJECT-TYPE
				SYNTAX  INTEGER {
                    			        log(1),
                    			        trap(2),
						logAndTrap(3),
						noLogAndtrap(4) 
                    			        }
                    		MAX-ACCESS  read-write
                    		STATUS  current
                    		DESCRIPTION
                    			"RTR entity alarm type,
                    			 log－log message,
                    			 trap－snmp trap,
					 logAndTrap-log message and snmp trap,
					 noLogAndtrap-no log message and no snmp trap,default."
                    		::= { sysSlaUdpEchoEntry   14 }

slaUdpEchoTableRowStatus	  	OBJECT-TYPE
                    			SYNTAX  RowStatus
                    			MAX-ACCESS  read-write
                    			STATUS  current
                    			DESCRIPTION
                    				"UDPECHO row status"
                    		::= { sysSlaUdpEchoEntry   15 }

--
sysSlaUdpEchoHistoryTable   	OBJECT-TYPE
                    		SYNTAX  SEQUENCE OF   SysSlaUdpEchoHistoryEntry   
                    		MAX-ACCESS  not-accessible
                    		STATUS  current
                    		DESCRIPTION
                    			"RTR UDPECHO entity table"
                    		::= { sysSlaUdpEchoMgt     200 }

sysSlaUdpEchoHistoryEntry   	OBJECT-TYPE
                    		SYNTAX  SysSlaUdpEchoHistoryEntry   
                    		MAX-ACCESS  not-accessible
                    		STATUS  current
                    		DESCRIPTION
                    			"RTR UDPECHO entity entry"
                    		INDEX  { slaUdpEchoHisTableEntityId , slaUdpEchoHistoryIndex }
                    		::= { sysSlaUdpEchoHistoryTable   1 }

SysSlaUdpEchoHistoryEntry   	::= SEQUENCE {
					slaUdpEchoHisTableEntityId		INTEGER,
                    			slaUdpEchoHistoryIndex	INTEGER,
                   			slaUdpEchoPktLoss	INTEGER,
					slaUdpEchoRtt		INTEGER,
					slaUdpEchoTime		DisplayString,
                    			slaUdpEchoHisTableRowStatus	RowStatus
                    	             }

slaUdpEchoHisTableEntityId			OBJECT-TYPE
                    		SYNTAX  INTEGER(1..2000)
                    		MAX-ACCESS  read-write
                    		STATUS  current
                    		DESCRIPTION
                    			"UDPECHO entity id,idx"
                    		::= { sysSlaUdpEchoHistoryEntry   1 }

slaUdpEchoHistoryIndex		OBJECT-TYPE
                    		SYNTAX  INTEGER(1..255)
                    		MAX-ACCESS  read-write
                    		STATUS  current
                    		DESCRIPTION
                    			"UDPECHO history index"
                    		::= { sysSlaUdpEchoHistoryEntry   2 }
                    		

slaUdpEchoPktLoss		OBJECT-TYPE
                    		SYNTAX  INTEGER
                    		MAX-ACCESS  read-only
                    		STATUS  current
                    		DESCRIPTION
                    			"UDPECHO total lossed pakcets which send by the source "
                    		::= { sysSlaUdpEchoHistoryEntry   3 }

slaUdpEchoRtt		 	OBJECT-TYPE
                    		SYNTAX  INTEGER
                    		MAX-ACCESS  read-only
                    		STATUS  current
                    		DESCRIPTION
                    			"UDPECHO rtt in millisecond"
                    		::= { sysSlaUdpEchoHistoryEntry   4 }

slaUdpEchoTime		 	OBJECT-TYPE
                    		SYNTAX  DisplayString(SIZE(0..40))
                    		MAX-ACCESS  read-only
                    		STATUS  current
                    		DESCRIPTION
                    			"UDPECHO rtt in millisecond"
                    		::= { sysSlaUdpEchoHistoryEntry   5 }



slaUdpEchoHisTableRowStatus	  	OBJECT-TYPE
                    			SYNTAX  RowStatus
                    			MAX-ACCESS  read-write
                    			STATUS  current
                    			DESCRIPTION
                    				"UDPECHO row status"
                    		::= { sysSlaUdpEchoHistoryEntry   6 }



------------------------------------------------------------------------------
sysSlaFlStaMgt		OBJECT IDENTIFIER ::= { sysSLA 8 }

sysSlaFlStaTable	OBJECT-TYPE
                    		SYNTAX  SEQUENCE OF   SysSlaFlStaEntry
                    		MAX-ACCESS  not-accessible
                    		STATUS  current
                    		DESCRIPTION
                    			"RTR flow statistics table"
                    		::= { sysSlaFlStaMgt  100 }

sysSlaFlStaEntry	OBJECT-TYPE
                    		SYNTAX  SysSlaFlStaEntry
                    		MAX-ACCESS  not-accessible
                    		STATUS  current
                    		DESCRIPTION
                    			"RTR flow statistics entry"
                    		INDEX  { slaFlStaTableEntityId }
                    		::= { sysSlaFlStaTable 1 }

SysSlaFlStaEntry	::= SEQUENCE {
                    			slaFlStaTableEntityId		INTEGER,
                    			slaFlStaIfName   DisplayString,
                    			slaFlStaInterval   INTEGER,
					slaFlStaHistorySize	INTEGER,
					slaFlStaPeriods		INTEGER,
					slaFlStaAlarmType	INTEGER,
                    			slaFlStaTableRowStatus	RowStatus
                    	             }


slaFlStaTableEntityId		OBJECT-TYPE
                    		SYNTAX  INTEGER(1..2000)
                    		MAX-ACCESS  read-write
                    		STATUS  current
                    		DESCRIPTION
                    			"flow statistics entity Id"
                    		::= { sysSlaFlStaEntry  1 }

slaFlStaIfName		OBJECT-TYPE
                    		SYNTAX  DisplayString(SIZE(0..40))
                    		MAX-ACCESS  read-write
                    		STATUS  current
                    		DESCRIPTION
                    			"interface name which will be statistic"
                    		::= { sysSlaFlStaEntry  2 }

slaFlStaInterval		OBJECT-TYPE
                    		SYNTAX  INTEGER(10..600)
                    		MAX-ACCESS  read-write
                    		STATUS  current
                    		DESCRIPTION
                    			"monitor interval in second,default 600."
                    		::= { sysSlaFlStaEntry  3 }

slaFlStaHistorySize	OBJECT-TYPE
                    		SYNTAX  INTEGER(1..255)
                    		MAX-ACCESS  read-write
                    		STATUS  current
                    		DESCRIPTION
                    			"flow statistics entity's history size,default 1."
                    		::= { sysSlaFlStaEntry  4 }

slaFlStaPeriods		OBJECT-TYPE
                    		SYNTAX  INTEGER(1..500)
                    		MAX-ACCESS  read-write
                    		STATUS  current
                    		DESCRIPTION
                    			"periods,default 1."
                    		::= { sysSlaFlStaEntry  5 }

slaFlStaAlarmType	OBJECT-TYPE
				SYNTAX  INTEGER {
                    			        log(1),
                    			        trap(2),
						logAndTrap(3),
						noLogAndtrap(4) 
                    			        }
                    		MAX-ACCESS  read-write
                    		STATUS  current
                    		DESCRIPTION
                    			"RTR entity alarm type。
                    			 log－log message
                    			 trap－snmp trap
					 logAndTrap-log message and snmp trap
					 noLogAndtrap-no log message and no snmp trap,default"
                    		::= { sysSlaFlStaEntry  6 }

slaFlStaTableRowStatus	OBJECT-TYPE
                    		SYNTAX  RowStatus
                    		MAX-ACCESS  read-write
                    		STATUS  current
                    		DESCRIPTION
                    			"flow statistics row status"
                    		::= { sysSlaFlStaEntry  7 }


------------------------------------------------------------------------------

sysSlaFlStaHistoryTable		OBJECT-TYPE
                    		SYNTAX  SEQUENCE OF   SysSlaFlStaHistoryEntry
                    		MAX-ACCESS  not-accessible
                    		STATUS  current
                    		DESCRIPTION
                    			"RTR flow statistics table"
                    		::= { sysSlaFlStaMgt 200 }

sysSlaFlStaHistoryEntry		OBJECT-TYPE
                    		SYNTAX  SysSlaFlStaHistoryEntry
                    		MAX-ACCESS  not-accessible
                    		STATUS  current
                    		DESCRIPTION
                    			"RTR flow statistics entry"
                    		INDEX  { slaFlStaHisTableEntityId , slaFlStaHistoryIndex }
                    		::= { sysSlaFlStaHistoryTable 1 }

SysSlaFlStaHistoryEntry	::= SEQUENCE {
                    			slaFlStaHisTableEntityId			INTEGER,
					slaFlStaHistoryIndex		INTEGER,
                    			slaFlStaInputPkts		INTEGER,
                    			slaFlStaInputFlow		INTEGER,
                    			slaFlStaOutputPkts		INTEGER,
                    			slaFlStaOutputFlow		INTEGER,
					slaFlStaTime			DisplayString,  
					slaFlStaHisTableRowStatus		RowStatus
                    	             }


slaFlStaHisTableEntityId			OBJECT-TYPE
                    		SYNTAX  INTEGER(1..2000)
                    		MAX-ACCESS  read-write
                    		STATUS  current
                    		DESCRIPTION
                    			"flow statistics entity Id"
                    		::= { sysSlaFlStaHistoryEntry  1 }

slaFlStaHistoryIndex		OBJECT-TYPE
                    		SYNTAX  INTEGER(1..255)
                    		MAX-ACCESS  read-only
                    		STATUS  current
                    		DESCRIPTION
                    			"Pakcets received once sampling period "
                    		::= { sysSlaFlStaHistoryEntry  2 }


slaFlStaInputPkts	OBJECT-TYPE
                    		SYNTAX  INTEGER
                    		MAX-ACCESS  read-only
                    		STATUS  current
                    		DESCRIPTION
                    			"Pakcets received once sampling period "
                    		::= { sysSlaFlStaHistoryEntry  3 }


slaFlStaInputFlow	OBJECT-TYPE
                    		SYNTAX  INTEGER
                    		MAX-ACCESS  read-only
                    		STATUS  current
                    		DESCRIPTION
                    			"maximal flow value received"
                    		::= { sysSlaFlStaHistoryEntry  4 }


slaFlStaOutputPkts	OBJECT-TYPE
                    		SYNTAX  INTEGER
                    		MAX-ACCESS  read-only
                    		STATUS  current
                    		DESCRIPTION
                    			"Pakcets send once sampling period "
                    		::= { sysSlaFlStaHistoryEntry  5 }


slaFlStaOutputFlow	OBJECT-TYPE
                    		SYNTAX  INTEGER
                    		MAX-ACCESS  read-only
                    		STATUS  current
                    		DESCRIPTION
                    			"maximal flow send "
                    		::= { sysSlaFlStaHistoryEntry  6 }

slaFlStaTime			OBJECT-TYPE
                    		SYNTAX  DisplayString(SIZE(0..40))
                    		MAX-ACCESS  read-only
                    		STATUS  current
                    		DESCRIPTION
                    			"maximal flow send "
                    		::= { sysSlaFlStaHistoryEntry  7 }




slaFlStaHisTableRowStatus	OBJECT-TYPE
                    		SYNTAX  RowStatus
                    		MAX-ACCESS  read-write
                    		STATUS  current
                    		DESCRIPTION
                    			"flow statistics row status"
                    		::= { sysSlaFlStaHistoryEntry  8 }

------------------------------------------------------------------------------
sysSlaIcmpPathJitMgt   	OBJECT IDENTIFIER ::= { sysSLA 9 }

sysSlaIcmpPathJitTable 	OBJECT-TYPE
                    		SYNTAX  SEQUENCE OF   SysSlaIcmpPathJitEntry 
                    		MAX-ACCESS  not-accessible
                    		STATUS  current
                    		DESCRIPTION
                    			"RTR ICMP PATH JITTER entity table"
                    		::= { sysSlaIcmpPathJitMgt   100 }

sysSlaIcmpPathJitEntry 	OBJECT-TYPE
                    		SYNTAX  SysSlaIcmpPathJitEntry 
                    		MAX-ACCESS  not-accessible
                    		STATUS  current
                    		DESCRIPTION
                    			"RTR ICMP entity entry"
                    		INDEX  { slaIcmpPJTableEntityId }
                    		::= { sysSlaIcmpPathJitTable  1 }

SysSlaIcmpPathJitEntry 	::= SEQUENCE {
                    			slaIcmpPJTableEntityId		  	INTEGER,
                    			slaIcmpPJTargetIp		IpAddress,
                    			slaIcmpPJPktNum			Unsigned32,
                    			slaIcmpPJPktLen			INTEGER,
                    			slaIcmpPJTimeout		INTEGER,
                    			slaIcmpPJPktInterval		Unsigned32,
					slaIcmpPJSchInterval		Unsigned32,
                    			slaIcmpPJVrfName		DisplayString,
                    			slaIcmpPJSourceIp		IpAddress,
                    			slaIcmpPJTos		        INTEGER,
                    			slaIcmpPJVerifyData		TruthValue,
					slaIcmpPJAlarmType		INTEGER,
					slaIcmpPJTargetOnly		TruthValue,
					slaIcmpPJHistorySize		INTEGER,
					slaIcmpPJPeriods		INTEGER,
					slaIcmpPJLsrPath		IpAddress,
					slaIcmpPJIsScheduling		TruthValue,
                    			slaIcmpPJTableRowStatus		RowStatus
                    	             }


slaIcmpPJTableEntityId			OBJECT-TYPE
                    		SYNTAX  INTEGER(1..2000)
                    		MAX-ACCESS  read-write
                    		STATUS  current
                    		DESCRIPTION
                    			"ICMP PATH JITTER entity ID,index"
                    		::= { sysSlaIcmpPathJitEntry 1 }

slaIcmpPJTargetIp		OBJECT-TYPE
                    		SYNTAX  IpAddress
                    		MAX-ACCESS  read-write
                    		STATUS  current
                    		DESCRIPTION
                    			"ICMP PATH JITTER(ping) destination address"
                    		::= { sysSlaIcmpPathJitEntry 2 }

slaIcmpPJPktNum		OBJECT-TYPE
                    		SYNTAX  Unsigned32(1..200000000)
                    		MAX-ACCESS  read-write
                    		STATUS  current
                    		DESCRIPTION
                    			"ICMP PATH JITTER PING send packets number,default 10.
                    			pkt-num * pkt-interval must be less than timeout"
                    		::= { sysSlaIcmpPathJitEntry 3 }

slaIcmpPJPktLen		OBJECT-TYPE
                    		SYNTAX  INTEGER(36..18024)
                    		MAX-ACCESS  read-write
                    		STATUS  current
                    		DESCRIPTION
                    			"ICMP PATH JITTER PING send packets size,default 32."
                    		::= { sysSlaIcmpPathJitEntry 4 }

slaIcmpPJTimeout	OBJECT-TYPE
                    		SYNTAX  INTEGER(1..604800000)
                    		MAX-ACCESS  read-write
                    		STATUS  current
                    		DESCRIPTION
                    			"ICMP ping reply timeout in miliseconds,default 5000.
                    			schedule interval must be larger than timeout"
                    		::= { sysSlaIcmpPathJitEntry 5 }

slaIcmpPJPktInterval	OBJECT-TYPE
                    			SYNTAX  Unsigned32(20..6000)
                    			MAX-ACCESS  read-write
                    			STATUS  current
                    			DESCRIPTION
                    				"IcmpEcho packet interval in milliseconds,default 20.
                    				pkt-num * pkt-interval must be less than timeout"
                    			::= { sysSlaIcmpPathJitEntry 6 }

slaIcmpPJSchInterval	OBJECT-TYPE
                    			SYNTAX  Unsigned32(1..604800)
                    			MAX-ACCESS  read-write
                    			STATUS  current
                    			DESCRIPTION
                    				"IcmpEcho interval in seconds,default 60.
                    				schedule interval must be larger than timeout"
                    			::= { sysSlaIcmpPathJitEntry 7 }  
             		

slaIcmpPJVrfName	OBJECT-TYPE
                    		SYNTAX  DisplayString(SIZE(0..40))
                    		MAX-ACCESS  read-write
                    		STATUS  current
                    		DESCRIPTION
                    			"vrfname string,default global."
                    		::= { sysSlaIcmpPathJitEntry 8 }

slaIcmpPJSourceIp	OBJECT-TYPE
                    		SYNTAX  IpAddress
                    		MAX-ACCESS  read-write
                    		STATUS  current
                    		DESCRIPTION
                    			"ICMP PATH JITTER source IP address"
                    		::= { sysSlaIcmpPathJitEntry 9 }

slaIcmpPJTos		OBJECT-TYPE
                    		SYNTAX  INTEGER(0..255)
                    		MAX-ACCESS  read-write
                    		STATUS  current
                    		DESCRIPTION
                    			"ICMP PATH JITTER TOS value,default 0."
                    		::= { sysSlaIcmpPathJitEntry 10 }


slaIcmpPJVerifyData		OBJECT-TYPE
                    		SYNTAX  TruthValue
                    		MAX-ACCESS  read-write
                    		STATUS  current
                    		DESCRIPTION
                    			"ICMP PATH JITTER verifay data flag
					true(1)-verifa data;
					false(2)-don't verify data,default."
                    		::= { sysSlaIcmpPathJitEntry 11 }

slaIcmpPJAlarmType		OBJECT-TYPE
                    		SYNTAX  INTEGER {
                    			        log(1),
                    			        trap(2),
						logAndTrap(3),
						noLogAndtrap(4) 
                    			        }
                    		MAX-ACCESS  read-write
                    		STATUS  current
                    		DESCRIPTION
                    			"RTR entity alarm type。
                    			 log－log message
                    			 trap－snmp trap
					 logAndTrap-log message and snmp trap
					 noLogAndtrap-no log message and no snmp trap,default."
                    		::= { sysSlaIcmpPathJitEntry 12 }

slaIcmpPJTargetOnly		OBJECT-TYPE
                    		SYNTAX  TruthValue
                    		MAX-ACCESS  read-write
                    		STATUS  current
                    		DESCRIPTION
                    			"ICMP PATH JITTER target only or not.
                    			TRUE-target only,default;
                    			FALSE-hop by hop."
                    		::= { sysSlaIcmpPathJitEntry 13 }


slaIcmpPJHistorySize		OBJECT-TYPE
                    		SYNTAX  INTEGER(1..255)
                    		MAX-ACCESS  read-write
                    		STATUS  current
                    		DESCRIPTION
                    			"Max size of ICMP PATH JITTER entity's history,default 1."
                    		::= { sysSlaIcmpPathJitEntry 14 }


slaIcmpPJPeriods		OBJECT-TYPE
                    		SYNTAX  INTEGER(1..500)
                    		MAX-ACCESS  read-write
                    		STATUS  current
                    		DESCRIPTION
                    			"periods,default 1."
                    		::= { sysSlaIcmpPathJitEntry 15 }

slaIcmpPJLsrPath		OBJECT-TYPE
                    		SYNTAX  IpAddress
                    		MAX-ACCESS  read-write
                    		STATUS  current
                    		DESCRIPTION
                    			"Lsr-path of ICMP PATH JITTER entity,default 0.0.0.0"
                    		::= { sysSlaIcmpPathJitEntry 16 }

slaIcmpPJIsScheduling		OBJECT-TYPE
                    		SYNTAX  TruthValue
                    		MAX-ACCESS  read-only
                    		STATUS  current
                    		DESCRIPTION
                    			"Status of schedule of ICMP PATH JITTER entity
					TRUE(1)-in scheduling,
					FALSE(2)-not in scheduling"
                    		::= { sysSlaIcmpPathJitEntry 17 }

slaIcmpPJTableRowStatus		OBJECT-TYPE
                    		SYNTAX  RowStatus
                    		MAX-ACCESS  read-write
                    		STATUS  current
                    		DESCRIPTION
                    			"ICMP PATH JITTER row status"
                    		::= { sysSlaIcmpPathJitEntry 18 }
------------------------------------------------------------------------------
sysSlaIcmpPathJitHistoryTable 	OBJECT-TYPE
                    		SYNTAX  SEQUENCE OF   SysSlaIcmpPathJitHistoryEntry 
                    		MAX-ACCESS  not-accessible
                    		STATUS  current
                    		DESCRIPTION
                    			"RTR ICMP PATH JITTER entity history table"
                    		::= { sysSlaIcmpPathJitMgt 200 }

sysSlaIcmpPathJitHistoryEntry 	OBJECT-TYPE
                    		SYNTAX  SysSlaIcmpPathJitHistoryEntry 
                    		MAX-ACCESS  not-accessible
                    		STATUS  current
                    		DESCRIPTION
                    			"RTR ICMP entity entry"
                    		INDEX  { slaIcmpPJHisTableEntityId ,  slaIcmpPJHopIndex , slaIcmpPJHistoryIndex ,slaIcmpPJGetStatus }
                    		::= { sysSlaIcmpPathJitHistoryTable 1 }

SysSlaIcmpPathJitHistoryEntry 	::= SEQUENCE {
					slaIcmpPJHisTableEntityId			INTEGER,
					slaIcmpPJHopIndex		INTEGER,
                    			slaIcmpPJHistoryIndex		INTEGER,
                    			slaIcmpPJRtt		   	INTEGER,
					slaIcmpPJJitter			INTEGER,
					slaIcmpPJPktLoss	   	INTEGER,
					slaIcmpPJTime			DisplayString,
					slaIcmpPJGetStatus		INTEGER,
					slaIcmpPJHisTableRowStatus	   	RowStatus
                    	             }
slaIcmpPJHisTableEntityId		OBJECT-TYPE
                    		SYNTAX  INTEGER(1..2000)
                    		MAX-ACCESS  read-write
                    		STATUS  current
                    		DESCRIPTION
                    			"ICMP PATH JITTER entity hop index"
                    		::= { sysSlaIcmpPathJitHistoryEntry 1 }


slaIcmpPJHopIndex	OBJECT-TYPE
                    		SYNTAX  INTEGER(1..30)
                    		MAX-ACCESS  read-write
                    		STATUS  current
                    		DESCRIPTION
                    			"ICMP PATH JITTER entity hop index"
                    		::= { sysSlaIcmpPathJitHistoryEntry 2 }

slaIcmpPJHistoryIndex		OBJECT-TYPE
                    		SYNTAX  INTEGER(1..255)
                    		MAX-ACCESS  read-write
                    		STATUS  current
                    		DESCRIPTION
                    			"ICMP PATH JITTER entity history index,now we only record the last message"
                    		::= { sysSlaIcmpPathJitHistoryEntry 3 }

slaIcmpPJRtt			OBJECT-TYPE
				SYNTAX  INTEGER(0..5000)
				MAX-ACCESS  read-only
				STATUS  current
				DESCRIPTION
					"ICMP entity rtt"
				::= { sysSlaIcmpPathJitHistoryEntry 4 }

slaIcmpPJJitter		OBJECT-TYPE
				SYNTAX  INTEGER(0..6000)
				MAX-ACCESS  read-only
				STATUS  current
				DESCRIPTION
					"ICMP entity jitter"
				::= { sysSlaIcmpPathJitHistoryEntry 5 }

slaIcmpPJPktLoss	OBJECT-TYPE
				SYNTAX  INTEGER
				MAX-ACCESS  read-only
				STATUS  current
				DESCRIPTION
					"ICMP entity packet loss"
				::= { sysSlaIcmpPathJitHistoryEntry 6 }

slaIcmpPJTime		OBJECT-TYPE
				SYNTAX  DisplayString(SIZE(0..40))
				MAX-ACCESS  read-only
				STATUS  current
				DESCRIPTION
					"recorded time"
				::= { sysSlaIcmpPathJitHistoryEntry 7 }

slaIcmpPJGetStatus		OBJECT-TYPE
				SYNTAX  INTEGER(1..2)
				MAX-ACCESS  read-only
				STATUS  current
				DESCRIPTION
					"1:has get all hop history;
					 0:has not get all hop history"
				::= { sysSlaIcmpPathJitHistoryEntry 8 }


slaIcmpPJHisTableRowStatus		OBJECT-TYPE
                    		SYNTAX  RowStatus
                    		MAX-ACCESS  read-write
                    		STATUS  current
                    		DESCRIPTION
                    			"ICMP row status"
                    		::= { sysSlaIcmpPathJitHistoryEntry 9 }

------------------------------------------------------------------------------
sysSlaIcmpPathEchoMgt   	OBJECT IDENTIFIER ::= { sysSLA 10 }

sysSlaIcmpPathEchoTable 	OBJECT-TYPE
                    		SYNTAX  SEQUENCE OF   SysSlaIcmpPathEchoEntry 
                    		MAX-ACCESS  not-accessible
                    		STATUS  current
                    		DESCRIPTION
                    			"RTR ICMP PATH JITTER entity table"
                    		::= { sysSlaIcmpPathEchoMgt   100 }

sysSlaIcmpPathEchoEntry 	OBJECT-TYPE
                    		SYNTAX  SysSlaIcmpPathEchoEntry 
                    		MAX-ACCESS  not-accessible
                    		STATUS  current
                    		DESCRIPTION
                    			"RTR ICMP entity entry"
                    		INDEX  { slaIcmpPETableEntityId }
                    		::= { sysSlaIcmpPathEchoTable 1 }

SysSlaIcmpPathEchoEntry 	::= SEQUENCE {
                    			slaIcmpPETableEntityId		INTEGER,
                    			slaIcmpPETargetIp	IpAddress,
                    			slaIcmpPEPktLen		INTEGER,
                    			slaIcmpPETimeout		INTEGER,
					slaIcmpPESchInterval		Unsigned32,
                    			slaIcmpPEVrfName		DisplayString,
                    			slaIcmpPESourceIp		IpAddress,
                    			slaIcmpPETos		        INTEGER,
                    			slaIcmpPEVerifyData		TruthValue,
					slaIcmpPELsrPath		IpAddress,
					slaIcmpPEHistorySize		INTEGER,
					slaIcmpPEPeriods		INTEGER,
					slaIcmpPEAlarmType		INTEGER,
					slaIcmpPETargetOnly		TruthValue,
					slaIcmpPEIsScheduling		TruthValue,
                    			slaIcmpPETableRowStatus		RowStatus
                    	             }


slaIcmpPETableEntityId			OBJECT-TYPE
                    		SYNTAX  INTEGER(1..2000)
                    		MAX-ACCESS  read-write
                    		STATUS  current
                    		DESCRIPTION
                    			"ICMP PATH ECHO entity ID,index"
                    		::= { sysSlaIcmpPathEchoEntry 1 }

slaIcmpPETargetIp		OBJECT-TYPE
                    		SYNTAX  IpAddress
                    		MAX-ACCESS  read-write
                    		STATUS  current
                    		DESCRIPTION
                    			"ICMP PATH ECHO(ping) destination address"
                    		::= { sysSlaIcmpPathEchoEntry 2 }

slaIcmpPEPktLen			OBJECT-TYPE
                    		SYNTAX  INTEGER(36..18024)
                    		MAX-ACCESS  read-write
                    		STATUS  current
                    		DESCRIPTION
                    			"ICMP PATH ECHO PING send packets size,default 32."
                    		::= { sysSlaIcmpPathEchoEntry 3 }

slaIcmpPETimeout		OBJECT-TYPE
                    		SYNTAX  INTEGER(0..604800000)
                    		MAX-ACCESS  read-write
                    		STATUS  current
                    		DESCRIPTION
                    			"ICMP ping reply timeout in miliseconds,default 5000.
                    			schedule interval must be larger than timeout"
                    		::= { sysSlaIcmpPathEchoEntry 4 }

slaIcmpPESchInterval		OBJECT-TYPE
                    			SYNTAX  Unsigned32(1..2147483647)
                    			MAX-ACCESS  read-write
                    			STATUS  current
                    			DESCRIPTION
                    				"IcmpPathEcho interval in seconds,default 60.
                    				schedule interval must be larger than timeout"
                    			::= { sysSlaIcmpPathEchoEntry 5 }  
             		

slaIcmpPEVrfName		OBJECT-TYPE
                    		SYNTAX  DisplayString(SIZE(0..40))
                    		MAX-ACCESS  read-write
                    		STATUS  current
                    		DESCRIPTION
                    			"vrfname string,default global."
                    		::= { sysSlaIcmpPathEchoEntry 6 }

slaIcmpPESourceIp		OBJECT-TYPE
                    		SYNTAX  IpAddress
                    		MAX-ACCESS  read-write
                    		STATUS  current
                    		DESCRIPTION
                    			"ICMP PATH ECHO source IP address"
                    		::= { sysSlaIcmpPathEchoEntry 7 }

slaIcmpPETos			OBJECT-TYPE
                    		SYNTAX  INTEGER(0..255)
                    		MAX-ACCESS  read-write
                    		STATUS  current
                    		DESCRIPTION
                    			"ICMP PATH ECHO TOS value,default 0."
                    		::= { sysSlaIcmpPathEchoEntry 8 }


slaIcmpPEVerifyData		OBJECT-TYPE
                    		SYNTAX  TruthValue
                    		MAX-ACCESS  read-write
                    		STATUS  current
                    		DESCRIPTION
                    			"ICMP PATH JITTER verifay data flag
					true(1)-verify data;
					false(2)-don't verify data,default."
                    		::= { sysSlaIcmpPathEchoEntry 9 }

					
slaIcmpPELsrPath		OBJECT-TYPE
                    		SYNTAX  IpAddress
                    		MAX-ACCESS  read-write
                    		STATUS  current
                    		DESCRIPTION
                    			"ICMP PATH JITTER lsr-path,default 0.0.0.0"
                    		::= { sysSlaIcmpPathEchoEntry 10 }


slaIcmpPEHistorySize		OBJECT-TYPE
                    		SYNTAX  INTEGER(1..255)
                    		MAX-ACCESS  read-write
                    		STATUS  current
                    		DESCRIPTION
                    			"Max size of ICMP PATH ECHO entity 's history,default 1."
                    		::= { sysSlaIcmpPathEchoEntry 11 }  

slaIcmpPEPeriods		OBJECT-TYPE
                    		SYNTAX  INTEGER(1..500)
                    		MAX-ACCESS  read-write
                    		STATUS  current
                    		DESCRIPTION
                    			"periods,default 1."
                    		::= { sysSlaIcmpPathEchoEntry 12 }  

slaIcmpPEAlarmType		OBJECT-TYPE
                    		SYNTAX  INTEGER {
                    			        log(1),
                    			        trap(2),
						logAndTrap(3),
						noLogAndtrap(4) 
                    			        }
                    		MAX-ACCESS  read-write
                    		STATUS  current
                    		DESCRIPTION
                    			"RTR entity alarm type。
                    			 log－log message
                    			 trap－snmp trap
					 logAndTrap-log message and snmp trap
					 noLogAndtrap-no log message and no snmp trap,default 1."
				::= { sysSlaIcmpPathEchoEntry 13 }  

slaIcmpPETargetOnly		OBJECT-TYPE
                    		SYNTAX TruthValue
                    		MAX-ACCESS  read-write
                    		STATUS  current
                    		DESCRIPTION
                    		"TRUE(1)-targetOnly
				 FALSE(2)-not targetOnly,default."
                    		::= { sysSlaIcmpPathEchoEntry 14 }  

slaIcmpPEIsScheduling		OBJECT-TYPE
                    		SYNTAX TruthValue
                    		MAX-ACCESS  read-only
                    		STATUS  current
                    		DESCRIPTION
                    		"The scheduling status of ICMP PATH ECHO entity
				TRUE(1)-in scheduling
				 FALSE(2)-not in scheduling"
                    		::= { sysSlaIcmpPathEchoEntry 15 }  


slaIcmpPETableRowStatus		OBJECT-TYPE
                    		SYNTAX  RowStatus
                    		MAX-ACCESS  read-write
                    		STATUS  current
                    		DESCRIPTION
                    			"ICMP PATH JITTER row status"
                    		::= { sysSlaIcmpPathEchoEntry 16 }


------------------------------------------------------------------------------
sysSlaIcmpPathEchoHistoryTable 	OBJECT-TYPE
                    		SYNTAX  SEQUENCE OF   SysSlaIcmpPathEchoHistoryEntry 
                    		MAX-ACCESS  not-accessible
                    		STATUS  current
                    		DESCRIPTION
                    			"RTR ICMP PATH ECHO entity history table"
                    		::= { sysSlaIcmpPathEchoMgt 200 }

sysSlaIcmpPathEchoHistoryEntry 	OBJECT-TYPE
                    		SYNTAX  SysSlaIcmpPathEchoHistoryEntry 
                    		MAX-ACCESS  not-accessible
                    		STATUS  current
                    		DESCRIPTION
                    			"RTR ICMP entity entry"
                    		INDEX  { slaIcmpPEHisTableEntityId	, slaIcmpPEHopIndex , slaIcmpPEHistoryIndex ,slaIcmpPEGetStatus }
                    		::= { sysSlaIcmpPathEchoHistoryTable 1 }

SysSlaIcmpPathEchoHistoryEntry 	::= SEQUENCE {
					slaIcmpPEHisTableEntityId			INTEGER,
					slaIcmpPEHopIndex		INTEGER,
                    			slaIcmpPEHistoryIndex		INTEGER,
                    			slaIcmpPERtt		   	INTEGER,
                    			slaIcmpPEPktLoss		INTEGER,
					slaIcmpPETime			DisplayString,
					slaIcmpPEGetStatus		INTEGER,
					slaIcmpPEHisTableRowStatus              RowStatus
                    	             }
slaIcmpPEHisTableEntityId			OBJECT-TYPE
                    		SYNTAX  INTEGER(1..2000)
                    		MAX-ACCESS  read-write
                    		STATUS  current
                    		DESCRIPTION
                    			"ICMP PATH ECHO entity id,index"
                    		::= { sysSlaIcmpPathEchoHistoryEntry 1 }

slaIcmpPEHopIndex		OBJECT-TYPE
                    		SYNTAX  INTEGER(1..30)
                    		MAX-ACCESS  read-only
                    		STATUS  current
                    		DESCRIPTION
                    			"ICMP PATH ECHO hop index"
                    		::= { sysSlaIcmpPathEchoHistoryEntry 2 }

slaIcmpPEHistoryIndex		OBJECT-TYPE
                    		SYNTAX  INTEGER
                    		MAX-ACCESS  read-only
                    		STATUS  current
                    		DESCRIPTION
                    			"ICMP PATH ECHO entity history index"
                    		::= { sysSlaIcmpPathEchoHistoryEntry 3 }

slaIcmpPERtt			OBJECT-TYPE
				SYNTAX  INTEGER(0..5000)
				MAX-ACCESS  read-only
				STATUS  current
				DESCRIPTION
					"ICMP PATH ECHO entity rtt"
				::= { sysSlaIcmpPathEchoHistoryEntry 4 }

slaIcmpPEPktLoss		OBJECT-TYPE
				SYNTAX  INTEGER(0..1)
				MAX-ACCESS  read-only
				STATUS  current
				DESCRIPTION
					"ICMP PATH ECHO entity packet loss"
				::= { sysSlaIcmpPathEchoHistoryEntry 5 }

slaIcmpPETime			OBJECT-TYPE
				SYNTAX  DisplayString(SIZE(0..29))
				MAX-ACCESS  read-only
				STATUS  current
				DESCRIPTION
					"recorded time"
				::= { sysSlaIcmpPathEchoHistoryEntry 6 }


slaIcmpPEGetStatus		OBJECT-TYPE
				SYNTAX  INTEGER(1..2)
				MAX-ACCESS  read-only
				STATUS  current
				DESCRIPTION
					"1:has get all hop history;
					 0:has not get all hop history"
				::= { sysSlaIcmpPathEchoHistoryEntry 7 }

slaIcmpPEHisTableRowStatus              OBJECT-TYPE
                    		SYNTAX  RowStatus
                    		MAX-ACCESS  read-write
                    		STATUS  current
                    		DESCRIPTION
                    			"ICMP PATH ECHO row status"
                    		::= { sysSlaIcmpPathEchoHistoryEntry 8 }


------------------------------------------------------------------------------
sysSlaThresholdMgt   	OBJECT IDENTIFIER ::= { sysSLA 11 }
	
sysSlaThresholdTable 		OBJECT-TYPE
                    		SYNTAX  SEQUENCE OF   SysSlaThresholdEntry 
                    		MAX-ACCESS  not-accessible
                    		STATUS  current
                    		DESCRIPTION
                    			"RTR alarm table"
                    		::= { sysSlaThresholdMgt   100 }

sysSlaThresholdEntry 		OBJECT-TYPE
                    		SYNTAX  SysSlaThresholdEntry 
                    		MAX-ACCESS  not-accessible
                    		STATUS  current
                    		DESCRIPTION
                    			"RTR threshold entry"
                    		INDEX  { slaThresholdTableEntityId, slaThresholdString,slaThresholdIndex }
                    		::= { sysSlaThresholdTable 1 }

SysSlaThresholdEntry 		::= SEQUENCE {
                    			slaThresholdTableEntityId		 	INTEGER,
                    			slaThresholdString	    	DisplayString,
                    			slaThresholdValue		INTEGER,
					slaThresholdDirection		INTEGER,
					slaThresholdIndex		INTEGER,
                    			slaThresholdRowStatus	  	RowStatus
                    	             }


slaThresholdTableEntityId			OBJECT-TYPE
                    		SYNTAX  INTEGER(1..2000)
                    		MAX-ACCESS  read-write
                    		STATUS  current
                    		DESCRIPTION
                    			"SLA entity ID,index"
                    		::= { sysSlaThresholdEntry 1 }

slaThresholdString		OBJECT-TYPE
                    		SYNTAX  DisplayString(SIZE(0..29))
                    		MAX-ACCESS  read-write
                    		STATUS  current
                    		DESCRIPTION
                    			"icmpEcho-rtt(threshold of icmp echo's rtt,0-9000ms(default:9000ms)),
					icmpEcho-pktLoss(threshold of icmp echo's pkt loss,0-200000000(default:200000000)),
					udpEcho-rtt(threshold of udp echo's rtt,0-9000ms(default:9000ms)),
					udpEcho-pktLoss(threshold of udp echo's packet loss,0-1(default:1))
					jitter-rtt(threshold of jitter's rtt,0-9000ms(default:9000ms)),
					jitter-jitterSd(threshold of jitter entity's jitter from source to dest,0-6000ms(default:6000ms)),
					jitter-jitterDs(threshold of jitter entity's jitter from dest to source,0-6000ms(default:6000ms)),
					jitter-delaySd(threshold of jitter entity's delay from source to dest,0-5000ms(default:5000ms)),
					jitter-delayDs(threshold of jitter entity's delay from dest to source,0-5000ms(default:5000ms)),
					jitter-pktLossSd(threshold of jitter entity's pkt loss from source to dest,0-200000000(default:200000000)),
					jitter-PktLossDs(threshold of jitter entity's pkt loss from dest to source,0-200000000(default:200000000)),
					jitter-mos(threshold of jitter entity's mos,0-10000000(default:10000000)),
					jitter-icpif(threshold of jitter entity's icpif,0-100000000(default:100000000)),
					icmpPathJitter-rtt(threshold of icmp path jitter entity's rtt,0-9000ms(default:9000ms)),
					icmpPathJitter-pktLoss(threshold of icmp path jitter entity's pkt loss,0-200000000(default:200000000)),
					icmpPathJitter-jitter(threshold of icmp path jitter entity's jitter,0-6000ms(default:6000ms)),
					icmpPathEcho-rtt(threshold of icmp path echo entity's rtt,0-9000ms(default:9000ms)), 
					icmpPathEcho-pktloss(threshold of icmp path echo entity's [kt loss,0-1(default:1)), 
					flSta-inPkt(threshold of flow statistics entity's input packet,0-200000000(default:200000000)),
					flSta-inFlow(threshold of flow statistics entity's input flow,0-200000000(default:200000000)),
					flSta-outPkt(threshold of flow statistics entity's output packet,0-200000000(default:200000000)),
					flSta-outFlow(threshold of flow statistics entity's output flow,0-200000000(default:200000000)),
					macping-delay(threshold of mac sla unidrectional delay, 0-5000ms(default:500ms)),
					macping-rtDelay(threshold of mac sla ring back delay, 0-5000ms(default:500ms)),
					macping-jitter(threshold of mac sla jitter, 0-5000ms(default:500ms)),
					macping-lostPC(threshold of mac sla lost percent, 0-50(default:50%))"
                    		::= { sysSlaThresholdEntry 2 }

slaThresholdValue		OBJECT-TYPE
                    		SYNTAX  INTEGER
                    		MAX-ACCESS  read-write
                    		STATUS  current
                    		DESCRIPTION
                    			"The value of each threshold"
                    		::= { sysSlaThresholdEntry 3 }

slaThresholdDirection		OBJECT-TYPE
                    		SYNTAX  INTEGER(1..2)
                    		MAX-ACCESS  read-write
                    		STATUS  current
                    		DESCRIPTION
                    			"1(>= -Alarm when result is bigger than or equal to threshold(default)),
					 2(<= -Alarm when result is smaller than or equal to threshold)"
                    		::= { sysSlaThresholdEntry 4 }


slaThresholdIndex		OBJECT-TYPE
                    		SYNTAX  INTEGER
                    		MAX-ACCESS  read-write
                    		STATUS  current
                    		DESCRIPTION
                    			"Only used by equipment."
                    		::= { sysSlaThresholdEntry 5 }



slaThresholdRowStatus		OBJECT-TYPE
                    		SYNTAX  RowStatus
                    		MAX-ACCESS  read-write
                    		STATUS  current
                    		DESCRIPTION
                    			"Rtr entity row status"
                    		::= { sysSlaThresholdEntry 6 }

--MAC SLA MIB定义
sysSlaMacPingMgt     	OBJECT IDENTIFIER ::= { sysSLA 12 }
--MAC SLA TRAP
mpMacPingTraps	OBJECT IDENTIFIER ::= { sysSlaMacPingMgt 1 }


--------------------------------
--	MAC SLA 实体信息表
--------------------------------                    		
sysSlaMacPingTable   	OBJECT-TYPE
		SYNTAX  SEQUENCE OF   SysSlaMacPingEntry   
		MAX-ACCESS  not-accessible
		STATUS  current
		DESCRIPTION
			"MAC SLA实体信息表"
		::= { sysSlaMacPingMgt     100 }

sysSlaMacPingEntry   	OBJECT-TYPE
		SYNTAX  SysSlaMacPingEntry   
		MAX-ACCESS  not-accessible
		STATUS  current
		DESCRIPTION
			"MAC SLA实体信息表表项"
		INDEX  { slaMacPingEntityId }
		::= { sysSlaMacPingTable   1 }

SysSlaMacPingEntry   	::= SEQUENCE {
		slaMacPingEntityId      INTEGER,
		slaMacPingState         INTEGER,
		slaMacPingName 			DisplayString,
		slaMacPingCfmMdId		DisplayString,
		slaMacPingCfmMaId		DisplayString,
		slaMacPingCfmSrcMepId   Unsigned32,
		slaMacPingDesMepId    	Unsigned32,	
		slaMacPingCyclsec	    Unsigned32,
		slaMacPingPktNumPerCycl Unsigned32,
		slaMacPingAvgCyclNum    Unsigned32,	
		slaMacPingLastCycleTime	DisplayString,
		slaMacPingAvgValueTimes	Unsigned32,
		slaMacPingRowStatus     RowStatus,
		slaMacPingSchedInterval	Unsigned32,
		slaMacPingHistoryMaxCount	INTEGER,
		slaMacPingDesMac	PhysAddress,
		slaMacPingRemDevName	DisplayString
   }

slaMacPingEntityId   	OBJECT-TYPE
		SYNTAX  INTEGER(1..2000)
		MAX-ACCESS  read-only
		STATUS  current
		DESCRIPTION
			"MAC SLA 实体ID"
		::= { sysSlaMacPingEntry   1 }
		
slaMacPingState          OBJECT-TYPE
	SYNTAX	INTEGER	{
		stop(1),
		run(2),
		pause(3)
	}
	MAX-ACCESS  read-only
		STATUS  current
		DESCRIPTION
		"MAC SLA 实体当前运行状态：1－stop，2－run，3－pause"
	::= { sysSlaMacPingEntry   2 }
							
slaMacPingName   	OBJECT-TYPE
		SYNTAX  DisplayString(SIZE(0..49))
		MAX-ACCESS  read-write
		STATUS  current
		DESCRIPTION
			"MAC SLA实体名称"
		::= { sysSlaMacPingEntry   3 }
		
slaMacPingCfmMdId   	OBJECT-TYPE
		SYNTAX  DisplayString(SIZE(0..43))
		MAX-ACCESS  read-write
		STATUS  current
		DESCRIPTION
			"MAC SLA实体所绑定的CFM管理域名称"
		::= { sysSlaMacPingEntry   4 }
		
slaMacPingCfmMaId   	OBJECT-TYPE
		SYNTAX  DisplayString(SIZE(0..45))
		MAX-ACCESS  read-write
		STATUS  current
		DESCRIPTION
			"MAC SLA实体所绑定的CFM管理实例名称"
		::= { sysSlaMacPingEntry   5 }
		

slaMacPingCfmSrcMepId   	OBJECT-TYPE
		SYNTAX  Unsigned32(1..8191)
		MAX-ACCESS  read-write
		STATUS  current
		DESCRIPTION
			"该MAC SLA实体测试的源MEP ID"
		::= { sysSlaMacPingEntry   6}
		
slaMacPingDesMepId   	OBJECT-TYPE
		SYNTAX  Unsigned32(1..8191)
		MAX-ACCESS  read-write
		STATUS  current
		DESCRIPTION
			"该MAC SLA实体测试的目的MEP ID"
		::= { sysSlaMacPingEntry   7}
slaMacPingCyclsec   	OBJECT-TYPE
		SYNTAX  Unsigned32
		MAX-ACCESS  read-write
		STATUS  current
		DESCRIPTION
			"一次MAC SLA的测试周期,默认600(s),其值必须小于slaMacPingSchedInterval(测试周期间隔时间)"
		::= { sysSlaMacPingEntry   8}
		
slaMacPingPktNumPerCycl   	OBJECT-TYPE
		SYNTAX  Unsigned32(1..10)
		MAX-ACCESS  read-write
		STATUS  current
		DESCRIPTION
			"一次测试周期内测试报文个数(默认10个)"
		::= { sysSlaMacPingEntry   9}
		
slaMacPingAvgCyclNum   	OBJECT-TYPE
		SYNTAX  Unsigned32(1..5)
		MAX-ACCESS  read-write
		STATUS  current
		DESCRIPTION
			"平均值统计周期个数(默认5次)"
		::= { sysSlaMacPingEntry   10}            
                    		      
slaMacPingLastCycleTime   	OBJECT-TYPE
		SYNTAX  DisplayString(SIZE(0..40))
		MAX-ACCESS  read-only
		STATUS  current
		DESCRIPTION
			"该MAC SLA实体最后一轮测试时间"
		::= { sysSlaMacPingEntry   11}      
		
slaMacPingAvgValueTimes   	OBJECT-TYPE
		SYNTAX  Unsigned32
		MAX-ACCESS  read-only
		STATUS  current
		DESCRIPTION
			"平均值计算统计次数"
		::= { sysSlaMacPingEntry   12}                   		

slaMacPingRowStatus	  	OBJECT-TYPE
		SYNTAX  RowStatus
		MAX-ACCESS  read-create
		STATUS  current
		DESCRIPTION
			"MAC SLA实体信息表行状态"
		::= { sysSlaMacPingEntry   13 }

slaMacPingSchedInterval   	OBJECT-TYPE
		SYNTAX  Unsigned32(2..4294967295)
		MAX-ACCESS  read-write
		STATUS  current
		DESCRIPTION
			"MAC SLA实体调度周期间隔,默认605(s), 其值必须大于测试周期时间slaMacPingCycleTime."
		::= { sysSlaMacPingEntry   14}                   		

slaMacPingHistoryMaxCount  	OBJECT-TYPE
		SYNTAX  INTEGER(1..255)
		MAX-ACCESS  read-write
		STATUS  current
		DESCRIPTION
			"MAC SLA实体平均值历史记录最大条数，默认为了，最大255"
		::= { sysSlaMacPingEntry   15}                   		

slaMacPingDesMac	OBJECT-TYPE
		    		SYNTAX  PhysAddress
		    		MAX-ACCESS  read-write
		    		STATUS  current
		    		DESCRIPTION
		    			"SLA destination mac address ,目的Mac地址"
		    		::= { sysSlaMacPingEntry   16}
		            		
slaMacPingRemDevName	OBJECT-TYPE
                    		SYNTAX  DisplayString (SIZE (0..31))
                    		MAX-ACCESS  read-only
                    		STATUS  current
                    		DESCRIPTION
                    			"SLA destination device name ,远端设备的名称"
                    		::= { sysSlaMacPingEntry   17}
                    		
------------------------------------------------------------------------------
mpSlaTrap       	NOTIFICATION-TYPE
                                OBJECTS {
                    		         slaThresholdTableEntityId ,
                    		         slaThresholdString ,
                    		         slaThresholdValue ,
                    		         slaThresholdDirection		         
                    		        }
                    		STATUS  current
                    		DESCRIPTION
                    			"This notification is generated when network trafic is not so good."
                    		::= { mpSla 1 }

sysSlaNmsMgt	 OBJECT IDENTIFIER ::= { sysSLA 13 }
sysSlaNmsTable	 OBJECT-TYPE
			SYNTAX SEQUENCE OF	 SysSlaNmsEntry
			MAX-ACCESS not-accessible
			STATUS current
			DESCRIPTION
			 "Rtr entity table,config or view information about Rtr entity"
			::= { sysSlaNmsMgt 100 }

sysSlaNmsEntry	 OBJECT-TYPE
			SYNTAX SysSlaNmsEntry
		 	MAX-ACCESS not-accessible
			STATUS current
			DESCRIPTION
				"Rtr entity,config or view information about Rtr entity"
			INDEX { rtrEntityId }
			::= { sysSlaNmsTable 1 }

SysSlaNmsEntry	 ::= SEQUENCE {
			slaNmsEntityId	INTEGER,
			slaNmsScheduleId	INTEGER,
			slaNmsId	Unsigned32,
			slaNmsRowStatus	RowStatus
						}

slaNmsEntityId	OBJECT-TYPE
			SYNTAX INTEGER(1..2000)
			MAX-ACCESS read-write
			STATUS current
			DESCRIPTION
					"Rtr entity Id,index"
			::= { sysSlaNmsEntry 1 }
			
slaNmsScheduleId	 OBJECT-TYPE
			SYNTAX INTEGER(1..2000)
			MAX-ACCESS read-write
			STATUS current
			DESCRIPTION
				"Rtr schedule id."
			::= { sysSlaNmsEntry 2 }

slaNmsId		 OBJECT-TYPE
			SYNTAX Unsigned32
			MAX-ACCESS read-write
			STATUS current
			DESCRIPTION
				"Rtr NMS schedule Id,specified by NMS(mp5)"
			::= { sysSlaNmsEntry 3 }

slaNmsRowStatus	 OBJECT-TYPE
			SYNTAX RowStatus
			MAX-ACCESS read-write
			STATUS current
			DESCRIPTION
				"rtr entity row status"
			::= { sysSlaNmsEntry 4 }
------------------------------------------------------------------------------

END
