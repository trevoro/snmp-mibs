ACC-CALLINGNUMBER DEFINITIONS ::= BEGIN

    IMPORTS
	       OBJECT-TYPE FROM RFC1155-SMI
			 accTrapLogSeqNum FROM ACC-SYSTEM
	accBRG, DisplayString, RowStatus, IfIndex, SmdsAddress
             FROM ACC-MIB;

-- Calling Number Group
    accCallingNumber OBJECT IDENTIFIER ::= { accBRG 67 }
	-- The Calling Number Table Group
	-- A table of calling party number patterns and bearer types
	-- that will be used to screen incoming calls.
	accCallingNumberTable OBJECT-TYPE
	    SYNTAX SEQUENCE OF AccCallingNumberEntry
	    ACCESS not-accessible
	    STATUS mandatory
	    DESCRIPTION
	       "The Calling Number Table"
	    ::= { accCallingNumber 1 }
	accCallingNumberEntry OBJECT-TYPE
	    SYNTAX AccCallingNumberEntry
	    ACCESS not-accessible
	    STATUS mandatory
	    DESCRIPTION
	       "An entry in the Calling Number Table"
	    INDEX  { accCallingNumberGroup }
	    ::= { accCallingNumberTable 1 }
	AccCallingNumberEntry ::= SEQUENCE {
	    accCallingNumberGroup		INTEGER,
	    accCallingNumberType		INTEGER,
	    accCallingNumberDigits		DisplayString,
	    accCallingNumberAction		INTEGER,
	    accCallingNumberStatus		INTEGER,
	    accCallingNumberCallbackNumber	DisplayString,
	    accCallingNumberCallbackDelay	INTEGER,
	    accCallingNumberDialoutUserName	DisplayString,
	    accCallingNumberDialoutPassword	DisplayString,
	    accCallingNumberDialoutAuthMode	DisplayString,
	    accCallingNumberEgressInfc          INTEGER,
	    accCallingNumberEgressType          INTEGER,
	    accCallingNumberEgressNumber        OCTET STRING
	}
	accCallingNumberGroup OBJECT-TYPE
	    SYNTAX INTEGER (1..127)
	    ACCESS read-only
	    STATUS mandatory
	    DESCRIPTION
	       "The index of a number group defined in the Calling 
	        Number Table.  A number group is a set calling party 
	        numbers and bearer types associated with incoming calls."
	    ::= { accCallingNumberEntry 1 }
	accCallingNumberType OBJECT-TYPE
	    SYNTAX INTEGER {
		cm56(1),
		cm64(2),
		udi(3),
		rdi(4),
		data(7),
		voice(8),
		audio(16),
		modem(24),
		any(31)
	    }
	    ACCESS read-only
	    STATUS mandatory
	    DESCRIPTION
	       "The bearer type for an incoming call.  Used for matching 
	        an entry in the Calling Number Table with the bearer 
	        capabilites of a switched connection.  This object is treated 
	        as a bit mask."
	    ::= { accCallingNumberEntry 2 }
	accCallingNumberDigits OBJECT-TYPE
	    SYNTAX DisplayString -- (SIZE (1..16))
	    ACCESS read-only
	    STATUS mandatory
	    DESCRIPTION
	       "The string of digits comprising the directory number 
	        assigned to the calling party.  This string may contain the 
	        pattern matching characters 'x' or 'X' (don't care digits) and 
	        '*' (wild card string)."
	    ::= { accCallingNumberEntry 3 }
	accCallingNumberAction OBJECT-TYPE
	    SYNTAX INTEGER {
		accept(1),
		reject(2)
	    }
	    ACCESS read-write
	    STATUS mandatory
	    DESCRIPTION
	       "The action to take if a match occurs."
	    ::= { accCallingNumberEntry 4 }
	accCallingNumberStatus OBJECT-TYPE
	    SYNTAX INTEGER {
		add(1),
		delete(2)
	    }
	    ACCESS read-write
	    STATUS mandatory
	    DESCRIPTION
	       "The status of this entry"
	    ::= { accCallingNumberEntry 5 }
	accCallingNumberCallbackNumber OBJECT-TYPE
	    SYNTAX DisplayString
	    ACCESS read-write
	    STATUS mandatory
	    DESCRIPTION
	       "Callback Number for CLI Screening"
	    ::= { accCallingNumberEntry 6 }
	accCallingNumberCallbackDelay OBJECT-TYPE
	    SYNTAX INTEGER (0..255)
	    ACCESS read-write
	    STATUS mandatory
	    DESCRIPTION
	       "Callback delay for CLI Screening Callback"
	    ::= { accCallingNumberEntry 7 }
	accCallingNumberDialoutUserName OBJECT-TYPE
	    SYNTAX DisplayString
	    ACCESS read-write
	    STATUS mandatory
	    DESCRIPTION
	       "Dialout username used during CLI Callback call"
	    ::= { accCallingNumberEntry 8 }
	accCallingNumberDialoutPassword OBJECT-TYPE
	    SYNTAX DisplayString
	    ACCESS read-write
	    STATUS mandatory
	    DESCRIPTION
	       "Dialout password used during CLI Callback call"
	    ::= { accCallingNumberEntry 9 }
	accCallingNumberDialoutAuthMode OBJECT-TYPE
	    SYNTAX DisplayString
	    ACCESS read-write
	    STATUS mandatory
	    DESCRIPTION
	       "Dialout authentication method used during CLI Callback call"
	    ::= { accCallingNumberEntry 10 }
	accCallingNumberEgressInfc OBJECT-TYPE
	    SYNTAX INTEGER
	    ACCESS read-write
	    STATUS mandatory
	    DESCRIPTION
	    " Egress interface for switched calls "
	    ::= { accCallingNumberEntry 11 }
	accCallingNumberEgressType OBJECT-TYPE
	    SYNTAX INTEGER {
		cm64 (1),
		cm56 (2),
		udi (3),
		rdi (4),
		v-110 (5),
		data (7),
		voice (8),
		audio (16),
		modem (24),
		any (31)
	    }
	    ACCESS read-write
	    STATUS mandatory
	    DESCRIPTION
	    " Call type for egress call of a switched call "
	    ::= { accCallingNumberEntry 12 }
	accCallingNumberEgressNumber OBJECT-TYPE
	    SYNTAX OCTET STRING
	    ACCESS read-write
	    STATUS mandatory
	    DESCRIPTION
	    " Called number to use for egress call of switched call "
	    ::= { accCallingNumberEntry 13 }
	-- The Calling Number Screening Group
	-- The actual calling number screening table maintained in RAM.
	-- Entries in this table contain a calling party number pattern
	-- and bearer type used to screen incoming calls.  The entries
	-- in this table are maintained in the order in which they are
	-- applied to incoming calls, and may be sourced from information
	-- manually configued in NVM or from dial port entries maintained
	-- by DOD.
	accCallingNumberScreeningTable OBJECT-TYPE
	    SYNTAX SEQUENCE OF AccCallingNumberScreeningEntry
	    ACCESS not-accessible
	    STATUS mandatory
	    DESCRIPTION
	       "The Calling Number Screening Table"
	    ::= { accCallingNumber 2 }
	accCallingNumberScreeningEntry OBJECT-TYPE
	    SYNTAX AccCallingNumberScreeningEntry
	    ACCESS not-accessible
	    STATUS mandatory
	    DESCRIPTION
	       "An entry in the Calling Number ScreeningTable"
	    INDEX  { accCallingNumberScreeningGroup }
	    ::= { accCallingNumberScreeningTable 1 }
	AccCallingNumberScreeningEntry ::= SEQUENCE {
	    accCallingNumberScreeningGroup        INTEGER,
	    accCallingNumberScreeningIndex        INTEGER,
	    accCallingNumberScreeningType         INTEGER,
	    accCallingNumberScreeningDigits       DisplayString,
	    accCallingNumberScreeningAction       INTEGER,
	    accCallingNumberScreeningSource       INTEGER,
	    accCallingNumberScreeningEgressInfc   INTEGER,
	    accCallingNumberScreeningEgressType   INTEGER,
	    accCallingNumberScreeningEgressNumber OCTET STRING
	}
	accCallingNumberScreeningGroup OBJECT-TYPE
	    SYNTAX INTEGER (1..127)
	    ACCESS read-only
	    STATUS mandatory
	    DESCRIPTION
	       "The index of a number group defined in the Calling 
	        Number Table.  A number group is a set calling party 
	        numbers and bearer types associated with incoming calls."
	    ::= { accCallingNumberScreeningEntry 1 }
	accCallingNumberScreeningIndex OBJECT-TYPE
	    SYNTAX INTEGER (1..'7fffffff'h)
	    ACCESS read-only
	    STATUS mandatory
	    DESCRIPTION
	       "The numerical index of this calling number entry.  This is 
	        also the sequence number by which calling number filters 
	        are applied during incoming call screening."
	    ::= { accCallingNumberScreeningEntry 2 }
	accCallingNumberScreeningType OBJECT-TYPE
	    SYNTAX INTEGER {
		cm56(1),
		cm64(2),
		udi(3),
		rdi(4),
		data(7),
		voice(8),
		audio(16),
		modem(24),
		any(31)
	    }
	    ACCESS read-only
	    STATUS mandatory
	    DESCRIPTION
	       "The bearer type for an incoming call.  Used for matching 
	        an entry in the Calling Number Table with the bearer 
	        capabilites of a switched connection.  This object is treated 
	        as a bit mask."
	    ::= { accCallingNumberScreeningEntry 3 }
	accCallingNumberScreeningDigits OBJECT-TYPE
	    SYNTAX DisplayString -- (SIZE (1..16))
	    ACCESS read-only
	    STATUS mandatory
	    DESCRIPTION
	       "The string of digits comprising the directory number 
	        assigned to the calling party.  This string may contain the 
	        pattern matching characters 'x' or 'X' (don't care digits) and 
	        '*' (wild card string)."
	    ::= { accCallingNumberScreeningEntry 4 }
	accCallingNumberScreeningAction OBJECT-TYPE
	    SYNTAX INTEGER {
		accept(1),
		reject(2)
	    }
	    ACCESS read-only
	    STATUS mandatory
	    DESCRIPTION
	       "The action to take if a match occurs."
	    ::= { accCallingNumberScreeningEntry 5 }
	accCallingNumberScreeningSource OBJECT-TYPE
	    SYNTAX INTEGER {
		nvm(1),
		dod(2)
	    }
	    ACCESS read-only
	    STATUS mandatory
	    DESCRIPTION
	       "The source of this entry."
	    ::= { accCallingNumberScreeningEntry 6 }
	accCallingNumberScreeningEgressInfc OBJECT-TYPE
	    SYNTAX INTEGER
	    ACCESS read-write
	    STATUS mandatory
	    DESCRIPTION
	    " Egress interface for switched calls "
	    ::= { accCallingNumberScreeningEntry 7 }
	accCallingNumberScreeningEgressType OBJECT-TYPE
	    SYNTAX INTEGER {
		cm64 (1),
		cm56 (2),
		udi (3),
		rdi (4),
		v-110 (5),
		data (7),
		voice (8),
		audio (16),
		modem (24),
		any (31)
	    }
	    ACCESS read-write
	    STATUS mandatory
	    DESCRIPTION
	    " Call type for egress call of a switched call "
	    ::= { accCallingNumberScreeningEntry 8 }
	accCallingNumberScreeningEgressNumber OBJECT-TYPE
	    SYNTAX OCTET STRING
	    ACCESS read-write
	    STATUS mandatory
	    DESCRIPTION
	    " Called number to use for egress call of switched call "
	    ::= { accCallingNumberScreeningEntry 9 }
	-- The Calling Number Default Action Group
	-- A table of default actions for each number group.
	accCallingNumberDefaultTable OBJECT-TYPE
	    SYNTAX SEQUENCE OF AccCallingNumberDefaultEntry
	    ACCESS not-accessible
	    STATUS mandatory
	    DESCRIPTION
	       "The Calling Number Default Action Table"
	    ::= { accCallingNumber 3 }
	accCallingNumberDefaultEntry OBJECT-TYPE
	    SYNTAX AccCallingNumberDefaultEntry
	    ACCESS not-accessible
	    STATUS mandatory
	    DESCRIPTION
	       "An entry in the Calling Number Default Action Table"
	    INDEX  { accCallingNumberDefaultGroup }
	    ::= { accCallingNumberDefaultTable 1 }
	AccCallingNumberDefaultEntry ::= SEQUENCE {
	    accCallingNumberDefaultGroup  INTEGER,
	    accCallingNumberDefaultAction INTEGER
	}
	accCallingNumberDefaultGroup OBJECT-TYPE
	    SYNTAX INTEGER (1..127)
	    ACCESS read-only
	    STATUS mandatory
	    DESCRIPTION
	       "The index of a number group defined in the Calling 
	        Number Table.  A number group is a set calling party 
	        numbers and bearer types associated with incoming calls."
	    ::= { accCallingNumberDefaultEntry 1 }
	accCallingNumberDefaultAction OBJECT-TYPE
	    SYNTAX INTEGER {
		accept(1),
		reject(2)
	    }
	    ACCESS read-write
	    STATUS mandatory
	    DESCRIPTION
	       "The default action to take if no matching entries are found 
	        in this number group."
	    ::= { accCallingNumberDefaultEntry 2 }

END
