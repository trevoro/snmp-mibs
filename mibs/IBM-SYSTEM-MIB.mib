IBM-SYSTEM-MIB DEFINITIONS ::= BEGIN

-- From file: "ibmSystem.mib"

IMPORTS
   OBJECT-TYPE
      FROM RFC-1212

   enterprises
      FROM RFC1155-SMI;


-- MODULE-IDENTITY
--  LastUpdated
--    200506010000Z
--  OrgName
--    IBM eServer
--  ContactInfo
--    IBM http://www.ibm.com/support
--  Descr
--    The MIB module for managing IBM eServer Systems
--  RevDate
--    200506010000Z
--  RevDescr
--    Initial Version of ibmSystem MIB.


ibm                             OBJECT IDENTIFIER ::= { enterprises 2 }
ibmProd                         OBJECT IDENTIFIER ::= { ibm 6 }
ibmServer                       OBJECT IDENTIFIER ::= { ibmProd 159 }
ibmSystem                       OBJECT IDENTIFIER ::= { ibmServer 1 }
ibmStorage                      OBJECT IDENTIFIER ::= { ibmServer 3 }

--
-- ibmSystem components
--
ibmSystemMIB                    OBJECT IDENTIFIER ::= { ibmSystem 1 }

ibmSystemTrap                   OBJECT IDENTIFIER ::= { ibmSystemMIB 0 }

ibmSystemAgent                  OBJECT IDENTIFIER ::= { ibmSystemMIB 10 }
ibmSystemEventSubsystem         OBJECT IDENTIFIER ::= { ibmSystemMIB 20 }
ibmSystemHealth                 OBJECT IDENTIFIER ::= { ibmSystemMIB 30 }
ibmSystemVitalProductData       OBJECT IDENTIFIER ::= { ibmSystemMIB 40 }
ibmSystemSMART                  OBJECT IDENTIFIER ::= { ibmSystemMIB 50 }
ibmSystemAssetID                OBJECT IDENTIFIER ::= { ibmSystemMIB 60 }
ibmSystemAlertOnLAN             OBJECT IDENTIFIER ::= { ibmSystemMIB 70 }
ibmSystemLMSensor               OBJECT IDENTIFIER ::= { ibmSystemMIB 80 }
ibmSystemITDirector             OBJECT IDENTIFIER ::= { ibmSystemMIB 90 }
ibmSystemSmbios                 OBJECT IDENTIFIER ::= { ibmSystemMIB 100 }
ibmSystemNetwork                OBJECT IDENTIFIER ::= { ibmSystemMIB 110 }
ibmSystemMemory                 OBJECT IDENTIFIER ::= { ibmSystemMIB 120 }
ibmSystemPower                  OBJECT IDENTIFIER ::= { ibmSystemMIB 130 }
ibmSystemProcessor              OBJECT IDENTIFIER ::= { ibmSystemMIB 140 }
ibmSystemSmartDisk              OBJECT IDENTIFIER ::= { ibmSystemMIB 150 }
ibmSystemRaid                   OBJECT IDENTIFIER ::= { ibmSystemMIB 200 }

--
-- win32 components
--
win32                            OBJECT IDENTIFIER ::= { ibmSystemMIB 2 }

win32Event                       OBJECT IDENTIFIER ::= { win32 0 }

win32WMI                         OBJECT IDENTIFIER ::= { win32 10 }
win32SMBIOS                      OBJECT IDENTIFIER ::= { win32 20 }

--
-- Primitive types
--
Boolean  ::= INTEGER (0..1)
Uint8    ::= INTEGER (0..255)
Sint8    ::= INTEGER (-128..127)
Uint16   ::= INTEGER (0..65535)
Sint16   ::= INTEGER (-32767..32766)
Uint32   ::= INTEGER (0..4294967295)
Sint32   ::= INTEGER (-2147483647..2147483646)
Uint64   ::= OCTET STRING
Sint64   ::= OCTET STRING
Real32   ::= INTEGER (-1..1)
Real64   ::= INTEGER (-1..1)
String   ::= OCTET STRING
Datetime ::= OCTET STRING

ibmSystemAgentVersion OBJECT-TYPE
        SYNTAX String
        ACCESS read-only
        STATUS mandatory
        DESCRIPTION "IBM Director Agent Version"
        ::= { ibmServer 0 }

ibmSystemAgentUpObjs OBJECT IDENTIFIER ::= { ibmSystemAgent 0 }

ibmSystemMgmtHwIPEndPointUp OBJECT-TYPE
        SYNTAX String
        ACCESS read-only
        STATUS mandatory
        DESCRIPTION "Returns Agent Version if RSA IP information available."
        ::= { ibmSystemAgentUpObjs 3 }

ibmSystemHealthUp OBJECT IDENTIFIER ::= { ibmSystemHealth 0 }

ibmSystemStorageUp OBJECT IDENTIFIER ::= { ibmSystemHealthUp 1 }

ibmSystemPhysicalDiskUp OBJECT-TYPE
        SYNTAX String
        ACCESS read-only
        STATUS mandatory
        DESCRIPTION "Returns Agent Version if Physical Disk Health is available."
        ::= { ibmSystemStorageUp 1 }

ibmSystemLogicalDiskUp OBJECT-TYPE
        SYNTAX String
        ACCESS read-only
        STATUS mandatory
        DESCRIPTION "Returns Agent Version if Logical Disk Health is available."
        ::= { ibmSystemStorageUp 2 }

ibmSystemLMSensorUp OBJECT IDENTIFIER ::= { ibmSystemLMSensor 0 }

ibmSystemVoltageUp OBJECT-TYPE
        SYNTAX String
        ACCESS read-only
        STATUS mandatory
        DESCRIPTION "Returns Agent Version if Voltage Sensor Health is available."
        ::= { ibmSystemLMSensorUp 1 }

ibmSystemTemperatureUp OBJECT-TYPE
        SYNTAX String
        ACCESS read-only
        STATUS mandatory
        DESCRIPTION "Returns Agent Version if Temperature Sensor Health is available."
        ::= { ibmSystemLMSensorUp 2 }

ibmSystemTachometerUp OBJECT-TYPE
        SYNTAX String
        ACCESS read-only
        STATUS mandatory
        DESCRIPTION "Returns Agent Version if Tachometer Health is available."
        ::= { ibmSystemLMSensorUp 3 }

ibmSystemNetworkUp OBJECT-TYPE
        SYNTAX String
        ACCESS read-only
        STATUS mandatory
        DESCRIPTION "Returns Agent Version if Network Interface Health is available."
        ::= { ibmSystemNetwork 0 }

ibmSystemMemoryUp OBJECT-TYPE
        SYNTAX String
        ACCESS read-only
        STATUS mandatory
        DESCRIPTION "Returns Agent Version if Memory PFA Health is available."
        ::= { ibmSystemMemory 0 }

ibmSystemPowerUp OBJECT-TYPE
        SYNTAX String
        ACCESS read-only
        STATUS mandatory
        DESCRIPTION "Returns Agent Version if Power Supply Health is available."
        ::= { ibmSystemPower 0 }

ibmSystemProcessorUp OBJECT-TYPE
        SYNTAX String
        ACCESS read-only
        STATUS mandatory
        DESCRIPTION "Returns Agent Version if Proccesor PFA Health is available."
        ::= { ibmSystemProcessor 0 }

END
