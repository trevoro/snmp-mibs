-- LLC-2 Frame Relay Convergence MIB

CXLlcFrConv-MIB DEFINITIONS ::= BEGIN

--#CURRENT-VERSION 3

IMPORTS
	Counter         FROM RFC1155-SMI
	OBJECT-TYPE     FROM RFC-1212
	cxLlcFrConv,Alias
				FROM CXProduct-SMI;

    -- All representations of MAC addresses in this MIB Module
    -- use, as a textual convention (i.e. this convention does
    -- not affect their encoding), the data type:

-- Proprietary Data Types
    MacAddress ::= OCTET STRING (SIZE (6))    
    SubRef     ::= INTEGER (0..255)


llcfrcnvSysRouteConnectInterval OBJECT-TYPE
	SYNTAX  INTEGER (10..900)
	ACCESS  read-write
	STATUS  mandatory
	DESCRIPTION
"Determines the number of seconds between route connection attempts by the 
LLC-2 Frame Relay Convergence layer.

Range of Values: 10 - 900 seconds

Default Value: 30 seconds

Configuration Changed: administrative"
	DEFVAL {30 }
	::= { cxLlcFrConv 1 }


llcfrcnvMibLevel OBJECT-TYPE
	SYNTAX	INTEGER
	ACCESS	read-only
	STATUS	mandatory
	DESCRIPTION
"Used to determine current MIB module release supported
by the agent. Object is in decimal."
	DEFVAL { 0 }
	--#STARTING-VERSION 1
	::= { cxLlcFrConv 2 }

-- gap (8) for future global parameters



--  Service Access Point Configuration Table

--     The table defining all the parameters, status, control and statistics 
--     required to manipulate a LLC-2 Frame Relay Convergence Service Access 
--     Point (SAP).


llcfrcnvSapTable OBJECT-TYPE
	SYNTAX  SEQUENCE OF LlcfrcnvSapEntry
	ACCESS  not-accessible
	STATUS  mandatory
	DESCRIPTION
"This table contains configuration information for each LLC-2 Frame Relay 
Convergence layer SAP (service access point)."
	::= { cxLlcFrConv 10 }


	llcfrcnvSapEntry OBJECT-TYPE
		SYNTAX  LlcfrcnvSapEntry
		ACCESS  not-accessible
		STATUS  mandatory
		DESCRIPTION
"Defines a row in the llcfrcnvSapTable. Each row contains the objects 
which define a service access point."
		INDEX { llcfrcnvSapNumber }
		::= { llcfrcnvSapTable 1 }


	LlcfrcnvSapEntry ::=
		SEQUENCE {
-- Parameters
			llcfrcnvSapNumber                        INTEGER,
			llcfrcnvSapRowStatus                     INTEGER,
			llcfrcnvSapAlias                         Alias,
			llcfrcnvSapSrcLlcSap                     INTEGER,
			llcfrcnvSapDstLlcSap                     INTEGER,
         llcfrcnvSapHostMacAddr                   MacAddress,
         llcfrcnvSapCntrMacAddr                   MacAddress,
			llcfrcnvSapRouteIndex                    INTEGER,
-- Control
			llcfrcnvSapControl                       INTEGER,
-- Status
			llcfrcnvSapState                         INTEGER,
-- Statistics
			llcfrcnvSapTxFrames                      Counter,
			llcfrcnvSapRxFrames                      Counter,
			llcfrcnvSapTxOctets                      Counter,
			llcfrcnvSapRxOctets                      Counter,
			llcfrcnvSapUnopenedServiceDiscards       Counter,
			llcfrcnvSapTxResets                      Counter,
			llcfrcnvSapRxResets                      Counter
			}


	llcfrcnvSapNumber OBJECT-TYPE
		SYNTAX  INTEGER (0..255)
		ACCESS  read-only
		STATUS  mandatory
		DESCRIPTION
"Identifies this SAP (service access point) with a numerical value which 
must be unique for each LLC-2 Frame Relay Convergence SAP. Value 0 is 
allocated to the Public SAP (PSAP) used to interface with the FRIM module 
via IAM. The row associated with value 0 always exists and cannot be 
deleted. All other SAPs are used to communicate with other higher layer 
protocols."
		::= { llcfrcnvSapEntry 1 }


	llcfrcnvSapRowStatus OBJECT-TYPE
		SYNTAX  INTEGER {
					invalid         (1),
					valid           (2)
					}
		ACCESS  read-write
		STATUS  mandatory
		DESCRIPTION
"Determines the status of the objects in a table row. 

Options:
invalid (1): Row is flagged, after next reset the values will be disabled 
and the row is deleted from the table

valid (2): Values are enabled

Configuration Changed: administrative"
	       ::= { llcfrcnvSapEntry 2 }


	llcfrcnvSapAlias OBJECT-TYPE
		SYNTAX  Alias
		ACCESS  read-write
		STATUS  mandatory
		DESCRIPTION
"Identifies this service access point by a textual name. Names must be 
unique across all service access points at all layers.

Range of Values: 1 -16 alphanumeric characters (first character must be a 
letter)

Default Value: none

Configuration Changed: administrative"
		::= { llcfrcnvSapEntry 3 }


	llcfrcnvSapSrcLlcSap OBJECT-TYPE
		SYNTAX  INTEGER (2..254)
		ACCESS  read-write
		STATUS  mandatory
		DESCRIPTION
"Determines the source LLC-2 SAP address associated with this connection. 
Only even values are allowed (usually assigned as a multiple of 04 
hexadecimal). This SAP address should not be confused with the internal 
SAP numbers used by the LLC-2 layer. 

Range of Values: 2 - 254 (even values only)

Default Value: 4

Configuration Changed: administrative and operative"
		DEFVAL{ 4 }
		::= { llcfrcnvSapEntry 4 }


	llcfrcnvSapDstLlcSap OBJECT-TYPE
		SYNTAX  INTEGER (2..254)
		ACCESS  read-write
		STATUS  mandatory
		DESCRIPTION
"Determines the destination LLC-2 SAP address associated with this 
connection. Only even values are allowed (usually assigned as a multiple 
of 04 hexadecimal). This SAP address should not be confused with the 
internal SAP numbers used by the LLC-2 layer. 

Range of Values: 2 - 254 (even values only)

Default Value: 4

Configuration Changed: administrative 
and operative"
		DEFVAL{ 4 }
		::= { llcfrcnvSapEntry 5 }


	llcfrcnvSapRouteIndex OBJECT-TYPE
		SYNTAX  INTEGER (0..64)
		ACCESS  read-write
		STATUS  mandatory
		DESCRIPTION
"Determines the route associated with this SAP (service access point). The 
value of this object is the llcfrcnvSRIndex which identifies the route in 
the llcfrcnvSysRouteTable. Multiple SAP entries may use the same system 
route provided that they have a different 
llcfrcnvSapSrcLlcSap-llcfrcnvSapDstLlcSap pair.

Range of Values: 0 - 64

Note:
A value of 0 indicates no route is selected.

Default Value: none

Related Objects:

llcfrcnvSRIndex

llcfrcnvSapSrcLlcSap

llcfrcnvSapDstLlcSap

Configuration Changed: administrative and operative"
		::= { llcfrcnvSapEntry 6 }


	llcfrcnvSapControl OBJECT-TYPE
		SYNTAX  INTEGER {
					clearStats              (1)
				}
		ACCESS  write-only
		STATUS  mandatory
		DESCRIPTION
"Clears all objects that contain statistics for this service access point.

Options:
clearStats (1)

Configuration Changed: administrative and operative"
		::= { llcfrcnvSapEntry 7 }


	llcfrcnvSapState OBJECT-TYPE
		SYNTAX  INTEGER {
					offLine         (1),
					unbound         (2),
					bound           (3),
					connected       (4)
				}
		ACCESS  read-only
		STATUS  mandatory
		DESCRIPTION
"Indicates the status of the SAP (service access point).

Options:
offLine (1): Indicates that the SAP is not configured.

unbound (2): Indicates that this SAP is not bound to its companion SAP.

bound (3): Indicates that this SAP is bound to its companion SAP.

connected (4):.Indicates that this SAP is bound and is available for data 
transfer."
		::= { llcfrcnvSapEntry 8 }


	llcfrcnvSapTxFrames OBJECT-TYPE
		SYNTAX  Counter
		ACCESS  read-only
		STATUS  mandatory
		DESCRIPTION
"Indicates the number of frames transmitted by this service access point."
		::= { llcfrcnvSapEntry 9 }


	llcfrcnvSapRxFrames OBJECT-TYPE
		SYNTAX  Counter
		ACCESS  read-only
		STATUS  mandatory
		DESCRIPTION
"Indicates the number of frames received by this service access point."
		::= { llcfrcnvSapEntry 10 }


	llcfrcnvSapTxOctets OBJECT-TYPE
		SYNTAX  Counter
		ACCESS  read-only
		STATUS  mandatory
		DESCRIPTION
"Indicates the number of octets transmitted by this service access point."
		::= { llcfrcnvSapEntry 11 }


	llcfrcnvSapRxOctets OBJECT-TYPE
		SYNTAX  Counter
		ACCESS  read-only
		STATUS  mandatory
		DESCRIPTION
"Indicates the number of octets received by this service access point."
		::= { llcfrcnvSapEntry 12 }


	llcfrcnvSapUnopenedServiceDiscards OBJECT-TYPE
		SYNTAX  Counter
		ACCESS  read-only
		STATUS  mandatory
		DESCRIPTION
"Indicates the number of frames received and discarded by this service 
access point because there was no associated connection."
		::= { llcfrcnvSapEntry 13 }


	llcfrcnvSapTxResets OBJECT-TYPE
		SYNTAX  Counter
		ACCESS  read-only
		STATUS  mandatory
		DESCRIPTION
"Indicates the number of connection reset requests issued from this 
service access point."
		::= { llcfrcnvSapEntry 14 }


	llcfrcnvSapRxResets OBJECT-TYPE
		SYNTAX  Counter
		ACCESS  read-only
		STATUS  mandatory
		DESCRIPTION
"Indicates the number of connection reset requests/indications received by 
this service access point."
		::= { llcfrcnvSapEntry 15 }

   llcfrcnvSapHostMacAddr OBJECT-TYPE
      SYNTAX  MacAddress
      ACCESS  read-write
      STATUS  mandatory
      DESCRIPTION
"This object specifies the MAC address of the host station to which 
the FR LLC-2  connection will be established  - Used only for SNA BAN Transport.
If this object is configured, then it is automatically assumed that BAN will be
the SNA transport used. Otherwise, the SNA transport is BNN."
	--#STARTING-VERSION 2
      ::= { llcfrcnvSapEntry 16 }

   llcfrcnvSapCntrMacAddr OBJECT-TYPE
      SYNTAX  MacAddress
      ACCESS  read-write
      STATUS  mandatory
      DESCRIPTION
"This object specifies the MAC address of the work station which 
will be connected to the host - Used only for SNA BAN Transport.
If this object is configured, then it is automatically assumed that BAN will be
the SNA transport used. Otherwise, the SNA transport is BNN."
	--#STARTING-VERSION 2
      ::= { llcfrcnvSapEntry 17 }

--  LLC-2 Frame Relay Convergence System Route Table
--
--      This table contains the parameters, status, control and statistics 
--      objects which allow the management of LLC-2 Frame Relay Convergence 
--      System Routes.


llcfrcnvSysRouteTable OBJECT-TYPE
	SYNTAX  SEQUENCE OF LlcfrcnvSysRouteEntry
	ACCESS  not-accessible
	STATUS  mandatory
	DESCRIPTION
"This table contains information about each LLC-2 FR Convergence system 
route."
	::= { cxLlcFrConv 11 }


	llcfrcnvSysRouteEntry OBJECT-TYPE
		SYNTAX  LlcfrcnvSysRouteEntry
		ACCESS  not-accessible
		STATUS  mandatory
		DESCRIPTION
"Defines a row in the llcfrcnvSysRouteTable. Each row contains the objects 
which define an LLC-2 FR Convergence system route."
		INDEX { llcfrcnvSRIndex }
		::= { llcfrcnvSysRouteTable 1 }


	LlcfrcnvSysRouteEntry ::=
		SEQUENCE {
-- Parameters
			llcfrcnvSRIndex                          INTEGER,
			llcfrcnvSRRowStatus                      INTEGER,
			llcfrcnvSRDestAlias                      Alias,
-- Control
			llcfrcnvSRControl                        INTEGER,
-- New Parameter
			llcfrcnvSRPriority                       INTEGER,
         llcfrcnvSRSubRef                         SubRef,
-- Status
			llcfrcnvSRRouteStatus                    INTEGER,
			llcfrcnvSRClearStatus                    INTEGER,
-- Statistics
			llcfrcnvSROutSuccessfullConnects         Counter,
			llcfrcnvSROutUnsuccessfullConnects       Counter
			}


	llcfrcnvSRIndex OBJECT-TYPE
		SYNTAX  INTEGER(1..64)
		ACCESS  read-only
		STATUS  mandatory
		DESCRIPTION
"A number that uniquely identifies each LLC-2 Frame Relay Convergence 
Route.

Related Objects:

llcfrcnvSapRouteIndex

Range of Values: 0 - 64"
		::= { llcfrcnvSysRouteEntry 1 }


	llcfrcnvSRRowStatus OBJECT-TYPE
		SYNTAX  INTEGER {
					invalid         (1),
					valid           (2)
				}
		ACCESS  read-write
		STATUS  mandatory
		DESCRIPTION
"Determines the status of the objects in a table row.

Options:
invalid (1): Row is flagged, after next reset the values will be disabled 
and the row is deleted from the table

valid (2): Values are enabled

Default Value: none

Configuration Changed: administrative"
		::= { llcfrcnvSysRouteEntry 2 }


	llcfrcnvSRDestAlias OBJECT-TYPE
		SYNTAX  Alias
		ACCESS  read-write
		STATUS  mandatory
		DESCRIPTION
"Identifies the textual name of the destination service this route 
connects to. The destination alias is the name of the Frame Relay layer 
outlet circuit (frpCircuitAlias). 

Range of Values: 1 -16 alphanumeric characters (first character must be a 
letter)

Default Value: none

Configuration Changed: administrative and operative"
		::= { llcfrcnvSysRouteEntry 3 }


	llcfrcnvSRControl OBJECT-TYPE
		SYNTAX  INTEGER {
					clearStats              (1)
				}
		ACCESS  write-only
		STATUS  mandatory
		DESCRIPTION
"Permits control of a specific SAP (service access point).

Options:
clearStats (1): Clear all statistics stored by statistics objects.

Configuration Changed: administrative and operative"
	::= { llcfrcnvSysRouteEntry 4 }

     llcfrcnvSRPriority  OBJECT-TYPE
		SYNTAX  INTEGER {
			discard(1),
			forward(2),
			priority-low(3),
			priority-high(4)
				}
		ACCESS  read-write
		STATUS  mandatory
		DESCRIPTION 
"Determines the filtering/forwarding action and the forwarding priority 
for data sent from the STP bridge.
 
Options:
discard (1): Do not forward the data.

forward (2): Forward the data.

priority-low (3): Forward with a low priority (Frame Relay only).

priority-high (4): Forward with a high priority (Frame Relay only).
 
Default Value:  forward (2)

Configuration Changed:  Administrative"
		DEFVAL { forward }
		--#STARTING-VERSION 1
		::= { llcfrcnvSysRouteEntry 5 }

   llcfrcnvSRSubRef OBJECT-TYPE
      SYNTAX  SubRef
      ACCESS  read-write
      STATUS  mandatory
      DESCRIPTION
"Specifies a reference number that uniquely identifies this route. This 
number is used by the FRIM (Frame Relay Interface Module) to identify 
routes using the same DLCI (enables PVC consolidation). This number must 
be unique for all routes sharing the same DLCI.

Range of Values: 1 - 255 (when using PVC consolidation)

0 (when not using PVC consolidation)

Default Value: 0

Configuration Changed: administrative and operative"
		--#STARTING-VERSION 3
      ::= { llcfrcnvSysRouteEntry 6 }

-- gap (4) for future configuration parameters  


	llcfrcnvSRRouteStatus OBJECT-TYPE
		SYNTAX  INTEGER {
					offLine         (1),
					notConnected    (2),
					inProgress      (3),
					connected       (4)
				}
		ACCESS  read-only
		STATUS  mandatory
		DESCRIPTION
"Indicates the status of this route.

Options:
offLine (1): Indicates that the route is not configured.

notConnected (2): Indicates that the remote destination may not exist, or 
has refused the connection.

inProgress (3): Indicates that the connection is in the process of being 
established. This is a transient state.

connected (4): Indicates that the connection is established and is ready 
for data transfer."
		::= { llcfrcnvSysRouteEntry 10 }


	llcfrcnvSRClearStatus OBJECT-TYPE
		SYNTAX  INTEGER {
					noFailure                       (1),
					internalError                   (2),
					remoteAllocFailure              (3),
					remoteNoAccess                  (4),
					remotePvcDown                   (5),
					remotePvcBusy                   (6),
					localFcnFailure                 (7),
					remoteFcnFailure                (8),
					remoteAliasNotFound             (9)
				}
		ACCESS  read-only
		STATUS  mandatory
		DESCRIPTION
"Indicates the status of a failed connection. The value of this object is 
only valid only between attempts to establish the route connection 
(llcfrcnvSRRouteStatus =  notConnected), and may or may not change after 
successive failed attempts.

Options:
noFailure (1): Once a system route has been successfully connected, this 
value is maintained for the duration of the connection.

internalError (2): An internal error has occurred.

remoteAllocFailure (3): There is insufficient memory available for FRIM to 
establish this connection.

remoteNoAccess (4): The requested frame relay service does not exist. 

remotePvcDown (5): The requested Frame Relay outlet circuit is down.

remotePvcBusy (6): The requested Frame 
Relay outlet circuit is already 
connected.

localFcnFailure (7): Flow control negotiation failed.

remoteFcnFailure (8): Flow control negotiation failed at the Frame Relay 
layer.

remoteAliasNotFound (9): The destination service alias 
(llcfrcnvSRDestAlias) does not exist."

		::= { llcfrcnvSysRouteEntry 11 }


	llcfrcnvSROutSuccessfullConnects OBJECT-TYPE
		SYNTAX  Counter
		ACCESS  read-only
		STATUS  mandatory
		DESCRIPTION
"Indicates the number of successful connections originated for this route. 
An outgoing connection is always attempted from LLC-2 Frame Relay 
Convergence to FRIM."

		::= { llcfrcnvSysRouteEntry 12 }


	llcfrcnvSROutUnsuccessfullConnects OBJECT-TYPE
		SYNTAX  Counter
		ACCESS  read-only
		STATUS  mandatory
		DESCRIPTION
"Indicates the number of unsuccessful connections originated for this 
route. An outgoing connection is always attempted from LLC-2 Frame Relay 
Convergence to FRIM."
		::= { llcfrcnvSysRouteEntry 13 }


END
