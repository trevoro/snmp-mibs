CXBOPIO-MIB DEFINITIONS ::= BEGIN


IMPORTS
   Counter                         FROM RFC1155-SMI
   OBJECT-TYPE                     FROM RFC-1212
   TRAP-TYPE                       FROM RFC-1215
   cxBOPIO,
   Alias                           FROM CXProduct-SMI;


--#CURRENT-VERSION 2

--  Active Configuration Table

--  The table describing:
--      active (current) parameters used in each BOP/COP ports.
--
--      parameters required to configure traps in each BOP/COP ports.
--
--      status and statistics for each BOP/COP port.


bopSapOprTable OBJECT-TYPE
   SYNTAX  SEQUENCE OF BopSapOprEntry
   ACCESS  not-accessible
   STATUS  mandatory
   DESCRIPTION
"A table containing the current configuration information about each
 BOP/COP port."
   ::= { cxBOPIO 1 }


   bopSapOprEntry OBJECT-TYPE
      SYNTAX  BopSapOprEntry
      ACCESS  not-accessible
      STATUS  mandatory
      DESCRIPTION
"The configuration information for a specific BOP/COP port."
      INDEX { bopSapOprNumber }
      ::= { bopSapOprTable 1 }
   BopSapOprEntry ::=
      SEQUENCE {
         bopSapOprNumber
            INTEGER,
         bopSapOprAlias
            Alias,
         bopSapOprProtocol
            INTEGER,
         bopSapOprPortClockSource
            INTEGER,
         bopSapOprPortSpeed
            INTEGER,
         bopSapOprPortDuplex
            INTEGER,
         bopSapOprPortMaxFrameSize
            INTEGER,
         bopSapOprPortDataEncoding
            INTEGER,
         bopSapOprPortIdleCondition
            INTEGER,
         bopSapOprPortPreAmbleLength
            INTEGER,
         bopSapOprPortFlagSharing
            INTEGER,
         bopSapOprPortFilterMask
            INTEGER,
         bopSapOprPortFilterAddress1
            INTEGER,
         bopSapOprPortFilterAddress2
            INTEGER,
         bopSapOprPortFilterAddress3
            INTEGER,
         bopSapOprPortFilterAddress4
            INTEGER,
         bopSapOprPortCrc
            INTEGER,
         bopSapOprPortDtrUpTimer
            INTEGER,
         bopSapOprPortTxWindow
            INTEGER,            
         bopSapOprPortDialMode
            INTEGER,
         bopSapOprPortLoopback
            INTEGER,
         bopSapOprPortSignalSamplingPeriod
            INTEGER,
         bopSapOprPortDcdDtrSignalSamples
            INTEGER,
         bopSapOprPortCtsRtsSignalSamples
            INTEGER,
         bopSapOprPortDsrDrsSignalSamples
            INTEGER,
         bopSapOprPortTmLlSignalSamples
            INTEGER,
         bopSapOprPortRiRlSignalSamples
            INTEGER,
         bopSapOprPortStatisticsTimer
            INTEGER,
         bopSapOprPortCarrierAction
            INTEGER,
         bopSapOprPortDataGenerator
            INTEGER,
         bopSapOprPortGenFrames
            INTEGER,
         bopSapOprPortGenFrameSize
            INTEGER,
         bopSapOprPortGenFrameHeader
            INTEGER,
         bopSapOprPortThreshBandwidth
            INTEGER,
         bopSapOprPortActualSpeed
            INTEGER,
         bopSapOprCodeSet
            INTEGER,
         bopSapOprParity
            INTEGER,
         bopOprPortTrap
            INTEGER,
         bopOprTxClockTrap
            INTEGER,
         bopOprControlLine
            INTEGER,
         bopOprControlStats
            INTEGER,
         bopStatOprPortType
            INTEGER,
         bopStatOprPortInterfaceType
            INTEGER,
         bopStatOprPortState
            INTEGER,
         bopStatOprTxClockState
            INTEGER,
         bopStatOprDCDState
            INTEGER,
         bopStatOprDTRState
            INTEGER,
         bopStatOprRTSState
            INTEGER,
         bopStatOprCTSState
            INTEGER,
         bopStatOprDSRState
            INTEGER,
         bopStatOprDRSState
            INTEGER,
         bopStatOprTMState
            INTEGER,
         bopStatOprLLState
            INTEGER,
         bopStatOprRIState
            INTEGER,
         bopStatOprRLState
            INTEGER,
         bopStatOprTxFrames
            Counter,
         bopStatOprRxFrames
            Counter,
         bopStatOprLocalLoopbackFrames
            Counter,
         bopStatOprTxBps
            Counter,
         bopStatOprRxBps
            Counter,
         bopStatOprTxBpsMax
            Counter,
         bopStatOprRxBpsMax
            Counter,
         bopStatOprTxFps
            Counter,
         bopStatOprRxFps
            Counter,
         bopStatOprTxFpsMax
            Counter,
         bopStatOprRxFpsMax
            Counter,
         bopStatOprTxUnderrunFrames
            Counter,
         bopStatOprTxCtsLostFrames
            Counter,
         bopStatOprTxBadStateDiscards
            Counter,
         bopStatOprTxResetDiscards
            Counter,
         bopStatOprTxSysCongestionDiscards
            Counter,
         bopStatOprTxInvWinDiscards
            Counter,
         bopStatOprTxInvRLpbkWinDiscards
            Counter,
         bopStatOprRxBadCrcFrames
            Counter,
         bopStatOprRxAbortedFrames
            Counter,
         bopStatOprRxNonIntegralBitFrames
            Counter,
         bopStatOprRxLongFrames
            Counter,
         bopStatOprRxOverrunFrames
            Counter,
         bopStatOprRxCdLostFrames
            Counter,
         bopStatOprRxBadStateDiscards
            Counter,
         bopStatOprRxBusyDiscards
            Counter,
         bopStatOprPortStateChanges
            Counter,
         bopStatOprTxClockStateChanges
            Counter,
         bopStatOprDCDStateChanges
            Counter,
         bopStatOprDTRStateChanges
            Counter,
         bopStatOprRTSStateChanges
            Counter,
         bopStatOprCTSStateChanges
            Counter,
         bopStatOprDSRStateChanges
            Counter,
         bopStatOprDRSStateChanges
            Counter,
         bopStatOprTMStateChanges
            Counter,
         bopStatOprLLStateChanges
            Counter,
         bopStatOprRIStateChanges
            Counter,
         bopStatOprRLStateChanges
            Counter,
         bopStatOprPortResets
            Counter,
         bopStatOprRxGenError
            Counter
         }


   bopSapOprNumber OBJECT-TYPE
      SYNTAX  INTEGER
      ACCESS  read-only
      STATUS  mandatory
      DESCRIPTION
"Defines the SAP ID using 2,3 or 4 digits. The first digit (A) is the slot #,
 the second digit (B) is the port #, and the remaining digits (CD) are the
 channel #.  If a 2 digit number is entered, digits CD are assumed to be 0 and
 are inserted automatically when reading object.  If a 3 digit number is
 entered, digit C is assumed to be 0 and is inserted automatically when
 reading object.

Ranges of Values for  A: 1-7 for CX900, 1-4 for CX1000
Ranges of Values for  B: 1-5 for CX900, 1-4 for CX1000
Ranges of Values for CD: 00-30

Default Value: not applicable"
      ::= { bopSapOprEntry 1 }


   bopSapOprAlias OBJECT-TYPE
      SYNTAX  Alias
      ACCESS  read-only
      STATUS  mandatory
      DESCRIPTION
"Determines the active textual name uniquely identifying this port SAP.

Range of Values: 0 - 16 alphanumeric characters beginning with a 
non-numeric character

Default Value: undefined"
      ::= { bopSapOprEntry 2 }


   bopSapOprProtocol OBJECT-TYPE
      SYNTAX  INTEGER {
               hdlc        (1),
               bsc3270     (2),
               borroughs   (3),
               sperry      (4),
               bsc3780     (5)               
               }
      ACCESS  read-only
      STATUS  mandatory
      DESCRIPTION
"Determines if the port is HDLC or Bisync.
Only HDLC is supported by ISDN and T1/E1 ports.

Indicates in the operative
configuration the type of bisync protocol 
used by the controllers of the
port associated with this SAP. 

Options:
hdlc
bsc3270    = Bisync 3270 controllers
borroughs  = Borroughs controllers
sperry     = Sperry controllers
bsc3780    = Bisync 2780/3780 controllers

Default Value: hdlc"
--#STARTING-VERSION 2
      ::= { bopSapOprEntry 3 }


-- gap (1) for future parameter

   
bopSapOprPortClockSource OBJECT-TYPE
      SYNTAX  INTEGER {
               internal  (1),
               external  (2),
               split     (3),
               slave     (4)
               }
      ACCESS  read-only
      STATUS  mandatory
      DESCRIPTION
"Determines the active data clock source for this port.

Options:
internal (1): Tx and Rx clocks are internally generated

external (2): Tx and Rx clocks are externally supplied on separate pins

split (3): Tx clock is internally generated and Rx clock is externally supplied

slave (4): Tx and Rx clocks are externally supplied on the same pins

Note: Split clocking is not supported in CX900 slots 5, 6 and 7.

Default Value: external (locked to internal for ISDN)"
      ::= { bopSapOprEntry 5 }


   bopSapOprPortSpeed OBJECT-TYPE
      SYNTAX  INTEGER (375 .. 2048000)
      ACCESS  read-only
      STATUS  mandatory
      DESCRIPTION
"Determines the input and output speed in bits per second for this port.

Note: Meaningful only if 'bopSapOprPortClockSource' is 'internal' or 'split'.

Ranges of Values: 375-2048000; limited to 1875-256000 for CX900 slots 5,6,7.

Default Value: 64,000"
      ::= { bopSapOprEntry 6 }


   bopSapOprPortDuplex OBJECT-TYPE
      SYNTAX  INTEGER {
               half            (1),
               full            (2)
               }
      ACCESS  read-only
      STATUS  mandatory
      DESCRIPTION
"Determines whether this port is communicating simultaneously in both
 directions (full-duplex) or alternates between directions (half-duplex).
 Not applicable for ISDN and T1/E1 ports.

Options:
half (1): half-duplex

full (2): full-duplex

Default Value: full"
      ::= { bopSapOprEntry 7 }


   bopSapOprPortMaxFrameSize OBJECT-TYPE
      SYNTAX  INTEGER (32..9000)
      ACCESS  read-only
      STATUS  mandatory
      DESCRIPTION
"Determines the active maximum frame size supported by this port. 

Ranges of Values: 32-9000

Default Value: 1,600 (512 for ISDN)"
      ::= { bopSapOprEntry 8 }


   
bopSapOprPortDataEncoding OBJECT-TYPE
      SYNTAX  INTEGER {
               nrz             (1),
               nrzi-mark       (2),
               nrzi-space      (3)
               }
      ACCESS  read-only
      STATUS  mandatory
      DESCRIPTION
"Determines the active data formatting and encoding used by this port.

Options:
n/a (0): object is not applicable

nrz (1): NRZ (locked for ISDN 'D' channel; ISDN 'B' channel can use only this 
value or NRZI-Space value)

nrzi-mark (2): NRZI-Mark

nrzi-space (3): NRZI-Space (ISDN 'B' channel can use only this value or NRZ 
value)

Note: CX900 Slot/port/channel 51x-71x can use only NRZ or NRZI-Space.

Default Value: nrz"
      ::= { bopSapOprEntry 9 }


   
bopSapOprPortIdleCondition OBJECT-TYPE
      SYNTAX  INTEGER {
               flags           (1),
               marks           (2),
               as400           (3)
               }
      ACCESS  read-only
      STATUS  mandatory
      DESCRIPTION
"Determines the active idle line condition supported by this port.

Options:
flags (1): flags

marks (2): marks

as400 (3): AS400

Default Value: flags"
      ::= { bopSapOprEntry 10 }


   bopSapOprPortPreAmbleLength OBJECT-TYPE
      SYNTAX  INTEGER (0 .. 16)
      ACCESS  read-only
      STATUS  mandatory
      DESCRIPTION
"Determines the minimum number of flags or sync pairs that will be inserted between frames
 by the port's transmitter.

For HDLC frames:
A value of zero causes flag sharing between frames.
A value of one means no flag sharing and zero flags inserted between frames.
A value of two means no flag sharing and one flag inserted between frames.
A value of three means no flag sharing and two flags inserted between frames.
Etc.

For Bisync frames:
A value of zero or one causes one sync pair to be inserted between frames.
A value of two causes two sync pairs to be inserted between frames.
A value of three causes three sync pairs to be inserted between frames.
Etc.

Ranges of Values: 0 -16

Default Value: 1"
      ::= { bopSapOprEntry 11 }


   bopSapOprPortFlagSharing OBJECT-TYPE
      SYNTAX  INTEGER {
               disabled        (1),
               enabled         (2)
               }
      ACCESS  read-only
      STATUS  obsolete
      DESCRIPTION
"Determines whether back-to-back Tx frames share opening and closing flag.
This value is meaningful only if 'bopSapAdmPortPreAmbleLength' is set to 
zero.

Options:
disabled (1): back-to-back frames do not share flag

enabled (2): back-to-back frames share flag

Default Value: disabled"
--#ENDING-VERSION 2      
::= { bopSapOprEntry 12 }


   bopSapOprPortFilterMask OBJECT-TYPE
      SYNTAX  INTEGER (0 .. 255)
      ACCESS  read-only
      STATUS  obsolete
      DESCRIPTION
"Indicates which bits of the 8-bit HDLC address are being used for address
 filtering on this port (CX900 or USIO only).

Note: When a bit is set to '1', the position of bits will be checked. When a bit is 
set to '0', it will not be checked.

Ranges of Values: 0 - 255

Default Value: 0"
--#ENDING-VERSION 2
      ::= { bopSapOprEntry 13 }


   bopSapOprPortFilterAddress1 OBJECT-TYPE
      SYNTAX  INTEGER (0 .. 255)
      ACCESS  read-only
      STATUS  obsolete
      DESCRIPTION
"Indicates one of four 8-bit addresses used for address filtering (CX900 or
 USIO only).

Ranges of Values: 0 - 255

Default Value: 126"
--#ENDING-VERSION 2
      ::= { bopSapOprEntry 14 }


   bopSapOprPortFilterAddress2 OBJECT-TYPE
      SYNTAX  INTEGER (0 .. 255)
      ACCESS  read-only
      STATUS  obsolete
      DESCRIPTION
"Indicates one of four 8-bit addresses used for address filtering (CX900 or
 USIO only).

Ranges of Values: 0 - 255

Default Value: 126"
--#ENDING-VERSION 2
      ::= { bopSapOprEntry 15 }


   bopSapOprPortFilterAddress3 OBJECT-TYPE
      SYNTAX  INTEGER (0 .. 255)
      ACCESS  read-only
      STATUS  obsolete
      DESCRIPTION
"Indicates one of four 8-bit addresses used for address filtering (CX900 or
 USIO only).

Ranges of Values: 0 - 255

Default Value: 126"
--#ENDING-VERSION 2
      ::= { bopSapOprEntry 16 }


   bopSapOprPortFilterAddress4 OBJECT-TYPE
      SYNTAX  INTEGER (0 .. 255)
      ACCESS  read-only
      STATUS  obsolete
      DESCRIPTION
"Indicates one of four 8-bit addresses used for address filtering (CX900 or
 USIO only).

Ranges of Values: 0 - 255

Default Value: 126"
--#ENDING-VERSION 2
      ::= { bopSapOprEntry 17 }



   bopSapOprPortCrc OBJECT-TYPE
      SYNTAX  INTEGER {
               crc-ccitt    (1),
               crc-32       (2)
               }
      ACCESS  read-only
      STATUS  obsolete
      DESCRIPTION
"Determines which algorithm is being used for error detection.

Options:
crc-ccitt (1): CRC-ITU-T (uses X15+X12+X5+1 polynomial; ITU-T formerly CCITT) 
(locked for ISDN 'D' channel; can be selected for ISDN 'B' channel)

crc-32 (2): CRC-32 (for Ethernet; uses X32+X26+X23+X22+X16+X12+X11+ 
X10+X8+X7+X5+X4+X2+X+1) (can be selected for ISDN 'B' channel)

Default Value: crc-ccitt (1)"
--#ENDING-VERSION 2
      ::= { bopSapOprEntry 18 }


   bopSapOprPortDtrUpTimer OBJECT-TYPE
      SYNTAX  INTEGER (0..65535)
      ACCESS  read-only
      STATUS  mandatory
      DESCRIPTION
"Determines the time in seconds that the port must wait for DCD (DTR if DCE)
 after raising DTR (DCD if DCE) to determine if a connection can be established.
 This object has no meaning in ISDN connections.

Note: This value will be set to zero if the port does not support an application 
requiring it.

Ranges of Values: 0 - 65535

Default Value: 0"
      ::= { bopSapOprEntry 19 }


   bopSapOprPortTxWindow OBJECT-TYPE
      SYNTAX  INTEGER (1..255)
      ACCESS  read-only
      STATUS  mandatory
      DESCRIPTION
"Determines the active maximum number of buffers that may be queued onto the
 port driver (for transmission) by the associated upper layer.
 For ISDN ports, the value is locked at 8.

Ranges of Values: 1 - 255

Default Value: 255"
   ::= { bopSapOprEntry 20 }

   bopSapOprPortDialMode OBJECT-TYPE
      SYNTAX  INTEGER {
               dial-in-only   (1),
               dial-out-only  (2),
               dial-in-out    (3)
               }
      ACCESS  read-only
      STATUS  mandatory
      DESCRIPTION
"Identifies the operation mode when setting up connections. 
Options:
n/a (0): object is not applicable
dial-in-only  (1): Only accept incoming calls; Will not make any outgoing calls.
dial-out-only (2): Only make outgoing calls; Will not accept any incoming calls.
dial-in-out    (3): Accept incoming calls and make outgoing calls. 

Ranges of Values: 1 - 3

Default Value: dial-in-out"
	--#STARTING-VERSION 2
      ::= { bopSapOprEntry 21 }

-- gap (6) for future parameters

   bopSapOprPortLoopback OBJECT-TYPE
      SYNTAX  INTEGER {
               none            (1),
               local           (2),
               remote          (3),
               both            (4),
               isdn-uif-uif    (5),
               isdn-uif-idl2   (6),
               isdn-uif-framer (7),
               isdn-uif-external       (8)
               }
      ACCESS  read-only
      STATUS  mandatory
      DESCRIPTION
"Determines whether loopback is enabled and what kind of loopback is enabled.

Options: 
n/a (0): object is not applicable

none  (1): Loopback is not enabled

local (2): Local loopback is enabled (return outbound frames to the originating
 software layer without transmitting them)

remote (3): Remote loopback is enabled (forces the port to return (transmit) 
 any frame received on the line, and causes the port to deny communication
 with any upper layer that requests service)

both (4):Both local and remote loopbacks are enabled.

isdn-uif-uif (5): ISDN loopback is enabled at U-Interface (forces TB1Q signal 
from a remote transmitter to pass through the entire U-Interface Transceiver 
before being transmitted back to the remote receiver)

isdn-uif-idl2 (6): ISDN loopback is enabled at IDL2 Controller (forces IDL2 
Controller to take in B and D channel data on IDL RX pin and send it out on 
IDL2 TX pin)

isdn-uif-framer (7): ISDN loopback is enabled at framer (forces B and D 
channel data in on D-in pin and M channel data in on SCP which together 
undergo framing and deframing functions before B and D channel data go out 
D-out pin and M channel data go out SCP)

isdn-uif-external (8): ISDN loopback is enabled at external line (forces TB1Q 
signal coming in on D-in pin to pass through Tx Driver pins, the U-Interface 
circuit and Rx input pins before recovering it and sending it out the D-out 
pin)

Default Value: none"
      ::= { bopSapOprEntry 28 }


   bopSapOprPortSignalSamplingPeriod OBJECT-TYPE
      SYNTAX  INTEGER (3..100)
      ACCESS  read-write
      STATUS  mandatory
      DESCRIPTION
"Determines the active sampling period in 100 millisecond increments that this
 port uses to sample signals. This object has no meaning in ISDN connections.

Ranges of Values: 3 - 100

Default Value: 5

Configuration Changed: operative "
      ::= { bopSapOprEntry 29 }


   bopSapOprPortDcdDtrSignalSamples OBJECT-TYPE
      SYNTAX  INTEGER (1..30)
      ACCESS  read-write
      STATUS  mandatory
      DESCRIPTION
"Determines the active number of sampling periods that this port must wait
 before validating DCD (DTR if DCE).
 This object has no meaning in ISDN connections.

Ranges of Values: 1 - 30

Default Value: 3

Configuration Changed: operative "
      ::= { bopSapOprEntry 30 }


   bopSapOprPortCtsRtsSignalSamples OBJECT-TYPE
      SYNTAX  INTEGER (1..30)
      ACCESS  read-write
      STATUS  mandatory
      DESCRIPTION
"Determines the active number of sampling periods that this port must wait
 before validating CTS (RTS if DCE).
 This object has no meaning in ISDN connections.

Ranges of Values: 1-30

Default Value: 3

Configuration Changed: operative "
      ::= { bopSapOprEntry 31 }


   bopSapOprPortDsrDrsSignalSamples OBJECT-TYPE
      SYNTAX  INTEGER (1..30)
      ACCESS  read-write
      STATUS  mandatory
      DESCRIPTION
"Determines the active number of sampling periods that this port must wait
 before validating DRS (DSR if DCE).
 This object has no meaning in ISDN connections.

Ranges of Values: 1 - 30

Default Value: 3

Configuration Changed: operative "
      ::= { bopSapOprEntry 32 }


   bopSapOprPortTmLlSignalSamples OBJECT-TYPE
      SYNTAX  INTEGER (1..30)
      ACCESS  read-write
      STATUS  mandatory
      DESCRIPTION
"Determines the active number of sampling periods that this port must wait
 before validating TM (LL if DCE).
 This object has no meaning in ISDN connections.

Ranges of Values: 1 - 30

Default Value: 3

Configuration Changed: operative "
      ::= { bopSapOprEntry 33 }


   bopSapOprPortRiRlSignalSamples OBJECT-TYPE
      SYNTAX  INTEGER (1..30)
      ACCESS  read-write
      STATUS  mandatory
      DESCRIPTION
"Determines the active number of sampling periods that this port must wait
 before validating RI (RL if DCE).
 This object has no meaning in ISDN connections.

Ranges of Values: 1 - 30

Default Value: 3

Configuration Changed: operative "
      ::= { bopSapOprEntry 34 }


   bopSapOprPortStatisticsTimer OBJECT-TYPE
      SYNTAX  INTEGER (0..60)
      ACCESS  read-only
      STATUS  mandatory
      DESCRIPTION
"Determines the active period in seconds during which BOP performance
 statistics are measured.

Note: If set to zero, BOP performance statistics are not measured.

Ranges of Values: 0 - 60

Default Value: 0"
      ::= { bopSapOprEntry 35 }


  
 bopSapOprPortCarrierAction OBJECT-TYPE
      SYNTAX  INTEGER {
               disabled      (1),
               enabled       (2)
               }
      ACCESS  read-write
      STATUS  mandatory
      DESCRIPTION
"Determines if the port driver informs it's associated upper layer that
service is no longer available following loss of DCD if DTE, or DTR if DCE.

Options:
disabled (1): do not notify upper layer (locked for ISDN and T1/E1 ports)

enabled (2): notify upper layer

Default Value: enabled (2)

Configuration Changed: operative "
      ::= { bopSapOprEntry 36 }


   bopSapOprPortDataGenerator OBJECT-TYPE
      SYNTAX  INTEGER {
               disabled        (1),
               enabled         (2),
               enabled-verify  (3),
               retrigger       (4)
               }
      ACCESS  read-write
      STATUS  mandatory
      DESCRIPTION
"Determines whether this port acts as an internal data generator.

Options:
n/a (0): object is not applicable

disabled (1): port is not a data generator

enabled (2): port is a data generator

enabled-verify (3): port is a data generator and its incoming data is 
verified

retrigger (4): port restarts data generation with defined parameters

Default Value: disabled (1)

Configuration Changed: operative "
      ::= { bopSapOprEntry 37 }


   bopSapOprPortGenFrames OBJECT-TYPE
      SYNTAX  INTEGER (0..255)
      ACCESS  read-write
      STATUS  mandatory
      DESCRIPTION
"Determines the number of frames that the port configured as an internal
 data generator will generate at one time.

Ranges of Values: 0 - 255

Note: When set to zero, frames are generated continuously

Default Value: 1

Configuration Changed: operative "
      ::= { bopSapOprEntry 38 }


   bopSapOprPortGenFrameSize OBJECT-TYPE
      SYNTAX  INTEGER (2..65535)
      ACCESS  read-write
      STATUS  mandatory
      DESCRIPTION
"Determines the size in bytes of internally generated frames (excluding flags).

Ranges of Values: 2 - 65,535

Note: When set to zero, frames are sized randomly.

Default Value: 128

Configuration Changed: operative "
      ::= { bopSapOprEntry 39 }


   bopSapOprPortGenFrameHeader OBJECT-TYPE
      SYNTAX  INTEGER (0..65535)
      ACCESS  read-write
      STATUS  mandatory
      DESCRIPTION
"Determines the 16-bit header that is inserted in the first two octets after
 the opening flag of each internally generated frame.

Ranges of Values: 0 - 65,535

Default Value: 1

Configuration Changed: operative "
      ::= { bopSapOprEntry 40 }


   bopSapOprPortThreshBandwidth OBJECT-TYPE
      SYNTAX  INTEGER (0..65535)
      ACCESS  read-only
      STATUS  mandatory
      DESCRIPTION
"Determines the value of the minimum critical bandwidth that determines
whether Frame Relay should filter certain restricted types of packets or not.

The value entered should be a multiple of 1 Kilo bits per second.

Ranges of Values: 0 - 65,535

Default Value: 0

Configuration Changed: operative "
      --#STARTING-VERSION 1
      ::= { bopSapOprEntry 41 }


   bopSapOprPortActualSpeed OBJECT-TYPE
      SYNTAX  INTEGER (375 .. 2048000)
      ACCESS  read-only
      STATUS  mandatory
      DESCRIPTION
"Determines the actual calculated output speed in bits per second of the port.

Ranges of Values: 375 - 2,048,000

Default Value: 0"
      --#STARTING-VERSION 1
      ::= { bopSapOprEntry 42 }


   bopSapOprCodeSet  OBJECT-TYPE
        SYNTAX  INTEGER { 
            ebcdic    (1),  
            ascii     (2) 
                }
        ACCESS  read-only
        STATUS  mandatory
        DESCRIPTION
"Indicates the code used to communicate with the Bisync device. 
Options:
(0) N/A: object is not applicable
(1) EBCDIC code set
(2) ASCII code set
Default value: ebcdic"
--#STARTING-VERSION 2
      ::= { bopSapOprEntry 43 }


   bopSapOprParity OBJECT-TYPE
    SYNTAX  INTEGER {
        none    (1),  
        odd     (2),
        even    (3),
        space   (4),
        mark    (5)
        }
    ACCESS  read-only
    STATUS  mandatory
    DESCRIPTION
"Indicates the parity used to communicate with the Bisync device
    Options:
        (0) N/A:   Object is not applicable
        (1) none:  No parity
        (2) odd:   Odd parity
        (3) even:  Even parity
        (4) space: Low parity (always 0's)
        (5) mark:  High parity (always 1's)
        
Default value: none"
--#STARTING-VERSION 2
      ::= { bopSapOprEntry 44 }


-- gap (2) for future parameters

   bopOprPortTrap OBJECT-TYPE
      SYNTAX  INTEGER {
               disabled  (1),
               enabled   (2)
               }
      ACCESS  read-write
      STATUS  mandatory
      DESCRIPTION
"Determines whether this port produces a 'bopPortStatusChange' trap which
 can be retrieved by SNMP network management.

Options:
disabled (1): do not produce port status trap

enabled (2): produce port status trap

Default Value: disabled (1)

Configuration Changed: operative "
      ::= { bopSapOprEntry 47 }


   bopOprTxClockTrap OBJECT-TYPE
      SYNTAX  INTEGER {
               disabled  (1),
               enabled   (2)
               }
      ACCESS  read-write
      STATUS  mandatory
      DESCRIPTION
"Determines whether this port produces a 'bopTxClockStatusChange' trap which
 can be retrieved by SNMP network management.

Options:
disabled (1): do not produce transmit clock status trap

enabled (2): produce transmit clock status trap

Default Value: disabled (1)

Configuration Changed: operative "
      ::= { bopSapOprEntry 48 }


-- gap (3) for future traps


   bopOprControlLine OBJECT-TYPE
      SYNTAX  INTEGER {
               forceDown               (1),
               forceUp                 (2),
               forceReset              (3)
               }
      ACCESS  write-only
      STATUS  mandatory
      DESCRIPTION
"Controls the state of the port.

Options:
forceDown (1): forces the port into a 'down' state

forceUp (2): forces the port into an 'up' state

forceReset (3): forces a reset of the port

Default Value: none"
      ::= { bopSapOprEntry 52 }


   bopOprControlStats OBJECT-TYPE
      SYNTAX  INTEGER {
               clearSapStats   (1)
               }
      ACCESS  write-only
      STATUS  mandatory
      DESCRIPTION
"Specifies that port statistics are to be cleared.

Options:
clearSapStats (1): clears port statistics

Default Value: none"
      ::= { bopSapOprEntry 53 }


-- gap (1) for future write-only commands


   bopStatOprPortType OBJECT-TYPE
      SYNTAX  INTEGER {
               unknown   (1),
               dte       (2),
               dce       (3)
               }
      ACCESS  read-only
      STATUS  mandatory
      DESCRIPTION
"Indicates the type of hardware strapping for the port.

Options:
unknown  (1): unknown strapping

dte  (2): DTE strapping

dce (3): DCE strapping

Default Value: none"
      ::= { bopSapOprEntry 55 }


   bopStatOprPortInterfaceType OBJECT-TYPE
      SYNTAX  INTEGER {
               unknown   (1),
               rs232d    (2),
               v35       (3),
               x21       (4),
               v34       (5),
               dds       (6),
               uif       (7),
               v36       (8)
               }
      ACCESS  read-only
      STATUS  mandatory
      DESCRIPTION
"Indicates the type of hardware interface of the port.

Options:
unknown (1)

rs232d (2): V.24

v35 (3): V.35

x21(4): X.21

v34 (5): V.34 modem

dds (6): 56K DSU/CSU

uif (7): ISDN U-interface

v36 (8): V.36

Default Value: none"
      ::= { bopSapOprEntry 56 }


   bopStatOprPortState OBJECT-TYPE
      SYNTAX  INTEGER {
               portUp                          (1),
               portDown                        (2),
               portShutDown                    (3),
               portDownBadConfiguration        (4),
               portOutOfOrder                  (5)
               }
      ACCESS  read-only
      STATUS  mandatory
      DESCRIPTION
"Indicates the state of availability of the port.

Options:
portUp (1): port is up

portDown (2): port is down

portShutDown (3): port has been shut down

portDownBadConfiguration (4): port is down due to bad 
configuration

portOutOfOrder (5): port is out of order

Default Value: none"
      ::= { bopSapOprEntry 57 }


-- gap (3) for future states


   bopStatOprTxClockState OBJECT-TYPE
      SYNTAX  INTEGER {
               txClockDown     (1),
               txClockUp       (2)
               }
      ACCESS  read-only
      STATUS  mandatory
      DESCRIPTION
"Indicates the state availability of the transmit clock.

Options:
txClockDown (1): transmit clock is down

txClockUp (2): transmit clock is up

Default Value: none"
      ::= { bopSapOprEntry 61 }


   bopStatOprDCDState OBJECT-TYPE
      SYNTAX  INTEGER {
               unknown   (1),
               inactive  (2),
               active    (3)
               }
      ACCESS  read-only
      STATUS  mandatory
      DESCRIPTION
"Indicates the state of the DCD signal.

Options:
unknown (1): DCD signal is in unknown state because hardware is not present

inactive(2): DCD signal is low

active (3): DCD signal is high

Default Value: none"
      ::= { bopSapOprEntry 62 }


   bopStatOprDTRState OBJECT-TYPE
      SYNTAX  INTEGER {
               unknown   (1),
               inactive  (2),
               active    (3)
               }
      ACCESS  read-only
      STATUS  mandatory
      DESCRIPTION
"Indicates the state of the DTR signal.

Options:
unknown (1): DTR signal is in unknown state because hardware is not present

inactive (2): DTR signal is low

active (3): DTR signal is high

Default Value: none"
      ::= { bopSapOprEntry 63 }


   bopStatOprRTSState OBJECT-TYPE
      SYNTAX  INTEGER {
               unknown   (1),
               inactive  (2),
               active    (3)
               }
      ACCESS  read-only
      STATUS  mandatory
      DESCRIPTION
"Indicates the state of the RTS signal.

Options:
unknown (1): RTS signal is in unknown state because hardware is not present

inactive (2): RTS signal is low

active (3): RTS signal is high

Default Value: none"
      ::= { bopSapOprEntry 64 }


   bopStatOprCTSState OBJECT-TYPE
      SYNTAX  INTEGER {
               unknown   (1),
               inactive  (2),
               active    (3)
               }
      ACCESS  read-only
      STATUS  mandatory
      DESCRIPTION
"Indicates the state of the CTS signal.

Options:
unknown (1): CTS signal is in unknown state because hardware is not present

inactive (2): CTS signal is low

active (3): CTS signal is high

Default Value: none"
      ::= { bopSapOprEntry 65 }


   bopStatOprDSRState OBJECT-TYPE
      SYNTAX  INTEGER {
               unknown   (1),
               inactive  (2),
               active    (3)
               }
      ACCESS  read-only
      STATUS  mandatory
      DESCRIPTION
"Indicates the state of the DSR signal.

Options:
unknown (1): DSR signal is in unknown state because hardware is not present

inactive (2): DSR signal is low

active =(3): SR signal is high

Default Value: none"
      ::= { bopSapOprEntry 66 }


   bopStatOprDRSState OBJECT-TYPE
      SYNTAX  INTEGER {
               unknown   (1),
               inactive  (2),
               active    (3)
               }
      ACCESS  read-only
      STATUS  mandatory
      DESCRIPTION
"Indicates the state of the DRS signal.

Options:
unknown (1): DRS signal is in unknown state because hardware is not present

inactive (2): DRS signal is low

active = DRS signal is high

Default Value: none"
      ::= { bopSapOprEntry 67 }


   bopStatOprTMState OBJECT-TYPE
      SYNTAX  INTEGER {
               unknown   (1),
               inactive  (2),
               active    (3)
               }
      ACCESS  read-only
      STATUS  mandatory
      DESCRIPTION
"Indicates the state of the TM signal.

Options:
unknown (1): TM signal is in unknown state because hardware is not present

inactive (2): TM signal is low

active (3): TM signal is high

Default Value: none"
      ::= { bopSapOprEntry 68 }


   bopStatOprLLState OBJECT-TYPE
      SYNTAX  INTEGER {
               unknown    (1),
               inactive   (2),
               active     (3)
               }
      ACCESS  read-only
      STATUS  mandatory
      DESCRIPTION
"Indicates the state of the LL signal.

Options:
unknown (1): LL signal is in unknown state because hardware is not present

inactive (2): LL signal is low

active (3): LL signal is high

Default Value: none"
      ::= { bopSapOprEntry 69 }


   bopStatOprRIState OBJECT-TYPE
      SYNTAX  INTEGER {
               unknown   (1),
               inactive  (2),
               active    (3)
               }
      ACCESS  read-only
      STATUS  mandatory
      DESCRIPTION
"Indicates the state of the RI signal.

Options:
unknown (1): RI signal is in unknown state because hardware is not present

inactive (2): RI signal is low

active (3): RI signal is high

Default Value: none"
      ::= { bopSapOprEntry 70 }


   bopStatOprRLState OBJECT-TYPE
      SYNTAX  INTEGER {
               unknown   (1),
               inactive  (2),
               active    (3)
               }
      ACCESS  read-only
      STATUS  mandatory
      DESCRIPTION
"Indicates the state of the RL signal.

Options:
unknown (1): RL signal is in unknown state because hardware is not present

inactive (2): RL signal is low

active (3): RL signal is high

Default Value: none"
      ::= { bopSapOprEntry 71 }

-- gap (3) for future states

   bopStatOprTxFrames OBJECT-TYPE
      SYNTAX  Counter
      ACCESS  read-only
      STATUS  mandatory
      DESCRIPTION
"Indicates the total number of Tx frames since statistics were last reset.

Ranges of Values: 0 - 4,294,967,295

Default Value: none"
      ::= { bopSapOprEntry 75 }


   bopStatOprRxFrames OBJECT-TYPE
      SYNTAX  Counter
      ACCESS  read-only
      STATUS  mandatory
      DESCRIPTION
"Indicates the total number of Rx frames since statistics were last reset.

Ranges of Values: 0 - 4,294,967,295

Default Value: none"
      ::= { bopSapOprEntry 76 }


   bopStatOprLocalLoopbackFrames OBJECT-TYPE
      SYNTAX  Counter
      ACCESS  read-only
      STATUS  mandatory
      DESCRIPTION
"Indicates the total number of frames locally looped back since statistics
 were last reset.

Ranges of Values: 0 - 4,294,967,295

Default Value: none"
      ::= { bopSapOprEntry 77 }

   bopStatOprTxBps OBJECT-TYPE
      SYNTAX   Counter
      ACCESS   read-only
      STATUS   mandatory
      DESCRIPTION
"Indicates the number of transmitted bits divided by the number of seconds
 set in 'bopSapOprPortStatisticsTimer'.

Ranges of Values: 0 - 4,294,967,295

Default Value: none"
      ::= { bopSapOprEntry 78 }

   bopStatOprRxBps OBJECT-TYPE
      SYNTAX   Counter
      ACCESS   read-only
      STATUS   mandatory
      DESCRIPTION
"Indicates the number of received bits divided by the number of seconds
 set in 'bopSapOprPortStatisticsTimer'.

Ranges of Values: 0 - 4,294,967,295

Default Value: none"
      ::= { bopSapOprEntry 79 }

   bopStatOprTxBpsMax OBJECT-TYPE
      SYNTAX   Counter
      ACCESS   read-only
      STATUS   mandatory
      DESCRIPTION
"Indicates the highest number of bits per second transmitted since statistics
 were last reset.

Ranges of Values: 0 - 4,294,967,295

Default Value: none"
      ::= { bopSapOprEntry 80 }

   bopStatOprRxBpsMax OBJECT-TYPE
      SYNTAX   Counter
      ACCESS   read-only
      STATUS   mandatory
      DESCRIPTION
"Indicates the highest number of bits per second received since statistics
 were last reset.

Ranges of Values: 0 - 4,294,967,295

Default Value: none"
      ::= { bopSapOprEntry 81 }

   bopStatOprTxFps OBJECT-TYPE
      SYNTAX   Counter
      ACCESS   read-only
      STATUS   mandatory
      DESCRIPTION
"Indicates the number of transmitted frames divided by the number of seconds
 set in 'bopSapOprPortStatisticsTimer'.

Ranges of Values: 0 - 4,294,967,295

Default Value: none"
      ::= { bopSapOprEntry 82 }

   bopStatOprRxFps OBJECT-TYPE
      SYNTAX   Counter
      ACCESS   read-only
      STATUS   mandatory
      DESCRIPTION
"Indicates the number of received frames divided by the number of seconds set
 in 'bopSapOprPortStatisticsTimer'.

Ranges of Values: 0 - 4,294,967,295

Default Value: none"
      ::= { bopSapOprEntry 83 }

   bopStatOprTxFpsMax OBJECT-TYPE
      SYNTAX   Counter
      ACCESS   read-only
      STATUS   mandatory
      DESCRIPTION
"Indicates the highest number of frames per second transmitted since
 statistics were last reset.

Ranges of Values: 0 - 4,294,967,295

Default Value: none"
      ::= { bopSapOprEntry 84 }

   bopStatOprRxFpsMax OBJECT-TYPE
      SYNTAX   Counter
      ACCESS   read-only
      STATUS   mandatory
      DESCRIPTION
"Indicates the highest number of frames per second received since statistics
 were last reset.

Ranges of Values: 0 - 4,294,967,295

Default Value: none"
      ::= { bopSapOprEntry 85 }

   bopStatOprTxUnderrunFrames OBJECT-TYPE
      SYNTAX  Counter
      ACCESS  read-only
      STATUS  mandatory
      DESCRIPTION
"Indicates the total number of underrun frames that have been unsuccessfully
 transmitted since statistics were last reset.

Ranges of Values: 0 - 4,294,967,295

Default Value: none"
      ::= { bopSapOprEntry 86 }

   bopStatOprTxCtsLostFrames OBJECT-TYPE
      SYNTAX  Counter
      ACCESS  read-only
      STATUS  mandatory
      DESCRIPTION
"Indicates the total number of frames unsuccessfully transmitted in half-duplex
 because CTS was dropped during transmission.

Ranges of Values: 0 - 65,535

Default Value: none"
      ::= { bopSapOprEntry 87 }

   bopStatOprTxBadStateDiscards OBJECT-TYPE
      SYNTAX  Counter
      ACCESS  read-only
      STATUS  mandatory
      DESCRIPTION
"Indicates the total number of frames discarded since statistics were last
 reset, due to a request for frame transmission while the port was down
 ('bopStatOprPortState' = portDown, portShutDown, portDownBadConfiguration,
 or portOutOfOrder).

Ranges of Values: 0 - 65,535

Default Value: none"
      ::= { bopSapOprEntry 88 }


   bopStatOprTxResetDiscards OBJECT-TYPE
      SYNTAX  Counter
      ACCESS  read-only
      STATUS  mandatory
      DESCRIPTION
"Indicates the total number of frames discarded since statistics were last
 reset, due to a management request for a line reset.

Ranges of Values: 0 - 65,535

Default Value: none"
      ::= { bopSapOprEntry 89 }

   bopStatOprTxSysCongestionDiscards OBJECT-TYPE
      SYNTAX  Counter
      ACCESS  read-only
      STATUS  mandatory
      DESCRIPTION
"Indicates the total number of frames discarded since statistics were last
 reset, due to system congestion.

Ranges of Values: 0 - 65,535

Default Value: none"
      ::= { bopSapOprEntry 90 }


   bopStatOprTxInvWinDiscards OBJECT-TYPE
      SYNTAX  Counter
      ACCESS  read-only
      STATUS  mandatory
      DESCRIPTION
"Indicates the total number of frames discarded since statistics were last
 reset, due to the transmit window being exceeded.

Ranges of Values: 0 - 65,535

Default Value: none"
      ::= { bopSapOprEntry 91 }


   bopStatOprTxInvRLpbkWinDiscards OBJECT-TYPE
      SYNTAX  Counter
      ACCESS  read-only
      STATUS  mandatory
      DESCRIPTION
"Indicates the total number of frames discarded since statistics were last
 reset, due to the transmit window being exceeded while in loopback mode.

Ranges of Values: 0 - 65,535

Default Value: none"
      ::= { bopSapOprEntry 92 }

-- gap (5) for future transmit type statistics

   bopStatOprRxBadCrcFrames OBJECT-TYPE
      SYNTAX  Counter
      ACCESS  read-only
      STATUS  mandatory
      DESCRIPTION
"Indicates the total number of bad CRC frames received since statistics were
 last reset.

Ranges of Values: 0 - 65,535

Default Value: none"
      ::= { bopSapOprEntry 98 }


   bopStatOprRxAbortedFrames OBJECT-TYPE
      SYNTAX  Counter
      ACCESS  read-only
      STATUS  mandatory
      DESCRIPTION
"Indicates the total number of aborted frames received since statistics were
 last reset.

Note: A frame is aborted when the port's receiver detects seven consecutive
 ones in that frame.

Ranges of Values: 0 - 65,535

Default Value: none"
      ::= { bopSapOprEntry 99 }


   bopStatOprRxNonIntegralBitFrames OBJECT-TYPE
      SYNTAX  Counter
      ACCESS  read-only
      STATUS  mandatory
      DESCRIPTION
"Indicates the total number of frames received since statistics were last
 reset, that did not have eight bits per byte.

Note: Non-integral bit frames cannot be divided evenly by eight (the number of bits 
per byte in a frame).

Ranges of Values: 0 - 65,535

Default Value: none"
      ::= { bopSapOprEntry 100 }


   bopStatOprRxLongFrames OBJECT-TYPE
      SYNTAX  Counter
      ACCESS  read-only
      STATUS  mandatory
      DESCRIPTION
"Indicates the total number of long frames received since statistics were last
 reset.

Note: A long frame is counted each time a received frame exceeds the permitted 
frame length defined in 'bopSapOprPortMaxFrameSize'.

Ranges of Values: 0 - 65,535

Default Value: none"
      ::= { bopSapOprEntry 101 }


   bopStatOprRxOverrunFrames OBJECT-TYPE
      SYNTAX  Counter
      ACCESS  read-only
      STATUS  mandatory
      DESCRIPTION
"Indicates the total number of overrun frames received since statistics were
 last reset.

Note:
An overrun indicates that a frame's contents have been corrupted due to slow 
response in data reception.

Ranges of Values: 0 - 65,535

Default Value: none"
      ::= { bopSapOprEntry 102 }

   bopStatOprRxCdLostFrames OBJECT-TYPE
      SYNTAX  Counter
      ACCESS  read-only
      STATUS  mandatory
      DESCRIPTION
"Indicates the total number of frames received with DCD loss in half-duplex by
 the port.

Ranges of Values: 0 - 65, 535

Default Value: none"
      ::= { bopSapOprEntry 103 }

   bopStatOprRxBadStateDiscards OBJECT-TYPE
      SYNTAX  Counter
      ACCESS  read-only
      STATUS  mandatory
      DESCRIPTION
"Indicates the total number of frames discarded since statistics were last
 reset, because BOP software layer was not bound to other layers.

Ranges of Values: 0 - 65,535

Default Value: none"
      ::= { bopSapOprEntry 104 }

   bopStatOprRxBusyDiscards OBJECT-TYPE
      SYNTAX  Counter
      ACCESS  read-only
      STATUS  mandatory
      DESCRIPTION
"Indicates the total number of frames discarded since statistics were last
 reset, due to a lack of receive buffers.

Ranges of Values: 0 - 65,535

Default Value: none"
      ::= { bopSapOprEntry 105 }

-- gap (3) for future receive type statistics


   bopStatOprPortStateChanges OBJECT-TYPE
      SYNTAX  Counter
      ACCESS  read-only
      STATUS  mandatory
      DESCRIPTION
"Indicates the total number of times the port has moved from one state to
 another since statistics were last reset.

Ranges of Values: 0 - 65,535

Default Value: none"
      ::= { bopSapOprEntry 109 }


   bopStatOprTxClockStateChanges OBJECT-TYPE
      SYNTAX  Counter
      ACCESS  read-only
      STATUS  mandatory
      DESCRIPTION
"Indicates the total number of times that 'bopStatOprTxClockState' has moved
from one state to another since were last reset.

Ranges of Values: 0 - 65,535

Default Value: none"
      ::= { bopSapOprEntry 110 }


   bopStatOprDCDStateChanges OBJECT-TYPE
      SYNTAX  Counter
      ACCESS  read-only
      STATUS  mandatory
      DESCRIPTION
"Indicates the total number of times DCD has moved from one state to
 another since statistics were last reset.

Ranges of Values: 0 - 65,535

Default Value: none"
      ::= { bopSapOprEntry 111 }


   bopStatOprDTRStateChanges OBJECT-TYPE
      SYNTAX  Counter
      ACCESS  read-only
      STATUS  mandatory
      DESCRIPTION
"Indicates the total number of times DTR has moved from one state to
 another since statistics were last reset.

Ranges of Values: 0 - 65,535

Default Value: none"
      ::= { bopSapOprEntry 112 }


   bopStatOprRTSStateChanges OBJECT-TYPE
      SYNTAX  Counter
      ACCESS  read-only
      STATUS  mandatory
      DESCRIPTION
"Indicates the total number of times RTS has moved from one state to
 another since statistics were last reset.

Ranges of Values: 0 - 65,535

Default Value: none"
      ::= { bopSapOprEntry 113 }


   bopStatOprCTSStateChanges OBJECT-TYPE
      SYNTAX  Counter
      ACCESS  read-only
      STATUS  mandatory
      DESCRIPTION
"Indicates the total number of times CTS has moved from one state to
 another since statistics were last reset.

Ranges of Values: 0 - 65,535

Default Value: none"
      ::= { bopSapOprEntry 114 }


   bopStatOprDSRStateChanges OBJECT-TYPE
      SYNTAX  Counter
      ACCESS  read-only
      STATUS  mandatory
      DESCRIPTION
"Indicates the total number of times DSR has moved from one state to
 another since statistics were last reset.

Ranges of Values: 0 - 65,535

Default Value: none"
      ::= { bopSapOprEntry 115 }

   bopStatOprDRSStateChanges OBJECT-TYPE
      SYNTAX  Counter
      ACCESS  read-only
      STATUS  mandatory
      DESCRIPTION
"Indicates the total number of times DRS has moved from one state to
 another since statistics were last reset.

Ranges of Values: 0 - 65,535

Default Value: none"
      ::= { bopSapOprEntry 116 }

   bopStatOprTMStateChanges OBJECT-TYPE
      SYNTAX  Counter
      ACCESS  read-only
      STATUS  mandatory
      DESCRIPTION
"Indicates the total number of times TM has moved from one state to
 another since statistics were last reset.

Ranges of Values: 0 - 65,535

Default Value: none"
      ::= { bopSapOprEntry 117 }

   bopStatOprLLStateChanges OBJECT-TYPE
      SYNTAX  Counter
      ACCESS  read-only
      STATUS  mandatory
      DESCRIPTION
"Indicates the total number of times LL has moved from one state to
 another since statistics were last reset.

Ranges of Values: 0 - 65,535

Default Value: none"
      ::= { bopSapOprEntry 118 }

   bopStatOprRIStateChanges OBJECT-TYPE
      SYNTAX  Counter
      ACCESS  read-only
      STATUS  mandatory
      DESCRIPTION
"Indicates the total number of times RI has moved from one state to
 another since statistics were last reset.

Ranges of Values: 0 - 65,535

Default Value: none"
      ::= { bopSapOprEntry 119 }

   bopStatOprRLStateChanges OBJECT-TYPE
      SYNTAX  Counter
      ACCESS  read-only
      STATUS  mandatory
      DESCRIPTION
"Indicates the total number of times RL has moved from one state to
 another since statistics were last reset.

Ranges of Values: 0 - 65,535

Default Value: none"
      ::= { bopSapOprEntry 120 }

   bopStatOprPortResets OBJECT-TYPE
      SYNTAX  Counter
      ACCESS  read-only
      STATUS  mandatory
      DESCRIPTION
"Indicates the total number of port resets that have occurred at the port
 since statistics were last reset.

Ranges of Values: 0 - 65,535

Default Value: none"
      ::= { bopSapOprEntry 121 }

   bopStatOprRxGenError OBJECT-TYPE
      SYNTAX  Counter
      ACCESS  read-only
      STATUS  mandatory
      DESCRIPTION
"Indicates the total number of frames received in error since statistics were
 last reset, while 'bopSapOprPortDataGenerator' was set to 'enabled-verify'.

Ranges of Values: 0 - 65,535

Default Value: none"
      ::= { bopSapOprEntry 123 }

--  Planned Configuration and Control Table

--  The table describing:
--      parameters used to configure each BOP/COP port.
--
--      parameters required to configure traps at BOP/COP port.
--
--      parameters used to effect specific and immediate actions at each 
--      BOP/COP port.


bopSapAdmTable OBJECT-TYPE
   SYNTAX  SEQUENCE OF BopSapAdmEntry
   ACCESS  not-accessible
   STATUS  mandatory
   DESCRIPTION
"A table containing the planned configuration information about each BOP/COP 
 port."
   ::= { cxBOPIO 2 }


   bopSapAdmEntry OBJECT-TYPE
      SYNTAX  BopSapAdmEntry
      ACCESS  not-accessible
      STATUS  mandatory
      DESCRIPTION
"The planned configuration information for a specific BOP/COP port."
      INDEX { bopSapAdmNumber }
      ::= { bopSapAdmTable 1 }


   BopSapAdmEntry ::=
      SEQUENCE {
         bopSapAdmNumber
            INTEGER,
         bopSapAdmAlias
            Alias,
         bopSapAdmProtocol
            INTEGER,
         bopSapAdmPortClockSource
            INTEGER,
         bopSapAdmPortSpeed
            INTEGER,
         bopSapAdmPortDuplex
            INTEGER,
         bopSapAdmPortMaxFrameSize
            INTEGER,
         bopSapAdmPortDataEncoding
            INTEGER,
         bopSapAdmPortIdleCondition
            INTEGER,
         bopSapAdmPortPreAmbleLength
            INTEGER,
   		 bopSapAdmPortFlagSharing
            INTEGER, 
         bopSapAdmPortFilterMask
            INTEGER,
         bopSapAdmPortFilterAddress1
            INTEGER,
         bopSapAdmPortFilterAddress2
            INTEGER,
         bopSapAdmPortFilterAddress3
            INTEGER,
         bopSapAdmPortFilterAddress4
            INTEGER,
         bopSapAdmPortCrc
            INTEGER,
         bopSapAdmPortDtrUpTimer
            INTEGER,
         bopSapAdmPortTxWindow
            INTEGER,
         bopSapAdmPortThreshBandwidth
            INTEGER,     
         bopSapAdmPortDialMode
            INTEGER,
         bopSapAdmPortLoopback
            INTEGER,
         bopSapAdmPortSignalSamplingPeriod
            INTEGER,
         bopSapAdmPortDcdDtrSignalSamples
            INTEGER,
         bopSapAdmPortCtsRtsSignalSamples
            INTEGER,
         bopSapAdmPortDsrDrsSignalSamples
            INTEGER,
         bopSapAdmPortTmLlSignalSamples
            INTEGER,
         bopSapAdmPortRiRlSignalSamples
            INTEGER,
         bopSapAdmPortStatisticsTimer
            INTEGER,
         bopSapAdmPortCarrierAction
            INTEGER,
         bopSapAdmPortDataGenerator
            INTEGER,
         bopSapAdmPortGenFrames
            INTEGER,
         bopSapAdmPortGenFrameSize
            INTEGER,
         bopSapAdmPortGenFrameHeader
            INTEGER,
         bopSapAdmCodeSet
            INTEGER,
         bopSapAdmParity
            INTEGER,
         bopAdmPortTrap
            INTEGER,
         bopAdmTxClockTrap
            INTEGER
         }


   bopSapAdmNumber OBJECT-TYPE
      SYNTAX  INTEGER
      ACCESS  read-only
      STATUS  mandatory
      DESCRIPTION
"Defines the SAP ID using 2,3 or 4 digits. The first digit (A) is the slot #,
 the second digit (B) is the port #, and the remaining digits (CD) are the
 channel #.  If a 2 digit number is entered, digits CD are assumed to be 0 and
 are inserted automatically when reading object.  If a 3 digit number is
 entered, digit C is assumed to be 0 and is inserted automatically when
 reading object.

Ranges of Values for  A: 1-7 for CX900, 1-4 for CX1000
Ranges of Values for  B: 1-5 for CX900, 1-4 for CX1000
Ranges of Values for CD: 00-30

Default Value: not applicable"
      ::= { bopSapAdmEntry 1 }


   bopSapAdmAlias OBJECT-TYPE
      SYNTAX  Alias
      ACCESS  read-write
      STATUS  mandatory
      DESCRIPTION
"Determines the textual name uniquely identifying this SAP in the BOP Driver
 software layer.

Ranges of Values: 0-16 alphanumeric characters beginning with a 
non-numeric character

Default Value: undefined

Configuration Changed: administrative "
      ::= { bopSapAdmEntry 2 }



   bopSapAdmProtocol OBJECT-TYPE
      SYNTAX  INTEGER { 
               hdlc        (1),
               bsc3270     (2),
               borroughs   (3),
               sperry      (4),
               bsc3780     (5),
               aircat      (6)          
               }
      ACCESS  read-write
      STATUS  mandatory
      DESCRIPTION
"Determines if the port is HDLC or Bisync.
Only HDLC is supported by ISDN and T1/E1 ports.

Indicates in the operative
configuration the type of bisync protocol 
used by the controllers of the
port associated with this SAP. 

Options:
hdlc
bsc3270    = Bisync 3270 controllers
borroughs  = Borroughs controllers
sperry     = Sperry controllers
bsc3780    = Bisync 2780/3780 controllers
aircat     = aircat500 air traffic radar controllers
Default Value: hdlc"
--#STARTING-VERSION 2
      DEFVAL { hdlc }      
      ::= { bopSapAdmEntry 3 }


-- gap (1) for future parameter

   
bopSapAdmPortClockSource OBJECT-TYPE
      SYNTAX  INTEGER {
               internal   (1),
               external   (2),
               split      (3),
               slave      (4)
               }
      ACCESS  read-write
      STATUS  mandatory
      DESCRIPTION
"Determines the bit-rate clock source of the port.

Options:
internal (1): Tx and Rx clocks are internally generated

external (2): Tx and Rx clocks are externally supplied on separate pins

split (3): Tx clock is internally generated and Rx clock is externally supplied

slave (4): Tx and Rx clocks are externally supplied on the same pins

Note: Split clocking is not supported on ports in slots 5, 6 and 7 when the Data 
Expansion Module is installed.

Default Value: external (locked to internal for ISDN)

Configuration Changed: administrative "
      DEFVAL { external }
      ::= { bopSapAdmEntry 5 }


   bopSapAdmPortSpeed OBJECT-TYPE
      SYNTAX  INTEGER (375 .. 2048000)
      ACCESS  read-write
      STATUS  mandatory
      DESCRIPTION
"Indicates the input and output speed in bits per second of the port.

Note:
This value is meaningful only if 'bopSapAdmPortClockSource' is set to 
'internal' or to 'split'.

Ranges of Values: 
375 - 2,048,000 (locked at 16,000 for ISDN 'D' channel and at 64,000 for ISDN 
'B' channels) for slot/port/channel 11x-41x; 

300-256,000 for slot/port/channel 51x-71x.

1875 bps is the minimum speed supported on ports in slots 5, 6 and 7 when the 
Data Expansion Module is installed.

Default Value: 64,000

Configuration Changed: administrative "
      DEFVAL { 64000 }
      ::= { bopSapAdmEntry 6 }


   bopSapAdmPortDuplex OBJECT-TYPE
      SYNTAX  INTEGER {
               half            (1),
               full            (2)
               }
      ACCESS  read-write
      STATUS  mandatory
      DESCRIPTION
"Determines whether the port communicates simultaneously in both directions
 (full-duplex) or alternates between directions (half-duplex).

Options:
half (1): half-duplex

full (2): full-duplex (locked for ISDN)

Default Value: full

Configuration Changed: administrative "
      DEFVAL { full }
      ::= { bopSapAdmEntry 7 }


   bopSapAdmPortMaxFrameSize OBJECT-TYPE
      SYNTAX  INTEGER (32..9000)
      ACCESS  read-write
      STATUS  mandatory
      DESCRIPTION
"Determines the maximum frame size supported by the port.

Ranges of Values: 32-9000

Default Value: 1,600 (512 for ISDN)

Configuration Changed: administrative "
      DEFVAL { 1600 }
      ::= { bopSapAdmEntry 8 }


   bopSapAdmPortDataEncoding OBJECT-TYPE
      SYNTAX  INTEGER {
               nrz             (1),
               nrzi-mark       (2),
               nrzi-space      (3)
               }
      ACCESS  read-write
      STATUS  mandatory
      DESCRIPTION
"Determines the data formatting and encoding used by the port.

Options:
nrz (1): NRZ (locked for ISDN 'D' channel; ISDN 'B' channel can use only this 
value or NRZI-Space value)

nrzi-mark (2): NRZI-Mark

nrzi-space (3): NRZI-Space (ISDN 'B' channel can use only this value or NRZ 
value)

Note: Slot/port/channel 51x-71x can use only NRZ or NRZI-Space.

Default Value: nrz (1)

Configuration Changed: administrative "
      DEFVAL { nrz }
      ::= { bopSapAdmEntry 9 }


   bopSapAdmPortIdleCondition OBJECT-TYPE
      SYNTAX  INTEGER {
               flags      (1),
               marks      (2),
               as400      (3)
               }
      ACCESS  read-write
      STATUS  mandatory
      DESCRIPTION
"Determines the idle line condition supported by the port.

Options:
flags (1): flags

marks (2): marks

as400 (3): AS400

Default Value: flags

Configuration Changed: administrative "
      DEFVAL { flags }
      ::= { bopSapAdmEntry 10 }


   bopSapAdmPortPreAmbleLength OBJECT-TYPE
      SYNTAX  INTEGER (0 .. 16)
      ACCESS  read-write
      STATUS  mandatory
      DESCRIPTION
"Determines the minimum number of flags or sync pairs that will be inserted between frames
 by the port's transmitter.

For HDLC frames:
A value of zero causes flag sharing between frames.
A value of one means no flag sharing and zero flags inserted between frames.
A value of two means no flag sharing and one flag inserted between frames.
A value of three means no flag sharing and two flags inserted between frames.
Etc.

For Bisync frames:
A value of zero or one causes one sync pair to be inserted between frames.
A value of two causes two sync pairs to be inserted between frames.
A value of three causes three sync pairs to be inserted between frames.
Etc.

Ranges of Values: 0-16

Default Value: 1

Configuration Changed: administrative "

      DEFVAL { 1 }
      ::= { bopSapAdmEntry 11 }

   bopSapAdmPortFlagSharing OBJECT-TYPE
      SYNTAX  INTEGER {
               disabled        (1),
               enabled         (2)
               }
      ACCESS  read-write
      STATUS  obsolete
      DESCRIPTION
"Determines whether back-to-back transmit frames will have a flag in common
 This value is meaningful only if 'bopSapAdmPortPreAmbleLength' is set to zero.

Options:
disabled (1): back-to-back frames do not share flag

enabled (2): back-to-back frames share flag

Default Value: disabled

Configuration Changed: administrative "
      DEFVAL { disabled }
--#ENDING-VERSION 2
      ::= { bopSapAdmEntry 12 }


   bopSapAdmPortFilterMask OBJECT-TYPE
      SYNTAX  INTEGER (0 .. 255)
      ACCESS  read-write
      STATUS  obsolete
      DESCRIPTION
"Determines which bits of the 8-bit HDLC address will be used for address
 filtering.

Note:
When a bit is set to '1', the position of bits will be checked. When a bit is 
set to '0', it will not be checked.

Ranges of Values: 0-255

Default Value: 0

Configuration Changed: administrative "
      DEFVAL { 0 }
--#ENDING-VERSION 2
      ::= { bopSapAdmEntry 13 }


   bopSapAdmPortFilterAddress1 OBJECT-TYPE
      SYNTAX  INTEGER (0 .. 255)
      ACCESS  read-write
      STATUS  obsolete
      DESCRIPTION
"Determines one of four 8-bit addresses used for address filtering.

Ranges of Values: 0-255

Default Value: 126

Configuration Changed: administrative "
      DEFVAL { 126 }
--#ENDING-VERSION 2
      ::= { bopSapAdmEntry 14 }


   bopSapAdmPortFilterAddress2 OBJECT-TYPE
      SYNTAX  INTEGER (0 .. 255)
      ACCESS  read-write
      STATUS  obsolete
      DESCRIPTION
"Determines one of four 8-bit addresses used for address filtering.

Ranges of Values: 0-255

Default Value: 126

Configuration Changed: administrative "
      DEFVAL { 126 }
--#ENDING-VERSION 2
      ::= { bopSapAdmEntry 15 }


   bopSapAdmPortFilterAddress3 OBJECT-TYPE
      SYNTAX  INTEGER (0 .. 255)
      ACCESS  read-write
      STATUS  obsolete
      DESCRIPTION
"Determines one of four 8-bit addresses used for address filtering.

Ranges of Values: 0-255

Default Value: 126

Configuration Changed: administrative "
      DEFVAL { 126 }
--#ENDING-VERSION 2
      ::= { bopSapAdmEntry 16 }


   bopSapAdmPortFilterAddress4 OBJECT-TYPE
      SYNTAX  INTEGER (0 .. 255)
      ACCESS  read-write
      STATUS  obsolete
      DESCRIPTION
"Determines one of four 8-bit addresses used for address filtering.

Ranges of Values: 0-255

Default Value: 126

Configuration Changed: administrative "
      DEFVAL { 126 }
--#ENDING-VERSION 2
      ::= { bopSapAdmEntry 17 }


   bopSapAdmPortCrc OBJECT-TYPE
      SYNTAX  INTEGER {
               crc-ccitt    (1),
               crc-32       (2)
               }
      ACCESS  read-write
      STATUS  obsolete
      DESCRIPTION
"Determines which algorithm is used for error detection. 

Options:
crc-ccitt (1): CRC-ITU-T (uses X15+X12+X5+1 polynomial; ITU-T formerly CCITT) 
(locked for ISDN 'D' channel; can be selected for ISDN 'B' channel)

crc-32 (2): CRC-32 (for Ethernet; uses X32+X26+X23+X22+X16+X12+X11+ 
X10+X8+X7+X5+X4+X2+X+1) (can be selected for ISDN 'B' channel)

Default Value: crc-ccitt (1)

Configuration Changed: administrative "
      DEFVAL { crc-ccitt }
--#ENDING-VERSION 2
      ::= { bopSapAdmEntry 18 }


   bopSapAdmPortDtrUpTimer OBJECT-TYPE
      SYNTAX  INTEGER (0..65535)
      ACCESS  read-write
      STATUS  mandatory
      DESCRIPTION
"Determines the time in seconds that the port must wait for DCD
 (DTR if DCE) after raising DTR (DCD if DCE) to determine if a connection can
 be established.

Note: This value will be set to zero if the port does not support an application 
requiring it.

Ranges of Values: 0-65,535

Default Value: 0

Configuration Changed: administrative "
      DEFVAL { 0 }
      ::= { bopSapAdmEntry 19 }


   bopSapAdmPortTxWindow OBJECT-TYPE
      SYNTAX  INTEGER (1..255)
      ACCESS  read-write
      STATUS  mandatory
      DESCRIPTION
"Determines the maximum number of buffers that may be queued onto the port
 driver (for transmission) by the associated upper layer.
 For ISDN ports, the value is locked at 8.

Note:
When set to '255', the system automatically determines the number of buffers 
devoted to different kinds of traffic. When this object is set to a lesser 
value, the system compares this value with its own and uses the smaller. This 
object thereby provides a way to safeguard delay-sensitive voice traffic 
against such disruptions as bursty LAN traffic.

This value is locked to 255 for ISDN.

Ranges of Values: 1-255

Default Value: 255

Configuration Changed: administrative "
      DEFVAL {255}
      ::= { bopSapAdmEntry 20 }



   bopSapAdmPortThreshBandwidth OBJECT-TYPE
      SYNTAX  INTEGER (0..65535)
      ACCESS  read-write
      STATUS  mandatory
      DESCRIPTION
"Determines the value of the minimum critical bandwidth that will determine
whether Frame Relay should filter certain restricted types of packets or
not.

The value entered should be a multiple of 1 Kilo bits per second.

Ranges of Values: 0 - 65,535

Default Value: 0

Configuration Changed: operative "
      --#STARTING-VERSION 1
      DEFVAL {0}
      ::= { bopSapAdmEntry 21 }

   bopSapAdmPortDialMode OBJECT-TYPE
      SYNTAX  INTEGER {
               dial-in-only   (1),
               dial-out-only  (2),
               dial-in-out    (3)
               }
      ACCESS  read-write
      STATUS  mandatory
      DESCRIPTION
"Identifies the operation mode when setting up connections. 
Options:
dial-in-only   (1): Only accept incoming calls; Will not make any outgoing calls.
dial-out-only  (2): Only make outgoing calls; Will not accept any incoming calls.
dial-in-out    (3): Accept incoming calls and make outgoing calls. 

Configuration Changed: administrative "
      --#STARTING-VERSION 2
      DEFVAL { dial-in-out }
      ::= { bopSapAdmEntry 22 }

-- gap (5) for future parameters

   bopSapAdmPortLoopback OBJECT-TYPE
      SYNTAX  INTEGER {
               none            (1),
               local           (2),
               remote          (3),
               both            (4),
               isdn-uif-uif    (5),
               isdn-uif-idl2   (6),
               isdn-uif-framer (7),
               isdn-uif-external       (8)
               }
      ACCESS  read-write
      STATUS  mandatory
      DESCRIPTION
"Determines whether loopback is enabled and what kind of loopback is enabled.

Options:
none  (1): Loopback is not enabled

local (2): Local loopback is enabled (forces SAP associated with port to 
return outbound frames to the originating software layer without transmitting 
them)

remote (3): Remote loopback is enabled (forces the port to transmit 
immediately any frame received on the line, and also forces the associated 
SAP to deny communication with any upper software layer that requests service)

both (4): Both local and remote loopbacks are enabled.

isdn-uif-uif (5): ISDN loopback is enabled at U-Interface (forces TB1Q signal 
from a remote transmitter to pass through the entire U-Interface Transceiver 
before being transmitted back to the remote receiver)

isdn-uif-idl2 (6): ISDN loopback is enabled at IDL2 Controller (forces IDL2 
Controller to take in B and D channel data on IDL RX pin and send it out on 
IDL2 TX pin)

isdn-uif-framer (7): ISDN loopback is enabled at framer (forces B and D 
channel data in on D-in pin and M channel data in on SCP which together 
undergo framing and deframing functions before B and D channel data go out 
D-out pin and M channel data go out SCP)

isdn-uif-external (8): ISDN loopback is enabled at external line (forces TB1Q 
signal coming in on D-in pin to pass through Tx Driver pins, the U-Interface 
circuit and Rx input pins before recovering it and sending it out the D-out 
pin)

Default Value: none

Configuration Changed: administrative "
      DEFVAL { none }
      ::= { bopSapAdmEntry 28 }


   bopSapAdmPortSignalSamplingPeriod OBJECT-TYPE
      SYNTAX  INTEGER (3..100)
      ACCESS  read-write
      STATUS  mandatory
      DESCRIPTION

"Determines the sampling period in 100 millisecond increments used to sample 
detectable signals.

Ranges of Values: 3-100 (locked at 5 for ISDN)

Default Value: 5

Configuration Changed: administrative "
      DEFVAL { 5 }
      ::= { bopSapAdmEntry 29 }


   bopSapAdmPortDcdDtrSignalSamples OBJECT-TYPE
      SYNTAX  INTEGER (1..30)
      ACCESS  read-write
      STATUS  mandatory
      DESCRIPTION
"Determines the active number of sampling periods that this port must wait
 before validating DCD (DTR if DCE).
 This object has no meaning in ISDN connections.

Ranges of Values: 1-30

Default Value: 3

Configuration Changed: administrative "
      DEFVAL { 3 }
      ::= { bopSapAdmEntry 30 }


   bopSapAdmPortCtsRtsSignalSamples OBJECT-TYPE
      SYNTAX  INTEGER (1..30)
      ACCESS  read-write
      STATUS  mandatory
      DESCRIPTION
"Determines the active number of sampling periods that this port must wait
 before validating CTS (RTS if DCE).
 This object has no meaning in ISDN connections.

Ranges of Values: 1-30

Default Value: 3

Configuration Changed: administrative "
      DEFVAL { 3 }
      ::= { bopSapAdmEntry 31 }


   bopSapAdmPortDsrDrsSignalSamples OBJECT-TYPE
      SYNTAX  INTEGER (1..30)
      ACCESS  read-write
      STATUS  mandatory
      DESCRIPTION
"Determines the active number of sampling periods that this port must wait
 before validating DSR (DRS if DCE).
 This object has no meaning in ISDN connections.

Ranges of Values: 1-30

Default Value: 3

Configuration Changed: administrative "
      DEFVAL { 3 }
      ::= { bopSapAdmEntry 32 }


   bopSapAdmPortTmLlSignalSamples OBJECT-TYPE
      SYNTAX  INTEGER (1..30)
      ACCESS  read-write
      STATUS  mandatory
      DESCRIPTION
"Determines the active number of sampling periods that this port must wait
 before validating TM (LL if DCE).
 This object has no meaning in ISDN connections.

Ranges of Values: 1-30

Default Value: 3

Configuration Changed: administrative "
      DEFVAL { 3 }
      ::= { bopSapAdmEntry 33 }


   bopSapAdmPortRiRlSignalSamples OBJECT-TYPE
      SYNTAX  INTEGER (1..30)
      ACCESS  read-write
      STATUS  mandatory
      DESCRIPTION
"Determines the active number of sampling periods that this port must wait
 before validating RI (RL if DCE).
 This object has no meaning in ISDN connections.

Ranges of Values: 1-30

Default Value: 3

Configuration Changed: administrative "
      DEFVAL { 3 }
      ::= { bopSapAdmEntry 34 }


   bopSapAdmPortStatisticsTimer OBJECT-TYPE
      SYNTAX  INTEGER (0..60)
      ACCESS  read-write
      STATUS  mandatory
      DESCRIPTION
"Determines the period in seconds during which BOP performance statistics are
 measured.

Note: If set to zero, BOP performance statistics are not measured.

Ranges of Values: 0-60

Default Value: 0

Configuration Changed: administrative "
      DEFVAL { 0 }
      ::= { bopSapAdmEntry 35 }


   bopSapAdmPortCarrierAction OBJECT-TYPE
      SYNTAX  INTEGER {
               disabled  (1),
               enabled   (2)
               }
      ACCESS  read-write
      STATUS  mandatory
      DESCRIPTION
"Determines if the port driver informs it's associated upper layer that
service is no longer available following loss of DCD if DTE, or DTR if DCE.

Options:
disabled (1): do not notify upper layer of service loss (locked for ISDN)

enabled (2): inform upper layer of service loss

Default Value: enabled

Configuration Changed: administrative "
      DEFVAL { enabled }
      ::= { bopSapAdmEntry 36 }


   bopSapAdmPortDataGenerator OBJECT-TYPE
      SYNTAX  INTEGER {
               disabled        (1),
               enabled         (2),
               enabled-verify  (3)
               }
      ACCESS  read-write
      STATUS  mandatory
      DESCRIPTION
"Determines whether the port will act as an internal data generator.

Options:
disabled  (1): port is not a data generator

enabled (2): port is a data generator

enabled-verify (3): port is a data generator and its incoming data is 
verified

Default Value: disabled

Configuration Changed: administrative "
      DEFVAL { disabled }
      ::= { bopSapAdmEntry 37 }


   bopSapAdmPortGenFrames OBJECT-TYPE
      SYNTAX  INTEGER (0..255)
      ACCESS  read-write
      STATUS  mandatory
      DESCRIPTION
"Determines the number of frames that the port configured as an internal data
 generator will generate at one time.

Ranges of Values: 0-255

Note: When set to zero, frames are generated continuously

Default Value: 1

Configuration Changed: administrative "
      DEFVAL { 1 }
      ::= { bopSapAdmEntry 38 }


   bopSapAdmPortGenFrameSize OBJECT-TYPE
      SYNTAX  INTEGER (2..65535)
      ACCESS  read-write
      STATUS  mandatory
      DESCRIPTION
"Determines the size in bytes of internally generated frames (excluding flags).

Ranges of Values: 2-65535

Note: When set to zero, frames are sized randomly.

Default Value: 128

Configuration Changed: administrative "
      DEFVAL { 128 }
      ::= { bopSapAdmEntry 39 }


   bopSapAdmPortGenFrameHeader OBJECT-TYPE
      SYNTAX  INTEGER (0..65535)
      ACCESS  read-write
      STATUS  mandatory
      DESCRIPTION
"Determines the 16-bit header that will be inserted in the first two octets
 after the opening flag of each internally generated frame.

Ranges of Values: 0-65, 535

Default Value: 1

Configuration Changed: administrative "
      DEFVAL { 1 }
      ::= { bopSapAdmEntry 40 }


-- gap (4) for future parameters

        bopSapAdmCodeSet OBJECT-TYPE
        SYNTAX  INTEGER {
        			other				(1),
                    ebcdic              (2),  
                    ascii               (3) 
                    }
        ACCESS  read-write
        STATUS  mandatory
        DESCRIPTION
"Determines in the administrative
configuration the code used by the port 
associated with this SAP to communicate 
to the Bisync device. 

Options:

other
ebcdic = EBCDIC
ascii = ASCII


Default value: ebcdic

Configuration changed: administrative

Further action: system reset to change"
        DEFVAL { ebcdic } 
--#STARTING-VERSION 2
        ::= { bopSapAdmEntry 45 }

   bopSapAdmParity OBJECT-TYPE
    SYNTAX  INTEGER {
        none    (1),  
        odd     (2),
        even    (3),
        space   (4),
        mark    (5)
        }
    ACCESS  read-write
    STATUS  mandatory
    DESCRIPTION
"Indicates the parity used to communicate with the Bisync device
    Options:
        (1) none:  No parity
        (2) odd:   Odd parity
        (3) even:  Even parity
        (4) space: Low parity (always 0's)
        (5) mark:  High parity (always 1's)
        
Default value: none"
--#STARTING-VERSION 2
      DEFVAL { none }
      ::= { bopSapAdmEntry 46 }

   bopAdmPortTrap OBJECT-TYPE
      SYNTAX  INTEGER {
               disabled   (1),
               enabled    (2)
               }
      ACCESS  read-write
      STATUS  mandatory
      DESCRIPTION
"Determines whether this port produces a 'bopPortStatusChange' trap which
 can be retrieved by SNMP network management.

Options:
disabled (1): do not produce port status trap

enabled (2): produce port status trap

Default Value: disabled (1)

Configuration Changed: administrative "
      DEFVAL { disabled }
      ::= { bopSapAdmEntry 47 }


   bopAdmTxClockTrap OBJECT-TYPE
      SYNTAX  INTEGER {
               disabled   (1),
               enabled    (2)
               }
      ACCESS  read-write
      STATUS  mandatory
      DESCRIPTION
"Determines whether this port produces a 'bopTxClockStatusChange' trap which
 can be retrieved by SNMP network management.

Options:
disabled (1): do not produce transmit clock status trap

enabled (2): produce transmit clock status trap

Default Value: disabled (1)

Configuration Changed: administrative "
      DEFVAL { disabled }
      ::= { bopSapAdmEntry 48 }


bopMibLevel OBJECT-TYPE
   SYNTAX  INTEGER
   ACCESS  read-only
   STATUS  mandatory
   DESCRIPTION
"Used to determine current MIB module release supported
by the agent. Object is in decimal."
   DEFVAL { 0 }
   --#STARTING-VERSION 1
   ::= { cxBOPIO 3 }





-- Service access point related traps


bopPortStatusChange TRAP-TYPE
   ENTERPRISE      cxBOPIO
   VARIABLES               {       bopSapOprNumber,
               bopStatOprPortState
            }
   DESCRIPTION
"Indicates that the hardware port associated with the service access point 
has changed state. It has toggled between any of the states defined in 
object bopStatOprPortState."
   ::= 1


bopTxClockStatusChange TRAP-TYPE
   ENTERPRISE      cxBOPIO
   VARIABLES               {       bopSapOprNumber,
               bopStatOprTxClockState
            }
   DESCRIPTION
"Indicates that the transmit clock at hardware port associated with the 
service access point has changed state. It has toggled between any of the 
states defined in object bopStatOprTxClockState."
   ::= 2


END
