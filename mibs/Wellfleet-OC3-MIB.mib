Wellfleet-OC3-MIB DEFINITIONS ::= BEGIN

-- Created 1998


    IMPORTS

      OBJECT-TYPE
        FROM RFC-1212
      DisplayString
        FROM RFC1213-MIB
      wfSonetGroup
        FROM Wellfleet-COMMON-MIB;

    wfOc3ConfigTable OBJECT-TYPE
        SYNTAX	SEQUENCE OF WfOc3ConfigEntry
        ACCESS	not-accessible
        STATUS	mandatory
        DESCRIPTION
                "Statistics for the SONET medium table"
        ::= { wfSonetGroup 12 }

    wfOc3ConfigEntry OBJECT-TYPE
        SYNTAX	WfOc3ConfigEntry
        ACCESS	not-accessible
        STATUS	mandatory
        DESCRIPTION
                "An entry in the medium table"
        INDEX	{ wfOc3ConfigIndex }
        ::= { wfOc3ConfigTable 1 }

    WfOc3ConfigEntry ::= SEQUENCE {
    	    wfOc3ConfigDelete
    		INTEGER,
    	    wfOc3ConfigIndex
    		INTEGER,
    	    wfOc3ConfigType
    		INTEGER,
    	    wfOc3ConfigTimeElapsed
    		INTEGER,
    	    wfOc3ConfigValidIntervals
    		INTEGER,
    	    wfOc3ConfigLineCoding
    		INTEGER,
    	    wfOc3ConfigLineType
    		INTEGER,
    	    wfOc3ConfigCircuitIdentifier
    		DisplayString
        }

    wfOc3ConfigDelete OBJECT-TYPE
        SYNTAX  INTEGER {
                    created(1),
                    deleted(2)
                }
        ACCESS  read-write
        STATUS  mandatory
        DESCRIPTION
                "Create/Delete parameter"
        DEFVAL  { created }
        ::= { wfOc3ConfigEntry 1 }

    wfOc3ConfigIndex OBJECT-TYPE
        SYNTAX	INTEGER
        ACCESS	read-only
        STATUS	mandatory
        DESCRIPTION
                "Index for this physical Sonet interface."
        ::= { wfOc3ConfigEntry 2 }

    wfOc3ConfigType OBJECT-TYPE
        SYNTAX	INTEGER
        ACCESS	read-only
        STATUS	mandatory
        DESCRIPTION
                "This variable identifies whether a SONET or a SDH signal is used
                across this interface."
        ::= { wfOc3ConfigEntry 3 }

    wfOc3ConfigTimeElapsed OBJECT-TYPE
        SYNTAX	INTEGER
        ACCESS	read-only
        STATUS	mandatory
        DESCRIPTION
                "The number of seconds that have elapsed since the beginning of
                the current error-measurement period."
        ::= { wfOc3ConfigEntry 4 }

    wfOc3ConfigValidIntervals OBJECT-TYPE
        SYNTAX	INTEGER
        ACCESS	read-only
        STATUS	mandatory
        DESCRIPTION
                "The number of previous intervals for which valid data has been stored."
        ::= { wfOc3ConfigEntry 5 }

    wfOc3ConfigLineCoding OBJECT-TYPE
        SYNTAX	INTEGER {
    		    other(1),
    		    b3zs(2),
    		    cmi(3),
    		    nrz(4),
    		    rz(5)
    		}
        ACCESS	read-write
        STATUS	mandatory
        DESCRIPTION
                "This variable describes the line coding for this interface."
        DEFVAL	{ nrz }
        ::= { wfOc3ConfigEntry 6 }

    wfOc3ConfigLineType OBJECT-TYPE
        SYNTAX	INTEGER {
    		    other(1),
    		    shortsinglemode(2),
    		    longsinglemode(3),
    		    multimode(4),
    		    coax(5),
    		    utp(6)
    		}
        ACCESS	read-write
        STATUS	mandatory
        DESCRIPTION
                "This variable describes the line type for this interface."
        DEFVAL	{ shortsinglemode }
        ::= { wfOc3ConfigEntry 7 }

    wfOc3ConfigCircuitIdentifier OBJECT-TYPE
        SYNTAX	DisplayString
        ACCESS	read-only
        STATUS	mandatory
        DESCRIPTION
                "This variable contains the transmission vendor's circuit identifier."
        ::= { wfOc3ConfigEntry 8 }


    END  -- Wellfleet-OC3-MIB
