AIDIALOUT-MIB DEFINITIONS ::=  BEGIN

-- Applied Innovation Dialout MIB definitions

IMPORTS
	MODULE-IDENTITY, OBJECT-TYPE, enterprises
			FROM SNMPv2-SMI
	DisplayString, TruthValue
			FROM SNMPv2-TC;

	PositiveInteger    ::= INTEGER (1..2147483647)

	aii OBJECT IDENTIFIER ::= {enterprises 539}

aiDialOut MODULE-IDENTITY
	LAST-UPDATED "9909151700Z"
	ORGANIZATION "Applied Innovation Inc."
	CONTACT-INFO "Engineering MIB Administrator
   					Postal: Applied Innovation Inc.
						5800 Innovation Drive
						Dublin, Ohio 43017-3271

					Tel:    614-798-2000
					Fax:    614-798-1770
					Email:  snmp@aiinet.com"
	DESCRIPTION "MIB module for Dialout Modem.."
	::= {aii 36}

--=========================================================================
aiDialOutTable OBJECT-TYPE
	SYNTAX		SEQUENCE OF AIDialOutEntry
	MAX-ACCESS	not-accessible
	STATUS		current
	DESCRIPTION
		"Table of dialout information indexed by link number."
	::= {aiDialOut 1}

aiDialOutEntry OBJECT-TYPE
	SYNTAX		AIDialOutEntry
	MAX-ACCESS	not-accessible
	STATUS		current
	DESCRIPTION	"Entry of aiDialOutTable."
	INDEX		{aiDialOutLinkNumber}
	::= {aiDialOutTable 1}

AIDialOutEntry ::= SEQUENCE {
   aiDialOutLinkNumber           PositiveInteger,
   aiDialOutStatus               TruthValue,
   aiDialOutPrimaryDialString    DisplayString,
   aiDialOutSecondaryDialString  DisplayString,
   aiDialOutTimeOut              INTEGER,
   aiDialOutAttempts             INTEGER,
   aiDialOutInterval             INTEGER
}

aiDialOutLinkNumber OBJECT-TYPE
	SYNTAX		PositiveInteger
	MAX-ACCESS	read-only
	STATUS		current
	DESCRIPTION	"Link number to which this table row applies."
	::= {aiDialOutEntry 1}

aiDialOutStatus OBJECT-TYPE
	SYNTAX		TruthValue
	MAX-ACCESS	read-write
	STATUS		current
	DESCRIPTION
		"Dial Out Modem Status."
	::= {aiDialOutEntry 2}

aiDialOutPrimaryDialString OBJECT-TYPE
	SYNTAX		DisplayString
	MAX-ACCESS	read-write
	STATUS		current
	DESCRIPTION
		"Primary Dial Out String.	Maximum length is 80 characters."
	::= {aiDialOutEntry 3}

aiDialOutSecondaryDialString OBJECT-TYPE
	SYNTAX		DisplayString
	MAX-ACCESS	read-write
	STATUS		current
	DESCRIPTION
		"Secondary Dial Out String.	Maximum length is 80 characters."
	::= {aiDialOutEntry 4}

aiDialOutTimeOut OBJECT-TYPE
	SYNTAX		INTEGER (5..300)
	UNITS		"seconds"
	MAX-ACCESS	read-write
	STATUS		current
	DESCRIPTION
		"Dialing time-out."
	::= {aiDialOutEntry 5}

aiDialOutAttempts OBJECT-TYPE
	SYNTAX		INTEGER (1..10)
	UNITS		"seconds"
	MAX-ACCESS	read-write
	STATUS		current
	DESCRIPTION
		"Dialing attempts."
	::= {aiDialOutEntry 6}

aiDialOutInterval OBJECT-TYPE
	SYNTAX		INTEGER (0..300)
	UNITS		"seconds"
	MAX-ACCESS	read-write
	STATUS		current
	DESCRIPTION
		"Interval between dialing."
	::= {aiDialOutEntry 7}

END
