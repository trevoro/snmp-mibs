-- *****************************************************************************
-- Juniper-IPV6-PROFILE-MIB
--
-- Juniper Networks Enterprise MIB
--   IPv6 Profile MIB
--
-- Copyright (c) 2003 Juniper Networks, Inc.  All Rights Reserved.
-- *****************************************************************************

Juniper-IPV6-PROFILE-MIB  DEFINITIONS ::= BEGIN

IMPORTS
    MODULE-IDENTITY, OBJECT-TYPE, Integer32, Unsigned32
        FROM SNMPv2-SMI
    DisplayString
        FROM SNMPv2-TC
    MODULE-COMPLIANCE, OBJECT-GROUP
        FROM SNMPv2-CONF
    InetAddressIPv6
        FROM INET-ADDRESS-MIB
    juniMibs
        FROM Juniper-MIBs
    JuniEnable, JuniName, JuniSetMap
        FROM Juniper-TC;

juniIpv6ProfileMIB  MODULE-IDENTITY
    LAST-UPDATED "200309291758Z"  -- 29-Sep-03 01:58 PM EDT
    ORGANIZATION "Juniper Networks"
    CONTACT-INFO
        "       Juniper Networks, Inc.
        Postal: 10 Technology Park Drive
                Westford MA  01886-3146
                USA
        Tel:    +1 978 589 5800
        Email:  mib@Juniper.net"
    DESCRIPTION
        "The IPv6 Profile MIB for the Juniper Networks enterprise."
    -- Revision History
    REVISION    "200309291758Z"  -- 29-Sep-03 01:58 PM EDT  - JUNOSe 5.1
    DESCRIPTION
        "Initial version of this MIB module."
    ::= { juniMibs 68 }


-- +++++++++++++++++++++++++++++++++++++++++++++++++++++++++++++++++++++++++++++
-- Managed object groups
-- +++++++++++++++++++++++++++++++++++++++++++++++++++++++++++++++++++++++++++++
juniIpv6ProfileObjects  OBJECT IDENTIFIER ::= { juniIpv6ProfileMIB 1 }
juniIpv6Profile         OBJECT IDENTIFIER ::= { juniIpv6ProfileObjects 1 }


-- +++++++++++++++++++++++++++++++++++++++++++++++++++++++++++++++++++++++++++++
-- Managed objects for IPv6 Profiles
-- +++++++++++++++++++++++++++++++++++++++++++++++++++++++++++++++++++++++++++++
--
-- This MIB defines configuration profile structure for IPv6 interfaces.
-- The creation/deletion of profiles and mapping of profile names to profile
-- indices is coordinated in the Juniper-PROFILE-MIB.
--
--
-- The IPv6 Profile Table
--
juniIpv6ProfileTable OBJECT-TYPE
    SYNTAX      SEQUENCE OF JuniIpv6ProfileEntry
    MAX-ACCESS  not-accessible
    STATUS      current
    DESCRIPTION
        "The entries in this table describe profiles for configuring IP
        interfaces.

        Entries in this table are created/deleted as a side-effect of
        corresponding operations to the juniProfileNameTable in the
        Juniper-PROFILE-MIB."
    ::= { juniIpv6Profile 1 }

juniIpv6ProfileEntry OBJECT-TYPE
    SYNTAX      JuniIpv6ProfileEntry
    MAX-ACCESS  not-accessible
    STATUS      current
    DESCRIPTION
        "A profile describing configuration of an IPv6 interface."
    INDEX     { juniIpv6ProfileId }
    ::= { juniIpv6ProfileTable 1 }

JuniIpv6ProfileEntry ::= SEQUENCE {
    juniIpv6ProfileId                  Unsigned32,
    juniIpv6ProfileSetMap              JuniSetMap,
    juniIpv6ProfileRouterName          JuniName,
    juniIpv6ProfileIpv6Addr            InetAddressIPv6,
    juniIpv6ProfileIpv6MaskLen         Integer32,
    juniIpv6ProfileMtu                 Integer32,
    juniIpv6ProfileSrcAddrValidEnable  JuniEnable,
    juniIpv6ProfileInheritNumString    DisplayString }

juniIpv6ProfileId OBJECT-TYPE
    SYNTAX      Unsigned32
    MAX-ACCESS  not-accessible
    STATUS      current
    DESCRIPTION
        "The integer identifier associated with this profile.  A value for this
        identifier is determined by locating or creating a profile name in the
        juniProfileNameTable."
    ::= { juniIpv6ProfileEntry 1 }

juniIpv6ProfileSetMap OBJECT-TYPE
    SYNTAX      JuniSetMap
    MAX-ACCESS  read-write
    STATUS      current
    DESCRIPTION
        "A bitmap representing which objects in this entry have been explicitly
        configured.  See the definition of the JuniSetMap TEXTUAL-CONVENTION for
        details of use.

        The INDEX object(s) and this object are excluded from representation
        (i.e. their bits are never set).

        When a SET request does not explicitly configure JuniSetMap, bits in
        JuniSetMap are set as a side-effect of configuring other profile
        attributes in the same entry.

        If, however, a SET request explicitly configures JuniSetMap, the
        explicitly configured value overrides 1) any previous bit settings, and
        2) any simultaneous 'side-effect' settings that would otherwise occur.

        Once set, bits can only be cleared by explicitly configuring
        JuniSetMap."
    ::= { juniIpv6ProfileEntry 2 }

juniIpv6ProfileRouterName OBJECT-TYPE
    SYNTAX      JuniName
    MAX-ACCESS  read-write
    STATUS      current
    DESCRIPTION
        "The virtual router to which an IPv6 interface configured by this
        profile will be assigned, if other mechanisms do not otherwise specify a
        virtual router assignment."
    DEFVAL    { "" }
    ::= { juniIpv6ProfileEntry 3 }

juniIpv6ProfileIpv6Addr OBJECT-TYPE
    SYNTAX      InetAddressIPv6
    MAX-ACCESS  read-write
    STATUS      current
    DESCRIPTION
        "An IPv6 address to be used by an IPv6 interface configured by this
        profile.  This object will have a value of 0::0 for an unnumbered
        interface."
    DEFVAL    { '00000000000000000000000000000000'H }
    ::= { juniIpv6ProfileEntry 4 }

juniIpv6ProfileIpv6MaskLen OBJECT-TYPE
    SYNTAX      Integer32 (0..128)
    MAX-ACCESS  read-write
    STATUS      current
    DESCRIPTION
        "An IPv6 address mask length to be used by an IPv6 interface configured
        by this profile.  This object will have a value of 0 for an unnumbered
        interface."
    DEFVAL    { 0 }
    ::= { juniIpv6ProfileEntry 5 }

juniIpv6ProfileMtu OBJECT-TYPE
    SYNTAX      Integer32 (0|1280..10240)
    MAX-ACCESS  read-write
    STATUS      current
    DESCRIPTION
        "The configured MTU size for this IPv6 network interface.  If set to
        zero, the default MTU size, as determined by the underlying network
        media, is used."
    DEFVAL    { 0 }
    ::= { juniIpv6ProfileEntry 6 }

juniIpv6ProfileSrcAddrValidEnable OBJECT-TYPE
    SYNTAX      JuniEnable
    MAX-ACCESS  read-write
    STATUS      current
    DESCRIPTION
        "Enable/disable whether source addresses in received IPv6 packets are
        validated.  Validation is performed by looking up the source IPv6
        address in the routing database and determining whether the packet
        arrived on the expected interface; if not, the packet is discarded."
    DEFVAL    { disable }
    ::= { juniIpv6ProfileEntry 7 }

juniIpv6ProfileInheritNumString OBJECT-TYPE
    SYNTAX      DisplayString (SIZE(0..80))
    MAX-ACCESS  read-write
    STATUS      current
    DESCRIPTION
        "The text identifier of the numbered interface, associated with the
        specified virtual router, whose IPv6 address is used as the source
        address when transmitting IPv6 packets on unnumbered remote access user
        links.  Types/formats/examples for this string include:

            Loopback
            loopback <id>
            'loopback 0'

            ATM Virtual Circuit
            atm <slot>/<port>.<distinguisher>
            'atm 3/1.100'

            Ethernet
            { fastEthernet | gigabitEthernet } <slot>/<port>
            'fastEthernet 3/0'
            'gigabitEthernet 3/0'

            Ethernet VLAN
            { fastEthernet | gigabitEthernet } <slot>/<port>:<vlanID>
            'fastEthernet 3/0:1000'
            'gigabitEthernet 3/0:1000'

            Channelized Serial
            serial <slot>/<port>:<channelSpecifier>[/<channelSpecifier>]*
            'serial 3/0:4'            (T1/E1)
            'serial 3/0:2/4'          (T3/E3)
            'serial 3/0:2/1/1/4'      (OC3/OC12 - channelized DS3)
            'serial 3/0:2/1/1/1/4'    (OC3/OC12 - virtual tributaries)

        Other formats may be supported over time.

        An empty string indicates the referenced interface is unspecified, e.g.,
        when this IPv6 interface is numbered."
    DEFVAL    { "" }
    ::= { juniIpv6ProfileEntry 8 }


-- +++++++++++++++++++++++++++++++++++++++++++++++++++++++++++++++++++++++++++++
-- Notifications
-- +++++++++++++++++++++++++++++++++++++++++++++++++++++++++++++++++++++++++++++
-- No notifications are defined in this MIB.  Placeholders follow.
-- juniIpv6ProfileTrapControl  OBJECT IDENTIFIER ::= { juniIpv6ProfileMIB 2 }
-- juniIpv6ProfileTraps        OBJECT IDENTIFIER ::= { juniIpv6ProfileMIB 3 }
-- juniIpv6ProfileTrapPrefix   OBJECT IDENTIFIER ::= { juniIpv6ProfileTraps 0 }


-- +++++++++++++++++++++++++++++++++++++++++++++++++++++++++++++++++++++++++++++
-- Conformance information
-- +++++++++++++++++++++++++++++++++++++++++++++++++++++++++++++++++++++++++++++
juniIpv6ProfileMIBConformance
             OBJECT IDENTIFIER ::= { juniIpv6ProfileMIB 4 }
juniIpv6ProfileMIBCompliances
             OBJECT IDENTIFIER ::= { juniIpv6ProfileMIBConformance 1 }
juniIpv6ProfileMIBGroups
             OBJECT IDENTIFIER ::= { juniIpv6ProfileMIBConformance 2 }


--
-- compliance statements
--
juniIpv6ProfileCompliance  MODULE-COMPLIANCE
    STATUS      current
    DESCRIPTION
        "Compliance statement for systems supporting IPv6 configuration
        profiles."
    MODULE   -- this module
        MANDATORY-GROUPS {
            juniIpv6ProfileGroup }
    ::= { juniIpv6ProfileMIBCompliances 1 }                        -- JUNOSe 5.1

--
-- units of conformance
--
juniIpv6ProfileGroup  OBJECT-GROUP
    OBJECTS {
        juniIpv6ProfileSetMap,
        juniIpv6ProfileRouterName,
        juniIpv6ProfileIpv6Addr,
        juniIpv6ProfileIpv6MaskLen,
        juniIpv6ProfileMtu,
        juniIpv6ProfileSrcAddrValidEnable,
        juniIpv6ProfileInheritNumString }
    STATUS      current
    DESCRIPTION
        "The basic collection of objects providing management of IPv6 Profile
        functionality in a Juniper product."
    ::= { juniIpv6ProfileMIBGroups 1 }                             -- JUNOSe 5.1

END
