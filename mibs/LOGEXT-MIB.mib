LOGEXT-MIB 

   --FORCE-INCLUDE <mib.h>
   --FORCE-INCLUDE <snmpdefs.h>
   --FORCE-INCLUDE <snmpstat.h>
   --FORCE-INCLUDE "mibproto.h"
 
	DEFINITIONS ::= BEGIN

	IMPORTS
		MODULE-IDENTITY, OBJECT-TYPE, IpAddress
			FROM SNMPv2-SMI
		RowStatus,DisplayString
			FROM SNMPv2-TC
		logExt
			FROM APENT-MIB;

--LOGEXT MIB

    apLogExtMib MODULE-IDENTITY
	   LAST-UPDATED "9707202000Z" -- Wed July 20 20:00:00 EST 1997
	   ORGANIZATION "ArrowPoint Communications Inc."
	   CONTACT-INFO
	   "                Steven Colby
	   Postal:               ArrowPoint Communications Inc.
				                 50 Nagog Park
				                 Acton, Massachusetts 01720
	   Tel:                   +1 978-206-3000  option 1
	   E-Mail:                support@arrowpoint.com"
       DESCRIPTION
	  "The MIB module used to describe the ArrowPoint Communications
	  logging functionality"
      ::= { logExt 1}


apLogFileName OBJECT-TYPE
	SYNTAX			DisplayString (SIZE(0..32))
	MAX-ACCESS		read-write
	STATUS			current
	DESCRIPTION
		""
	::= { logExt 2}

apLogBufferSize OBJECT-TYPE
	SYNTAX			INTEGER (0..64000)
	MAX-ACCESS		read-write
	STATUS			current
	DESCRIPTION
		""
	::= { logExt 3}

apLogHostTable OBJECT-TYPE
	SYNTAX          SEQUENCE OF APLOGHostEntry
	MAX-ACCESS      not-accessible
	STATUS          current
	DESCRIPTION
		""
	::= { logExt 4}


apLogCmds OBJECT-TYPE
	SYNTAX      INTEGER {
                             disable(0),
                             enable(1)
                            }
	MAX-ACCESS  read-write
	STATUS      current
	DESCRIPTION
	       "Control of command logging"
	DEFVAL {disable}
	::= { logExt 5}


apLogHostEntry OBJECT-TYPE
	SYNTAX          APLOGHostEntry
	MAX-ACCESS      not-accessible
	STATUS          current
	DESCRIPTION
		""
	INDEX   { apLogHostIpAddress }
	::= { apLogHostTable 1 }

APLOGHostEntry ::= SEQUENCE {
		apLogHostIpAddress     IpAddress,
		apLogHostFacility	   INTEGER,
		apLogHostStatus        RowStatus
}

apLogHostIpAddress OBJECT-TYPE
	SYNTAX          IpAddress
    MAX-ACCESS      read-create
	STATUS          current
	DESCRIPTION     
			"The ip address of the syslog daemon"
	::= { apLogHostEntry 1}

apLogHostFacility OBJECT-TYPE
	SYNTAX			INTEGER (0..7)
	MAX-ACCESS		read-create
	STATUS			current
	DESCRIPTION
		""
	::= { apLogHostEntry 2 }

apLogHostStatus OBJECT-TYPE
	SYNTAX          RowStatus
	MAX-ACCESS      read-create
	STATUS          current
	DESCRIPTION      
		"Status entry for this row "
	::= {apLogHostEntry 3}


apLogSubSystemTable OBJECT-TYPE
	SYNTAX          SEQUENCE OF APLOGSubSystemEntry
	MAX-ACCESS      not-accessible
	STATUS          current
	DESCRIPTION
		""
	::= { logExt 7 }

apLogSubSystemEntry OBJECT-TYPE
	SYNTAX          APLOGSubSystemEntry
	MAX-ACCESS      not-accessible
	STATUS          current
	DESCRIPTION
		""
	INDEX   { apLogSubSystemName}
	::= { apLogSubSystemTable 1 }

APLOGSubSystemEntry ::= SEQUENCE {
		apLogSubSystemName      DisplayString,
		apLogSubSystemLevel     INTEGER
}

apLogSubSystemName OBJECT-TYPE
	SYNTAX          DisplayString (SIZE(1..10))
    MAX-ACCESS      read-only
	STATUS          current
	DESCRIPTION     
			""
	::= { apLogSubSystemEntry 1}

apLogSubSystemLevel OBJECT-TYPE
	SYNTAX          INTEGER {
							fatal(0),
							alert(1),
							critical(2),
							error(3),
							warning(4),
							notice(5),
							info(6),
							debug(7),
							off(8)
							}
	MAX-ACCESS      read-write
	STATUS          current
	DESCRIPTION      
		""
	::= {apLogSubSystemEntry 2}

apLogSendMailTable OBJECT-TYPE
	SYNTAX          SEQUENCE OF APLOGSendMailEntry
	MAX-ACCESS      not-accessible
	STATUS          current
	DESCRIPTION
		""
	::= { logExt 8 }

apLogSendMailEntry OBJECT-TYPE
	SYNTAX          APLOGSendMailEntry
	MAX-ACCESS      not-accessible
	STATUS          current
	DESCRIPTION
		""
	INDEX   { apLogRecipientName }
	::= { apLogSendMailTable 1 }

APLOGSendMailEntry ::= SEQUENCE {
		apLogRecipientAddress		IpAddress,
		apLogRecipientName			DisplayString,
		apLogSendMailLevel			INTEGER,
		apLogSendMailStatus			RowStatus,
        apLogSendMailDomain         DisplayString
}

apLogRecipientAddress OBJECT-TYPE
	SYNTAX          IpAddress
    MAX-ACCESS      read-create
	STATUS          current
	DESCRIPTION     
			"The IP address of SMTP host"
	::= { apLogSendMailEntry 1}

apLogRecipientName OBJECT-TYPE
	SYNTAX          DisplayString (SIZE(1..30))
    MAX-ACCESS      read-create
	STATUS          current
	DESCRIPTION     
			"The email address of recipient"
	::= { apLogSendMailEntry 2}

apLogSendMailLevel OBJECT-TYPE
	SYNTAX          INTEGER {
							fatal(0)                                  ,
							alert(1)                                  ,
							critical(2)                                     ,
							error(3)                                    ,
							warning(4)                              ,
							notice(5)                             ,
							info(6)                                    
							}
	MAX-ACCESS      read-create
	STATUS          current
	DESCRIPTION      
		"The level of which sendmail is logging"
	::= {apLogSendMailEntry 3}

apLogSendMailStatus OBJECT-TYPE
	SYNTAX          RowStatus
	MAX-ACCESS      read-create
	STATUS          current
	DESCRIPTION      
		"Status entry for this row "
	::= {apLogSendMailEntry 4}

apLogSendMailDomain OBJECT-TYPE
	SYNTAX          DisplayString (SIZE (0..64))
    MAX-ACCESS      read-create
	STATUS          current
	DESCRIPTION     
		"The domain name for the email server."
	::= { apLogSendMailEntry 5}

END
