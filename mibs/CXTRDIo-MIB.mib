CXTRDIo-MIB DEFINITIONS ::= BEGIN


IMPORTS
   Counter                 FROM RFC1155-SMI
   OBJECT-TYPE             FROM RFC-1212
   cxTrdIo,
   Alias                   FROM CXProduct-SMI;


--  Active Configuration Table

--  The table describing:
--      active (current) parameters used in the Token Ring SAP and its associated hardware port.
--      statistics for each hardware port that is associated with a Token Ring SAP.


trdSapOprTable OBJECT-TYPE
   SYNTAX  SEQUENCE OF TrdSapOprEntry
   ACCESS  not-accessible
   STATUS  mandatory
   DESCRIPTION
"Provides configuration information for each Token Ring service access 
point and its associated hardware port.

Each row of the table (entry) contains information that corresponds to a 
particular service access point."

   ::= { cxTrdIo 1 }


   trdSapOprEntry OBJECT-TYPE
      SYNTAX  TrdSapOprEntry
      ACCESS  not-accessible
      STATUS  mandatory
      DESCRIPTION
"Provides the configuration of a particular Token Ring service access 
point and its associated hardware port."
      INDEX { trdSapOprNumber }
      ::= { trdSapOprTable 1 }


   TrdSapOprEntry ::=
      SEQUENCE {
         trdSapOprNumber
            INTEGER,
         trdSapOprAlias
            Alias,
         trdSapOprPortSpeed
            INTEGER,
         trdSapOprTxBufferQueue
            INTEGER,
         trdSapOprRxBufferQueue
            INTEGER,
         trdSapOprDataGenerator
            INTEGER,
         trdSapOprGenFrames
            INTEGER,
         trdSapOprGenFrameSize
            INTEGER,
         trdOprControlStats
            INTEGER,
         trdStatOprRxGenErrors
            Counter
         }


   trdSapOprNumber OBJECT-TYPE
      SYNTAX  INTEGER
      ACCESS  read-only
      STATUS  mandatory
      DESCRIPTION
"Identifies the service access point by a numerical value. Each service 
access point is assigned a unique number. The number is assigned by the 
system."
      ::= { trdSapOprEntry 1 }


   trdSapOprAlias OBJECT-TYPE
      SYNTAX  Alias
      ACCESS  read-only
      STATUS  mandatory
      DESCRIPTION
"Identifies the textual name (Alias) of this service access point. Each 
service access point must have a unique name.

Range of Values: 
0-16 alphanumeric characters. (Note that the first 
character must be a letter and spaces are not allowed).

Default Value: None"
      ::= { trdSapOprEntry 2 }


   trdSapOprPortSpeed OBJECT-TYPE
      SYNTAX INTEGER {
               speed-4-mbps    (1),
               speed-16-mbps   (2)
               }
      ACCESS  read-only
      STATUS  mandatory
      DESCRIPTION
"Defines the input and output speed, in bits per second, for the 
associated hardware port.

Default Value: speed-16-mbps (2)

Range of Values:
speed-4-mbps (1)

speed-16-mbps (2)"
      ::= { trdSapOprEntry 3 }


   trdSapOprTxBufferQueue OBJECT-TYPE
      SYNTAX INTEGER(32..240)
      ACCESS  read-only
      STATUS  mandatory
      DESCRIPTION
"Defines the transmit queue length, in number of buffers, for the 
associated hardware port. The number of buffers is usually equal to the 
number of frames (i.e. one frame per buffer). 

After the queue has reached this length, up to eight additional frames are 
stored before data is discarded.


Default Value: 64"
      ::= { trdSapOprEntry 4 }


   trdSapOprRxBufferQueue OBJECT-TYPE
      SYNTAX INTEGER(32..240)
      ACCESS  read-only
      STATUS  mandatory
      DESCRIPTION
"Defines the receive queue length, in number of buffers, for the associated 
hardware port. The number of buffers is usually equal to the 
number of frames (i.e. one frame per buffer).

After the queue has reached this length, data is discarded.


Default Value: 64"
      ::= { trdSapOprEntry 5 }


-- gap (2) for future parameters


   trdSapOprDataGenerator OBJECT-TYPE
      SYNTAX  INTEGER {
               disabled        (1),
               enabled         (2),
               enabled-verify  (3),
               retrigger       (4)
               }
      ACCESS  read-write
      STATUS  mandatory
      DESCRIPTION
"Determines whether the Data Generator is enabled. The Data Generator is 
used for testing purposes.

Options:                             

disabled (1): The Data Generator is disabled.

enabled (2): The Data Generator is enabled.

enabled-verify (3): The Data Generator is enabled, and checks data it 
receives against data it has sent. The result of the test is displayed in 
trdStatOprRxGenErrors.

retrigger (4): The Data Generator repeats the transmission, as specified 
in trdSapOprGenFrames and trdSapOprGen.

Default Value: disabled

Configuration Changed: operative

The change cannot be saved."
      ::= { trdSapOprEntry 8 }


   trdSapOprGenFrames OBJECT-TYPE
      SYNTAX  INTEGER
      ACCESS  read-write
      STATUS  mandatory
      DESCRIPTION
"Determines the number of times a frame will be generated (for testing 
purposes). Frames are generated every 50 msec. If the value is set to 
zero, then frames will be generated continuously (every 50 msec).

If the Data Generator is disabled (using trdSapOprDataGenerator), then the 
value is ignored.

Range of Values: 0 - 255

Default Value: 1

Configuration Changed: operative

The change cannot be saved."
      ::= { trdSapOprEntry 9 }


   trdSapOprGenFrameSize OBJECT-TYPE
      SYNTAX  INTEGER
      ACCESS  read-write
      STATUS  mandatory
      DESCRIPTION
"Determines the size of the frames (in bytes) to be generated for testing 
purposes. If the Data Generator is disabled, then this value is ignored.

Range of Values: 18-2100 bytes

Default Value: 512 bytes

Configuration Changed: operative

The change cannot be saved."
      ::= { trdSapOprEntry 10 }


-- gap (4) for future parameters


   trdOprControlStats OBJECT-TYPE
      SYNTAX  INTEGER {
               clearSapStats   (1)
               }
      ACCESS  write-only
      STATUS  mandatory
      DESCRIPTION
"Determines whether statistics for the hardware port will be cleared. When 
the clearSapStats option is selected, all counters for this port are 
cleared, including counters kept in the Interfaces Group MIB, (RFC 1213) 
and in the dot5 Table (RFC 1231).

Options:

clearSapStats (1): clears all statistics for the hardware port.


Configuration Changed: operative"
      ::= { trdSapOprEntry 15 }


-- gap (1) for future write-only commands


   trdStatOprRxGenErrors OBJECT-TYPE
      SYNTAX  Counter
      ACCESS  read-only
      STATUS  mandatory
      DESCRIPTION
"Identifies the total number of frames received that contain errors for a 
port that is set to enable-verify in 'trdSapOprDataGenerator'.

Range of Values: 0 to 4,294,967,295

Default Value: None"
      ::= { trdSapOprEntry 17 }



--  Planned Configuration Table

--  The table describing:
--   parameters used to configure each Token Ring SAP and its associated hardware port.


trdSapAdmTable OBJECT-TYPE
   SYNTAX  SEQUENCE OF TrdSapAdmEntry
   ACCESS  not-accessible
   STATUS  mandatory
   DESCRIPTION
"Provides configuration information for each Token Ring service access 
point and its associated hardware port.

Each row (entry) of the table corresponds to a particular service access 
point."

   ::= { cxTrdIo 2 }


   trdSapAdmEntry OBJECT-TYPE
      SYNTAX  TrdSapAdmEntry
      ACCESS  not-accessible
      STATUS  mandatory
      DESCRIPTION
"Provides configuration information for a particular Token Ring service 
access point and its associated hardware port."
      INDEX { trdSapAdmNumber }
      ::= { trdSapAdmTable 1 }


   TrdSapAdmEntry ::=
      SEQUENCE {
         trdSapAdmNumber
            INTEGER,
         trdSapAdmAlias
            Alias,
         trdSapAdmPortSpeed
            INTEGER,
         trdSapAdmTxBufferQueue
            INTEGER,
         trdSapAdmRxBufferQueue
            INTEGER,
         trdSapAdmDataGenerator
            INTEGER,
         trdSapAdmGenFrames
            INTEGER,
         trdSapAdmGenFrameSize
            INTEGER
         }


   trdSapAdmNumber OBJECT-TYPE
      SYNTAX  INTEGER
      ACCESS  read-only
      STATUS  mandatory
      DESCRIPTION
"Identifies the service access point by a number. The system assigns each 
service access point a unique number."
      ::= { trdSapAdmEntry 1 }


   trdSapAdmAlias OBJECT-TYPE
      SYNTAX  Alias
      ACCESS  read-write
      STATUS  mandatory
      DESCRIPTION
"Determines the textual name (alias) of this service access point. Each 
service access point is assigned a unique name.

Range of Values: 0-16 alphanumeric characters.The first 
character must be a letter, and spaces are not allowed."
      ::= { trdSapAdmEntry 2 }


   trdSapAdmPortSpeed OBJECT-TYPE
      SYNTAX INTEGER {
               speed-4-mbps    (1),
               speed-16-mbps   (2)
               }
      ACCESS  read-write
      STATUS  mandatory
      DESCRIPTION
"Defines the input and output speed, in bits per second, for the 
associated hardware port.

Options:

speed-4-mbps (1): 4 mbps ring speed

speed-16-mbps (2): 16 mbps ring speed


Default Value: speed-16-mbps (2)"
      DEFVAL { speed-16-mbps }
      ::= { trdSapAdmEntry 3 }


   trdSapAdmTxBufferQueue OBJECT-TYPE
      SYNTAX INTEGER(32..240)
      ACCESS  read-write
      STATUS  mandatory
      DESCRIPTION
"Defines the transmit queue length, in number of buffers, for the 
associated hardware port. The number of buffers is usually equal to the 
number of frames (i.e. one frame per buffer). 

After the queue has reached this length, up to eight additional frames are 
stored before data is discarded.

Range of Values: 32-240

Default Value: 64"
      DEFVAL { 64 }
      ::= { trdSapAdmEntry 4 }


   trdSapAdmRxBufferQueue OBJECT-TYPE
      SYNTAX INTEGER(32..240)
      ACCESS  read-write
      STATUS  mandatory
      DESCRIPTION
"Defines the receive queue length, in number of buffers, for the associated 
hardware port. The number of buffers is usually equal to the 
number of frames (i.e. one frame per buffer).

After the queue has reached this length, data is discarded.

Range of Values: 32-240

Default Value: 64"
      DEFVAL { 64 }
      ::= { trdSapAdmEntry 5 }


-- gap (2) for future parameters


   trdSapAdmDataGenerator OBJECT-TYPE
      SYNTAX  INTEGER {
          disabled       (1),
          enabled        (2),
          enabled-verify (3)
          }
      ACCESS  read-write
      STATUS  mandatory
      DESCRIPTION
"Determines whether the Data Generator is enabled. The Data Generator is 
used for testing purposes.

Options:

disabled (1)      

enabled (2)       

enabled-verify (3): The Data Generator is enabled, and checks data it 
receives against data it has sent. The result of the test is displayed in 
trdStatOprRxGenErrors.

Default Value: disabled (1)

Configuration Changed: administrative

Further Action: to activate changed
value, click on  Action in EMS menu
bar, then click on Reset with Save."
      DEFVAL { disabled }
      ::= { trdSapAdmEntry 8 }


   trdSapAdmGenFrames OBJECT-TYPE
      SYNTAX  INTEGER (0..255)
      ACCESS  read-write
      STATUS  mandatory
      DESCRIPTION
"Determines the number of times a frame will be generated for testing 
purposes. Frames are generated every 50 msec. If the value is set to zero, 
then frames will be generated continuously (every 50 msec).

If the Data Generator is disabled (using trdSapAdmDataGenerator), then the 
value is ignored.

Range of Values: 0 - 255

Default Value: 1

Configuration Changed: administrative

Further action: to activate changed
value, click on  Action in EMS menu
bar, then click on Reset with Save."
      DEFVAL { 1 }
      ::= { trdSapAdmEntry 9 }


   trdSapAdmGenFrameSize OBJECT-TYPE
      SYNTAX  INTEGER (18..2100)
      ACCESS  read-write
      STATUS  mandatory
      DESCRIPTION
"Determines the size of the frames (in bytes) to be generated for testing 
purposes. If the Data Generator is disabled, then this value is ignored.

Range of Values: 18 - 2100 bytes

Default Value: 512 bytes

Configuration Changed: administrative

Further action: to activate changed
value, click on  Action in EMS menu
bar, then click on Reset with Save."
      DEFVAL { 512 }
      ::= { trdSapAdmEntry 10 }

END
