Wellfleet-DS3E3-MIB DEFINITIONS ::= BEGIN

-- Creation date: 1998


    IMPORTS

      TimeTicks
	FROM RFC1155-SMI
      OBJECT-TYPE
        FROM RFC-1212
      wfDsx3Group
        FROM Wellfleet-COMMON-MIB;


    wfDs3E3ConfigTable OBJECT-TYPE
        SYNTAX	SEQUENCE OF WfDs3E3ConfigEntry
        ACCESS	not-accessible
        STATUS	mandatory
        DESCRIPTION
                "The DS3/E3 Configuration table"
        ::= { wfDsx3Group 10 }

    wfDs3E3ConfigEntry OBJECT-TYPE
        SYNTAX	WfDs3E3ConfigEntry
        ACCESS	not-accessible
        STATUS	mandatory
        DESCRIPTION
                "per circuit DS3/E3 configuration objects;
		wfDs3E3ConfigLineIndex corresponds to Wellfleet circuit number"
        INDEX	{ wfDs3E3ConfigLineIndex }
        ::= { wfDs3E3ConfigTable 1 }

    WfDs3E3ConfigEntry ::= SEQUENCE {
    	    wfDs3E3ConfigDelete
    		INTEGER,
    	    wfDs3E3ConfigDisable
    		INTEGER,
	    wfDs3E3ConfigState
		INTEGER,
	    wfDs3E3ConfigLastChange
		TimeTicks,
    	    wfDs3E3ConfigLineIndex
    		INTEGER,
    	    wfDs3E3ConfigIfIndex
    		INTEGER,
    	    wfDs3E3ConfigLineType
    		INTEGER,
    	    wfDs3E3ConfigLineCoding
    		INTEGER,
    	    wfDs3E3ConfigLoopbackConfig
    		INTEGER,
    	    wfDs3E3ConfigLineStatus
    		INTEGER,
	    wfDs3E3ConfigPrimaryClockSource
    		INTEGER,
	    wfDs3E3ConfigSecondaryClockSource
    		INTEGER,
	    wfDs3E3ConfigMtu
    		INTEGER,
	    wfDs3E3ConfigLineBuildOut
    		INTEGER,
	    wfDs3E3ConfigCurrentClock
               INTEGER,
            wfDs3E3ConfigExtClockOperational
               INTEGER,
	    wfDs3E3ConfigSetupAlarmThreshold
               INTEGER,
	    wfDs3E3ConfigClearAlarmThreshold
               INTEGER,
	    wfDs3E3ConfigLoopbackState
               INTEGER,
    	    wfDs3E3ConfigSendCode
               INTEGER
        }

    wfDs3E3ConfigDelete OBJECT-TYPE
	SYNTAX  INTEGER {
		    created(1),
		    deleted(2)
		}
	ACCESS  read-write
	STATUS  mandatory
	DESCRIPTION
		"Create/Delete parameter"
	DEFVAL  { created }
	::= { wfDs3E3ConfigEntry 1 }

    wfDs3E3ConfigDisable OBJECT-TYPE
	SYNTAX  INTEGER {
		    enabled(1),
		    disabled(2)
		}
	ACCESS  read-write
	STATUS  mandatory
	DESCRIPTION
		"Enable/Disable parameter"
	DEFVAL  { enabled }
	::= { wfDs3E3ConfigEntry 2 }

    wfDs3E3ConfigState OBJECT-TYPE
        SYNTAX  INTEGER {
                    up(1),
                    down(2),
		    los(3),
		    lof(4),
		    raif(5),
		    ais(6),
		    loopback(7),
		    notpresent(20)
		}
	ACCESS  read-only
	STATUS  mandatory
	DESCRIPTION
		"State of the DS3 Port."
	DEFVAL  { notpresent }
	::= { wfDs3E3ConfigEntry 3 }

    wfDs3E3ConfigLastChange OBJECT-TYPE
	SYNTAX  TimeTicks
	ACCESS  read-only
	STATUS  mandatory
	DESCRIPTION
		"The value of sysUpTime at the time the interface entered
		its current operational state."
	::= { wfDs3E3ConfigEntry 4 }

    wfDs3E3ConfigLineIndex OBJECT-TYPE
        SYNTAX	INTEGER(1..65535)
        ACCESS	read-only
        STATUS	mandatory
        DESCRIPTION
                "this corresponds to the Wellfleet circuit number"
        ::= { wfDs3E3ConfigEntry 5 }

    wfDs3E3ConfigIfIndex OBJECT-TYPE
        SYNTAX	INTEGER
        ACCESS	read-only
        STATUS	mandatory
        DESCRIPTION
                "this is value of ifIndex from the Interfaces table of
                MIB II (RFC 1213)."
        ::= { wfDs3E3ConfigEntry 6 }

    wfDs3E3ConfigLineType OBJECT-TYPE
        SYNTAX	INTEGER {
    		    ds3other(1),
    		    ds3m23(2),
    		    ds3syntran(3),
    		    ds3cbitparity(4),
    		    ds3clearchannel(5),
    		    e3other(6),
    		    e3framed(7),
    		    e3plcp(8),
    		    autodetect(9)
    		}
        ACCESS	read-write
        STATUS	mandatory
        DESCRIPTION
                "the variety of DS3/E3 application implementing this circuit"
	DEFVAL { autodetect }
        ::= { wfDs3E3ConfigEntry 7 }

    wfDs3E3ConfigLineCoding OBJECT-TYPE
        SYNTAX	INTEGER {
    		    other(1),
    		    b3zs(2),
    		    hdb3(3)
    		}
        ACCESS	read-write
        STATUS	mandatory
        DESCRIPTION
                "the variety of Zero Code Suppression used on the link"
	DEFVAL { b3zs }
        ::= { wfDs3E3ConfigEntry 8 }

    wfDs3E3ConfigLoopbackConfig OBJECT-TYPE
        SYNTAX	INTEGER {
    		    noloop(1),
    		    payloadloop(2),
    		    lineloop(3)
    		}
        ACCESS	read-write
        STATUS	mandatory
        DESCRIPTION
                "the loopback configuration of the DS3/E3 interface"
	DEFVAL { noloop }
        ::= { wfDs3E3ConfigEntry 9 }

    wfDs3E3ConfigLineStatus OBJECT-TYPE
        SYNTAX	INTEGER {
    		    noalarm(1),
    		    rcrai(2),
    		    txrai(4),
    		    rcais(8),
    		    txais(16),
    		    lof(32),
    		    los(64),
    		    loopback(128),
    		    rctestcode(256),
    		    otherfailure(512)
    		}
        ACCESS	read-only
        STATUS	mandatory
        DESCRIPTION
                "the status of the DS3/E3 line"
        DEFVAL  { noalarm }
        ::= { wfDs3E3ConfigEntry 10 }

    wfDs3E3ConfigPrimaryClockSource OBJECT-TYPE
        SYNTAX	INTEGER {
    		    internal(1),
    		    external(2),
    		    loop(3)
    		}
        ACCESS	read-write
        STATUS	mandatory
        DESCRIPTION
                "Selects the Primary source of the Tx Clock for the DS3/E3
		interface"
	DEFVAL { loop }
        ::= { wfDs3E3ConfigEntry 11 }

    wfDs3E3ConfigSecondaryClockSource OBJECT-TYPE
        SYNTAX	INTEGER {
    		    internal(1),
    		    external(2),
    		    loop(3)
    		}
        ACCESS	read-write
        STATUS	mandatory
        DESCRIPTION
                "Selects the Secondary source of the Tx Clock for the DS3/E3
		interface"
	DEFVAL { internal }
        ::= { wfDs3E3ConfigEntry 12 }

    wfDs3E3ConfigMtu OBJECT-TYPE
	SYNTAX  INTEGER(3..4608)
	ACCESS  read-write
	STATUS  mandatory
	DESCRIPTION
		"MTU parameter for all channels on DS3 ."
	DEFVAL  { 4608 }
	::= { wfDs3E3ConfigEntry 13 }

    wfDs3E3ConfigLineBuildOut OBJECT-TYPE
        SYNTAX	INTEGER {
    		    long(1),
    		    short(2)
    		}
	ACCESS  read-write
	STATUS  mandatory
	DESCRIPTION
		"Set according to cable length, short (less than 225 feet)
		or long (greater than 225 feet)."
	DEFVAL  { short }
	::= { wfDs3E3ConfigEntry 14 }

    wfDs3E3ConfigCurrentClock OBJECT-TYPE
        SYNTAX  INTEGER {
                    internal(1),
                    external(2),
                    loop(3)
                }
        ACCESS  read-only
        STATUS  mandatory
        DESCRIPTION
                "Indicates the clock source currently in use by the DS1"
        DEFVAL  { loop }
        ::= { wfDs3E3ConfigEntry 15 }

    wfDs3E3ConfigExtClockOperational OBJECT-TYPE
        SYNTAX  INTEGER {
                    present(1),
                    notpresent(2)
                }
        ACCESS  read-only
        STATUS  mandatory
        DESCRIPTION
                "Indicates whether the External clock is operational"
        DEFVAL  { notpresent }
        ::= { wfDs3E3ConfigEntry 16 }

    wfDs3E3ConfigSetupAlarmThreshold OBJECT-TYPE
	SYNTAX  INTEGER(2..10)
	ACCESS  read-write
	STATUS  mandatory
	DESCRIPTION
		"Specifies setup time for performance failure conditions,
		in seconds. When a performance defect is present for greater
		than the time specified by this parameter a performance
		failure is registered and a message is logged."
	DEFVAL  { 2 }
        ::= { wfDs3E3ConfigEntry 17 }

    wfDs3E3ConfigClearAlarmThreshold OBJECT-TYPE
	SYNTAX  INTEGER(2..10)
	ACCESS  read-write
	STATUS  mandatory
	DESCRIPTION
		"Specifies clear time for performance failure conditions,
		in seconds. When a performance failure condition has been
		cleared for greater than the time specified by this parameter
		then the failure cleared condition is registered and a
		message is logged."
	DEFVAL  { 2 }
        ::= { wfDs3E3ConfigEntry 18 }

    wfDs3E3ConfigLoopbackState OBJECT-TYPE
	SYNTAX  INTEGER {
		    noloop(1),
		    mgrreqlineloop(2),
		    mgrreqpayloadloop(3),
		    netreqlineloop(4),
		    netreqpayloadloop(5)
		}
	ACCESS  read-only
	STATUS  mandatory
	DESCRIPTION
		"Indicates the current loopback state of this interface.
		The interface can be in one the following states:

                 Line Loopback
                 Payload Loopback
                 no loopback

                Loopback modes can be initiated by either of two methods:

		Manager requested Loopback is initiated by the Manager of
		this device.

                Network requested Loopback is initiated by this interface
		receiving an in-band request on the network from the far
		end device."
	DEFVAL  { noloop }
	::= { wfDs3E3ConfigEntry 19 }

    wfDs3E3ConfigSendCode OBJECT-TYPE
        SYNTAX	INTEGER {
    		    sendnocode(1),
    		    sendlinecode(2),
    		    sendpayloadcode(3),
    		    sendds1loopcode(4)
    		}
        ACCESS	read-only
        STATUS	mandatory
        DESCRIPTION
                "This variable is currently read-only and it indicates what type of code has
                been sent across the DS3 interface by the device.  The values mean:

                  SENDNOCODE - sending looped or normal data
                  SENDLINECODE - sending a request for a line loopback
                  SENDPAYLOADCODE - sending a request for a payload loopback
                  SENDDS1LOOPCODE - sending a request for a DS1 loopback 
		"
        DEFVAL	{ sendnocode }
        ::= { wfDs3E3ConfigEntry 20 }





    wfDs3E3ActionTable OBJECT-TYPE
        SYNTAX	SEQUENCE OF WfDs3E3ActionEntry
        ACCESS	not-accessible
        STATUS	mandatory
        DESCRIPTION
                "DS3E3 configuration Action record - 
                write only Configuration parameters"
        ::= { wfDsx3Group 17 }

    wfDs3E3ActionEntry OBJECT-TYPE
        SYNTAX	WfDs3E3ActionEntry
        ACCESS	not-accessible
        STATUS	mandatory
        DESCRIPTION
                "An entry in the DS3E3 Config table"
        INDEX	{ wfDs3E3ActionPortLineNumber }
        ::= { wfDs3E3ActionTable 1 }

    WfDs3E3ActionEntry ::= SEQUENCE {
    	    wfDs3E3ActionPortLineNumber
    		INTEGER,
	    wfDs3E3ActionSendFeacLoopCode
    		INTEGER,
	    wfDs3E3ActionSendFeacDs1LoopUpCode
    		INTEGER,
	    wfDs3E3ActionSendFeacDs1LoopDownCode
    		INTEGER,
	    wfDs3E3ActionClearCurrentStats
    		INTEGER,
	    wfDs3E3ActionClearFarEndCurrentStats
    		INTEGER,
	    wfDs3E3ActionClearDayCurrentStats
    		INTEGER,
	    wfDs3E3ActionClearFarEndDayCurrentStats
    		INTEGER,
	    wfDs3E3ActionClearIntervalStats
    		INTEGER,
	    wfDs3E3ActionClearFarEndIntervalStats
    		INTEGER
        }

    wfDs3E3ActionPortLineNumber OBJECT-TYPE
        SYNTAX	INTEGER
        ACCESS	read-only
        STATUS	mandatory
        DESCRIPTION
                "Instance ID LineNumber, filled in by driver"
        ::= { wfDs3E3ActionEntry 1 }

    wfDs3E3ActionSendFeacLoopCode OBJECT-TYPE
        SYNTAX  INTEGER {
                    lineloop(1),
                    deactivatell(2),
                    payloadloop(3),
                    deactivatepl(4),
                    noaction(21)
                }
        ACCESS  read-write
        STATUS  mandatory
        DESCRIPTION
                "Selects a Far End Alarm and Control Channel code to be
		sent to the remote end."
        DEFVAL  { noaction }
        ::= { wfDs3E3ActionEntry 2 }

    wfDs3E3ActionSendFeacDs1LoopUpCode OBJECT-TYPE
        SYNTAX  INTEGER {
                    noaction(29)
                }
        ACCESS  read-write
        STATUS  mandatory
        DESCRIPTION
                "Selects Loop Up code to be sent to the remote end for a DS1.
                Value passed through this attribute is the DS1 Port number
                (1 through 28)."
        DEFVAL  { noaction }
        ::= { wfDs3E3ActionEntry 3 }

    wfDs3E3ActionSendFeacDs1LoopDownCode OBJECT-TYPE
        SYNTAX  INTEGER {
                    noaction(29)
                }
        ACCESS  read-write
        STATUS  mandatory
        DESCRIPTION
                "Selects Loop Down code to be sent to the remote end for a DS1.
                Value passed through this attribute is the DS1 Port number
                (1 through 28)."
        DEFVAL  { noaction }
        ::= { wfDs3E3ActionEntry 4 }

    wfDs3E3ActionClearCurrentStats OBJECT-TYPE
	SYNTAX	INTEGER {
		    clrStats(1),
		    noaction(2)
		}
	ACCESS	read-write
	STATUS	mandatory
	DESCRIPTION
		"Clears this port's Current 15 minute Statistics."
	DEFVAL	{ noaction }
	::= { wfDs3E3ActionEntry 5 }

    wfDs3E3ActionClearFarEndCurrentStats OBJECT-TYPE
	SYNTAX	INTEGER {
		    clrStats(1),
		    noaction(2)
		}
	ACCESS	read-write
	STATUS	mandatory
	DESCRIPTION
		"Clears this port's Far End, Current 15 minute Statistics."
	DEFVAL	{ noaction }
	::= { wfDs3E3ActionEntry 6 }

    wfDs3E3ActionClearDayCurrentStats OBJECT-TYPE
	SYNTAX	INTEGER {
		    clrStats(1),
		    noaction(2)
		}
	ACCESS	read-write
	STATUS	mandatory
	DESCRIPTION
		"Clears this port's Current Day Statistics."
	DEFVAL	{ noaction }
	::= { wfDs3E3ActionEntry 7 }

    wfDs3E3ActionClearFarEndDayCurrentStats OBJECT-TYPE
	SYNTAX	INTEGER {
		    clrStats(1),
		    noaction(2)
		}
	ACCESS	read-write
	STATUS	mandatory
	DESCRIPTION
		"Clears this port's Far End, Current Day Statistics."
	DEFVAL	{ noaction }
	::= { wfDs3E3ActionEntry 8 }

    wfDs3E3ActionClearIntervalStats OBJECT-TYPE
	SYNTAX	INTEGER {
		    clrStats(1),
		    noaction(2)
		}
	ACCESS	read-write
	STATUS	mandatory
	DESCRIPTION
		"Clears All Interval Statistics (15 minute and day) of this port."
	DEFVAL	{ noaction }
	::= { wfDs3E3ActionEntry 9 }

    wfDs3E3ActionClearFarEndIntervalStats OBJECT-TYPE
	SYNTAX	INTEGER {
		    clrStats(1),
		    noaction(2)
		}
	ACCESS	read-write
	STATUS	mandatory
	DESCRIPTION
		"Clears All Far End Interval Statistics (15 minute and day) of this port."
	DEFVAL	{ noaction }
	::= { wfDs3E3ActionEntry 10 }



    END  -- Wellfleet-DS3E3-MIB
