-- MIB File Generated on 18-Oct-1995 at 08:27:08

CHS-MIB DEFINITIONS ::= BEGIN

IMPORTS
   enterprises,
   experimental,
   IpAddress,
   TimeTicks,
   Gauge,
   Counter
      FROM RFC1155-SMI
   DisplayString
      FROM RFC1213-MIB
   OBJECT-TYPE
      FROM RFC-1212;


usr OBJECT IDENTIFIER ::= { enterprises 429 }

nas OBJECT IDENTIFIER ::= { usr 1 }

chs OBJECT IDENTIFIER ::= { nas 1 }

uchasSlot OBJECT IDENTIFIER ::= { chs 1 }

uchasSlotTable OBJECT-TYPE
SYNTAX SEQUENCE OF UchasSlotEntry
ACCESS not-accessible
STATUS mandatory
DESCRIPTION
"A table that contains information about the slots in the 
chassis.  For those slots that do not contain a physical 
module, the table will contain a conceptual row with the 
type of physical module set to 'uchasSlotEmpty'."
::= { uchasSlot 1 }

uchasSlotEntry OBJECT-TYPE
SYNTAX UchasSlotEntry
ACCESS not-accessible
STATUS mandatory
DESCRIPTION
"A list of information for each slot in the chassis.  
Conceptual rows may not be created or deleted with SNMP 
operations, but rather, the Proxy agent running in the 
Network Management Card will automatically create and 
delete rows as cards are inserted and removed."
INDEX { uchasSlotIndex }
::= { uchasSlotTable 1 }

UchasSlotEntry ::=
SEQUENCE {
uchasSlotIndex
    INTEGER,
uchasSlotModuleType
    OBJECT IDENTIFIER,
uchasSlotLastChange
    TimeTicks,
uchasSlotModuleDescr
    DisplayString,
uchasSlotModuleVersion
    DisplayString,
uchasSlotModuleSerialNumber
    DisplayString,
uchasSlotModuleProductCode
    DisplayString,
uchasSlotStatFeEna
    INTEGER,
uchasSlotFeKey
    DisplayString,
uchasSlotNacConfig
    OCTET STRING,
uchasSlotSwitchSettings
    INTEGER,
uchasSlotRamInstalled
    INTEGER,
uchasSlotFlashInstalled
    INTEGER
}

uchasSlotIndex OBJECT-TYPE
SYNTAX INTEGER (1..37)
ACCESS read-only
STATUS mandatory
DESCRIPTION
"The slot number for which this entry contains management 
information.  NAC slots are numbered from 1 to 16.  The 
Network Management Card (NMC) goes in slot 17.  For 
simplicity's sake, the corresponding NIC slot numbers will 
be 21 through 37.  Rows will not exist in this table for 
slots 18 through 20."
::= { uchasSlotEntry 1 }

uchasSlotModuleType OBJECT-TYPE
SYNTAX OBJECT IDENTIFIER
ACCESS read-only
STATUS mandatory
DESCRIPTION
"The type of physical module contained in this slot of the 
chassis.  A value of uchasSlotEmpty indicates an empty 
slot.  A value of uchasSlotUnknown indicates that the type 
of module is unknown."
::= { uchasSlotEntry 2 }

uchasSlotLastChange OBJECT-TYPE
SYNTAX TimeTicks
ACCESS read-only
STATUS mandatory
DESCRIPTION
"The value of MIB-II's sysUpTime (in the agent supporting 
this chassis MIB) at which a module was last inserted or 
removed from this slot.  If no module has been inserted or 
removed from this slot since the last time the network 
management card was re-initialized, then this object has a 
zero value."
::= { uchasSlotEntry 3 }

uchasSlotModuleDescr OBJECT-TYPE
SYNTAX DisplayString (SIZE(0..124))
ACCESS read-only
STATUS mandatory
DESCRIPTION
"A textual description of the module plugged into the slot."
::= { uchasSlotEntry 4 }

uchasSlotModuleVersion OBJECT-TYPE
SYNTAX DisplayString (SIZE(0..124))
ACCESS read-only
STATUS mandatory
DESCRIPTION
"A textual description of the version/revision level for 
this module's hardware."
::= { uchasSlotEntry 5 }

uchasSlotModuleSerialNumber OBJECT-TYPE
SYNTAX DisplayString (SIZE(0..31))
ACCESS read-only
STATUS mandatory
DESCRIPTION
"The serial number of the module present in the slot.  If 
the slot is empty, this value will be a zero length string."
::= { uchasSlotEntry 6 }

uchasSlotModuleProductCode OBJECT-TYPE
SYNTAX DisplayString (SIZE(0..8))
ACCESS read-only
STATUS mandatory
DESCRIPTION
"The product code of the module present in the slot.  For 
certain entries in the slot table the NMC will not be able 
to read product codes.  In such cases the product code 
string will be NULL."
::= { uchasSlotEntry 7 }

uchasSlotStatFeEna OBJECT-TYPE
SYNTAX INTEGER
ACCESS read-only
STATUS optional
DESCRIPTION
"This object can be read to determine what options have been 
enabled in the NACs. It uses individual bits to represent 
the enable status of the features which are NAC specific."
::= { uchasSlotEntry 8 }

uchasSlotFeKey OBJECT-TYPE
SYNTAX DisplayString (SIZE(0..22))
ACCESS read-write
STATUS optional
DESCRIPTION
"This object sends the feature key to the appropriate NAC 
for enabling added cost features.  When read, this object 
returns a null string."
::= { uchasSlotEntry 9 }

uchasSlotNacConfig OBJECT-TYPE
SYNTAX OCTET STRING (SIZE(0..160))
ACCESS read-only
STATUS optional
DESCRIPTION
"This is a proprietary encoding of a module's view of the 
chassis NAC configuration as it is stored in the module. 
For modules not supporting chassis configuration storage, 
the values will be all 0."
::= { uchasSlotEntry 10 }

uchasSlotSwitchSettings OBJECT-TYPE
SYNTAX INTEGER
ACCESS read-only
STATUS mandatory
DESCRIPTION
"This represents the DIP switch settings on the NAC. It is a 
bitmapped integer."
::= { uchasSlotEntry 11 }

uchasSlotRamInstalled OBJECT-TYPE
SYNTAX INTEGER
ACCESS read-only
STATUS mandatory
DESCRIPTION
"This represents the amount of DRAM memory installed on the 
NAC in Kbytes."
::= { uchasSlotEntry 12 }

uchasSlotFlashInstalled OBJECT-TYPE
SYNTAX INTEGER
ACCESS read-only
STATUS mandatory
DESCRIPTION
"This represents the amount of flash ROM memory installed on 
the NAC in Kbytes."
::= { uchasSlotEntry 13 }

uchasEntity OBJECT IDENTIFIER ::= { chs 2 }

uchasEntityTable OBJECT-TYPE
SYNTAX SEQUENCE OF UchasEntityEntry
ACCESS not-accessible
STATUS mandatory
DESCRIPTION
"A table that contains information about the 'logical' 
networking devices (entities) in this chassis."
::= { uchasEntity 1 }

uchasEntityEntry OBJECT-TYPE
SYNTAX UchasEntityEntry
ACCESS not-accessible
STATUS mandatory
DESCRIPTION
"Information concerning an entity in the chassis.  
Conceptual rows may not be created or deleted with SNMP 
operations, but rather, will be automatically created and 
deleted by the proxy agent running on the Network 
Management Card."
INDEX { uchasEntityIndex }
::= { uchasEntityTable 1 }

UchasEntityEntry ::=
SEQUENCE {
uchasEntityIndex
    INTEGER,
uchasEntityObjectID
    OBJECT IDENTIFIER,
uchasEntityDescr
    DisplayString,
uchasEntityVersion
    DisplayString,
uchasEntityOperStatus
    INTEGER,
uchasEntityTimeStamp
    TimeTicks
}

uchasEntityIndex OBJECT-TYPE
SYNTAX INTEGER (1..65535)
ACCESS read-only
STATUS mandatory
DESCRIPTION
"A unique index for the entity for which this entry contains 
information.  For simplicity's sake, entity index values 
will be assigned according to the formula E=1000*S+I, where 
E is the entity index, S is the slot index, and I is the 
index of the entity on the specific card.  For example, the 
third modem on a quad modem card that is in slot 5 has an 
entity index of 5003."
::= { uchasEntityEntry 1 }

uchasEntityObjectID OBJECT-TYPE
SYNTAX OBJECT IDENTIFIER
ACCESS read-only
STATUS mandatory
DESCRIPTION
"The specific type of entity.  The value of this object is 
analogous to MIB-II's sysObjectID.  In particular, it has 
the same value as would be returned if the MIB view 
identified by uchasIpAddress and uchasCommunity, were 
queried for sysObjectID."
::= { uchasEntityEntry 2 }

uchasEntityDescr OBJECT-TYPE
SYNTAX DisplayString (SIZE(0..124))
ACCESS read-only
STATUS mandatory
DESCRIPTION
"A textual description of the entity.  The value of this 
object is analogous to MIB-II's sysDescr.  In particular, 
it has the same value as would be returned if the MIB view 
identified by uchasIpAddress and uchasCommunity were 
queried for sysDescr."
::= { uchasEntityEntry 3 }

uchasEntityVersion OBJECT-TYPE
SYNTAX DisplayString (SIZE(0..124))
ACCESS read-only
STATUS mandatory
DESCRIPTION
"A textual description of the version/revision level for 
this entity's software."
::= { uchasEntityEntry 4 }

uchasEntityOperStatus OBJECT-TYPE
SYNTAX INTEGER{
  other(1),
  outOfService(2),
  testing(3),
  operational(4),
  failed(5),
  loading(6)
}
ACCESS read-only
STATUS mandatory
DESCRIPTION
"Provides operational status of the entity for which this 
row corresponds."
::= { uchasEntityEntry 5 }

uchasEntityTimeStamp OBJECT-TYPE
SYNTAX TimeTicks
ACCESS read-only
STATUS mandatory
DESCRIPTION
"The value of MIB-II's sysUpTime (in the NMC's proxy agent) 
at which this entity was last (re-)initialized."
::= { uchasEntityEntry 6 }

uchasConfig OBJECT IDENTIFIER ::= { chs 3 }

uchasType OBJECT-TYPE
SYNTAX OBJECT IDENTIFIER
ACCESS read-only
STATUS mandatory
DESCRIPTION
"An authoritative identification of the type of chassis.  
This object provides an easy and unambiguaous means for 
determining what kind of box is being managed."
::= { uchasConfig 1 }

uchasDescr OBJECT-TYPE
SYNTAX DisplayString (SIZE(0..124))
ACCESS read-write
STATUS mandatory
DESCRIPTION
"A textual description of the specific chassis being 
managed."
::= { uchasConfig 2 }

uchasDisplayName OBJECT-TYPE
SYNTAX DisplayString (SIZE(0..4))
ACCESS read-write
STATUS mandatory
DESCRIPTION
"A four digit name given to the chassis.  The name will be 
displayed on the alpha-numeric display on the front panel 
of the Network Management Card in the given chassis."
::= { uchasConfig 3 }

uchasPhysicalChanges OBJECT-TYPE
SYNTAX Counter
ACCESS read-only
STATUS mandatory
DESCRIPTION
"The number of physical changes that have occurred in the 
chassis since the agent was warm/cold started.  This 
includes additions and removal of physical modules."
::= { uchasConfig 4 }

uchasFrontPanelLedStates OBJECT-TYPE
SYNTAX OCTET STRING (SIZE(0..255))
ACCESS read-only
STATUS mandatory
DESCRIPTION
"This object is a proprietarily encoded octet string that is 
used by USR's management console to retrieve the front 
panel LED states  (attributes) from all of the devices 
installed in the chassis by getting a single object."
::= { uchasConfig 5 }

uchasFrontPanelLedColor OBJECT-TYPE
SYNTAX OCTET STRING (SIZE(0..255))
ACCESS read-only
STATUS mandatory
DESCRIPTION
"This object is a proprietary encoded octet string used to 
get the color of every LED from all the devices in the 
chassis."


::= { uchasConfig 6 }

uchasNicStates OBJECT-TYPE
SYNTAX OCTET STRING (SIZE(0..255))
ACCESS read-only
STATUS optional
DESCRIPTION
"This object is a proprietary encoded octet string used to 
get the status of every NIC in the chassis."


::= { uchasConfig 7 }

uchasPowerSupply OBJECT IDENTIFIER ::= { chs 4 }

uchasPowerSupplyTable OBJECT-TYPE
SYNTAX SEQUENCE OF UchasPowerSupplyEntry
ACCESS not-accessible
STATUS optional
DESCRIPTION
"A list of power supply entries, one for each power supply 
in the chassis.  This table is a dense table, so rows 
appear for all possible power supplies that could be 
present in the given chassis."
::= { uchasPowerSupply 1 }

uchasPowerSupplyEntry OBJECT-TYPE
SYNTAX UchasPowerSupplyEntry
ACCESS not-accessible
STATUS optional
DESCRIPTION
"There is one entry in the power supply table for each 
possible power supply in the chassis."
INDEX { uchasPowerSupplyIndex }
::= { uchasPowerSupplyTable 1 }

UchasPowerSupplyEntry ::=
SEQUENCE {
uchasPowerSupplyIndex
    INTEGER,
uchasPowerSupplyDescr
    DisplayString,
uchasPowerSupplyOperStatus
    INTEGER,
uchasPowerSupplyFailures
    Counter
}

uchasPowerSupplyIndex OBJECT-TYPE
SYNTAX INTEGER
ACCESS read-only
STATUS optional
DESCRIPTION
"An index value that uniquely identifies a power supply."
::= { uchasPowerSupplyEntry 1 }

uchasPowerSupplyDescr OBJECT-TYPE
SYNTAX DisplayString (SIZE(0..124))
ACCESS read-only
STATUS optional
DESCRIPTION
"A textual description of the power supply."
::= { uchasPowerSupplyEntry 2 }

uchasPowerSupplyOperStatus OBJECT-TYPE
SYNTAX INTEGER{
  unknown(1),
  bad(2),
  good(3),
  empty(4)
}
ACCESS read-only
STATUS optional
DESCRIPTION
"Actual status of the power supply represented by this entry 
in the power supply table."
::= { uchasPowerSupplyEntry 3 }

uchasPowerSupplyFailures OBJECT-TYPE
SYNTAX Counter
ACCESS read-only
STATUS optional
DESCRIPTION
"The number of times that uchasPowerSupplyOperStatus has 
gone to bad(4)."
::= { uchasPowerSupplyEntry 4 }

uchasPowerSupplyOutTable OBJECT-TYPE
SYNTAX SEQUENCE OF UchasPowerSupplyOutEntry
ACCESS not-accessible
STATUS optional
DESCRIPTION
"A list of power supply output entries, one for each output 
of each power supply in the chassis."
::= { uchasPowerSupply 2 }

uchasPowerSupplyOutEntry OBJECT-TYPE
SYNTAX UchasPowerSupplyOutEntry
ACCESS not-accessible
STATUS optional
DESCRIPTION
"There is one row in this table for each power supply output 
for each power supply in the chassis."
INDEX { uchasPowerSupplyOutPSIndex, uchasPowerSupplyOutIndex }
::= { uchasPowerSupplyOutTable 1 }

UchasPowerSupplyOutEntry ::=
SEQUENCE {
uchasPowerSupplyOutPSIndex
    INTEGER,
uchasPowerSupplyOutIndex
    INTEGER,
uchasPowerSupplyOutStatus
    INTEGER,
uchasPowerSupplyOutNominalVolt
    INTEGER,
uchasPowerSupplyOutOfferedVolt
    INTEGER,
uchasPowerSupplyOutWarnings
    Counter
}

uchasPowerSupplyOutPSIndex OBJECT-TYPE
SYNTAX INTEGER
ACCESS read-only
STATUS optional
DESCRIPTION
"An index which specifies the power supply to which this 
output relates.  The value of this index corresponds 
directly to values of the index for the power supply table."
::= { uchasPowerSupplyOutEntry 1 }

uchasPowerSupplyOutIndex OBJECT-TYPE
SYNTAX INTEGER
ACCESS read-only
STATUS optional
DESCRIPTION
"An index that, together with uchasPowerSupplyOutPSIndex, 
uniquely defines an output for the specified power supply."
::= { uchasPowerSupplyOutEntry 2 }

uchasPowerSupplyOutStatus OBJECT-TYPE
SYNTAX INTEGER{
  unknown(1),
  warning(2),
  good(3)
}
ACCESS read-only
STATUS optional
DESCRIPTION
"Actual status of the supply output.  One of unknown(1), 
warning(2), or good(3)."
::= { uchasPowerSupplyOutEntry 3 }

uchasPowerSupplyOutNominalVolt OBJECT-TYPE
SYNTAX INTEGER
ACCESS read-only
STATUS optional
DESCRIPTION
"In hundredths of a volt, the voltage the output is supposed 
to supply, such as -5V, which would be represented by the 
value -500, or +12V, which would correspond to a value of 
+1200."
::= { uchasPowerSupplyOutEntry 4 }

uchasPowerSupplyOutOfferedVolt OBJECT-TYPE
SYNTAX INTEGER
ACCESS read-only
STATUS optional
DESCRIPTION
"In hundredths of a volt, the voltage actually offered by 
the output.  If uchasPowerSupplyOutStatus is good(4), the 
value 0 means offered voltage is not available."
::= { uchasPowerSupplyOutEntry 5 }

uchasPowerSupplyOutWarnings OBJECT-TYPE
SYNTAX Counter
ACCESS read-only
STATUS optional
DESCRIPTION
"The number of times uchasPowerSupplyOutputStatus has gone 
to warning(3)."
::= { uchasPowerSupplyOutEntry 6 }

uchasEnviron OBJECT IDENTIFIER ::= { chs 5 }

uchasEnvironTable OBJECT-TYPE
SYNTAX SEQUENCE OF UchasEnvironEntry
ACCESS not-accessible
STATUS optional
DESCRIPTION
"A list of environmental entries, one for each environmental 
sensor in the chassis."
::= { uchasEnviron 1 }

uchasEnvironEntry OBJECT-TYPE
SYNTAX UchasEnvironEntry
ACCESS not-accessible
STATUS optional
DESCRIPTION
"Values for an environmental sensor in the chassis."
INDEX { uchasEnvironIndex }
::= { uchasEnvironTable 1 }

UchasEnvironEntry ::=
SEQUENCE {
uchasEnvironIndex
    INTEGER,
uchasEnvironSensor
    OBJECT IDENTIFIER,
uchasEnvironStatus
    INTEGER,
uchasEnvironWarnings
    Counter,
uchasEnvironFailures
    Counter
}

uchasEnvironIndex OBJECT-TYPE
SYNTAX INTEGER
ACCESS read-only
STATUS optional
DESCRIPTION
"A index that uniquely identifies an environmental sensor."
::= { uchasEnvironEntry 1 }

uchasEnvironSensor OBJECT-TYPE
SYNTAX OBJECT IDENTIFIER
ACCESS read-only
STATUS optional
DESCRIPTION
"The identification of the type of environmental sensor to 
which this entry applies."
::= { uchasEnvironEntry 2 }

uchasEnvironStatus OBJECT-TYPE
SYNTAX INTEGER{
  unknown(1),
  bad(2),
  warning(3),
  good(4)
}
ACCESS read-only
STATUS optional
DESCRIPTION
"Actual status indicated by the sensor."
::= { uchasEnvironEntry 3 }

uchasEnvironWarnings OBJECT-TYPE
SYNTAX Counter
ACCESS read-only
STATUS optional
DESCRIPTION
"The number of times uchasEnvironStatus has gone to 
warning(3)."
::= { uchasEnvironEntry 4 }

uchasEnvironFailures OBJECT-TYPE
SYNTAX Counter
ACCESS read-only
STATUS optional
DESCRIPTION
"The number of times uchasEnvironStatus has gone to bad(2)."
::= { uchasEnvironEntry 5 }

uchasKnownTypes OBJECT IDENTIFIER ::= { chs 6 }

uchasKnownChassis OBJECT IDENTIFIER ::= { uchasKnownTypes 1 }

uchas17SlotChassis OBJECT IDENTIFIER ::= { uchasKnownChassis 1 }

uchas7SlotChassis OBJECT IDENTIFIER ::= { uchasKnownChassis 2 }

uchasKnownModules OBJECT IDENTIFIER ::= { uchasKnownTypes 2 }

uchasSlotEmpty OBJECT IDENTIFIER ::= { uchasKnownModules 1 }

uchasSlotUnknown OBJECT IDENTIFIER ::= { uchasKnownModules 2 }

uchasNetwMgtCard OBJECT IDENTIFIER ::= { uchasKnownModules 3 }

uchasDualT1NAC OBJECT IDENTIFIER ::= { uchasKnownModules 4 }

uchasDualModemNAC OBJECT IDENTIFIER ::= { uchasKnownModules 5 }

uchasQuadModemNAC OBJECT IDENTIFIER ::= { uchasKnownModules 6 }

uchasTrGatewayNAC OBJECT IDENTIFIER ::= { uchasKnownModules 7 }

uchasX25GatewayNAC OBJECT IDENTIFIER ::= { uchasKnownModules 8 }

uchasDualV34ModemNAC OBJECT IDENTIFIER ::= { uchasKnownModules 9 }

uchasQuadV32DigitalModemNAC OBJECT IDENTIFIER ::= { uchasKnownModules 10 }

uchasQuadV32AnalogModemNAC OBJECT IDENTIFIER ::= { uchasKnownModules 11 }

uchasQuadV32DigAnlModemNAC OBJECT IDENTIFIER ::= { uchasKnownModules 12 }

uchasQuadV34DigModemNAC OBJECT IDENTIFIER ::= { uchasKnownModules 13 }

uchasQuadV34AnlModemNAC OBJECT IDENTIFIER ::= { uchasKnownModules 14 }

uchasQuadV34DigAnlModemNAC OBJECT IDENTIFIER ::= { uchasKnownModules 15 }

uchasSingleT1NAC OBJECT IDENTIFIER ::= { uchasKnownModules 16 }

uchasEthernetGatewayNAC OBJECT IDENTIFIER ::= { uchasKnownModules 17 }

uchasAccessServer OBJECT IDENTIFIER ::= { uchasKnownModules 18 }

uchas486TrGatewayNAC OBJECT IDENTIFIER ::= { uchasKnownModules 19 }

uchas486EthernetGatewayNAC OBJECT IDENTIFIER ::= { uchasKnownModules 20 }

uchasDualRS232NAC OBJECT IDENTIFIER ::= { uchasKnownModules 22 }

uchas486X25GatewayNAC OBJECT IDENTIFIER ::= { uchasKnownModules 23 }

uchasApplicationServerNAC OBJECT IDENTIFIER ::= { uchasKnownModules 25 }

uchasISDNGatewayNAC OBJECT IDENTIFIER ::= { uchasKnownModules 26 }

uchasISDNpriT1NAC OBJECT IDENTIFIER ::= { uchasKnownModules 27 }

uchasModemPoolManagmentNAC OBJECT IDENTIFIER ::= { uchasKnownModules 29 }

uchasModemPoolNetserverNAC OBJECT IDENTIFIER ::= { uchasKnownModules 30 }

uchasModemPoolV34ModemNAC OBJECT IDENTIFIER ::= { uchasKnownModules 31 }

uchasModemPoolISDNNAC OBJECT IDENTIFIER ::= { uchasKnownModules 32 }

uchasNTServerNAC OBJECT IDENTIFIER ::= { uchasKnownModules 33 }

uchasQuadV34AnalogG2NAC OBJECT IDENTIFIER ::= { uchasKnownModules 34 }

uchasQuadV34DigitalG2NAC OBJECT IDENTIFIER ::= { uchasKnownModules 35 }

uchasQuadV34DigAnlgG2NAC OBJECT IDENTIFIER ::= { uchasKnownModules 36 }

uchasNETServerFrameRelayNAC OBJECT IDENTIFIER ::= { uchasKnownModules 37 }

uchasNETServerTokenRingNAC OBJECT IDENTIFIER ::= { uchasKnownModules 38 }

uchasX2524ChannelNAC OBJECT IDENTIFIER ::= { uchasKnownModules 39 }

uchasDualT1NIC OBJECT IDENTIFIER ::= { uchasKnownModules 1001 }

uchasDualAlogMdmNIC OBJECT IDENTIFIER ::= { uchasKnownModules 1002 }

uchasQuadDgtlMdmNIC OBJECT IDENTIFIER ::= { uchasKnownModules 1003 }

uchasQuadAlogDgtlMdmNIC OBJECT IDENTIFIER ::= { uchasKnownModules 1004 }

uchasTokenRingNIC OBJECT IDENTIFIER ::= { uchasKnownModules 1005 }

uchasSingleT1NIC OBJECT IDENTIFIER ::= { uchasKnownModules 1006 }

uchasEthernetNIC OBJECT IDENTIFIER ::= { uchasKnownModules 1007 }

uchasShortHaulDualT1NIC OBJECT IDENTIFIER ::= { uchasKnownModules 1008 }

uchasDualAlogMgdIntlMdmNIC OBJECT IDENTIFIER ::= { uchasKnownModules 1009 }

uchasX25NIC OBJECT IDENTIFIER ::= { uchasKnownModules 1010 }

uchasQuadAlogNonMgdMdmNIC OBJECT IDENTIFIER ::= { uchasKnownModules 1011 }

uchasQuadAlogMgdIntlMdmNIC OBJECT IDENTIFIER ::= { uchasKnownModules 1012 }

uchasQuadAlogNonMgdIntlMdmNIC OBJECT IDENTIFIER ::= { uchasKnownModules 1013 }

uchasQuadLsdLiMgdMdmNIC OBJECT IDENTIFIER ::= { uchasKnownModules 1014 }

uchasQuadLsdLiNonMgdMdmNIC OBJECT IDENTIFIER ::= { uchasKnownModules 1015 }

uchasQuadLsdLiMgdIntlMdmNIC OBJECT IDENTIFIER ::= { uchasKnownModules 1016 }

uchasQuadLsdLiNonMgdIntlMdmNIC OBJECT IDENTIFIER ::= { uchasKnownModules 1017 }

uchasHSEthernetWithV35NIC OBJECT IDENTIFIER ::= { uchasKnownModules 1018 }

uchasHSEthernetWithoutV35NIC OBJECT IDENTIFIER ::= { uchasKnownModules 1019 }

uchasDualHighSpeedV35NIC OBJECT IDENTIFIER ::= { uchasKnownModules 1020 }

uchasQuadV35RS232LowSpeedNIC OBJECT IDENTIFIER ::= { uchasKnownModules 1021 }

uchasDualE1NIC OBJECT IDENTIFIER ::= { uchasKnownModules 1022 }

uchasShortHaulDualE1NIC OBJECT IDENTIFIER ::= { uchasKnownModules 1023 }

uchasKnownEntities OBJECT IDENTIFIER ::= { uchasKnownTypes 3 }

uchasNetwMgtEntity OBJECT IDENTIFIER ::= { uchasKnownEntities 1 }

uchasDualT1Entity OBJECT IDENTIFIER ::= { uchasKnownEntities 2 }

uchasDS1Entity OBJECT IDENTIFIER ::= { uchasKnownEntities 3 }

uchasModemEntity OBJECT IDENTIFIER ::= { uchasKnownEntities 4 }

uchasDualStandardModemEntity OBJECT IDENTIFIER ::= { uchasKnownEntities 5 }

uchasHSTModemEntity OBJECT IDENTIFIER ::= { uchasKnownEntities 6 }

uchasV32ModemEntity OBJECT IDENTIFIER ::= { uchasKnownEntities 7 }

uchasTokenRingEntity OBJECT IDENTIFIER ::= { uchasKnownEntities 8 }

uchasX25GatewayEntity OBJECT IDENTIFIER ::= { uchasKnownEntities 9 }

uchasDualStandardV32TerboMdEnt OBJECT IDENTIFIER ::= { uchasKnownEntities 10 }

uchasV32TerboModemEntity OBJECT IDENTIFIER ::= { uchasKnownEntities 11 }

uchasV32TerboFaxModemEntity OBJECT IDENTIFIER ::= { uchasKnownEntities 12 }

uchasDualStandardV34Modem OBJECT IDENTIFIER ::= { uchasKnownEntities 13 }

uchasV34ModemEntity OBJECT IDENTIFIER ::= { uchasKnownEntities 14 }

uchasV34FaxModemEntity OBJECT IDENTIFIER ::= { uchasKnownEntities 15 }

uchasSingleT1Entity OBJECT IDENTIFIER ::= { uchasKnownEntities 16 }

uchasEthernetGatewayEntity OBJECT IDENTIFIER ::= { uchasKnownEntities 17 }

uchasX25GatewaySubnetEntity OBJECT IDENTIFIER ::= { uchasKnownEntities 18 }

uchasTokenRingAccSrvrEntity OBJECT IDENTIFIER ::= { uchasKnownEntities 19 }

uchasEthernetAccSrvrEntity OBJECT IDENTIFIER ::= { uchasKnownEntities 20 }

uchasDualRS232Entity OBJECT IDENTIFIER ::= { uchasKnownEntities 22 }

uchasEnetFRIsdnNetservrEntity OBJECT IDENTIFIER ::= { uchasKnownEntities 23 }

uchasIsdnPriT1Entity OBJECT IDENTIFIER ::= { uchasKnownEntities 24 }

uchasTknRngIsdnNetserverEntity OBJECT IDENTIFIER ::= { uchasKnownEntities 25 }

uchasEnetNetserverEntity OBJECT IDENTIFIER ::= { uchasKnownEntities 26 }

uchasIsdnPriE1Entity OBJECT IDENTIFIER ::= { uchasKnownEntities 27 }

uchasAnalogMdmNicEntity OBJECT IDENTIFIER ::= { uchasKnownEntities 1001 }

uchasWellKnownSensors OBJECT IDENTIFIER ::= { uchasKnownTypes 4 }

uchasSensorOther OBJECT IDENTIFIER ::= { uchasWellKnownSensors 1 }

uchasSensorTemperature OBJECT IDENTIFIER ::= { uchasWellKnownSensors 2 }

uchasSensorFans OBJECT IDENTIFIER ::= { uchasWellKnownSensors 3 }

uchasCmd OBJECT IDENTIFIER ::= { chs 7 }

uchasCmdTable OBJECT-TYPE
SYNTAX SEQUENCE OF UchasCmdEntry
ACCESS not-accessible
STATUS mandatory
DESCRIPTION
"The Chassis Command table contains an entry for each of the 
NIC and NAC slots in the chassis.  It provides a means 
through which to take specific actions on one or more 
devices in the chassis at a card level.  Device specific 
commands are not included here, but rather in the specific 
MIB used to manage the device."
::= { uchasCmd 1 }

uchasCmdEntry OBJECT-TYPE
SYNTAX UchasCmdEntry
ACCESS not-accessible
STATUS mandatory
DESCRIPTION
"There is one entry in this table for each row in 
uchasSlotTable."
INDEX { uchasCmdSlotIndex }
::= { uchasCmdTable 1 }

UchasCmdEntry ::=
SEQUENCE {
uchasCmdSlotIndex
    INTEGER,
uchasCmdMgtStationId
    OCTET STRING,
uchasCmdReqId
    INTEGER,
uchasCmdFunction
    INTEGER,
uchasCmdForce
    INTEGER,
uchasCmdParam
    OCTET STRING,
uchasCmdResult
    INTEGER,
uchasCmdCode
    INTEGER
}

uchasCmdSlotIndex OBJECT-TYPE
SYNTAX INTEGER
ACCESS read-only
STATUS mandatory
DESCRIPTION
"This index uniquely identifies the slot to which the 
command being written is to take place.  Values of 
uchasCmdSlotIndex correspond to values used to index 
uchasSlotTable."
::= { uchasCmdEntry 1 }

uchasCmdMgtStationId OBJECT-TYPE
SYNTAX OCTET STRING (SIZE(0..8))
ACCESS read-write
STATUS mandatory
DESCRIPTION
"This object is a generic read-write variable that a 
Management Station (MS) can use to guarantee that the 
results from a given command are the results of a command 
issued by that specific MS.  Each MS must SET a unique 
value to this object when doing commands and GET the value 
of this object together with uchasCmdReqId and 
uchasCmdResult to detect interference from other MSs."
::= { uchasCmdEntry 2 }

uchasCmdReqId OBJECT-TYPE
SYNTAX INTEGER
ACCESS read-only
STATUS mandatory
DESCRIPTION
"Ths object contains the value of the request-id field in 
the SNMP PDU which invoked the current or most recent 
command on the device in the specified slot of the chassis. 
 If the request-id is unknown or undefined, this value 
contains the value zero."
::= { uchasCmdEntry 3 }

uchasCmdFunction OBJECT-TYPE
SYNTAX INTEGER{
  noCommand(1),
  removeFromService(2),
  restoreToService(3),
  hardwareReset(4),
  softwareDownload(5)
}
ACCESS read-write
STATUS mandatory
DESCRIPTION
"A control variable used to start and stop 
operator-initiated commands.  A command is initiated by 
setting this object to a value other than noCommand(1).  
When the value noCommand(1) is written to this object, no 
action is taken, unless a command is in progress, in which 
case the command is aborted."
::= { uchasCmdEntry 4 }

uchasCmdForce OBJECT-TYPE
SYNTAX INTEGER{
  force(1),
  noForce(2)
}
ACCESS read-write
STATUS mandatory
DESCRIPTION
"In some cases, the devices in the  chassis may be in a 
state such that certain commands could adversely affect 
connections or other device specific operations.  In such 
cases, a command with uchasCmdForce set to noForce will 
result in a warning.  If the operator elects to ignore such 
warnings, uchasCmdForce can be set to force in the command 
request and the command will be carried out regardless of 
its potentially hazzardous effects."
::= { uchasCmdEntry 5 }

uchasCmdParam OBJECT-TYPE
SYNTAX OCTET STRING (SIZE(0..24))
ACCESS read-write
STATUS mandatory
DESCRIPTION
"This object contains parameters that are specific to the 
particular command being issued.  In some cases, there will 
be no additional parameters required."
::= { uchasCmdEntry 6 }

uchasCmdResult OBJECT-TYPE
SYNTAX INTEGER{
  none(1),
  success(2),
  inProgress(3),
  notSupported(4),
  unAbleToRun(5),
  aborted(6),
  failed(7)
}
ACCESS read-only
STATUS mandatory
DESCRIPTION
"This object contains the result of the most recently 
requested test, or the value none(1) if not commands have 
been requested since the last reset.  Note that this 
facility provides no provision for saving the results of 
one command when starting another, as could be required if 
used by multiple managers concurrently."
::= { uchasCmdEntry 7 }

uchasCmdCode OBJECT-TYPE
SYNTAX INTEGER{
  noError(1),
  unable(2),
  unrecognizedCommand(6),
  slotEmpty(8),
  noResponse(12),
  connected(14),
  unsupportedCommand(20),
  nonManagedDevice(21),
  deviceDisabled(22),
  userInterfaceActive(58),
  badFlashRomID(61),
  badFlashVoltage(62),
  flashEraseError(63),
  eraseSequenceError(64),
  eraseExecutionError(65),
  receiveBufferOverflow(66),
  badAddressInData(67),
  badProgramVoltage(68),
  programmingDataError(69),
  programCodeError(70),
  invalidCodeError(71),
  romCrcBad(72),
  pendingSoftwareDownload(73),
  ramCrcBad(74),
  invalidRomId(75),
  sdlTrigger(76),
  downloadingSdlFile(77),
  crcTestingSdlFile(78),
  queryWorkSpaceSize(79),
  executeLoadedProgram(80),
  erasingFlash(81),
  downloadingNacFile(82),
  resetingNac(83),
  cardIdMismatch(84),
  cardIdUnknown(85),
  tftpTimeout(86),
  flashEraseTimeout(87),
  invalidFileHeader(88)
}
ACCESS read-only
STATUS mandatory
DESCRIPTION
"The value of this object upon command completion indicates 
a further description of what went wrong if the command was 
unsuccessful.  This object is also used as an indication of 
the in progress status of the software download command." 
::= { uchasCmdEntry 8 }

uchasTrapEnable OBJECT IDENTIFIER ::= { chs 8 }

uchasModuleInsertedTrapEna OBJECT-TYPE
SYNTAX INTEGER{
  enableTrap(1),
  disableAll(2),
  enableLog(3),
  enableAll(4)
}
ACCESS read-write
STATUS optional
DESCRIPTION
"Enables the generation of a trap when a card is inserted 
into the chassis.  This parameter is effective across all 
slots in the chassis."
::= { uchasTrapEnable 1 }

uchasModuleRemovedTrapEna OBJECT-TYPE
SYNTAX INTEGER{
  enableTrap(1),
  disableAll(2),
  enableLog(3),
  enableAll(4)
}
ACCESS read-write
STATUS optional
DESCRIPTION
"Enables the generation of a trap when a card is removed 
from the chassis.  This parameter is effective across all 
slots in the chassis."
::= { uchasTrapEnable 2 }

uchasPSUWarningTrapEna OBJECT-TYPE
SYNTAX INTEGER{
  enableTrap(1),
  disableAll(2),
  enableLog(3),
  enableAll(4)
}
ACCESS read-write
STATUS optional
DESCRIPTION
"Enables the generation of a trap when a power supply enters 
a warning state, such as one or more output voltages being 
out of range.  This parameter is effective across all PSUs 
in the chassis."
::= { uchasTrapEnable 3 }

uchasPSUFailureTrapEna OBJECT-TYPE
SYNTAX INTEGER{
  enableTrap(1),
  disableAll(2),
  enableLog(3),
  enableAll(4)
}
ACCESS read-write
STATUS optional
DESCRIPTION
"Enables the generation of a trap when a power supply fails 
and has been automatically shut down due to overvoltage, 
overcurrent, etc.  This parameter is effective across all 
PSUs in the chassis."
::= { uchasTrapEnable 4 }

uchasTempWarningTrapEna OBJECT-TYPE
SYNTAX INTEGER{
  enableTrap(1),
  disableAll(2),
  enableLog(3),
  enableAll(4)
}
ACCESS read-write
STATUS optional
DESCRIPTION
"Enables the generation of a trap when the temperature in 
the chassis, as detected by the NMC, becomes excessive."
::= { uchasTrapEnable 5 }

uchasFanFailureTrapEna OBJECT-TYPE
SYNTAX INTEGER{
  enableTrap(1),
  disableAll(2),
  enableLog(3),
  enableAll(4)
}
ACCESS read-write
STATUS optional
DESCRIPTION
"Enables the generation of a trap when the fan in the 
chassis is not rotating with sufficient speed to cool the 
power supplies."
::= { uchasTrapEnable 6 }

uchasEntityWatchdogTrapEna OBJECT-TYPE
SYNTAX INTEGER{
  enableTrap(1),
  disableAll(2),
  enableLog(3),
  enableAll(4)
}
ACCESS read-write
STATUS mandatory
DESCRIPTION
"Enables the generation of a trap when a logical networking 
entity in the chassis undergoes a watchdog timeout event, 
indicating software failure."
::= { uchasTrapEnable 7 }

uchasEntityMgtBusFailTrapEna OBJECT-TYPE
SYNTAX INTEGER{
  enableTrap(1),
  disableAll(2),
  enableLog(3),
  enableAll(4)
}
ACCESS read-write
STATUS mandatory
DESCRIPTION
"Enables the generation of a trap when the SNMP proxy agent 
in the NMC is unable to communicate properly with a logical 
networking entity in the chassis."
::= { uchasTrapEnable 8 }

uchasAutoResponse OBJECT IDENTIFIER ::= { chs 9 }

uchasArPsuVoltOutOfRange OBJECT-TYPE
SYNTAX OCTET STRING (SIZE(0..20))
ACCESS read-write
STATUS optional
DESCRIPTION
"This script is triggered when the NMC detects that voltage 
levels, for at least one power supply on the mid plane, are 
outside the normal operating range."
::= { uchasAutoResponse 1 }

uchasArPsuFailed OBJECT-TYPE
SYNTAX OCTET STRING (SIZE(0..20))
ACCESS read-write
STATUS optional
DESCRIPTION
"This script is triggered when the NMC detects an 
over-voltage or over-current condition present in the PSU."
::= { uchasAutoResponse 2 }

uchasArFanFailed OBJECT-TYPE
SYNTAX OCTET STRING (SIZE(0..20))
ACCESS read-write
STATUS optional
DESCRIPTION
"This script is triggered when the fan speed becomes 
dangerously slow as to risk damage to inadequate cooling of 
the chassis."
::= { uchasAutoResponse 3 }

uchasArHubTempOutOfRange OBJECT-TYPE
SYNTAX OCTET STRING (SIZE(0..20))
ACCESS read-write
STATUS optional
DESCRIPTION
"This script is triggered when the chassis temperature is 
outside the specified normal operating range."
::= { uchasAutoResponse 4 }

uchasArTimer1 OBJECT-TYPE
SYNTAX OCTET STRING (SIZE(0..20))
ACCESS read-write
STATUS optional
DESCRIPTION
"This script is triggered when the first general purpose 
timer expires."
::= { uchasAutoResponse 5 }

uchasArTimer2 OBJECT-TYPE
SYNTAX OCTET STRING (SIZE(0..20))
ACCESS read-write
STATUS optional
DESCRIPTION
"This script is triggered when the second general purpose 
timer expires."
::= { uchasAutoResponse 6 }

uchasArTimer3 OBJECT-TYPE
SYNTAX OCTET STRING (SIZE(0..20))
ACCESS read-write
STATUS optional
DESCRIPTION
"This script is triggered when the third general purpose 
timer expires."
::= { uchasAutoResponse 7 }

uchasArTimer4 OBJECT-TYPE
SYNTAX OCTET STRING (SIZE(0..20))
ACCESS read-write
STATUS optional
DESCRIPTION
"This script is triggered when the fourth general purpose 
timer expires."
::= { uchasAutoResponse 8 }

uchasArSlotTable OBJECT-TYPE
SYNTAX SEQUENCE OF UchasArSlotEntry
ACCESS not-accessible
STATUS optional
DESCRIPTION
"A table that contains auto response scripts, in the 
chassis, that act on a particular slot."
::= { uchasAutoResponse 9 }

uchasArSlotEntry OBJECT-TYPE
SYNTAX UchasArSlotEntry
ACCESS not-accessible
STATUS optional
DESCRIPTION
"A list of auto response scripts, in the chassis, that act 
on a slot."
INDEX { uchasArSlotIndex }
::= { uchasArSlotTable 1 }

UchasArSlotEntry ::=
SEQUENCE {
uchasArSlotIndex
    INTEGER,
uchasArModuleInserted
    OCTET STRING,
uchasArModuleReinit
    OCTET STRING,
uchasArModuleRemoved
    OCTET STRING,
uchasArModuleNonoper
    OCTET STRING,
uchasArModuleWatchdog
    OCTET STRING
}

uchasArSlotIndex OBJECT-TYPE
SYNTAX INTEGER (1..37)
ACCESS read-only
STATUS optional
DESCRIPTION
"The slot number for which this entry contains an auto 
response script. NAC slots are numbered from 1 to 16. The 
Network Management Card (NMC) goes into slot 17. To keep 
things simple, the corresponding NIC slot numbers are from 
21 to 37. Rows for slots 18 to 20 do not exist."
::= { uchasArSlotEntry 1 }

uchasArModuleInserted OBJECT-TYPE
SYNTAX OCTET STRING (SIZE(0..20))
ACCESS read-write
STATUS optional
DESCRIPTION
"This script is triggered when a module is inserted in the 
chassis."
::= { uchasArSlotEntry 2 }

uchasArModuleReinit OBJECT-TYPE
SYNTAX OCTET STRING (SIZE(0..20))
ACCESS read-write
STATUS optional
DESCRIPTION
"This script is triggered when the following occur: chassis 
power transitions from off to on; a module is inserted in 
the chassis; software download has just been completed to a 
module; a module is restored to service; or a module is 
reset (hardware)."
::= { uchasArSlotEntry 3 }

uchasArModuleRemoved OBJECT-TYPE
SYNTAX OCTET STRING (SIZE(0..20))
ACCESS read-write
STATUS optional
DESCRIPTION
"This script is triggered when a module is physically 
removed from the chassis."
::= { uchasArSlotEntry 4 }

uchasArModuleNonoper OBJECT-TYPE
SYNTAX OCTET STRING (SIZE(0..20))
ACCESS read-write
STATUS optional
DESCRIPTION
"This script is triggered when the following occur: software 
download to a module has just been started; a module is 
removed from service; or a module has failed (i.e. all 
entities on that module have failed)."
::= { uchasArSlotEntry 5 }

uchasArModuleWatchdog OBJECT-TYPE
SYNTAX OCTET STRING (SIZE(0..20))
ACCESS read-write
STATUS optional
DESCRIPTION
"This script is triggered when one or more module entities 
experience a watchdog time-out."
::= { uchasArSlotEntry 6 }

uchasArTimers OBJECT IDENTIFIER ::= { chs 10 }

uchasArTimerTable OBJECT-TYPE
SYNTAX SEQUENCE OF UchasArTimerEntry
ACCESS not-accessible
STATUS optional
DESCRIPTION
"A table that contains general purpose global timer 
parameters. These timers act on an entire chassis."
::= { uchasArTimers 1 }

uchasArTimerEntry OBJECT-TYPE
SYNTAX UchasArTimerEntry
ACCESS not-accessible
STATUS optional
DESCRIPTION
"A list of parameters for general purpose global timers."
INDEX { uchasArTimerIndex }
::= { uchasArTimerTable 1 }

UchasArTimerEntry ::=
SEQUENCE {
uchasArTimerIndex
    INTEGER,
uchasArTimerEna
    INTEGER,
uchasArTimerStartDate
    DisplayString,
uchasArTimerStartTime
    DisplayString,
uchasArTimerStopDate
    DisplayString,
uchasArTimerStopTime
    DisplayString,
uchasArTimerInterval
    INTEGER,
uchasArTimerState
    INTEGER,
uchasArTimerTriggers
    Counter
}

uchasArTimerIndex OBJECT-TYPE
SYNTAX INTEGER (1..4)
ACCESS read-only
STATUS optional
DESCRIPTION
"The number of general purpose global timers."
::= { uchasArTimerEntry 1 }

uchasArTimerEna OBJECT-TYPE
SYNTAX INTEGER{
  disable(1),
  enable(2)
}
ACCESS read-write
STATUS optional
DESCRIPTION
"Enable or disable the specified global timer."
::= { uchasArTimerEntry 2 }

uchasArTimerStartDate OBJECT-TYPE
SYNTAX DisplayString (SIZE(5..8))
ACCESS read-write
STATUS optional
DESCRIPTION
"This object determines the date on which the timer becomes 
active. This date is compared against the system date, time 
and time zone defined in management entity. 
Default=01/01/95"
::= { uchasArTimerEntry 3 }

uchasArTimerStartTime OBJECT-TYPE
SYNTAX DisplayString (SIZE(5..8))
ACCESS read-write
STATUS optional
DESCRIPTION
"This object determines the time on which the timer becomes 
active. This time is compared against the system date, time 
and time zone defined in management entity. 
Default=00:00:00"
::= { uchasArTimerEntry 4 }

uchasArTimerStopDate OBJECT-TYPE
SYNTAX DisplayString (SIZE(5..8))
ACCESS read-write
STATUS optional
DESCRIPTION
"This object specifies the date on which this timer becomes 
passive. This date is compared against the system date, 
time and time zone defined in management entity. The timer 
will not be active if the timer stop date and time  is less 
than system date and time. Default = 01/01/95" 
::= { uchasArTimerEntry 5 }

uchasArTimerStopTime OBJECT-TYPE
SYNTAX DisplayString (SIZE(5..8))
ACCESS read-write
STATUS optional
DESCRIPTION
"This object specifies the time on which this timer becomes 
passive. This time is compared against the system date, 
time and time zone defined in management entity. The timer 
will not be active if the timer stop date and time is less 
than system date and time. Default = 00:00:00" 
::= { uchasArTimerEntry 6 }

uchasArTimerInterval OBJECT-TYPE
SYNTAX INTEGER (0..2678400)
ACCESS read-write
STATUS optional
DESCRIPTION
"The interval in seconds between each timer firing. The 
firings will happen at each interval after the timer starts 
until the date/time specified if the following 2 conditions 
are met. First, TimerInterval must be  less than or equal 
to the timer active period. Second, The start date/time is 
less than the stop date/time. The timer will fire only once 
at stop date/time if a zero value has been assigned to this 
object. Default = 0. Max 259000 sec = 30 days."
::= { uchasArTimerEntry 7 }

uchasArTimerState OBJECT-TYPE
SYNTAX INTEGER{
  init(1),
  passive(2),
  active(3)
}
ACCESS read-only
STATUS optional
DESCRIPTION
"This object indicates the current state of the global 
timer."
::= { uchasArTimerEntry 8 }

uchasArTimerTriggers OBJECT-TYPE
SYNTAX Counter
ACCESS read-only
STATUS optional
DESCRIPTION
"This object indicates the number of times that a global 
timer has triggered since the last system boot time."
::= { uchasArTimerEntry 9 }

END
