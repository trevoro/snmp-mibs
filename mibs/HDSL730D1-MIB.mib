-- Copyright 1994 General DataComm Inc., Inc. All Rights Reserved.
--
-- Reproduction of this document is authorized on condition that the
-- foregoing copyright notice is included. This General DataComm, GDC,
-- SNMP Management Information Base Specification embodies GDCs'
-- confidential and proprietary intellectual property. GDC retains all
-- title and ownership in the Specification, including any revisions.
--
-- It is GDCs intent to encourage the widespread use of this Specification
-- in connection with the management of GDC's products. GDC grants vendors,
-- end-users, and other interested parties a non-exclusive license to use
-- this Specification in connection with the management of GDC's products.
--
-- This Specification is supplied "AS IS," and GDC makes no warranty,
-- either expressed or implied, as to the use operation, condition, or
-- performance of the Specification.

-- Revision History
-- Version   Date	Name		Description
-- 1.00A     10-Feb-95  E. Moreno-Leon  Initial Revision
-- 1.00B     01-Sep-95	C. Amorossi	Added Interface Comments
-- 1.00C     13-Mar-96	E. Moreno-Leon	Added Major and Minor BER Alarms

HDSL730D1-MIB DEFINITIONS ::= BEGIN

IMPORTS
	OBJECT-TYPE			FROM RFC-1212
	DisplayString			FROM RFC1213-MIB
	hdsl730D1                       FROM GDCHDSL-MIB;

hdsl730D1System          OBJECT IDENTIFIER ::= { hdsl730D1 1 }
hdsl730D1Version         OBJECT IDENTIFIER ::= { hdsl730D1System 1 }

-- This mib is a subset of the HDSL mib for the 730D1 product.

-- ***************************************************************************
-- The interfaces are defined as follows:
--	Unit	0
--	DTE	1
--	Loop1	2
-- ***************************************************************************

gdc730D1SystemMIBversion OBJECT-TYPE
     	SYNTAX DisplayString (SIZE (5))
     	ACCESS read-only
     	STATUS mandatory
     	DESCRIPTION
     		"Identifies the version of the MIB. The format of the version
     		is x.yzT, where 'x' identifies the major revision number, 'y'
     		identifies the minor revision number, 'z' identifies the
     		typographical revision, and T identifies the test revision.
     		Acceptable values for the individual revision components are
     		as follows:
 
     		x: 1 - 9
     		y: 0 - 9
     		z: 0 - 9
     		T: A - Z
 
     		Upon formal release, no designation for the test revision will
     		be present."
     	::= { hdsl730D1Version 1 }

--********************************************************************
-- GDC Hdsl Alarm Object Identifier Definitions
--********************************************************************
hdsl730D1Alarms          OBJECT IDENTIFIER ::= { hdsl730D1 2 }

hdsl730D1NoResponseAlm		OBJECT IDENTIFIER ::= { hdsl730D1Alarms 1 }
hdsl730D1DiagRxErrAlm		OBJECT IDENTIFIER ::= { hdsl730D1Alarms 2 }
hdsl730D1PowerUpAlm		OBJECT IDENTIFIER ::= { hdsl730D1Alarms 3 }
hdsl730D1UnitFailure	        OBJECT IDENTIFIER ::= { hdsl730D1Alarms 4 }
hdsl730D1ChecksumCorrupt        OBJECT IDENTIFIER ::= { hdsl730D1Alarms 5 }
hdsl730D1LossofSignal		OBJECT IDENTIFIER ::= { hdsl730D1Alarms 6 }
hdsl730D1UnavailableSec		OBJECT IDENTIFIER ::= { hdsl730D1Alarms 7 }
hdsl730D1ErrorSec		OBJECT IDENTIFIER ::= { hdsl730D1Alarms 8 }
hdsl730D1LossofSyncWord		OBJECT IDENTIFIER ::= { hdsl730D1Alarms 9 }
hdsl730D1MajorBER 		OBJECT IDENTIFIER ::= { hdsl730D1Alarms 10 }
hdsl730D1MinorBER 		OBJECT IDENTIFIER ::= { hdsl730D1Alarms 11 }


-- ALARM			Maskable	Valid Interfaces
--===============================================================
--hdslNoResponseAlm		No		Unit
--hdslDiagRxErrAlm              No              Unit
--hdslPowerUpAlm		No		Unit
--hdslUnitFailure               No              Unit
--hdslChecksumCorrupt           No              Unit
--hdslLossofSignal		Yes		L1 
--hdslUnavailableSec		Yes		L1
--hdslErrorSec			Yes		L1
--hdslLossofSyncWord		Yes		L1
--hdsl730D1MajorBER		Yes		L1
--hdsl730D1MinorBER		Yes		L1





END
