-- SONET HEC CELL ERROR MONITOR MIB
-- Srinibas Maharana, Alcatel Internetworking, Inc., India

XYLAN-SONET-CELL-ERR-MIB DEFINITIONS ::= BEGIN

IMPORTS
   DisplayString
      FROM RFC1213-MIB
   OBJECT-TYPE
      FROM RFC-1212
   xylanSonetArch
      FROM XYLAN-BASE-MIB;

xylanSonetErrStats  OBJECT IDENTIFIER  ::=  { xylanSonetArch 2 }


-- This is the Alcatel Internetworking, Inc. proprietary MIB module for 
-- monitoring the SONET/SDH Cell Error Statistics 

xylanSonetPortStatTable   OBJECT-TYPE
SYNTAX   SEQUENCE OF XylanSonetPortStatEntry 
     ACCESS   not-accessible
     STATUS   mandatory
     DESCRIPTION
        "A table for SONET Port Cell Error Statistics."
     ::= { xylanSonetErrStats 1}

  xylanSonetPortStatEntry   OBJECT-TYPE
     SYNTAX   XylanSonetPortStatEntry
     ACCESS   not-accessible
     STATUS   mandatory
     DESCRIPTION
        "An entry in the table, contains information about 
         Cell Error Statistics for the SONET ports."
     INDEX   { xylanSonetPortStatSlotIndex, xylanSonetPortStatPortIndex }
     ::= { xylanSonetPortStatTable 1 }

  XylanSonetPortStatEntry ::=
      SEQUENCE {
          xylanSonetPortStatSlotIndex
              INTEGER,
          xylanSonetPortStatPortIndex
              INTEGER,
          xylanSonetPortStatRxCellCount
              INTEGER,
          xylanSonetPortStatCorrHCSCellCount
              INTEGER,
          xylanSonetPortStatUncorrHCSCellCount
              INTEGER
  }

  xylanSonetPortStatSlotIndex OBJECT-TYPE
      SYNTAX   INTEGER (1..9)
      ACCESS   read-only
      STATUS   mandatory
      DESCRIPTION
         "A unique value which identifies the CSM/ASM board slot."
      ::= { xylanSonetPortStatEntry 1 }

  xylanSonetPortStatPortIndex OBJECT-TYPE
      SYNTAX   INTEGER
      ACCESS   read-only
      STATUS   mandatory
      DESCRIPTION
         "A unique value which identifies the SONET port on the slot."
      ::= { xylanSonetPortStatEntry 2 }

  xylanSonetPortStatRxCellCount OBJECT-TYPE
      SYNTAX   INTEGER 
      ACCESS   read-only
      STATUS   mandatory
      DESCRIPTION
         "The Receive Cell Count on the SONET port."
      ::= { xylanSonetPortStatEntry 3 }

 xylanSonetPortStatCorrHCSCellCount   OBJECT-TYPE
      SYNTAX   INTEGER 
      ACCESS   read-only
      STATUS   mandatory
      DESCRIPTION
         " The Correctable HCS Cell Receive Count on the SONET port. "
      ::= { xylanSonetPortStatEntry 4 }

  xylanSonetPortStatUncorrHCSCellCount OBJECT-TYPE
      SYNTAX   INTEGER 
      ACCESS   read-only
      STATUS   mandatory
      DESCRIPTION
         " The Uncorrectable HCS Cell Receive Count on the SONET port."
      ::= { xylanSonetPortStatEntry 5 }
END
