-- *****************************************************************
-- CISCO-IMA-EXT-CAPABILITY
--
-- AGENT-CAPABILITIES mib for CISCO-IMA-MIB
--
-- March 2002, Wayne W. Cai
-- Copyright(c) 2002 by Cisco Systems,Inc.
--
-- *****************************************************************

CISCO-IMA-EXT-CAPABILITY DEFINITIONS ::= BEGIN

IMPORTS
        MODULE-IDENTITY
                FROM SNMPv2-SMI
        MilliSeconds
                FROM IMA-MIB
        AGENT-CAPABILITIES
                FROM SNMPv2-CONF
        ciscoAgentCapability
                FROM CISCO-SMI;

ciscoImaExtCapability MODULE-IDENTITY
        LAST-UPDATED    "200203040000Z"
        ORGANIZATION    "Cisco Systems, Inc."
        CONTACT-INFO
                "       Cisco Systems
                        Customer Service

                Postal: 170 W Tasman Drive
                        San Jose, CA  95134
                        USA

                        Tel: +1 800 553-NETS

                E-mail: cs-wanatm@cisco.com"
DESCRIPTION
    "The Agent Capabilities for CISCO-IMA-MIB.

     - ciscoImaExtAxsmeCapabilityV3R0 is for 
       Enhanced ATM Switch Service Module(AXSM-E)."
           
REVISION    "200203040000Z"
DESCRIPTION
    "Initial version of this MIB module."

::= { ciscoAgentCapability  255 }

ciscoImaExtAxsmeCapabilityV3R0 AGENT-CAPABILITIES

PRODUCT-RELEASE "MGX8850 Release 3.0"
STATUS          current
DESCRIPTION     "Agent capabilities for CISCO-IMA-MIB
                 for AXSME Service Module in MGX8850 Series."

SUPPORTS        CISCO-IMA-MIB
INCLUDES        { ciscoImaGroupGroup, ciscoImaLinkGroup,
                  ciscoImaAlarmGroup, ciscoImaLinkMappingGroup }

VARIATION       cimaGrpAlarmType
ACCESS          not-implemented
DESCRIPTION     "Not Supported."

VARIATION       cimaLinkAlarmType
ACCESS          not-implemented
DESCRIPTION     "Not Supported."

VARIATION       cimaStuffAndCellIndication
DESCRIPTION     "Supported with limitation.
                 Agent only supports mandatory '000' and '001'
                 stuff events."

VARIATION       cimaGrpNumTxIcpCells
ACCESS          not-implemented
DESCRIPTION     "Not Supported."

VARIATION       cimaGrpNumRxIcpCells
ACCESS          not-implemented
DESCRIPTION     "Not Supported."

VARIATION       cimaGrpNumRxErrIcpCells
ACCESS          not-implemented
DESCRIPTION     "Not Supported."

VARIATION       cimaGrpNumRxInvalidIcpCells
ACCESS          not-implemented
DESCRIPTION     "Not Supported."

VARIATION       cimaGrpNumRxMissingIcpCells
ACCESS          not-implemented
DESCRIPTION     "Not Supported."

VARIATION       cimaGrpNumTxMissingIcpCells
ACCESS          not-implemented
DESCRIPTION     "Not Supported."

VARIATION       cimaLinkLifIntUpTime
SYNTAX          MilliSeconds (2500..2500)
ACCESS          read-only
DESCRIPTION     "Supported with limitation.
                 Agent only supports default 2500 milliseconds."

VARIATION       cimaLinkLifIntDownTime
SYNTAX          MilliSeconds (10000..10000)
ACCESS          read-only
DESCRIPTION     "Supported with limitation.
                 Agent only supports default 10000 milliseconds."

VARIATION       cimaLinkLodsIntUpTime
SYNTAX          MilliSeconds (2500..2500)
ACCESS          read-only
DESCRIPTION     "Supported with limitation.
                 Agent only supports default 2500 milliseconds."

VARIATION       cimaLinkLodsIntDownTime
SYNTAX          MilliSeconds (10000..10000)
ACCESS          read-only
DESCRIPTION     "Supported with limitation.
                 Agent only supports default 10000 milliseconds."

VARIATION       cimaLinkNumTxIcpCells
ACCESS          not-implemented
DESCRIPTION     "Not Supported."

VARIATION       cimaLinkNumRxErrIcpCells
ACCESS          not-implemented
DESCRIPTION     "Not Supported."

VARIATION       cimaLinkNumRxInvalidIcpCells
ACCESS          not-implemented
DESCRIPTION     "Not Supported."

VARIATION       cimaLinkNumRxMissingIcpCells
ACCESS          not-implemented
DESCRIPTION     "Not Supported."

VARIATION       cimaLinkNumTxMissingIcpCells
ACCESS          not-implemented
DESCRIPTION     "Not Supported."

::= { ciscoImaExtCapability 1 }

END
