INTEL-SYS-MIB DEFINITIONS ::= BEGIN

IMPORTS
IpAddress       FROM RFC1155-SMI
products        FROM Intel-Common-MIB
DisplayString   FROM RFC1213-MIB
OBJECT-TYPE     FROM RFC-1212;

snmp-agents     OBJECT IDENTIFIER ::= { products    6 }

agentConfiguration    OBJECT IDENTIFIER ::= { snmp-agents 1 }

agentVendorName   OBJECT-TYPE
    SYNTAX    DisplayString (SIZE (128))
    ACCESS    read-only
    STATUS    mandatory
    DESCRIPTION
          "Displays the SNMP agent's manufacturer name.  "
    ::= { agentConfiguration    1 }

agentProductName   OBJECT-TYPE
    SYNTAX    DisplayString (SIZE (128))
    ACCESS    read-only
    STATUS    mandatory
    DESCRIPTION
          "Displays the product name that contains the SNMP agent.  "
    ::= { agentConfiguration    2 }

agentChassisIndex   OBJECT-TYPE
    SYNTAX    INTEGER
    ACCESS    read-only
    STATUS    mandatory
    DESCRIPTION
          "Displays which chassis contains the SNMP agent's module.  "
    ::= { agentConfiguration    3 }

agentModuleIndex   OBJECT-TYPE
    SYNTAX    INTEGER
    ACCESS    read-only
    STATUS    mandatory
    DESCRIPTION
          "Displays which module in the chassis is the SNMP agent's
           module. The chassis number is in the object agentChassisIndex. "
    ::= { agentConfiguration    4 }

mibversion   OBJECT-TYPE
    SYNTAX    DisplayString (SIZE (8))
    ACCESS    read-only
    STATUS    mandatory
    DESCRIPTION
          "Displays the version of the MIB supported by the SNMP agent.  "
    ::= { agentConfiguration    5 }

resetAgent   OBJECT-TYPE
    SYNTAX    INTEGER  {
                reset(1),
                notreset(2)
                }
    ACCESS    read-write
    STATUS    mandatory
    DESCRIPTION
          "Performs a cold reset of the SNMP agent. If a new IP configuration
           was set, it will be used after the reset.  "
    ::= { agentConfiguration    6 }

ipConfiguration        OBJECT IDENTIFIER ::= { snmp-agents 2 }

ipAddressMethodInUse   OBJECT-TYPE
    SYNTAX    INTEGER  {
                fixed(1),
                bootp(2)
                }
    ACCESS    read-only
    STATUS    mandatory
    DESCRIPTION
          "Displays how the IP address in use was determined. 
           For example, fixed means the IP address was assigned by the
           user and stored within the Management Module. BOOTP means the
           SNMP agent used a BOOTP server to get its IP configuration. "
    ::= { ipConfiguration    1 }

ipAddressInUse   OBJECT-TYPE
    SYNTAX    IpAddress
    ACCESS    read-only
    STATUS    mandatory
    DESCRIPTION
          "Displays the IP address currently in use.  "
    ::= { ipConfiguration    2 }

gatewayorRouterAddrInUse   OBJECT-TYPE
    SYNTAX    IpAddress
    ACCESS    read-only
    STATUS    mandatory
    DESCRIPTION
          "Displays the default gateway address currently in use. 
           This is the device that routes to a different network. 
           Usually a router or a routing server.  "
    ::= { ipConfiguration    3 }

networkMaskInUse   OBJECT-TYPE
    SYNTAX    IpAddress
    ACCESS    read-only
    STATUS    mandatory
    DESCRIPTION
          "Displays the network (subnet) mask currently in use. This
           must match the masks of other devices on the same network.  "
    ::= { ipConfiguration    4 }

broadcastAddressInUse   OBJECT-TYPE
    SYNTAX    IpAddress
    ACCESS    read-only
    STATUS    mandatory
    DESCRIPTION
          "Displays the broadcast address currently in use. "
    ::= { ipConfiguration    5 }

ipAddressMethodNextReset   OBJECT-TYPE
    SYNTAX    INTEGER  {
                fixed(1),
                bootp(2)
                }
    ACCESS    read-write
    STATUS    mandatory
    DESCRIPTION
          "Displays how the IP address will be determined after the 
           SNMP agent is reset. For example, fixed means the IP address 
           will be determined locally. BOOTP means the SNMP agent will 
           search for a BOOTP server to get its IP configuration. "
    ::= { ipConfiguration    6 }

ipAddressNextReset   OBJECT-TYPE
    SYNTAX    IpAddress
    ACCESS    read-write
    STATUS    mandatory
    DESCRIPTION
          "Displays the IP address the SNMP agent will use the next
           time it is reset.  "
    ::= { ipConfiguration    7 }

gatewayorRouterAddrNextReset   OBJECT-TYPE
    SYNTAX    IpAddress
    ACCESS    read-write
    STATUS    mandatory
    DESCRIPTION
          "Displays the default gateway the SNMP agent will use the next
           time it is reset. "
    ::= { ipConfiguration    8 }

networkMaskNextReset   OBJECT-TYPE
    SYNTAX    IpAddress
    ACCESS    read-write
    STATUS    mandatory
    DESCRIPTION
          "Displays the netmask (subnet mask) the SNMP agent will use the next 
           time it is reset. "
    ::= { ipConfiguration    9 }

snmpConfiguration        OBJECT IDENTIFIER ::= { snmp-agents 3 }

snmpReadCommunityString   OBJECT-TYPE
    SYNTAX    DisplayString (SIZE (0..32))
    ACCESS    write-only
    STATUS    mandatory
    DESCRIPTION
          "Sets the password for reads from the SNMP agent's MIB.  "
    ::= { snmpConfiguration    1 }

snmpWriteCommunityString   OBJECT-TYPE
    SYNTAX    DisplayString (SIZE (0..32))
    ACCESS    write-only
    STATUS    mandatory
    DESCRIPTION
          "Sets the password for writes to the SNMP agent's MIB.  "
    ::= { snmpConfiguration    2 }

snmpTrapReceiverMAX   OBJECT-TYPE
    SYNTAX    INTEGER
    ACCESS    read-only
    STATUS    mandatory
    DESCRIPTION
          "Displays the maximum number of trap receiving stations.  "
    ::= { snmpConfiguration    3 }

snmpTrapReceiverNumber   OBJECT-TYPE
    SYNTAX    INTEGER
    ACCESS    read-only
    STATUS    mandatory
    DESCRIPTION
          "Displays the current number of trap receiving stations. "
    ::= { snmpConfiguration    4 }

snmpTrapAddressTable   OBJECT-TYPE
    SYNTAX    SEQUENCE OF SnmpTrapAddressEntry
    ACCESS    not-accessible
    STATUS    mandatory
    DESCRIPTION
          "Contains information on individual trap receiving stations. "
    ::= { snmpConfiguration    5 }

snmpTrapAddressEntry   OBJECT-TYPE
    SYNTAX    SnmpTrapAddressEntry
    ACCESS    not-accessible
    STATUS    mandatory
    INDEX    {  trapAddrIndex  }
        ::= { snmpTrapAddressTable    1 }

SnmpTrapAddressEntry ::=
    SEQUENCE {
        trapAddrIndex
            INTEGER,
        trapIPAddr
            IpAddress,
        trapCommunityString
            DisplayString,
        trapStatus
            INTEGER
    }
trapAddrIndex   OBJECT-TYPE
    SYNTAX    INTEGER
    ACCESS    read-only
    STATUS    mandatory
    DESCRIPTION
          "Displays the index number of the trap receiving station.  "
    ::= { snmpTrapAddressEntry    1 }

trapIPAddr   OBJECT-TYPE
    SYNTAX    IpAddress
    ACCESS    read-write
    STATUS    mandatory
    DESCRIPTION
          "Sets the IP address for a trap receiving station.  "
    ::= { snmpTrapAddressEntry    2 }

trapCommunityString   OBJECT-TYPE
    SYNTAX    DisplayString (SIZE (0..32))
    ACCESS    read-write
    STATUS    mandatory
    DESCRIPTION
          "Sets the password for sending traps from the SNMP agent
           to the SNMP application on the trap receiving station. "
    ::= { snmpTrapAddressEntry    3 }

trapStatus   OBJECT-TYPE
    SYNTAX    INTEGER  {
                active(1),
                ignore(2)
                }
    ACCESS    read-write
    STATUS    mandatory
    DESCRIPTION
          "Displays whether traps should be sent to this station (active)
           or whether traps should not be sent to this station (ignore). "
    ::= { snmpTrapAddressEntry    4 }

END
