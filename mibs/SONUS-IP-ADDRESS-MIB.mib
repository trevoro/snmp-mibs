--
-- This SMIv2 module has been generated by smidump 0.2-cvs. Do not edit.
--

SONUS-IP-ADDRESS-MIB DEFINITIONS ::= BEGIN

IMPORTS
    Integer32, IpAddress, MODULE-IDENTITY, OBJECT-TYPE
        FROM SNMPv2-SMI
    PhysAddress
        FROM SNMPv2-TC
    sonusPacketMIBs
        FROM SONUS-SMI;

sonusIpAddressMIB MODULE-IDENTITY
    LAST-UPDATED    "200102030000Z"
    ORGANIZATION    
            "Sonus Networks, Inc."
    CONTACT-INFO    
            "   Customer Support    
             Sonus Networks, Inc,
             5 carlisle Road
             Westford, MA 01886
             USA
             
             Tel: 978-692-8999
             Fax: 978-392-9118
             E-mail: cs.snmp@sonusnet.com"
    DESCRIPTION     
            "The MIB Module for IP Address Management."
    ::= { sonusPacketMIBs 2 }


sonusIpAddrTable OBJECT-TYPE
    SYNTAX          SEQUENCE OF SonusIpAddrEntry
    MAX-ACCESS      not-accessible
    STATUS          current
    DESCRIPTION     
            "The table of addressing information relevant to this
             entity's IP addresses."
    ::= { sonusIpAddressMIB 1 }

sonusIpAddrEntry OBJECT-TYPE
    SYNTAX          SonusIpAddrEntry
    MAX-ACCESS      not-accessible
    STATUS          current
    DESCRIPTION     
            "The addressing information for one of this entity's IP
             addresses."
    INDEX           { sonusIpAdEntShelf, sonusIpAdEntSlot, 
                      sonusIpAdEntInstance, sonusIpAdEntAddr }
    ::= { sonusIpAddrTable 1 }

SonusIpAddrEntry ::=
    SEQUENCE {
        sonusIpAdEntAddr                IpAddress,
        sonusIpAdEntIfIndex             Integer32,
        sonusIpAdEntNetMask             IpAddress,
        sonusIpAdEntBcastAddr           Integer32,
        sonusIpAdEntReasmMaxSize        Integer32,
        sonusIpAdEntShelf               Integer32,
        sonusIpAdEntSlot                Integer32,
        sonusIpAdEntInstance            Integer32
    }

sonusIpAdEntAddr OBJECT-TYPE
    SYNTAX          IpAddress
    MAX-ACCESS      read-only
    STATUS          current
    DESCRIPTION     
            "The IP address to which this entry's addressing information
             pertains."
    ::= { sonusIpAddrEntry 1 }

sonusIpAdEntIfIndex OBJECT-TYPE
    SYNTAX          Integer32 (1..2147483647)
    MAX-ACCESS      read-only
    STATUS          current
    DESCRIPTION     
            "The index value which uniquely identifies the interface to
             which this entry is applicable.  The interface identified by
             a particular value of this index is the same interface as
             identified by the same value of RFC 1573's ifIndex."
    ::= { sonusIpAddrEntry 2 }

sonusIpAdEntNetMask OBJECT-TYPE
    SYNTAX          IpAddress
    MAX-ACCESS      read-only
    STATUS          current
    DESCRIPTION     
            "The subnet mask associated with the IP address of this
             entry.  The value of the mask is an IP address with all the
             network bits set to 1 and all the hosts bits set to 0."
    ::= { sonusIpAddrEntry 3 }

sonusIpAdEntBcastAddr OBJECT-TYPE
    SYNTAX          Integer32 (0..1)
    MAX-ACCESS      read-only
    STATUS          current
    DESCRIPTION     
            "The value of the least-significant bit in the IP broadcast
             address used for sending datagrams on the (logical)
             interface associated with the IP address of this entry.  For
             example, when the Internet standard all-ones broadcast
             address is used, the value will be 1.  This value applies to
             both the subnet and network broadcasts addresses used by the
             entity on this (logical) interface."
    ::= { sonusIpAddrEntry 4 }

sonusIpAdEntReasmMaxSize OBJECT-TYPE
    SYNTAX          Integer32 (0..65535)
    MAX-ACCESS      read-only
    STATUS          current
    DESCRIPTION     
            "The size of the largest IP datagram which this entity can
             re-assemble from incoming IP fragmented datagrams received
             on this interface."
    ::= { sonusIpAddrEntry 5 }

sonusIpAdEntShelf OBJECT-TYPE
    SYNTAX          Integer32
    MAX-ACCESS      read-write
    STATUS          current
    DESCRIPTION     
            "A 32-bit integer identifying the shelf
             that the IP Addr table applies to"
    ::= { sonusIpAddrEntry 6 }

sonusIpAdEntSlot OBJECT-TYPE
    SYNTAX          Integer32
    MAX-ACCESS      read-write
    STATUS          current
    DESCRIPTION     
            "A 32-bit integer identifying the slot
             that the IP Addr table applies to"
    ::= { sonusIpAddrEntry 7 }

sonusIpAdEntInstance OBJECT-TYPE
    SYNTAX          Integer32
    MAX-ACCESS      read-write
    STATUS          current
    DESCRIPTION     
            "A 32-bit integer identifying the instance
             that the IP Addr table applies to"
    ::= { sonusIpAddrEntry 8 }

sonusIpNetToMediaTable OBJECT-TYPE
    SYNTAX          SEQUENCE OF SonusIpNetToMediaEntry
    MAX-ACCESS      not-accessible
    STATUS          current
    DESCRIPTION     
            "The IP Address Translation table used for mapping from IP
             addresses to physical addresses."
    ::= { sonusIpAddressMIB 2 }

sonusIpNetToMediaEntry OBJECT-TYPE
    SYNTAX          SonusIpNetToMediaEntry
    MAX-ACCESS      not-accessible
    STATUS          current
    DESCRIPTION     
            "Each entry contains one IpAddress to `physical' address
             equivalence."
    INDEX           { sonusIpNetToMediaShelf, sonusIpNetToMediaSlot, 
                      sonusIpNetToMediaInstance, 
                      sonusIpNetToMediaIfIndex, 
                      sonusIpNetToMediaNetAddress }
    ::= { sonusIpNetToMediaTable 1 }

SonusIpNetToMediaEntry ::=
    SEQUENCE {
        sonusIpNetToMediaIfIndex        Integer32,
        sonusIpNetToMediaPhysAddress    PhysAddress,
        sonusIpNetToMediaNetAddress     IpAddress,
        sonusIpNetToMediaType           INTEGER,
        sonusIpNetToMediaShelf          Integer32,
        sonusIpNetToMediaSlot           Integer32,
        sonusIpNetToMediaInstance       Integer32
    }

sonusIpNetToMediaIfIndex OBJECT-TYPE
    SYNTAX          Integer32 (1..2147483647)
    MAX-ACCESS      read-create
    STATUS          current
    DESCRIPTION     
            "The interface on which this entry's equivalence is
             effective.  The interface identified by a particular value
             of this index is the same interface as identified by the
             same value of RFC 1573's ifIndex."
    ::= { sonusIpNetToMediaEntry 1 }

sonusIpNetToMediaPhysAddress OBJECT-TYPE
    SYNTAX          PhysAddress
    MAX-ACCESS      read-create
    STATUS          current
    DESCRIPTION     
            "The media-dependent `physical' address."
    ::= { sonusIpNetToMediaEntry 2 }

sonusIpNetToMediaNetAddress OBJECT-TYPE
    SYNTAX          IpAddress
    MAX-ACCESS      read-create
    STATUS          current
    DESCRIPTION     
            "The IpAddress corresponding to the media-dependent
             `physical' address."
    ::= { sonusIpNetToMediaEntry 3 }

sonusIpNetToMediaType OBJECT-TYPE
    SYNTAX          INTEGER { other(1), invalid(2), dynamic(3), 
                        static(4) }
    MAX-ACCESS      read-create
    STATUS          current
    DESCRIPTION     
            "The type of mapping.
             Setting this object to the value invalid(2) has the effect
             of invalidating the corresponding entry in the
             ipNetToMediaTable.  That is, it effectively disassociates
             the interface identified with said entry from the mapping
             identified with said entry.  It is an implementation-
             specific matter as to whether the agent removes an
             invalidated entry from the table.  Accordingly, management
             stations must be prepared to receive tabular information
             from agents that corresponds to entries not currently in
             use.  Proper interpretation of such entries requires
             examination of the relevant ipNetToMediaType object."
    ::= { sonusIpNetToMediaEntry 4 }

sonusIpNetToMediaShelf OBJECT-TYPE
    SYNTAX          Integer32
    MAX-ACCESS      read-create
    STATUS          current
    DESCRIPTION     
            "A 32-bit integer identifying the shelf
             that the IP Net to Media table applies to"
    ::= { sonusIpNetToMediaEntry 5 }

sonusIpNetToMediaSlot OBJECT-TYPE
    SYNTAX          Integer32
    MAX-ACCESS      read-create
    STATUS          current
    DESCRIPTION     
            "A 32-bit integer identifying the slot
             that the IP Net to Media table applies to"
    ::= { sonusIpNetToMediaEntry 6 }

sonusIpNetToMediaInstance OBJECT-TYPE
    SYNTAX          Integer32
    MAX-ACCESS      read-create
    STATUS          current
    DESCRIPTION     
            "A 32-bit integer identifying the instance
             that the IP Net to Media table applies to"
    ::= { sonusIpNetToMediaEntry 7 }

END -- end of module SONUS-IP-ADDRESS-MIB.
