--

-- Copyright (c) 1993 Chipcom Corporation.  All Rights Reserved.
--
-- Reproduction of this document is authorized on condition that this
-- copyright notice is included.  This SNMP MIB Specification
-- embodies proprietary intellectual property.  The copyright
-- retains all title and ownership in the specification, including any
-- revisions. 
--
-- It is the intent to encourage the widespread use of this
-- specification in connection with the management of our
-- products. The copyright grants vendor, end-users, and other interested
-- parties a non-exclusive license to use this specification in
-- connection with the management of our products.
--
-- This specification is supplied "AS IS," and no
-- warranty, either express or implied, as to the use, operation,
-- condition, or performance of the specification, is made.
--
-- Copyright text courtesy of Dave Perkins.
--
-- The right to change this MIB without notification is retained.
--


--
-- If you have any questions about this MIB, please call your
-- Technical Support Center, or call 1-800-228-6840.
--

--
-- MIB Version Information:
--
-- Version     Description
------------------------------------------------------------------
--   v1.0      Initial version of the chipmib02 branch.
--   v2.0      Version tracking initiated.
--   v2.1      Version release with TRMM v.2.10
--
-- 

--
-- Agents supporting this MIB:
--	Ethernet Management Module, Software rev: v3.2
--	Ethernet to Ethernet Bridge Module, Software Rev: v2.12
--	Ethernet to Ethernet Bridge Box, Software Rev: v2.12
--	Token Ring Management Module, Software Rev: v2.1
--	Ethernet Interconnect Module, Software Rev: v1.0
--


CHIPCOM-MIB DEFINITIONS ::= BEGIN
IMPORTS
	enterprises, NetworkAddress, IpAddress,
	Counter, Gauge, TimeTicks, DisplayString
		FROM RFC1155-SMI
	OBJECT-TYPE
		FROM RFC-1212;
-- All representations of MAC addresses in this MIB Module use,
-- as a textual convention (i.e. this convention does not affect
-- their encoding), the data type:

MacAddress ::= OCTET STRING (SIZE (6))    -- a 6 octet address in
                                          -- the "canonical" order
-- defined by IEEE 802.1a, i.e., as if it were transmitted least
-- significant bit first, even though 802.5 (in contrast to other
-- 802.x protocols) requires MAC addresses to be transmitted most
-- significant bit first.
--
-- 16-bit addresses, if needed, are represented by setting their
-- upper 4 octets to all 0's, i.e., AAFF would be represented
-- as 00000000AAFF.


chipcom     	OBJECT IDENTIFIER ::= { enterprises 49 }

chipmib02 	OBJECT IDENTIFIER ::= { chipcom 2 }

--
-- Top level groups
--

chipGen    	OBJECT IDENTIFIER ::= { chipmib02 1 }
chipEcho   	OBJECT IDENTIFIER ::= { chipmib02 2 }
chipProducts   	OBJECT IDENTIFIER ::= { chipmib02 3 }
chipExperiment  OBJECT IDENTIFIER ::= { chipmib02 4 }
chipTTY	        OBJECT IDENTIFIER ::= { chipmib02 5 }
chipTFTP	OBJECT IDENTIFIER ::= { chipmib02 6 }
chipDownload	OBJECT IDENTIFIER ::= { chipmib02 7 }


--
-- Product specific branches.  Also used for sysObjectID.
--

online        	OBJECT IDENTIFIER ::= { chipProducts 1 }
oebm 	      	OBJECT IDENTIFIER ::= { chipProducts 2 }

midnight      	OBJECT IDENTIFIER ::= { chipProducts 3 }
workGroupHub    OBJECT IDENTIFIER ::= { chipProducts 4 }

emm		OBJECT IDENTIFIER ::= { chipProducts 5 }
chipBridge	OBJECT IDENTIFIER ::= { chipProducts 6 }
trmm		OBJECT IDENTIFIER ::= { chipProducts 7 }
fmm		OBJECT IDENTIFIER ::= { chipProducts 8 }
focus1		OBJECT IDENTIFIER ::= { chipProducts 9 }
oeim    	OBJECT IDENTIFIER ::= { chipProducts 10 }





--
-- Experimental Branches
--
-- When RFCs are still in the experimental stage, the MIB
-- is incorporated under the enterprise experimental branch
-- so that changes in the experimental MIB do not affect
-- the released product.  
--
-- As the RFC becomes standard and support is provided by the agents,
-- the support under this branch will be moved to the appropriate
-- standard branch.  That is, the support under this branch
-- for the MIB in question will be removed.
--

chipExpTokenRing OBJECT IDENTIFIER ::= { chipExperiment 1 }
dot1dBridge	OBJECT IDENTIFIER ::= { chipExperiment 14 }

dot5		OBJECT IDENTIFIER ::= { chipExpTokenRing 1}

--
-- ONline Groups 
--

olAgents   	OBJECT IDENTIFIER ::= { online   1 }
olConc    	OBJECT IDENTIFIER ::= { online   2 }
olEnv     	OBJECT IDENTIFIER ::= { online   3 }
olModules 	OBJECT IDENTIFIER ::= { online   4 }
olNets   	OBJECT IDENTIFIER ::= { online   5 }
olGroups   	OBJECT IDENTIFIER ::= { online   6 }
olAlarm   	OBJECT IDENTIFIER ::= { online   7 }

--
-- Value added module attributes 
--

olSpecMods	OBJECT IDENTIFIER ::= { olModules 4 }

--
-- A node for each module type  :
--

ol50nnMCTL  	OBJECT IDENTIFIER ::= { olSpecMods 3 }
ol51nnMMGT  	OBJECT IDENTIFIER ::= { olSpecMods 4 }
ol51nnMFIB  	OBJECT IDENTIFIER ::= { olSpecMods 5 }
ol51nnMUTP  	OBJECT IDENTIFIER ::= { olSpecMods 6 }
ol51nnMTP   	OBJECT IDENTIFIER ::= { olSpecMods 7 }
ol51nnMBNC  	OBJECT IDENTIFIER ::= { olSpecMods 8 }
ol51nnBEE   	OBJECT IDENTIFIER ::= { olSpecMods 9 }
ol51nnRES   	OBJECT IDENTIFIER ::= { olSpecMods 10 }
ol51nnREE   	OBJECT IDENTIFIER ::= { olSpecMods 11 }
ol51nnMAUIF 	OBJECT IDENTIFIER ::= { olSpecMods 12 }
ol51nnMAUIM 	OBJECT IDENTIFIER ::= { olSpecMods 13 }
ol5208MTP   	OBJECT IDENTIFIER ::= { olSpecMods 14 }
ol51nnMFP   	OBJECT IDENTIFIER ::= { olSpecMods 15 }
ol51nnMFBP  	OBJECT IDENTIFIER ::= { olSpecMods 16 }
ol51nnMTPL  	OBJECT IDENTIFIER ::= { olSpecMods 17 }
ol51nnMTPPL 	OBJECT IDENTIFIER ::= { olSpecMods 18 }
ol52nnMTP   	OBJECT IDENTIFIER ::= { olSpecMods 19 }
ol52nnMFR   	OBJECT IDENTIFIER ::= { olSpecMods 20 }
ol51nnMTS   	OBJECT IDENTIFIER ::= { olSpecMods 21 }
ol51nnMFL   	OBJECT IDENTIFIER ::= { olSpecMods 22 }
ol50nnMRCTL 	OBJECT IDENTIFIER ::= { olSpecMods 23 }
ol51nnMFB   	OBJECT IDENTIFIER ::= { olSpecMods 24 }
ol53nnMMGT  	OBJECT IDENTIFIER ::= { olSpecMods 25 }
ol53nnMFBMIC	OBJECT IDENTIFIER ::= { olSpecMods 26 }
ol53nnMFIBST	OBJECT IDENTIFIER ::= { olSpecMods 27 }
ol53nnMSTP  	OBJECT IDENTIFIER ::= { olSpecMods 28 }
ol51nnMTPCL 	OBJECT IDENTIFIER ::= { olSpecMods 29 }
ol52nnBTT 	OBJECT IDENTIFIER ::= { olSpecMods 30 }
ol51nnIx 	OBJECT IDENTIFIER ::= { olSpecMods 31 }
ol52nnMMGT  	OBJECT IDENTIFIER ::= { olSpecMods 32 }
ol50nnMHCTL 	OBJECT IDENTIFIER ::= { olSpecMods 33 }













--
-- Networking groups
--

olNet		OBJECT IDENTIFIER ::= { olNets 1 }
olEnet		OBJECT IDENTIFIER ::= { olNets 2 }
olTRnet 	OBJECT IDENTIFIER ::= { olNets 3 }
olFDDInet 	OBJECT IDENTIFIER ::= { olNets 4 }


--
-- Workgroup Hub
--

hubSysGroup        OBJECT IDENTIFIER ::= { workGroupHub 1 }
hardwareGroup      OBJECT IDENTIFIER ::= { workGroupHub 2 }
softwareGroup      OBJECT IDENTIFIER ::= { workGroupHub 3 }
hubGroup           OBJECT IDENTIFIER ::= { workGroupHub 4 }
boardGroup         OBJECT IDENTIFIER ::= { workGroupHub 5 }
portGroup          OBJECT IDENTIFIER ::= { workGroupHub 6 }
alarmGroup         OBJECT IDENTIFIER ::= { workGroupHub 7 }


--
-- Threshold group
--

olThresh	OBJECT IDENTIFIER ::= { olAlarm 1 }

olThreshControl	OBJECT IDENTIFIER ::= { olThresh 1 }



-- The chipGen Group
--
-- Implementation of the chipGen group is mandatory for all agent products.
-- 
-- The chipGen Group is used by all agent products.  It provides
-- objects that identify what the product is and who is managing it.
--



chipGenProduct OBJECT-TYPE
	SYNTAX INTEGER {
		product-5100M-MGT(1),	-- EMM
		product-5102B-EE(2),	-- OEBM

		product-8383B(3),	-- Midnight
		product-5112H-UTP(4),	-- 12 port Workgroup Hub

		product-5300M-MGT(5),	-- FMM
		product-5200M-MGT(7)	-- TRMM

	}
	ACCESS read-only
	STATUS mandatory
	DESCRIPTION
		"The product type represented by this agent."
	::= { chipGen 1 }

chipGenServiceDate OBJECT-TYPE
	SYNTAX DisplayString (SIZE(6))
	ACCESS read-only
	STATUS mandatory
	DESCRIPTION
		"The date that the product was last serviced in the
		format yymmdd.  If this date is unknown, the value of this
		object is '000000'."
	::= { chipGen 2 }

chipGenNetman OBJECT-TYPE
	SYNTAX IpAddress
	ACCESS read-only
	STATUS mandatory
	DESCRIPTION
		"The IP (source) Address of the last authenticated SNMP PDU 
		received by this entity before this request.  An IP Address
		of 00.00.00.00 represents the default value."
	::= { chipGen 3 } 

chipGenDiagnostics OBJECT-TYPE
	SYNTAX INTEGER {
		passed(1),
		failed(2)
	}
	ACCESS read-only
	STATUS mandatory
	DESCRIPTION
		"The result of this product's diagnostic test(s).  If
		any test fails, this will have the failed(2) value.
		Note, many products do not operate after a diagnostic
		failure.  In this case, no SNMP communication would
		be available."
	::= { chipGen 4 } 

chipGenSerial OBJECT-TYPE
	SYNTAX DisplayString (SIZE(1..128))
	ACCESS read-only
	STATUS mandatory
	DESCRIPTION
		"The serial number of this product."
	::= { chipGen 5 }

chipGenID OBJECT-TYPE
	SYNTAX INTEGER
	ACCESS read-write
	STATUS mandatory
	DESCRIPTION
		"A unique ID used for grouping disparate agents together.
		For example, a concentrator may contain multiple agents.
		This ID is could be assigned by the management station 
                to identify all of these agents as being contained in the  
		same concentrator."
	::= { chipGen 6 }

chipGenVers OBJECT-TYPE
	SYNTAX DisplayString (SIZE(0..80))
	ACCESS read-only
	STATUS mandatory
	DESCRIPTION
		"The version identifier(s) for this agent."
	::= { chipGen 7 }

chipGenAuthFailureAddr OBJECT-TYPE
	SYNTAX IpAddress
	ACCESS read-only
	STATUS mandatory
	DESCRIPTION
		"The source IP Address of the last SNMP request that caused
		an authentication failure trap to be generated. This
		object is also included in the SNMP authenticationFailure
		trap."
	::= { chipGen 8 }

chipGenTimeLastChanged OBJECT-TYPE
	SYNTAX TimeTicks
	ACCESS read-only
	STATUS mandatory
	DESCRIPTION
		"A snapshot of sysUpTime when the last trap was generated.
		This attribute can be used to save polling by a management
		station.  If there have been no traps generated since the last 
		poll, there is no need for the station to poll again."
	::= { chipGen 9 }



-- The chipEcho Group
--
-- Implementation of the chipEcho group is mandatory for all agent
-- products.
-- 
-- The chipEcho Group is used by a station to initiate a Ping from 
-- this agent to the address denoted by chipEchoAddr.  When all of
-- the pings are sent, the agent issues a ping trap (enterprise specific)
-- reporting the total number of responses received at that time.
--
-- To ping another host, you must minimally set the chipEchoAddr to the
-- host that you want to ping and chipEchoStart to startEcho(2).  The
-- other objects let you change the characteristic of the Ping packets.
-- Note that only one Ping can be processed at a time.
-- 

chipEchoStart OBJECT-TYPE
	SYNTAX INTEGER {
		noEcho(1),
		startEcho(2)
		}
	ACCESS read-write
	STATUS mandatory
	DESCRIPTION
		"Setting chipEchoStart to startEcho(2) causes the device
		to begin an ICMP echo sequence using the parameters 
		indicated by the rest of the chipEcho group."
	::= { chipEcho 1 }

chipEchoAddr OBJECT-TYPE
	SYNTAX IpAddress
	ACCESS read-write
	STATUS mandatory
	DESCRIPTION
		"The IP Address to which the device will ping.  The default
		value is the loopback address 127.0.0.1 ."
	::= { chipEcho 2 }

chipEchoPattern OBJECT-TYPE
	SYNTAX INTEGER {
		zeroes(1),
		ones(2),
		mixed(3)
		}
	ACCESS read-write
	STATUS mandatory
	DESCRIPTION
		"The actual pattern to be contained in the ICMP echo packet."
	::= { chipEcho 3 }


chipEchoNumber OBJECT-TYPE
	SYNTAX INTEGER (1..255)
	ACCESS read-write
	STATUS mandatory
	DESCRIPTION
		"The number of ICMP echo packets (pings) to send."
	::= { chipEcho 4 }


chipEchoSize OBJECT-TYPE
	SYNTAX INTEGER (64..1500)
	ACCESS read-write
	STATUS mandatory
	DESCRIPTION
		"The size of the ICMP echo packet (ping) to send when
		chipEchoStart is set. The valid range is between 64 and
		1500 octets."
	::= { chipEcho 5 }

chipEchoResponseCounts OBJECT-TYPE
	SYNTAX Counter
	ACCESS read-only
	STATUS mandatory
	DESCRIPTION
		"The count of ICMP echo response packets received since
		the last PING was initiated. "
	::= { chipEcho 6 }






-- The ONline Concentrator Groups:
-- 
-- The following groups are specific to the Concentrator product family.
--

-- The olAgents Group:

-- This group is mandatory for all agents that exist in the concentrator.
--
-- The master management module(s) indicate all of the other SNMP agents
-- present in the concentrator.  The olAgents group is also used
-- by each agent to indicate his own agent status, whether master or not.
--

olAgentsMySlot OBJECT-TYPE
	SYNTAX INTEGER
	ACCESS read-only
	STATUS mandatory
	DESCRIPTION
		"The slot id of this agent."
	::= { olAgents 1 }

olAgentsMasterReset OBJECT-TYPE
	SYNTAX  INTEGER {
		noReset(1),
		reset(2)
		}
	ACCESS read-write
	STATUS mandatory
	DESCRIPTION
		"Resetting mastership causes a new mastership election to 
		occur. The agent with the highest mastership priority will
		become the new master.  If there is more than one agent
		with the highest priority, the selection between
		those agents will be arbritrary."
	::= { olAgents 2 }
	
olAgentsTable OBJECT-TYPE
	SYNTAX  SEQUENCE OF OlAgentsEntry
	ACCESS  not-accessible
	STATUS  mandatory
	DESCRIPTION
		"A table of agents in the concentrator as seen by
		this agent.  A master will see all the agents; a slave
		will only see itself."
	::= { olAgents 3 }

olAgentsEntry OBJECT-TYPE
	SYNTAX  OlAgentsEntry
	ACCESS  not-accessible
	STATUS  mandatory
	DESCRIPTION
		"A profile of an agent within the concentrator."
	INDEX 	{ olAgentsSlotIndex }
	::= { olAgentsTable 1 }

OlAgentsEntry ::=
	SEQUENCE {
		olAgentsSlotIndex
			INTEGER,
		olAgentsStationAddr
			OCTET STRING,	
		olAgentsIpAddress
			IpAddress,
		olAgentsMasterStatus
			INTEGER,
		olAgentsMasterPriority
			INTEGER

		}

olAgentsSlotIndex OBJECT-TYPE
	SYNTAX  INTEGER
	ACCESS	read-only
	STATUS	mandatory
	DESCRIPTION
		"The slot number that identifies the referenced agent."
	::= { olAgentsEntry 1 }

olAgentsStationAddr OBJECT-TYPE
	SYNTAX	OCTET STRING (SIZE(6))
	ACCESS	read-only
	STATUS	mandatory
	DESCRIPTION
		"The unique identifier for this agent.  Often this
		is the value of ifPhysAddress for the first interface."
	::= { olAgentsEntry 2 }

olAgentsIpAddress OBJECT-TYPE
	SYNTAX 	IpAddress
	ACCESS	read-only
	STATUS	mandatory
	DESCRIPTION
		"An IP Address that can be used to communicate to 
		this agent.  Note, this object's value may change
		as the agent switches to different sub-networks."
	::= { olAgentsEntry 3 }

olAgentsMasterStatus OBJECT-TYPE
	SYNTAX INTEGER {
		master(1),
		non-master(2), -- slave
		electing(3)
		}
	ACCESS read-only
	STATUS mandatory
	DESCRIPTION
		"The mastership status of this agent."
	::= { olAgentsEntry 4 }

olAgentsMasterPriority OBJECT-TYPE
	SYNTAX INTEGER {
		one(1), 	-- lowest
		two(2),
		three(3),
		four(4),
		five(5),
		six(6),
		seven(7),
		eight(8),
		nine(9),
		ten(10),	-- highest
		never(11)
		}	
	ACCESS read-write
	STATUS mandatory
	DESCRIPTION
		"The mastership priority of this agent.  Ten is the
		highest and one is the lowest.  Never means will not
		be able become master.  Some agents do not have the 
		capability to become master (the etherent to ethernet bridge, 
		e.g.) and setting those agents to a value other than 
		never(11) will generate an invalid value error.  Priority is
		only used when an election occurs.  Mastership is not
		pre-emptive; use the reset mastership command 
		(olAgentsMasterReset)."
	::= { olAgentsEntry 5 } 


			

-- The olConc Group:

-- This group is mandatory for all devices that are acting as a concentrator
-- master.
--
-- The olConc group contains information and control relative to 
-- the concentrator.
--

olConcType OBJECT-TYPE
	SYNTAX INTEGER {
		online-seventeen-slot(1),
		online-six-slot(2),
		online-six-slot-ft(3),   -- 6 slot with flag board
	        online-six-slot-hc(4),   -- 6-slot with hidden controller
		online-six-slot-ft-hc(5) -- 6-slot with both



	}
	ACCESS read-only
	STATUS mandatory
	DESCRIPTION
		"This object identifies the type of concentrator represented
		by this agent."
	::= { olConc 1 }


olConcReset OBJECT-TYPE
	SYNTAX INTEGER {
		noReset(1),
		reset(2)
		}
	ACCESS read-write
	STATUS mandatory
	DESCRIPTION
		"Setting this value to reset(2) causes this concentrator to
		reset. "
	::= { olConc 2 }


olConcNumSlots OBJECT-TYPE
	SYNTAX INTEGER
	ACCESS read-only
	STATUS mandatory
	DESCRIPTION
		"The number of slots in this concentrator.  Note, that
		if a hidden controller is present, the number of slots
		is one more than the number of payload slots (six-slot-hc
		will report 7 slots, for example). The hidden controller
		does not actually occupy a main slot in the 6-slot
		concentrator, but it will report itself as slot 7."
	::= { olConc 3 }

olConcProfile OBJECT-TYPE
	SYNTAX OCTET STRING (SIZE(1..3))
	ACCESS read-only
	STATUS mandatory
	DESCRIPTION
		"A bit string where the least significant bit corresponds to
		slot 1.  A '1' in the bit indicates that a module is present
		in that slot.  The number of octets provided is based on 
		the olConcNumSlots value divided by 8.  Any extra bits
		(for example, bits 18-24 for 17 slots) are meaningless.  

		For example, the string 0x01 0xFF 0xFF would represent 
		a full 17 slot concentrator."
	::= { olConc 4 }

-- The olEnv Group

-- This group represents the concentrator's environment.  It is available
-- from agents that are acting as a concentrator master.

olEnvTempStatus OBJECT-TYPE
	SYNTAX INTEGER {
		okay(1),
		extremeTemp(2)
		}
	ACCESS read-only
	STATUS mandatory
	DESCRIPTION
		"The overall temperature status for this concentrator.
		This object's value is an aggregate of all the temperature
		probes in the concentrator, such that, when at least one probe
		reports	extreme temperature, this object will have the value
		extremeTemp(2)."
	::= { olEnv 1 }

olEnvPSCapacity OBJECT-TYPE
	SYNTAX INTEGER
	ACCESS read-only
	STATUS mandatory
	DESCRIPTION
		"The total capacity of power supplies for this concentrator."
	::= { olEnv 2 }

olEnvPSTable OBJECT-TYPE
	SYNTAX SEQUENCE OF OlEnvPSEntry
	ACCESS not-accessible
	STATUS mandatory
	DESCRIPTION
		"A table that contains information about each potential
		power supply in the concentrator."
	::= { olEnv 3 }


olEnvPSEntry OBJECT-TYPE
	SYNTAX OlEnvPSEntry
	ACCESS not-accessible
	STATUS mandatory
	DESCRIPTION
		"A list of of information for each power supply in the
		concentrator."
	INDEX { olEnvPSIndex }
	::= { olEnvPSTable 1 }

OlEnvPSEntry ::=
	SEQUENCE {
		olEnvPSIndex
			INTEGER,
		olEnvPSAdminState
			INTEGER,
		olEnvPSOperStatus
			INTEGER
		}

olEnvPSIndex OBJECT-TYPE
	SYNTAX INTEGER
	ACCESS read-only
	STATUS mandatory
	DESCRIPTION
		"Identifies the power supply for which this entry contains
		power supply information.  For systems with the
		primary and backup power supply (as opposed to
		the N+1 design), index 1 refers to the primary, 
		and index 2 refers to the backup. "
	::= { olEnvPSEntry 1 }

olEnvPSAdminState OBJECT-TYPE
	SYNTAX INTEGER {
		activate(1),
		standby(2)
		}
	ACCESS read-write
	STATUS mandatory
	DESCRIPTION
		"The current desired state of the power supply.  A power
		supply in standby does not provide power to the concentrator."
	::= { olEnvPSEntry 2 }

olEnvPSOperStatus OBJECT-TYPE
	SYNTAX INTEGER {
		active(1),
		standby(2),
		faulty(3),
		not-installed(4)
		}
	ACCESS read-only
	STATUS mandatory
	DESCRIPTION
		"The current operational state of the power supply.  A power
		supply in standby does not provide power to the concentrator."
	::= { olEnvPSEntry 3 }

olEnvFanStatus OBJECT-TYPE
	SYNTAX INTEGER {
		okay(1),
		faulty(3),
		not-installed(4),
		unknown(5)
		}
	ACCESS read-only
	STATUS mandatory
	DESCRIPTION
		"The overall status of the fan(s)."
	::= { olEnv 4 }




-- The olModules group

-- This group represents the information as seen by what is currently known
-- as the concentrator master.  If the module is not a master, this group
-- is not represented.  These tables have dynamic instances, that is, 
-- if the module does not exist in the concentrator, the tables are empty.
-- No excess information is presented.
--


olModTable	 OBJECT-TYPE
	SYNTAX SEQUENCE OF OlModEntry
	ACCESS not-accessible
	STATUS mandatory
	DESCRIPTION
		"A table that contains generic information about every
		module that is present within the concentrator.

		"
	::= { olModules 1 }

olModEntry OBJECT-TYPE
	SYNTAX OlModEntry
	ACCESS not-accessible
	STATUS mandatory
	DESCRIPTION
		"A list of information for each module in the concentrator.

		"
	INDEX { olModSlotIndex }
	::= { olModTable 1 }

OlModEntry ::=
	SEQUENCE {
		olModSlotIndex
			INTEGER,
		olModType
			INTEGER,
		olModClass
			INTEGER,
		olModDescr
			DisplayString,
		olModVersion
			DisplayString,
		olModVendor
			INTEGER,
		olModResetModule
			INTEGER,
		olModConfigToDips
			INTEGER, 
		olModConfigured
			INTEGER,
		olModNetwork
			INTEGER,
		olModNetworkType
			INTEGER,
		olModStatus
			INTEGER,
		olModNumPorts
			INTEGER,
		olModNumTrunks
			INTEGER

		}

olModSlotIndex OBJECT-TYPE
	SYNTAX INTEGER
	ACCESS read-only
	STATUS mandatory
	DESCRIPTION
		"The unique slot number of this module.  Its value ranges
		between 1 and olConcNumSlots and remains constant at
		least from one re-initialization of the entity's network
		management system to the next re-initialization."
	::= { olModEntry 1 }

olModType OBJECT-TYPE
	SYNTAX INTEGER {
		module-unmanageable(1), -- not manageable 
		module-unknown(2),	-- only generically manageable
		module-50nnM-CTL(3),	-- Controller 
		module-51nnM-MGT(4),	-- Ethernet Management
		module-51nnM-FIB(5),	-- Ethernet Fiber
		module-51nnM-UTP(6),	-- Ethernet 10BASE-T
		module-51nnM-TP(7),	-- Ethernet 10BASE-T
		module-51nnM-BNC(8),	-- Ethernet BNC
		module-51nnB-EE(9),	-- OEBM
		module-51nnR-ES(10),	-- Cisco Serial
		module-51nnR-EE(11),	-- Cisco Ethernet
		module-51nnM-AUIF(12),	-- Ethernet AUI Female
		module-51nnM-AUIM(13),	-- Ethernet AUI Male
		module-5208M-TP(14),	-- Token Ring 8-port MAU module
		module-51nnM-FP(15),	-- Ethernet Fiber port switching
		module-51nnM-FBP(16),	-- Ethernet 10BASE-F port switching
		module-51nnM-TPL(17),	-- Ethernet 10BASE-T
		module-51nnM-TPPL(18),  -- Ethernet 10BASE-T port switching
		module-52nnM-TP(19),    -- Token Ring Media Module
		module-52nnM-FR(20),	-- Token Ring FiberOptic Repeater
		module-51nnM-TS(21),	-- Ethernet Terminal Server
		module-51nnM-FL(22),	-- Ethernet FOIRL
		module-50nnM-RCTL(23),	-- Redundant Controller 
		module-51nnM-FB(24),	-- Ethernet 10BASE-F 
                module-53nnM-MGT(25),   -- FDDI managment module (FMM) 
                module-53nnM-FBMIC(26), -- FDDI media w/ ANSI MIC conn.
                module-53nnM-FIBST(27), -- FDDI media w/ ST conn.      
                module-53nnM-STP(28),   -- FDDI over copper
		module-51nnM-TPCL(29), 	-- Ethernet 10BASE-T per-connector
		module-52nnB-TT(30), 	-- Token Ring Bridge
		module-51nnI-x(31), 	-- Ethernet Interconnect Module
		module-52nnM-MGT(32),	-- Token Ring Management
		module-50nnM-HCTL(33)	-- Hidden Controller 











		}
	ACCESS read-only
	STATUS mandatory
	DESCRIPTION
		"The unique type identifier for this module.  This type
		is used to identify the branch in olSpecMods (see below).

		module-unmanageable(1) means that only the following
		objects are valid for this module:
	
			olModSlotIndex			
			olModClass
			olModVersion
			olModVendor
			olModReset
			olModConfigToDips
			olModConfigured

		module-unknown(2) means that all the generic attributes
		are manageable, but there is no olSpecMods branch
		for this module as viewed by this agent."
		::= { olModEntry 2 }

olModClass OBJECT-TYPE
	SYNTAX INTEGER {
		controller(1),
		ethernet-mgmt(2),
		ethernet-media(3),
		ethernet-interconnect(4),
		ethernet-portswitching-media(5),
		token-ring-media(6),
		terminal-server(7),
                fddi-media(8),
		token-ring-mgmt(9),
		ethernet-connswitching-media(10),
		token-ring-interconnect(11),
		fddi-mgmt(12)


		}
	ACCESS read-only
	STATUS mandatory
	DESCRIPTION
		"The class of this module.  Generally speaking, this
		object indicates the kind of module.  Specifically,
		the class identifier specifies the internal representation
		of the module's managed information base."
	::= { olModEntry 3 }

olModDescr OBJECT-TYPE
	SYNTAX DisplayString (SIZE(1..128))
	ACCESS read-only
	STATUS mandatory
	DESCRIPTION
		"A textual string containing information about the module."
	::= { olModEntry 4 }

olModVersion OBJECT-TYPE
	SYNTAX DisplayString (SIZE(1..32))
	ACCESS read-only
	STATUS mandatory
	DESCRIPTION
		"The software version number of this module.  "
	::= { olModEntry 5 }

olModVendor OBJECT-TYPE
	SYNTAX INTEGER {
		chipcom(1),
		cisco(2),
		pilkington(3),
		datability(5),
		ibm(6),
		raycom(7),
		retix(8),
		intellicom(9)
		}
	ACCESS read-only
	STATUS mandatory
	DESCRIPTION
		"The actual manufacturer of this board."
	::= { olModEntry 6 }

olModResetModule OBJECT-TYPE
	SYNTAX INTEGER {
		noReset(1),
		reset(2)
		}
	ACCESS read-write
	STATUS mandatory
	DESCRIPTION
		"Setting this object to reset(2) causes this module to reset."
	::= { olModEntry 7 }

olModConfigToDips OBJECT-TYPE
	SYNTAX INTEGER {
		noConfigure(1),
		configure(2)
		}
	ACCESS read-write
	STATUS mandatory
	DESCRIPTION
		"Setting this object to configure(2) causes this module to 
		configure based on the dip switch settings."
	::= { olModEntry 8 }

olModConfigured OBJECT-TYPE
	SYNTAX INTEGER {
		notConfigured(1),
		configured(2)
		}
	ACCESS read-only
	STATUS mandatory
	DESCRIPTION
		"This object indicates whether this module has already been
		configured.  An unconfigured module is configured to a safe
		state where the network is isolated and the ports are 
		disabled."
	::= { olModEntry 9 }


olModNetwork OBJECT-TYPE
	SYNTAX INTEGER {
		other(1),
		isolated(2),
		port-switching(3),
		front-panel(5),
		ethernet-1(6),		
		ethernet-2(7),
		ethernet-3(8),
		token-ring-1(9),
		token-ring-2(10),
		token-ring-3(11),
		token-ring-4(12),
		token-ring-5(13),
		token-ring-6(14),
		token-ring-7(15),
		fddi-1(16),
		fddi-2(17),
		fddi-3(18),
		fddi-4(19),
		per-connector(20),
		isolated-1(21),		-- for modules with multiple
		isolated-2(22)		-- isolated networks within the module

		}
	ACCESS read-write
	STATUS mandatory
	DESCRIPTION
		"The network that this module is attached to.  If the
		value is other(1) or port-switching(3), setting this object
		to a different value will generate the invalidData error.

		If the value is port-switching(3), manage the networks via
		the olPortNetwork object.

		The value per-connector(20) is returned if the managed 
 		module is a per-connector switchable and the connectors are on 
		different networks.  The connector networks are managed 
		by the objects defined in the olSpecMods branch 
		specified for this module.

		Modules and ports on the same network intercommunicate.
		Setting the module to isolated(2) (or other isolated values), 
		removes this module from the backplane.

		Setting this module to a value that is not the same 
		protocol type will return an invalidData error.

		Setting this module to a value that it does not support
		will return an invalidData error."
	::= { olModEntry 10 }

olModNetworkType OBJECT-TYPE
	SYNTAX INTEGER {
		other(1),	    -- other only
		port-switching(3),  -- use olPortNetwork
		ethernet(5),	    -- ethernet 1-3 or 1-8, isolated 
		token-ring(6),      -- token-ring 1-7, isolated
		fddi(7), 	    -- fddi 1-4, isolated
		serial(8)           -- front or isolated only
		}
	ACCESS read-only
	STATUS mandatory
	DESCRIPTION
		"The network type of this module.  port-switching(3)
		means that the network type differs depending on the 
		port (like the router module). The network type reflects
		the valid values for olModNetwork."
	::= { olModEntry 11 }

olModStatus OBJECT-TYPE
	SYNTAX INTEGER {
		okay(1),
 		fatalError(10),
                booting(20),
                partial-failure(21)
		}
	ACCESS read-only
	STATUS mandatory
	DESCRIPTION
		"The module's status."
	::= { olModEntry 12 }

olModNumPorts OBJECT-TYPE
	SYNTAX INTEGER
	ACCESS read-only
	STATUS mandatory
	DESCRIPTION
		"The number of ports on this module.  Note, ports may be 
		physical ports like 10BASE-T ports, or logical, like 
		the bridge module ports."
	::= { olModEntry 13 }

olModNumTrunks OBJECT-TYPE
	SYNTAX INTEGER
	ACCESS read-only
	STATUS mandatory
	DESCRIPTION
		"The number of trunks on this module.  Note, trunks
		are links that are, by definition, backbone connections.
		Examples of trunks are ring in and ring out ports for
		token ring, and the connections for rings to the backplane."
	::= { olModEntry 14 }



	
--
-- Generic Port Table
--

olPortTable OBJECT-TYPE
	SYNTAX SEQUENCE OF OlPortEntry
	ACCESS not-accessible
	STATUS mandatory
	DESCRIPTION
		"A table that contains generic information about
		each port on each module present within the concentrator."
	::= { olModules 2 }

olPortEntry OBJECT-TYPE
	SYNTAX OlPortEntry
	ACCESS not-accessible
	STATUS mandatory
	DESCRIPTION
		"A list of information about each port in the
		concentrator."
	INDEX { olPortSlotIndex, olPortIndex }
	::= { olPortTable 1}

OlPortEntry ::=
	SEQUENCE {
		olPortSlotIndex
			INTEGER,
		olPortIndex
			INTEGER,
		olPortType
			INTEGER,
		olPortConnector
			INTEGER,
		olPortStatus
			INTEGER,
		olPortAdminState
			INTEGER,
		olPortNetwork
			INTEGER,
		olPortNetworkType
			INTEGER



		}

olPortSlotIndex OBJECT-TYPE
	SYNTAX INTEGER
	ACCESS read-only
	STATUS mandatory
	DESCRIPTION
		"The slot number of this port's module."
	::= { olPortEntry 1 }

olPortIndex OBJECT-TYPE
	SYNTAX INTEGER
	ACCESS read-only
	STATUS mandatory
	DESCRIPTION
		"The port number of this port within this module."
	::= { olPortEntry 2 }

olPortType OBJECT-TYPE
	SYNTAX INTEGER {
		logical(1),	-- oebm's ports for example
		media(2), 	-- normal ports
		virtual(5)	-- oets'  ports for example
		}
	ACCESS read-only
	STATUS mandatory
	DESCRIPTION
		"The type of port.  logical(1) is used to manage
		port resources that may not map directly to physical
		connections.  The OEBM, for example, has two logical
		ports, although those two ports can be assigned to
		different combinations of four physical connections.
		media(2) refers to ports such as those on the 10BASE-T
		module. "
	::= { olPortEntry 3 }
		
		
olPortConnector OBJECT-TYPE
	SYNTAX INTEGER {
		backPlane(1),	-- connects directly to backplane
		bnc(2),		-- thinnet
		faui(3),	-- female aui
		maui(4),	-- male aui
		fiber(5),	-- fiber connector
		db-50(6),	-- serial port
		telco(7),	-- 50 pin connector
		rj45(8),	-- unshielded
		rj45S(9),	-- shielded
		db-9(10),	-- 9 pin connector
		virtual(11),	-- e.g. terminal server port
                fddi-lc(12),    -- low cost connector   
                fddi-st(13),    -- ST type connector    
		fddi-mic(14)	-- MIC connector
		}
	ACCESS read-only
	STATUS mandatory
	DESCRIPTION
		"The connector type of this port."
	::= { olPortEntry 4 }

olPortStatus OBJECT-TYPE
	SYNTAX INTEGER {
		okay(1),
		linkFailure(2),
		jabber(3),
		remoteLinkFailure(4),
		remoteJabber(5),
		invalidData(6),
		lowLight(7),
		fifoOverrun(8),
		fifoUnderrun(9),
		fatalError(10),
		partition(11),
		mjlp(12),
		noCable(13),
		noSquelch(14),
		noPhantom(15),
	        okay-standby(19),
                off(22),                
                connecting(23),
                backup-link(24),
		security-breach(25),
		unknownStatus(26),
		beacon(27),
		wireFault(28),
		macRemoved(29),
		notInserted(30),
		speedMismatch(31)
		}
	ACCESS read-only
	STATUS mandatory
	DESCRIPTION
		"The status of this port."
	::= { olPortEntry 5 }

olPortAdminState OBJECT-TYPE
	SYNTAX INTEGER {
		enabled(1),	      -- only valid value for class 2&4 modules
		disabled(2),
		redundant-primary(3), -- use olSpecMods to set
		redundant-backup(4),  -- redundancy buddys
		redundant-rfs(5),     -- used by FOIRL only 
		local(6),	      -- terminal server only
		remote(7),	      -- terminal server only
		remote-diagnostics(8),
		unknown(9)
		}
	ACCESS read-write
	STATUS mandatory
	DESCRIPTION
		"The desired state of this port.  Setting a port to be
		redundant-primary(3) or redundant-backup requires that the
		buddy slot and buddy port also be set to valid values
		(see appropriate olSpecMods objects).  If the 
		values associated with the redundant buddys
		are not valid, a genError will be returned.  If the port
		is already redundant, an invalid set may result in both
		ports being disabled."
	::= { olPortEntry 6 }

olPortNetwork OBJECT-TYPE
	SYNTAX INTEGER {
		other(1),
		isolated(2),
		per-module(4),
		front-panel(5),
		ethernet-1(6),
		ethernet-2(7),
		ethernet-3(8),
		token-ring-1(9),
		token-ring-2(10),
		token-ring-3(11),
		token-ring-4(12),
		token-ring-5(13),
		token-ring-6(14),
		token-ring-7(15),
		fddi-1(16),
		fddi-2(17),
		fddi-3(18),
		fddi-4(19),
		per-connector(20),
		isolated-1(21),		-- for modules with multiple
		isolated-2(22)		-- isolated networks within the module

		}
	ACCESS read-write
	STATUS mandatory
	DESCRIPTION
		"The network that this port is attached to.

		If the value of olPortNetwork is per-module(4),
		then use the olModNetwork to manage this port.
		Setting olPortNetwork to a different value in this
		case will generate the invalidData error.

		Setting this port to a value that is not the same protocol 
		type will return invalidData error.  front-panel(5) is used for 
		modules that have a logical port and a physical front 
		connection. An example of this is the Eth2Eth Bridge module.

		Setting this port to a value that it does not support will
		generate an invalidData error."
	::= { olPortEntry 7 }
		
olPortNetworkType OBJECT-TYPE
	SYNTAX INTEGER {
		other(1),	-- other only
		ethernet(5),    -- ethernet 1-3, isolated
		token-ring(6),  -- token ring 1 - 7, isolated
		fddi(7), 	    -- fddi 1-4, isolated
		serial(8)          -- front or isolated only
		}
	ACCESS read-only
	STATUS mandatory
	DESCRIPTION
		"The network type of this port.  The type reflects the
		valid values for olPortNetwork. "
	::= { olPortEntry 8 }



--
-- Trunk Table
-- 

olTrunkTable OBJECT-TYPE
	SYNTAX SEQUENCE OF OlTrunkEntry
	ACCESS not-accessible
	STATUS mandatory
	DESCRIPTION
		"A table that contains generic information about
		each trunk on each module present within the concentrator."
	::= { olModules 3 }

olTrunkEntry OBJECT-TYPE
	SYNTAX OlTrunkEntry
	ACCESS not-accessible
	STATUS mandatory
	DESCRIPTION
		"A list of information about each trunk in the
		concentrator."
	INDEX { olTrunkSlotIndex, olTrunkIndex }
	::= { olTrunkTable 1}

OlTrunkEntry ::=
	SEQUENCE {
		olTrunkSlotIndex
			INTEGER,
		olTrunkIndex
			INTEGER,
		olTrunkType
			INTEGER,
		olTrunkConnector
			INTEGER,
		olTrunkStatus
			INTEGER,
		olTrunkAdminState
			INTEGER,
		olTrunkWrapState
			INTEGER,
		olTrunkNeighbor
			INTEGER
		}

olTrunkSlotIndex OBJECT-TYPE
	SYNTAX INTEGER
	ACCESS read-only
	STATUS mandatory
	DESCRIPTION
		"The slot number of this trunk's module."
	::= { olTrunkEntry 1 }

olTrunkIndex OBJECT-TYPE
	SYNTAX INTEGER
	ACCESS read-only
	STATUS mandatory
	DESCRIPTION
		"The trunk number of this trunk."
	::= { olTrunkEntry 2 }

olTrunkType OBJECT-TYPE
	SYNTAX INTEGER {
		other(1),
		ringIn(3),	-- ring access trunks
		ringOut(4),
		backplaneIn(6), -- backplane access
		backplaneOut(7)
		}
	ACCESS read-only
	STATUS mandatory
	DESCRIPTION
		"The type of trunk. ringIn(3) and ringOut(4) refer to special
		trunks on the token ring protocol type modules."
	::= { olTrunkEntry 3 }
		
		
olTrunkConnector OBJECT-TYPE
	SYNTAX INTEGER {
		backplane(1),
		fiber(5),	-- 
		rj45S(9)	-- shielded
		}
	ACCESS read-only
	STATUS mandatory
	DESCRIPTION
		"The connector type of this trunk."
	::= { olTrunkEntry 4 }

olTrunkStatus OBJECT-TYPE
	SYNTAX INTEGER {
		okay(1),
		linkFailure(2),
		fatalError(10),
		noCable(13),
		noSquelch(14),
		lostLock(16),
		upstreamNeighborLost(17),
		invalidConfig(18),
                beacon(27),
                wireFault(28)
		}
	ACCESS read-only
	STATUS mandatory
	DESCRIPTION
		"The status of this trunk."
	::= { olTrunkEntry 5 }

olTrunkAdminState OBJECT-TYPE
	SYNTAX INTEGER {
		enabled(1),
		disabled(2)
		}
	ACCESS read-write
	STATUS mandatory
	DESCRIPTION
		"The desired state of this trunk.  Enabling a trunk allows
		the trunk to pass network traffic."
	::= { olTrunkEntry 6 }

olTrunkWrapState OBJECT-TYPE
	SYNTAX INTEGER {
		wrapped(1),
		unwrapped(2)
		}
	ACCESS read-only
	STATUS mandatory
	DESCRIPTION
		"The wrap state of this trunk.  A trunk can wrap in 
		response to a network event such as a break in
		the cable."
	::= { olTrunkEntry 7 }	

olTrunkNeighbor OBJECT-TYPE
	SYNTAX INTEGER {
		slot-1(1),
		slot-2(2),
		slot-3(3),
		slot-4(4),
		slot-5(5),
		slot-6(6),
		slot-7(7),
		slot-8(8),
		slot-9(9),
		slot-10(10),
		slot-11(11),
		slot-12(12),
		slot-13(13),
		slot-14(14),
		slot-15(15),
		slot-16(16),
		slot-17(17),
		external(255)
		}
	ACCESS read-only
	STATUS mandatory
	DESCRIPTION
		"The upstream or downstream neighbor of the trunk."
	::= { olTrunkEntry 8 }	




-- olSpecMods Group
-- 
-- This group contains the module and port tables specific to the 
-- particular module.  Each module is indexed by the olModType value.
-- For more information, please refer to the MIB information supplied
-- with each module.

-- olSpecMods Group takes the following object identifier format:
-- 
-- olSpecMods.<type>.<level>.1.<object>.<instance>
--
-- where :
-- 	<type> ::= the unique number identifying the type of this module
--			see olModType above.
--	<level> ::= module table (1) ||
-- 	 	    port table (2)   ||
--                  trunk  (3)       

--	1       ::= branch for entry, i.e. module entry or port entry
-- 	<object>::= the object ID as indicated in the MIB documentation for
--			this type module.
-- 	<instance> ::=
--			<slot> for module level ||
--			<slot>.<port> for port level ||
--			<slot>.<trunk> for trunk level

--			
--
--	The lexicographical ordering for this group is:
--
--	1. To walk through all of the instances associated 
--		particular module type.  That is, the group 
--		walks through a module type - all slots, before
--		walking to the next module type.  For example, if
--		module type A is in slot 1 & 5, and module type B
--		is in slot 3 (where A < B), then a tree walk would
--		yield A.1, A.3, and then B.3.
--
--	2. To walk through all of the resources of a particular module
--		before walking to the next module.  All ports and trunks
--		of a module are instantiated in the tree before the
--		the next module is instiated.
--


--
-- ONline Controller Module
--

ol50nnMCTLModTable OBJECT-TYPE
	SYNTAX SEQUENCE OF Ol50nnMCTLModEntry
	ACCESS not-accessible
	STATUS mandatory
	DESCRIPTION
		"A table that contains information about each 50nnM-CTL
		in the concentrator.  Note, current architecture will
		limit the number of instances to one per concentrator."
	::= { ol50nnMCTL 1 }

ol50nnMCTLModEntry OBJECT-TYPE
	SYNTAX Ol50nnMCTLModEntry
	ACCESS not-accessible
	STATUS mandatory
	DESCRIPTION
		"A list of information for each 50nnM-CTL module
		in the concentrator."
	INDEX { ol50nnMCTLModSlotIndex }
	::= { ol50nnMCTLModTable 1 }

Ol50nnMCTLModEntry ::= 
	SEQUENCE {
		ol50nnMCTLModSlotIndex
			INTEGER,
		ol50nnMCTLModTempStatus
			INTEGER
		}

ol50nnMCTLModSlotIndex OBJECT-TYPE
	SYNTAX INTEGER
	ACCESS read-only
	STATUS mandatory
	DESCRIPTION
		"The slot number for this module."
	::= { ol50nnMCTLModEntry 1 }

ol50nnMCTLModTempStatus OBJECT-TYPE
	SYNTAX INTEGER {
		okay(1),
		extremeTemp(2)
		}
	ACCESS read-only
	STATUS mandatory
	DESCRIPTION
		"The temperature as detected by the probes on this module."
	::= { ol50nnMCTLModEntry 2 }


ol51nnMMGTModTable OBJECT-TYPE
	SYNTAX SEQUENCE OF Ol51nnMMGTModEntry
	ACCESS not-accessible
	STATUS mandatory
	DESCRIPTION
		"A table that contains module information about each
		51nnM-MGT module in the concentrator."
	::= { ol51nnMMGT 1 }

ol51nnMMGTModEntry OBJECT-TYPE
	SYNTAX Ol51nnMMGTModEntry
	ACCESS not-accessible
	STATUS mandatory
	DESCRIPTION
		"A list of module information for each 51nnM-MGT module
		in the concentrator."
	INDEX { ol51nnMMGTModSlotIndex }
	::= { ol51nnMMGTModTable 1 }

Ol51nnMMGTModEntry ::= 
	SEQUENCE {
		ol51nnMMGTModSlotIndex
			INTEGER,
		ol51nnMMGTModMasterPriority
			INTEGER,
		ol51nnMMGTModMasterStatus
			INTEGER,
		ol51nnMMGTModStationAddr
			OCTET STRING
		}

ol51nnMMGTModSlotIndex OBJECT-TYPE
	SYNTAX INTEGER
	ACCESS read-only
	STATUS mandatory
	DESCRIPTION
		"The slot number of this module."
	::= { ol51nnMMGTModEntry 1 }

ol51nnMMGTModMasterPriority OBJECT-TYPE
	SYNTAX INTEGER {
		one(1),
		two(2),
		three(3),
		four(4),
		five(5),
		six(6),
		seven(7),
		eight(8),
		nine(9),
		ten(10)
		}	
	ACCESS read-write
	STATUS mandatory
	DESCRIPTION
		"The mastership priority of this agent.  Ten is the
		highest and one is the lowest.  Priority is
		only used when an election occurs.  Mastership is not
		preemptive unless the reset mastership command is used."
	::= { ol51nnMMGTModEntry 2 }

ol51nnMMGTModMasterStatus OBJECT-TYPE
	SYNTAX INTEGER {
		master(1),
		non-master(2),
		electing(3)
		}
	ACCESS read-only
	STATUS mandatory
	DESCRIPTION
		"The mastership status of this agent."
	::= { ol51nnMMGTModEntry 3 }

ol51nnMMGTModStationAddr OBJECT-TYPE
	SYNTAX OCTET STRING (SIZE(6))
	ACCESS read-only
	STATUS mandatory
	DESCRIPTION
		"A 6 octet address that uniquely identifies this module.
		The station address is the mac address of port 1.  Note
		that EMMs before v3.0 will have 00-00-00-00-00-00 as their
		station address."
	::= { ol51nnMMGTModEntry 4 }

ol51nnMMGTPortTable OBJECT-TYPE
	SYNTAX SEQUENCE OF Ol51nnMMGTPortEntry
	ACCESS not-accessible
	STATUS mandatory
	DESCRIPTION
		"A table of information that contains port-specific
		information for each port on each 51nnM-MGT module."
	::= { ol51nnMMGT 2 }

ol51nnMMGTPortEntry OBJECT-TYPE
	SYNTAX Ol51nnMMGTPortEntry
	ACCESS not-accessible
	STATUS mandatory
	DESCRIPTION
		"A list of information about a specific port on a 
		51nnM-MGT module."
	INDEX { ol51nnMMGTPortSlotIndex, ol51nnMMGTPortIndex }
	::= { ol51nnMMGTPortTable 1 }

Ol51nnMMGTPortEntry ::= 
	SEQUENCE {
		ol51nnMMGTPortSlotIndex
			INTEGER,			
		ol51nnMMGTPortIndex
			INTEGER,
		ol51nnMMGTIpAddress
			IpAddress
		}

ol51nnMMGTPortSlotIndex OBJECT-TYPE
	SYNTAX INTEGER
	ACCESS read-only
	STATUS mandatory
	DESCRIPTION
		"The slot number of this port's module."
	::= { ol51nnMMGTPortEntry 1 }


ol51nnMMGTPortIndex OBJECT-TYPE
	SYNTAX INTEGER
	ACCESS read-only
	STATUS mandatory
	DESCRIPTION
		"The port number of this port."
	::= { ol51nnMMGTPortEntry 2 }


ol51nnMMGTIpAddress OBJECT-TYPE
	SYNTAX IpAddress
	ACCESS read-only
	STATUS mandatory
	DESCRIPTION
		"The IP Address associated with this port."
	::= { ol51nnMMGTPortEntry 3 }

-- 
-- ONline Ethernet Synchronous Fiber Module
--


ol51nnMFIBModTable OBJECT-TYPE
	SYNTAX SEQUENCE OF Ol51nnMFIBModEntry
	ACCESS not-accessible
	STATUS mandatory
	DESCRIPTION
		"A table of module-specific information for each
		51nnM-FIB module in the concentrator."
	::= { ol51nnMFIB 1 }

ol51nnMFIBModEntry OBJECT-TYPE
	SYNTAX Ol51nnMFIBModEntry
	ACCESS not-accessible
	STATUS mandatory
	DESCRIPTION
		"A list of module-specific information associated
		with a particular 51nnM-FIB module in the concentrator."
	INDEX { ol51nnMFIBModSlotIndex }
	::= { ol51nnMFIBModTable 1 }

Ol51nnMFIBModEntry ::= 
	SEQUENCE {
		ol51nnMFIBModSlotIndex
			INTEGER,
		ol51nnMFIBModDipNetwork
			INTEGER,
		ol51nnMFIBModLLW
			INTEGER,
		ol51nnMFIBModDipLLW
			INTEGER
		}

ol51nnMFIBModSlotIndex OBJECT-TYPE
	SYNTAX INTEGER
	ACCESS read-only
	STATUS mandatory
	DESCRIPTION
		"The slot number of this module."
	::= { ol51nnMFIBModEntry 1 }

ol51nnMFIBModDipNetwork OBJECT-TYPE
	SYNTAX INTEGER {
		isolated(2),
		ethernet-1(6),
		ethernet-2(7),
		ethernet-3(8)
		}
	ACCESS read-only
	STATUS mandatory
	DESCRIPTION
		"The network indicated by the module's dip switches."	
	::= { ol51nnMFIBModEntry 2 }

ol51nnMFIBModLLW OBJECT-TYPE
	SYNTAX INTEGER {
		enabled(1),
		disabled(2)
		}
	ACCESS read-write
	STATUS mandatory
	DESCRIPTION
		"The current state of this module's low light warning 
		configuration.	Enabling this feature causes the module to 
		check for low light and to issue a warning if low light is
		present.  Disabling low light has the advantage of faster
		redundancy switchover in the event of a port error."
	::= { ol51nnMFIBModEntry 3 }
	
ol51nnMFIBModDipLLW OBJECT-TYPE
	SYNTAX INTEGER {
		enabled(1),
		disabled(2)
		}
	ACCESS read-only
	STATUS mandatory
	DESCRIPTION
		"The low light warning configuration indicated by this module's
		dip switches."
	::= { ol51nnMFIBModEntry 4 }
	
ol51nnMFIBPortTable OBJECT-TYPE
	SYNTAX SEQUENCE OF Ol51nnMFIBPortEntry
	ACCESS not-accessible
	STATUS mandatory
	DESCRIPTION
		"A table of port-specific information for each port
		of each 51nnM-FIB module."
	::= { ol51nnMFIB 2 }

ol51nnMFIBPortEntry OBJECT-TYPE
	SYNTAX Ol51nnMFIBPortEntry
	ACCESS not-accessible
	STATUS mandatory
	DESCRIPTION
		"A list of information about a specific port on a 
		51nnM-FIB module."
	INDEX { ol51nnMFIBPortSlotIndex, ol51nnMFIBPortIndex }
	::= { ol51nnMFIBPortTable 1 }

Ol51nnMFIBPortEntry ::= 
	SEQUENCE {
		ol51nnMFIBPortSlotIndex
			INTEGER,			
		ol51nnMFIBPortIndex
			INTEGER,
		ol51nnMFIBPortAdminState
			INTEGER,
		ol51nnMFIBPortBuddySlot
			INTEGER,
		ol51nnMFIBPortBuddyPort
			INTEGER,
		ol51nnMFIBPortDipAdminState
			INTEGER
		}

	ol51nnMFIBPortSlotIndex OBJECT-TYPE
	SYNTAX INTEGER
	ACCESS read-only
	STATUS mandatory
	DESCRIPTION
		"The slot number of this port's module."
	::= { ol51nnMFIBPortEntry 1 }


ol51nnMFIBPortIndex OBJECT-TYPE
	SYNTAX INTEGER
	ACCESS read-only
	STATUS mandatory
	DESCRIPTION
		"The port number of this port."
	::= { ol51nnMFIBPortEntry 2 }


ol51nnMFIBPortAdminState OBJECT-TYPE
	SYNTAX INTEGER {
		enabled(1),
		disabled(2),
		redundant-primary(3),
		redundant-backup(4)
		}
	ACCESS read-write
	STATUS mandatory
	DESCRIPTION
		"The desired state of this port.  Setting this port to 
		be redundant with invalid settings of buddy slot and
		buddy port will return the genError error."
	::= { ol51nnMFIBPortEntry 3 }

ol51nnMFIBPortBuddySlot OBJECT-TYPE
	SYNTAX INTEGER
	ACCESS read-write
	STATUS mandatory
	DESCRIPTION
		"The slot index of the redundant port's buddy.  To set
		a port to be redundant, the buddy's slot and port must 
		be set to valid values.

		The buddy is automatically set to be redundant to this port."
	::= { ol51nnMFIBPortEntry 4 }

ol51nnMFIBPortBuddyPort  OBJECT-TYPE
	SYNTAX INTEGER
	ACCESS read-write
	STATUS mandatory
	DESCRIPTION
		"The port index of the redundant port's buddy.  To set
		a port to be redundant, the buddy's slot and port must 
		be set to valid values.

		The buddy is automatically set to be redundant to this port."
	::= { ol51nnMFIBPortEntry 5 }


ol51nnMFIBPortDipAdminState OBJECT-TYPE
	SYNTAX INTEGER {
		enabled(1),
		disabled(2),
		redundant-primary(3),
		redundant-backup(4)
		}
	ACCESS read-only
	STATUS mandatory
	DESCRIPTION
		"The state of this port as indicated by the port's dip 
		switches."		
	::= { ol51nnMFIBPortEntry 6 }

--
-- ONline Ethernet 10BASE-T Module
--


ol51nnMUTPModTable OBJECT-TYPE
	SYNTAX SEQUENCE OF Ol51nnMUTPModEntry
	ACCESS not-accessible
	STATUS mandatory
	DESCRIPTION
		"A list of module-specific information associated
		with a particular 51nnM-UTP module in the concentrator."
	::= { ol51nnMUTP 1 }

ol51nnMUTPModEntry OBJECT-TYPE
	SYNTAX Ol51nnMUTPModEntry
	ACCESS not-accessible
	STATUS mandatory
	DESCRIPTION
		"A module entry containing objects that describe the 
		module level for that particular module."
	INDEX { ol51nnMUTPModSlotIndex }
	::= { ol51nnMUTPModTable 1 }

Ol51nnMUTPModEntry ::= 
	SEQUENCE {
		ol51nnMUTPModSlotIndex
			INTEGER,
		ol51nnMUTPModDipNetwork
			INTEGER,
		ol51nnMUTPModCrossover
			INTEGER,
		ol51nnMUTPModDipCrossover
			INTEGER,
		ol51nnMUTPModFFL
			INTEGER,
		ol51nnMUTPModDipFFL
			INTEGER
		}

ol51nnMUTPModSlotIndex OBJECT-TYPE
	SYNTAX INTEGER
	ACCESS read-only
	STATUS mandatory
	DESCRIPTION
		"The slot number of this module."
	::= { ol51nnMUTPModEntry 1 }

ol51nnMUTPModDipNetwork OBJECT-TYPE
	SYNTAX INTEGER {
		isolated(2),
		ethernet-1(6),
		ethernet-2(7),
		ethernet-3(8)
		}
	ACCESS read-only
	STATUS mandatory
	DESCRIPTION
		"The network indicated by the module's dip switches."	
	::= { ol51nnMUTPModEntry 2 }

ol51nnMUTPModCrossover OBJECT-TYPE
	SYNTAX INTEGER {
		crossed(1),
		uncrossed(2)
		}
	ACCESS read-write
	STATUS mandatory
	DESCRIPTION
		"The current state of this module's crossover
		configuration.  Setting this object to uncrossed(2)
		allows the last port to be used to connect to another
		repeater.  Often this feature is used to connect one 10BASE-T
		module to another."
	::= { ol51nnMUTPModEntry 3 }
	
ol51nnMUTPModDipCrossover OBJECT-TYPE
	SYNTAX INTEGER {
		crossed(1),
		uncrossed(2)
		}
	ACCESS read-only
	STATUS mandatory
	DESCRIPTION
		"The crossover configuration indicated by this module's
		dip switches."
	::= { ol51nnMUTPModEntry 4 }
	
ol51nnMUTPModFFL OBJECT-TYPE
	SYNTAX INTEGER {
		eight-bits(1),
		seven-bits(2)
		}
	ACCESS read-write
	STATUS mandatory
	DESCRIPTION
		"The number of bits to store in the repeater's fifo
		buffer.  See the module user's guide for more information."
	::= { ol51nnMUTPModEntry 5 }

ol51nnMUTPModDipFFL OBJECT-TYPE
	SYNTAX INTEGER {
		eight-bits(1),
		seven-bits(2)
		}
	ACCESS read-write
	STATUS mandatory
	DESCRIPTION
		"The fifo fill level as indicated by this module's dip
		switches."
	::= { ol51nnMUTPModEntry 6 }

ol51nnMUTPPortTable			 OBJECT-TYPE
	SYNTAX SEQUENCE OF Ol51nnMUTPPortEntry
	ACCESS not-accessible
	STATUS mandatory
	DESCRIPTION
		"A table of port-specific information for each port of
		this module type."
	::= { ol51nnMUTP 2 }

ol51nnMUTPPortEntry OBJECT-TYPE
	SYNTAX Ol51nnMUTPPortEntry
	ACCESS not-accessible
	STATUS mandatory
	DESCRIPTION
		"A port entry containing objects that describe this port."
	INDEX { ol51nnMUTPPortSlotIndex, ol51nnMUTPPortIndex }
	::= { ol51nnMUTPPortTable 1 }

Ol51nnMUTPPortEntry ::= 
	SEQUENCE {
		ol51nnMUTPPortSlotIndex
			INTEGER,			
		ol51nnMUTPPortIndex
			INTEGER,
		ol51nnMUTPPortAdminState
			INTEGER,
		ol51nnMUTPPortBuddySlot
			INTEGER,
		ol51nnMUTPPortBuddyPort
			INTEGER,
		ol51nnMUTPPortDipAdminState
			INTEGER,
		ol51nnMUTPPortLinkInteg
			INTEGER,
		ol51nnMUTPPortDipLinkInteg
			INTEGER,
		ol51nnMUTPPortSquelch
			INTEGER,
		ol51nnMUTPPortDipSquelch
			INTEGER
		}

	ol51nnMUTPPortSlotIndex OBJECT-TYPE
	SYNTAX INTEGER
	ACCESS read-only
	STATUS mandatory
	DESCRIPTION
		"The slot number of this port's module."
	::= { ol51nnMUTPPortEntry 1 }


ol51nnMUTPPortIndex OBJECT-TYPE
	SYNTAX INTEGER
	ACCESS read-only
	STATUS mandatory
	DESCRIPTION
		"The port number of this port."
	::= { ol51nnMUTPPortEntry 2 }

ol51nnMUTPPortAdminState OBJECT-TYPE
	SYNTAX INTEGER {
		enabled(1),
		disabled(2),
		redundant-primary(3),
		redundant-backup(4)
		}
	ACCESS read-write
	STATUS mandatory
	DESCRIPTION
		"The desired state of this port.  Setting this port to 
		be redundant with invalid settings of buddy slot and
		buddy port will return the genError error."
	::= { ol51nnMUTPPortEntry 3 }

ol51nnMUTPPortBuddySlot OBJECT-TYPE
	SYNTAX INTEGER
	ACCESS read-write
	STATUS mandatory
	DESCRIPTION
		"The slot index of the redundant port's buddy.  To set
		a port to be redundant, the buddy's slot and port must 
		be set to valid values.

		The buddy is automatically set to be redundant to this port."
	::= { ol51nnMUTPPortEntry 4 }

ol51nnMUTPPortBuddyPort  OBJECT-TYPE
	SYNTAX INTEGER
	ACCESS read-write
	STATUS mandatory
	DESCRIPTION
		"The port index of the redundant port's buddy.  To set
		a port to be redundant, the buddy's slot and port must 
		be set to valid values.

		The buddy is automatically set to be redundant to this port."
	::= { ol51nnMUTPPortEntry 5 }

ol51nnMUTPPortDipAdminState OBJECT-TYPE
	SYNTAX INTEGER {
		enabled(1),
		disabled(2)
		}
	ACCESS read-only
	STATUS mandatory
	DESCRIPTION
		"The state of this port as indicated by the port's dip 
		switches."		
	::= { ol51nnMUTPPortEntry 6 }

ol51nnMUTPPortLinkInteg OBJECT-TYPE
	SYNTAX INTEGER {
		enabled(1),
		disabled(2)
		}
	ACCESS read-write
	STATUS mandatory
	DESCRIPTION
		"The port's link integrity configuration.  Enabling
		link integrity configures the port to conform to
		the link integrity feature as specified by 10BASE-T."
	::= { ol51nnMUTPPortEntry 7 }

ol51nnMUTPPortDipLinkInteg OBJECT-TYPE
	SYNTAX INTEGER {
		enabled(1),
		disabled(2)
		}
	ACCESS read-only
	STATUS mandatory
	DESCRIPTION
		"The link integrity configuration as indicated by this
		port's dip switches."
	::= { ol51nnMUTPPortEntry 8 }

ol51nnMUTPPortSquelch	 OBJECT-TYPE
	SYNTAX INTEGER {
		normal(1),		-- high squelch
		low(2)
		}
	ACCESS read-write
	STATUS mandatory
	DESCRIPTION
		"The port's squelch configuration.  See the module's
		user's guide for more information."
	::= { ol51nnMUTPPortEntry 9 }

ol51nnMUTPPortDipSquelch	 OBJECT-TYPE
	SYNTAX INTEGER {
		normal(1),		-- high squelch
		low(2)
		}
	ACCESS read-only
	STATUS mandatory
	DESCRIPTION
		"The port's squelch configuration as indicated by this
		port's dip switches."
	::= { ol51nnMUTPPortEntry 10 }


--
-- ONline Ethernet 10BASE-T Module
--

ol51nnMTPModTable OBJECT-TYPE
	SYNTAX SEQUENCE OF Ol51nnMTPModEntry
	ACCESS not-accessible
	STATUS mandatory
	DESCRIPTION
		"A table of module-specific information for each 
		51nnM-TP module in the concentrator."
	::= { ol51nnMTP 1 }

ol51nnMTPModEntry OBJECT-TYPE
	SYNTAX Ol51nnMTPModEntry
	ACCESS not-accessible
	STATUS mandatory
	DESCRIPTION
		"A list of module-specific information about a 
		specific 51nnM-TP module in the concentrator."
	INDEX { ol51nnMTPModSlotIndex }
	::= { ol51nnMTPModTable 1 }

Ol51nnMTPModEntry ::= 
	SEQUENCE {
		ol51nnMTPModSlotIndex
			INTEGER,
		ol51nnMTPModDipNetwork
			INTEGER,
		ol51nnMTPModCrossover
			INTEGER,
		ol51nnMTPModDipCrossover
			INTEGER
		}

ol51nnMTPModSlotIndex OBJECT-TYPE
	SYNTAX INTEGER
	ACCESS read-only
	STATUS mandatory
	DESCRIPTION
		"The slot number of this module."
	::= { ol51nnMTPModEntry 1 }

ol51nnMTPModDipNetwork OBJECT-TYPE
	SYNTAX INTEGER {
		isolated(2),
		ethernet-1(6),
		ethernet-2(7),
		ethernet-3(8)
		}
	ACCESS read-only
	STATUS mandatory
	DESCRIPTION
		"The network indicated by the module's dip switches."	
	::= { ol51nnMTPModEntry 2 }

ol51nnMTPModCrossover OBJECT-TYPE
	SYNTAX INTEGER {
		crossed(1),
		uncrossed(2)
		}
	ACCESS read-write
	STATUS mandatory
	DESCRIPTION
		"The current state of this module's crossover
		configuration.  Setting this object to uncrossed(2)
		allows the last port to be used to connect to another
		repeater.  Often this feature is used to connect one 10BASE-T
		module to another."
	::= { ol51nnMTPModEntry 3 }
	
ol51nnMTPModDipCrossover OBJECT-TYPE
	SYNTAX INTEGER {
		crossed(1),
		uncrossed(2)
		}
	ACCESS read-only
	STATUS mandatory
	DESCRIPTION
		"The crossover configuration indicated by this module's
		dip switches."
	::= { ol51nnMTPModEntry 4 }
	

ol51nnMTPPortTable			 OBJECT-TYPE
	SYNTAX SEQUENCE OF Ol51nnMTPPortEntry
	ACCESS not-accessible
	STATUS mandatory
	DESCRIPTION
		"A table of port-specific information for each port of
		this module type."
	::= { ol51nnMTP 2 }

ol51nnMTPPortEntry OBJECT-TYPE
	SYNTAX Ol51nnMTPPortEntry
	ACCESS not-accessible
	STATUS mandatory
	DESCRIPTION
		"A port entry containing objects that describe this port."
	INDEX { ol51nnMTPPortSlotIndex, ol51nnMTPPortIndex }
	::= { ol51nnMTPPortTable 1 }

Ol51nnMTPPortEntry ::= 
	SEQUENCE {
		ol51nnMTPPortSlotIndex
			INTEGER,			
		ol51nnMTPPortIndex
			INTEGER,
		ol51nnMTPPortAdminState
			INTEGER,
		ol51nnMTPPortBuddySlot
			INTEGER,
		ol51nnMTPPortBuddyPort
			INTEGER,
		ol51nnMTPPortDipAdminState
			INTEGER,
		ol51nnMTPPortLinkInteg
			INTEGER,
		ol51nnMTPPortDipLinkInteg
			INTEGER,
		ol51nnMTPPortSquelch
			INTEGER,
		ol51nnMTPPortDipSquelch
			INTEGER
		}

	ol51nnMTPPortSlotIndex OBJECT-TYPE
	SYNTAX INTEGER
	ACCESS read-only
	STATUS mandatory
	DESCRIPTION
		"The slot number of this port's module."
	::= { ol51nnMTPPortEntry 1 }


ol51nnMTPPortIndex OBJECT-TYPE
	SYNTAX INTEGER
	ACCESS read-only
	STATUS mandatory
	DESCRIPTION
		"The port number of this port."
	::= { ol51nnMTPPortEntry 2 }

ol51nnMTPPortAdminState OBJECT-TYPE
	SYNTAX INTEGER {
		enabled(1),
		disabled(2),
		redundant-primary(3),
		redundant-backup(4)
		}
	ACCESS read-write
	STATUS mandatory
	DESCRIPTION
		"The desired state of this port.  Setting this port to 
		be redundant with invalid settings of buddy slot and
		buddy port will return the genError error."
	::= { ol51nnMTPPortEntry 3 }

ol51nnMTPPortBuddySlot OBJECT-TYPE
	SYNTAX INTEGER
	ACCESS read-write
	STATUS mandatory
	DESCRIPTION
		"The slot index of the redundant port's buddy.  To set
		a port to be redundant, the buddy's slot and port must 
		be set to valid values.

		The buddy is automatically set to be redundant to this port."
	::= { ol51nnMTPPortEntry 4 }

ol51nnMTPPortBuddyPort  OBJECT-TYPE
	SYNTAX INTEGER
	ACCESS read-write
	STATUS mandatory
	DESCRIPTION
		"The port index of the redundant port's buddy.  To set
		a port to be redundant, the buddy's slot and port must 
		be set to valid values.

		The buddy is automatically set to be redundant to this port."
	::= { ol51nnMTPPortEntry 5 }

ol51nnMTPPortDipAdminState OBJECT-TYPE
	SYNTAX INTEGER {
		enabled(1),
		disabled(2)
		}
	ACCESS read-only
	STATUS mandatory
	DESCRIPTION
		"The state of this port as indicated by the port's dip 
		switches."		
	::= { ol51nnMTPPortEntry 6 }

ol51nnMTPPortLinkInteg OBJECT-TYPE
	SYNTAX INTEGER {
		enabled(1),
		disabled(2)
		}
	ACCESS read-write
	STATUS mandatory
	DESCRIPTION
		"The port's link integrity configuration.  Enabling
		link integrity configures the port to conform to
		the link integrity feature as specified by 10BASE-T."
	::= { ol51nnMTPPortEntry 7 }

ol51nnMTPPortDipLinkInteg OBJECT-TYPE
	SYNTAX INTEGER {
		enabled(1),
		disabled(2)
		}
	ACCESS read-only
	STATUS mandatory
	DESCRIPTION
		"The link integrity configuration as indicated by this
		port's dip switches."
	::= { ol51nnMTPPortEntry 8 }

ol51nnMTPPortSquelch	 OBJECT-TYPE
	SYNTAX INTEGER {
		normal(1),		-- high squelch
		low(2)
		}
	ACCESS read-write
	STATUS mandatory
	DESCRIPTION
		"The port's squelch configuration.  See the module's
		user's guide for more information."
	::= { ol51nnMTPPortEntry 9 }

ol51nnMTPPortDipSquelch	 OBJECT-TYPE
	SYNTAX INTEGER {
		normal(1),		-- high squelch
		low(2)
		}
	ACCESS read-only
	STATUS mandatory
	DESCRIPTION
		"The port's squelch configuration as indicated by this
		port's dip switches."
	::= { ol51nnMTPPortEntry 10 }

--
-- ONline Ethernet BNC Module
--


ol51nnMBNCModTable OBJECT-TYPE
	SYNTAX SEQUENCE OF Ol51nnMBNCModEntry
	ACCESS not-accessible
	STATUS mandatory
	DESCRIPTION
		"A list of module-specific information associated
		with a particular 51nnM-BNC module in the concentrator."
	::= { ol51nnMBNC 1 }

ol51nnMBNCModEntry OBJECT-TYPE
	SYNTAX Ol51nnMBNCModEntry 
	ACCESS not-accessible
	STATUS mandatory
	DESCRIPTION
		"A module entry containing objects that describe the 
		module level for that particular module."
        INDEX { ol51nnMBNCModSlotIndex }
	::= { ol51nnMBNCModTable 1 }

Ol51nnMBNCModEntry ::=
	SEQUENCE {
		ol51nnMBNCModSlotIndex
			INTEGER,
		ol51nnMBNCModDipNetwork
			INTEGER
		}

ol51nnMBNCModSlotIndex OBJECT-TYPE
	SYNTAX INTEGER
	ACCESS read-only
	STATUS mandatory
	DESCRIPTION
		"The slot number of this module."
	::= { ol51nnMBNCModEntry 1 }

ol51nnMBNCModDipNetwork OBJECT-TYPE
	SYNTAX INTEGER {
		isolated(2),
		ethernet-1(6),
		ethernet-2(7),
		ethernet-3(8)
		}
	ACCESS read-only
	STATUS mandatory
	DESCRIPTION
		"The network indicated by the module's dip switches."	
	::= { ol51nnMBNCModEntry 2 }

ol51nnMBNCPortTable OBJECT-TYPE
	SYNTAX SEQUENCE OF Ol51nnMBNCPortEntry
	ACCESS not-accessible
	STATUS mandatory
	DESCRIPTION
		"A table of port-specific information for each port of
		this module type."
	::= { ol51nnMBNC 2 }

ol51nnMBNCPortEntry OBJECT-TYPE
	SYNTAX Ol51nnMBNCPortEntry 
	ACCESS not-accessible
	STATUS mandatory
	DESCRIPTION
		"A port entry containing objects that describe this port."
        INDEX { ol51nnMBNCPortSlotIndex, ol51nnMBNCPortIndex }
	::= { ol51nnMBNCPortTable 1 }

Ol51nnMBNCPortEntry ::=
	SEQUENCE {	
		ol51nnMBNCPortSlotIndex
			INTEGER,			
		ol51nnMBNCPortIndex
			INTEGER,
		ol51nnMBNCPortDipAdminState
			INTEGER,
		ol51nnMBNCPortDipTermination
			INTEGER,
		ol51nnMBNCPortDipGround
			INTEGER
		}

ol51nnMBNCPortSlotIndex OBJECT-TYPE
	SYNTAX INTEGER
	ACCESS read-only
	STATUS mandatory
	DESCRIPTION
		"The slot number of this port's module."
	::= { ol51nnMBNCPortEntry 1 }


ol51nnMBNCPortIndex OBJECT-TYPE
	SYNTAX INTEGER
	ACCESS read-only
	STATUS mandatory
	DESCRIPTION
		"The port number of this port."		
	::= { ol51nnMBNCPortEntry 2 }

ol51nnMBNCPortDipAdminState OBJECT-TYPE
	SYNTAX INTEGER {
		enabled(1),
		disabled(2)
		}
	ACCESS read-only
	STATUS mandatory
	DESCRIPTION
		"The state of this port as indicated by the port's dip 
		switches."		
	::= { ol51nnMBNCPortEntry 3 }

ol51nnMBNCPortDipTermination OBJECT-TYPE
	SYNTAX INTEGER {
		terminated(1),
		not-terminated(2)
		}
	ACCESS read-only
	STATUS mandatory
	DESCRIPTION
		"The state of this port's termination as indicated by the
		port's dip switches."		
	::= { ol51nnMBNCPortEntry 4 }

ol51nnMBNCPortDipGround OBJECT-TYPE
	SYNTAX INTEGER {
		grounded(1),
		not-grounded(2)
		}
	ACCESS read-only
	STATUS mandatory
	DESCRIPTION
		"The state of this port's ground as indicated by the port's 
		dip switches."		
	::= { ol51nnMBNCPortEntry 5 }

--
-- ONline Ethernet to Ethernet Bridge Module
--

ol51nnBEEModTable OBJECT-TYPE
	SYNTAX SEQUENCE OF Ol51nnBEEModEntry
	ACCESS not-accessible
	STATUS mandatory
	DESCRIPTION
		"A table of module-specific information for
		each 51nnB-EE module in the concentrator."
	::= { ol51nnBEE 1 }

ol51nnBEEModEntry OBJECT-TYPE
	SYNTAX Ol51nnBEEModEntry
	ACCESS not-accessible
	STATUS mandatory
	DESCRIPTION
		"A list of module-specific information about a specific
		51nnB-EE module in the concentrator."
	INDEX { ol51nnBEEModSlotIndex }
	::= { ol51nnBEEModTable 1 }

Ol51nnBEEModEntry ::= 
	SEQUENCE {
		ol51nnBEEModSlotIndex
			INTEGER,	
		ol51nnBEEModStationAddr
			OCTET STRING,
		ol51nnBEEModProtocols
			DisplayString
		}

ol51nnBEEModSlotIndex OBJECT-TYPE
	SYNTAX INTEGER
	ACCESS read-only
	STATUS mandatory
	DESCRIPTION
		"The slot number of this module."
	::= { ol51nnBEEModEntry 1 }

ol51nnBEEModStationAddr OBJECT-TYPE
	SYNTAX OCTET STRING (SIZE(6))
	ACCESS read-only
	STATUS mandatory
	DESCRIPTION
		"A 6 octet address that uniquely identifies this module.
		The station address is the mac address of port 1."
	::= { ol51nnBEEModEntry 2 }

ol51nnBEEModProtocols OBJECT-TYPE
	SYNTAX DisplayString
	ACCESS read-only
	STATUS mandatory
	DESCRIPTION
		"A textual description of the protocols supported by 
		this module"
	::= { ol51nnBEEModEntry 3 }
		
	
ol51nnBEEPortTable	OBJECT-TYPE
	SYNTAX SEQUENCE OF Ol51nnBEEPortEntry
	ACCESS not-accessible
	STATUS mandatory
	DESCRIPTION
		"A table of port-specific for each port of each 
		51nnBEE module in the concentrator."
	::= { ol51nnBEE 2 }


ol51nnBEEPortEntry OBJECT-TYPE
	SYNTAX Ol51nnBEEPortEntry
	ACCESS not-accessible
	STATUS mandatory
	DESCRIPTION
		"A list of port-specific informatoin about a specific
		51nnB-EE port in the concentrator."
        INDEX { ol51nnBEEPortSlotIndex, ol51nnBEEPortIndex }
	::= { ol51nnBEEPortTable 1 }

Ol51nnBEEPortEntry ::= 
	SEQUENCE {
		ol51nnBEEPortSlotIndex
			INTEGER,
		ol51nnBEEPortIndex
			INTEGER,
		ol51nnBEEPortIpAddress
			IpAddress,
		ol51nnBEEPortDipNetwork
			INTEGER,
		ol51nnBEEPortDefNetwork
			INTEGER
		}

ol51nnBEEPortSlotIndex OBJECT-TYPE
	SYNTAX INTEGER
	ACCESS read-only
	STATUS mandatory
	DESCRIPTION
		"The slot number for this port's module."
	::= { ol51nnBEEPortEntry 1 }

ol51nnBEEPortIndex OBJECT-TYPE
	SYNTAX INTEGER
	ACCESS read-only
	STATUS mandatory
	DESCRIPTION
		"The port number for this port within this slot."
	::= { ol51nnBEEPortEntry 2 }

ol51nnBEEPortIpAddress OBJECT-TYPE
	SYNTAX IpAddress
	ACCESS read-only
	STATUS mandatory
	DESCRIPTION
		"The IP Address associated with this port."
	::= { ol51nnBEEPortEntry 3 }

ol51nnBEEPortDipNetwork OBJECT-TYPE
	SYNTAX INTEGER {
		isolated(2),
		front-panel(5),
		ethernet-1(6),
		ethernet-2(7),
		ethernet-3(8)
		}
	ACCESS read-only
	STATUS mandatory
	DESCRIPTION
		"The network for this port as specified by this port's
		dip switches."
	::= { ol51nnBEEPortEntry 4 }

ol51nnBEEPortDefNetwork OBJECT-TYPE
	SYNTAX INTEGER {
		isolated(2),
		front-panel(5),
		ethernet-1(6),
		ethernet-2(7),
		ethernet-3(8)
		}
	ACCESS read-only
	STATUS mandatory
	DESCRIPTION
		"The network for this port as specified by the OEBM's
		non-volatile storage."
	::= { ol51nnBEEPortEntry 5 }

--
-- ONline Ethernet to Serial Router Module
--


ol51nnRESModTable OBJECT-TYPE
	SYNTAX SEQUENCE OF Ol51nnRESModEntry
	ACCESS not-accessible
	STATUS mandatory
	DESCRIPTION
		"A table of module-specific information for
		each 51nnR-ES module in the concentrator."
	::= { ol51nnRES 1 }

ol51nnRESModEntry OBJECT-TYPE
	SYNTAX Ol51nnRESModEntry
	ACCESS not-accessible
	STATUS mandatory
	DESCRIPTION
		"A list of module-specific information about a specific
		51nnR-ES module in the concentrator."
	INDEX { ol51nnRESModSlotIndex }
	::= { ol51nnRESModTable 1 }

Ol51nnRESModEntry ::= 
	SEQUENCE {
		ol51nnRESModSlotIndex
			INTEGER,	
		ol51nnRESModStationAddr
			OCTET STRING,
		ol51nnRESModProtocols
			DisplayString
		}

ol51nnRESModSlotIndex OBJECT-TYPE
	SYNTAX INTEGER
	ACCESS read-only
	STATUS mandatory
	DESCRIPTION
		"The slot number of this module."
	::= { ol51nnRESModEntry 1 }

ol51nnRESModStationAddr OBJECT-TYPE
	SYNTAX OCTET STRING (SIZE(6))
	ACCESS read-only
	STATUS mandatory
	DESCRIPTION
		"A 6 octet address that uniquely identifies this module.
		The station address is the mac address of port 1."
	::= { ol51nnRESModEntry 2 }


ol51nnRESModProtocols OBJECT-TYPE
	SYNTAX DisplayString
	ACCESS read-only
	STATUS mandatory
	DESCRIPTION
		"A textual description of the protocols supported by 
		this module"
	::= { ol51nnRESModEntry 3 }

ol51nnRESPortTable	OBJECT-TYPE
	SYNTAX SEQUENCE OF Ol51nnRESPortEntry
	ACCESS not-accessible
	STATUS mandatory
	DESCRIPTION
		"A table of port-specific for each port of each 
		51nnR-ES module in the concentrator."
	::= { ol51nnRES 2 }

ol51nnRESPortEntry OBJECT-TYPE
	SYNTAX Ol51nnRESPortEntry
	ACCESS not-accessible
	STATUS mandatory
	DESCRIPTION
		"A list of port-specific informatoin about a specific
		51nnR-ES port in the concentrator."
        INDEX { ol51nnRESPortSlotIndex, ol51nnRESPortIndex }
	::= { ol51nnRESPortTable 1 }

Ol51nnRESPortEntry ::= 
	SEQUENCE {
		ol51nnRESPortSlotIndex
			INTEGER,
		ol51nnRESPortIndex
			INTEGER,
		ol51nnRESPortIpAddress
			IpAddress,
		ol51nnRESPortDipNetwork
			INTEGER,
		ol51nnRESPortDefNetwork
			INTEGER
		}

ol51nnRESPortSlotIndex OBJECT-TYPE
	SYNTAX INTEGER
	ACCESS read-only
	STATUS mandatory
	DESCRIPTION
		"The slot number for this port's module."
	::= { ol51nnRESPortEntry 1 }

ol51nnRESPortIndex OBJECT-TYPE
	SYNTAX INTEGER
	ACCESS read-only
	STATUS mandatory
	DESCRIPTION
		"The port number for this port."
	::= { ol51nnRESPortEntry 2 }

ol51nnRESPortIpAddress OBJECT-TYPE
	SYNTAX IpAddress
	ACCESS read-only
	STATUS mandatory
	DESCRIPTION
		"The IP Address associated with this port."
	::= { ol51nnRESPortEntry 3 }

ol51nnRESPortDipNetwork OBJECT-TYPE
	SYNTAX INTEGER {
		isolated(2),
		front-panel(5),
		ethernet-1(6),
		ethernet-2(7),
		ethernet-3(8)
		}
	ACCESS read-only
	STATUS mandatory
	DESCRIPTION
		"The network for this port as specified by this port's
		dip switches."
	::= { ol51nnRESPortEntry 4 }

ol51nnRESPortDefNetwork OBJECT-TYPE
	SYNTAX INTEGER {
		isolated(2),
		front-panel(5),
		ethernet-1(6),
		ethernet-2(7),
		ethernet-3(8)
		}
	ACCESS read-only
	STATUS mandatory
	DESCRIPTION
		"The network for this port as specified by the OERM's
		non-volatile storage."
	::= { ol51nnRESPortEntry 5 }

--
-- ONline Ethernet to Ethernet Router Module
--


ol51nnREEModTable OBJECT-TYPE
	SYNTAX SEQUENCE OF Ol51nnREEModEntry
	ACCESS not-accessible
	STATUS mandatory
	DESCRIPTION
		"A table of module-specific information for
		each 51nnR-EE module in the concentrator."
	::= { ol51nnREE 1 }

ol51nnREEModEntry OBJECT-TYPE
	SYNTAX Ol51nnREEModEntry
	ACCESS not-accessible
	STATUS mandatory
	DESCRIPTION
		"A list of module-specific information about a specific
		51nnR-EE module in the concentrator."
	INDEX { ol51nnREEModSlotIndex }
	::= { ol51nnREEModTable 1 }

Ol51nnREEModEntry ::= 
	SEQUENCE {
		ol51nnREEModSlotIndex
			INTEGER,	
		ol51nnREEModStationAddr
			OCTET STRING,
		ol51nnREEModProtocols
			DisplayString
		}

ol51nnREEModSlotIndex OBJECT-TYPE
	SYNTAX INTEGER
	ACCESS read-only
	STATUS mandatory
	DESCRIPTION
		"The slot number of this module."
	::= { ol51nnREEModEntry 1 }

ol51nnREEModStationAddr OBJECT-TYPE
	SYNTAX OCTET STRING (SIZE(6))
	ACCESS read-only
	STATUS mandatory
	DESCRIPTION
		"A 6 octet address that uniquely identifies this module.
		The station address is the mac address of port 1."
	::= { ol51nnREEModEntry 2 }


ol51nnREEModProtocols OBJECT-TYPE
	SYNTAX DisplayString
	ACCESS read-only
	STATUS mandatory
	DESCRIPTION
		"A textual description of the protocols supported by 
		this module"
	::= { ol51nnREEModEntry 3 }

ol51nnREEPortTable	OBJECT-TYPE
	SYNTAX SEQUENCE OF Ol51nnREEPortEntry
	ACCESS not-accessible
	STATUS mandatory
	DESCRIPTION
		"A table of port-specific for each port of each 
		51nnR-EE module in the concentrator."
	::= { ol51nnREE 2 }

ol51nnREEPortEntry OBJECT-TYPE
	SYNTAX Ol51nnREEPortEntry
	ACCESS not-accessible
	STATUS mandatory
	DESCRIPTION
		"A list of port-specific informatoin about a specific
		51nnR-EE port in the concentrator."
        INDEX { ol51nnREEPortSlotIndex, ol51nnREEPortIndex }
	::= { ol51nnREEPortTable 1 }

Ol51nnREEPortEntry ::= 
	SEQUENCE {
		ol51nnREEPortSlotIndex
			INTEGER,
		ol51nnREEPortIndex
			INTEGER,
		ol51nnREEPortIpAddress
			IpAddress,
		ol51nnREEPortDipNetwork
			INTEGER,
		ol51nnREEPortDefNetwork
			INTEGER
		}

ol51nnREEPortSlotIndex OBJECT-TYPE
	SYNTAX INTEGER
	ACCESS read-only
	STATUS mandatory
	DESCRIPTION
		"The slot number for this port's module."
	::= { ol51nnREEPortEntry 1 }

ol51nnREEPortIndex OBJECT-TYPE
	SYNTAX INTEGER
	ACCESS read-only
	STATUS mandatory
	DESCRIPTION
		"The port number of this port."
	::= { ol51nnREEPortEntry 2 }

ol51nnREEPortIpAddress OBJECT-TYPE
	SYNTAX IpAddress
	ACCESS read-only
	STATUS mandatory
	DESCRIPTION
		"The IP Address associated with this port."
	::= { ol51nnREEPortEntry 3 }

ol51nnREEPortDipNetwork OBJECT-TYPE
	SYNTAX INTEGER {
		isolated(2),
		front-panel(5),
		ethernet-1(6),
		ethernet-2(7),
		ethernet-3(8)
		}
	ACCESS read-only
	STATUS mandatory
	DESCRIPTION
		"The network for this port as specified by this port's
		dip switches."
	::= { ol51nnREEPortEntry 4 }

ol51nnREEPortDefNetwork OBJECT-TYPE
	SYNTAX INTEGER {
		isolated(2),
		front-panel(5),
		ethernet-1(6),
		ethernet-2(7),
		ethernet-3(8)
		}
	ACCESS read-only
	STATUS mandatory
	DESCRIPTION
		"The network for this port as specified by the OERM's
		non-volatile storage."
	::= { ol51nnREEPortEntry 5 }

-- 
-- ONline Ethernet Female AUI Module
--

ol51nnMAUIFModTable OBJECT-TYPE
	SYNTAX SEQUENCE OF Ol51nnMAUIFModEntry
	ACCESS not-accessible
	STATUS mandatory
	DESCRIPTION
		"A list of module-specific information associated
		with a particular 51nnMAUIF module in the concentrator."
	::= { ol51nnMAUIF 1 }

ol51nnMAUIFModEntry OBJECT-TYPE
	SYNTAX Ol51nnMAUIFModEntry 
	ACCESS not-accessible
	STATUS mandatory
	DESCRIPTION
		"A list of module-specific information about a specific
		51nnMAUIF module in the concentrator."
	INDEX { ol51nnMAUIFModSlotIndex }
	::= { ol51nnMAUIFModTable 1 }

Ol51nnMAUIFModEntry ::=
	SEQUENCE {
		ol51nnMAUIFModSlotIndex
			INTEGER
		}

ol51nnMAUIFModSlotIndex OBJECT-TYPE
	SYNTAX INTEGER
	ACCESS read-only
	STATUS mandatory
	DESCRIPTION
		"The slot number of this module."
	::= { ol51nnMAUIFModEntry 1 }

ol51nnMAUIFPortTable OBJECT-TYPE
	SYNTAX SEQUENCE OF Ol51nnMAUIFPortEntry
	ACCESS not-accessible
	STATUS mandatory
	DESCRIPTION
		"A table of port-specific information for each port of
		this module type."
	::= { ol51nnMAUIF 2 }

ol51nnMAUIFPortEntry OBJECT-TYPE
	SYNTAX Ol51nnMAUIFPortEntry 
	ACCESS not-accessible
	STATUS mandatory
	DESCRIPTION
		"A list of module-specific information about a specific
		51nnM-AUIF port in the concentrator."
	INDEX { ol51nnMAUIFPortSlotIndex, ol51nnMAUIFPortIndex }
	::= { ol51nnMAUIFPortTable 1 }

Ol51nnMAUIFPortEntry ::=
	SEQUENCE {
		ol51nnMAUIFPortSlotIndex
			INTEGER,			
		ol51nnMAUIFPortIndex
			INTEGER,
		ol51nnMAUIFPortAdminState
			INTEGER,
		ol51nnMAUIFPortBuddySlot
			INTEGER,
		ol51nnMAUIFPortBuddyPort
			INTEGER,
		ol51nnMAUIFPortDipAdminState
			INTEGER,
		ol51nnMAUIFPortDipNetwork
			INTEGER
		}

ol51nnMAUIFPortSlotIndex OBJECT-TYPE
	SYNTAX INTEGER
	ACCESS read-only
	STATUS mandatory
	DESCRIPTION
		"The slot number of this port's module."
	::= { ol51nnMAUIFPortEntry 1 }


ol51nnMAUIFPortIndex OBJECT-TYPE
	SYNTAX INTEGER
	ACCESS read-only
	STATUS mandatory
	DESCRIPTION
		"The port number of this port."
	::= { ol51nnMAUIFPortEntry 2 }

ol51nnMAUIFPortAdminState OBJECT-TYPE
	SYNTAX INTEGER {
		enabled(1),
		disabled(2),
		redundant-primary(3),
		redundant-backup(4)
		}
	ACCESS read-write
	STATUS mandatory
	DESCRIPTION
		"The desired state of this port.  Setting this port to 
		be redundant with invalid settings of buddy slot and
		buddy port will return the genError error."
	::= { ol51nnMAUIFPortEntry 3 }

ol51nnMAUIFPortBuddySlot OBJECT-TYPE
	SYNTAX INTEGER
	ACCESS read-write
	STATUS mandatory
	DESCRIPTION
		"The slot index of the redundant port's buddy.  To set
		a port to be redundant, the buddy's slot and port must 
		be set to valid values.

		The buddy is automatically set to be redundant to this port."
	::= { ol51nnMAUIFPortEntry 4 }

ol51nnMAUIFPortBuddyPort  OBJECT-TYPE
	SYNTAX INTEGER
	ACCESS read-write
	STATUS mandatory
	DESCRIPTION
		"The port index of the redundant port's buddy.  To set
		a port to be redundant, the buddy's slot and port must 
		be set to valid values.

		The buddy is automatically set to be redundant to this port."
	::= { ol51nnMAUIFPortEntry 5 }

ol51nnMAUIFPortDipAdminState OBJECT-TYPE
	SYNTAX INTEGER {
		enabled(1),
		disabled(2),
		redundant-primary(3),
		redundant-backup(4)
		}
	ACCESS read-only
	STATUS mandatory
	DESCRIPTION
		"The state of this port as indicated by the port's dip 
		switches."		
	::= { ol51nnMAUIFPortEntry 6 }


ol51nnMAUIFPortDipNetwork OBJECT-TYPE
	SYNTAX INTEGER {
		isolated(2),
		ethernet-1(6),
		ethernet-2(7),
		ethernet-3(8)
		}
	ACCESS read-only
	STATUS mandatory
	DESCRIPTION
		"The network indicated by the port's dip switches."	
	::= { ol51nnMAUIFPortEntry 7 }


-- 
-- ONline Ethernet Male AUI Module 
--

ol51nnMAUIMModTable OBJECT-TYPE
	SYNTAX SEQUENCE OF Ol51nnMAUIMModEntry
	ACCESS not-accessible
	STATUS mandatory
	DESCRIPTION
		"A list of module-specific information associated
		with a particular 51nnM-AUIM module in the concentrator."
	::= { ol51nnMAUIM 1 }

ol51nnMAUIMModEntry OBJECT-TYPE
	SYNTAX Ol51nnMAUIMModEntry 
	ACCESS not-accessible
	STATUS mandatory
	DESCRIPTION
		"A list of module-specific information about a specific
		51nnM-AUIM module in the concentrator."
	INDEX { ol51nnMAUIMModSlotIndex }
	::= { ol51nnMAUIMModTable 1 }

Ol51nnMAUIMModEntry ::=
	SEQUENCE {
		ol51nnMAUIMModSlotIndex
			INTEGER
		}

ol51nnMAUIMModSlotIndex OBJECT-TYPE
	SYNTAX INTEGER
	ACCESS read-only
	STATUS mandatory
	DESCRIPTION
		"The slot number of this module."
	::= { ol51nnMAUIMModEntry 1 }

ol51nnMAUIMPortTable			 OBJECT-TYPE
	SYNTAX SEQUENCE OF Ol51nnMAUIMPortEntry
	ACCESS not-accessible
	STATUS mandatory
	DESCRIPTION
		"A table of port-specific information for each port of
		this module type."
	::= { ol51nnMAUIM 2 }

ol51nnMAUIMPortEntry OBJECT-TYPE
	SYNTAX Ol51nnMAUIMPortEntry 
	ACCESS not-accessible
	STATUS mandatory
	DESCRIPTION
		"A list of module-specific information about a specific
		51nnM-AUIM port in the concentrator."
	INDEX { ol51nnMAUIMPortSlotIndex, ol51nnMAUIMPortIndex }
	::= { ol51nnMAUIMPortTable 1 }

Ol51nnMAUIMPortEntry ::=
	SEQUENCE {
		ol51nnMAUIMPortSlotIndex
			INTEGER,			
		ol51nnMAUIMPortIndex
			INTEGER,
		ol51nnMAUIMPortAdminState
			INTEGER,
		ol51nnMAUIMPortBuddySlot
			INTEGER,
		ol51nnMAUIMPortBuddyPort
			INTEGER,
		ol51nnMAUIMPortDipAdminState
			INTEGER,
		ol51nnMAUIMPortDipNetwork
			INTEGER,
		ol51nnMAUIMPortSQETest
			INTEGER,
		ol51nnMAUIMPortDipSQETest
			INTEGER,
		ol51nnMAUIMPortCollision
			INTEGER,
		ol51nnMAUIMPortDipCollision
			INTEGER,
		ol51nnMAUIMPortHalfStep
			INTEGER,
		ol51nnMAUIMPortDipHalfStep
			INTEGER
		}

ol51nnMAUIMPortSlotIndex OBJECT-TYPE
	SYNTAX INTEGER
	ACCESS read-only
	STATUS mandatory
	DESCRIPTION
		"The slot number of this port's module."
	::= { ol51nnMAUIMPortEntry 1 }


ol51nnMAUIMPortIndex OBJECT-TYPE
	SYNTAX INTEGER
	ACCESS read-only
	STATUS mandatory
	DESCRIPTION
		"The port number of this port."
	::= { ol51nnMAUIMPortEntry 2 }

ol51nnMAUIMPortAdminState OBJECT-TYPE
	SYNTAX INTEGER {
		enabled(1),
		disabled(2),
		redundant-primary(3),
		redundant-backup(4)
		}
	ACCESS read-write
	STATUS mandatory
	DESCRIPTION
		"The desired state of this port.  Setting this port to 
		be redundant with invalid settings of buddy slot and
		buddy port will return the genError error."
	::= { ol51nnMAUIMPortEntry 3 }

ol51nnMAUIMPortBuddySlot OBJECT-TYPE
	SYNTAX INTEGER
	ACCESS read-write
	STATUS mandatory
	DESCRIPTION
		"The slot index of the redundant port's buddy.  To set
		a port to be redundant, the buddy's slot and port must 
		be set to valid values.

		The buddy is automatically set to be redundant to this port."
	::= { ol51nnMAUIMPortEntry 4 }

ol51nnMAUIMPortBuddyPort  OBJECT-TYPE
	SYNTAX INTEGER
	ACCESS read-write
	STATUS mandatory
	DESCRIPTION
		"The port index of the redundant port's buddy.  To set
		a port to be redundant, the buddy's slot and port must 
		be set to valid values.

		The buddy is automatically set to be redundant to this port."
	::= { ol51nnMAUIMPortEntry 5 }

ol51nnMAUIMPortDipAdminState OBJECT-TYPE
	SYNTAX INTEGER {
		enabled(1),
		disabled(2)
		}
	ACCESS read-only
	STATUS mandatory
	DESCRIPTION
		"The state of this port as indicated by the port's dip 
		switches."		
	::= { ol51nnMAUIMPortEntry 6 }

ol51nnMAUIMPortDipNetwork OBJECT-TYPE
	SYNTAX INTEGER {
		isolated(2),
		ethernet-1(6),
		ethernet-2(7),
		ethernet-3(8)
		}
	ACCESS read-only
	STATUS mandatory
	DESCRIPTION
		"The network indicated by the port's dip switches."
	::= { ol51nnMAUIMPortEntry 7 }	

ol51nnMAUIMPortSQETest OBJECT-TYPE
	SYNTAX INTEGER {
		enabled(1),
		disabled(2)
		}
	ACCESS read-write
	STATUS mandatory
	DESCRIPTION
		"The current SQE test configuration for this port."
	::= { ol51nnMAUIMPortEntry 8 }

ol51nnMAUIMPortDipSQETest OBJECT-TYPE
	SYNTAX INTEGER {
		enabled(1),
		disabled(2)
		}
	ACCESS read-only
	STATUS mandatory
	DESCRIPTION
		"The SQE test configuration for this port as indicated
		by the port's dip switches."
	::= { ol51nnMAUIMPortEntry 9 }

ol51nnMAUIMPortCollision OBJECT-TYPE
	SYNTAX INTEGER {
		normal(1),
		alternate(2)
		}
	ACCESS read-write
	STATUS mandatory
	DESCRIPTION
		"The current collision configuration for this port."
	::= { ol51nnMAUIMPortEntry 10 }

ol51nnMAUIMPortDipCollision OBJECT-TYPE
	SYNTAX INTEGER {
		normal(1),
		alternate(2)
		}
	ACCESS read-only
	STATUS mandatory
	DESCRIPTION
		"The collision configuration for this port as indicated
		by the port's dip switches."
	::= { ol51nnMAUIMPortEntry 11 }

ol51nnMAUIMPortHalfStep OBJECT-TYPE
	SYNTAX INTEGER {
		enabled(1),
		disabled(2)
		}
	ACCESS read-write
	STATUS mandatory
	DESCRIPTION
		"The current step configuration for this port."
	::= { ol51nnMAUIMPortEntry 12 }

ol51nnMAUIMPortDipHalfStep OBJECT-TYPE
	SYNTAX INTEGER {
		enabled(1),
		disabled(2)
		}
	ACCESS read-only
	STATUS mandatory
	DESCRIPTION
		"The step configuration for this port as indicated
		by the port's dip switches."
	::= { ol51nnMAUIMPortEntry 13 }

--
-- ONline Token Ring 8-Port MAU Module
--
ol5208MTPModTable OBJECT-TYPE
	SYNTAX SEQUENCE OF Ol5208MTPModEntry
	ACCESS not-accessible
	STATUS mandatory
	DESCRIPTION
		"A list of module-specific information associated
		with a particular 5208M-TP module in the concentrator."
	::= { ol5208MTP 1 }

ol5208MTPModEntry OBJECT-TYPE
	SYNTAX Ol5208MTPModEntry
	ACCESS not-accessible
	STATUS mandatory
	DESCRIPTION
		"A description of the 5208M-TP module attributes."
	INDEX { ol5208MTPModSlotIndex }
	::= { ol5208MTPModTable 1 }

Ol5208MTPModEntry ::= 
	SEQUENCE {
		ol5208MTPModSlotIndex
			INTEGER,
		ol5208MTPModBypsAdminState
			INTEGER,
		ol5208MTPModBypsOperState
			INTEGER,
		ol5208MTPModDipCableImp
			INTEGER
		}

ol5208MTPModSlotIndex OBJECT-TYPE
	SYNTAX INTEGER
	ACCESS read-only
	STATUS mandatory
	DESCRIPTION	
		"The slot number of this module."
	::= { ol5208MTPModEntry 1 }


ol5208MTPModBypsAdminState OBJECT-TYPE
	SYNTAX INTEGER {
		insert(1),
		bypass(2)
		}
	ACCESS read-write
	STATUS mandatory
	DESCRIPTION	
		"The desired state of this module with respect
		to the ring.  Setting this attribute to bypass(2) 
		will cause this module to be removed from the ring
		that passes through the module's ring in and ring out
		ports."
	::= { ol5208MTPModEntry 2 }

ol5208MTPModBypsOperState OBJECT-TYPE
	SYNTAX INTEGER {
		insert(1),
		bypass(2)
		}
	ACCESS read-only
	STATUS mandatory
	DESCRIPTION	
		"The operational state of this module with respect
		to the ring.  If this attribute is equal to bypass(2),
		then the module has been removed from the ring that
		passes through the module's ring in and ring out ports."
	::= { ol5208MTPModEntry 3 }

ol5208MTPModDipCableImp OBJECT-TYPE
	SYNTAX INTEGER {
		ohm100(1),
		ohm150(2)
		}
	ACCESS read-only
	STATUS mandatory
	DESCRIPTION
		"The setting of this module's port impedance matching, with
		100 ohm	corresponding to unshielded twisted pair cabling and
		150 ohm	corresponding to shielded twisted pair cabling.
		This setting is valid for all ports on this module."
	::= { ol5208MTPModEntry 4 }
		

ol5208MTPPortTable OBJECT-TYPE
	SYNTAX SEQUENCE OF Ol5208MTPPortEntry
	ACCESS not-accessible
	STATUS mandatory
	DESCRIPTION
		"A table of port-specific information for each port of
		this module type."
	::= { ol5208MTP 2 }

ol5208MTPPortEntry OBJECT-TYPE
	SYNTAX Ol5208MTPPortEntry
	ACCESS not-accessible
	STATUS mandatory
	DESCRIPTION
		"A description of 5208M-TP port attributes."		
	INDEX { ol5208MTPPortSlotIndex, ol5208MTPPortIndex }
	::= { ol5208MTPPortTable 1 }

Ol5208MTPPortEntry ::= 
	SEQUENCE {
		ol5208MTPPortSlotIndex	
			INTEGER,
		ol5208MTPPortIndex
			INTEGER,	
		ol5208MTPPortDipAdminState
			INTEGER,
		ol5208MTPPortStationType
			INTEGER
		}

ol5208MTPPortSlotIndex OBJECT-TYPE
	SYNTAX INTEGER
	ACCESS read-only
	STATUS mandatory
	DESCRIPTION
		"The slot number of this port's module."
	::= { ol5208MTPPortEntry 1 }


ol5208MTPPortIndex OBJECT-TYPE
	SYNTAX INTEGER
	ACCESS read-only
	STATUS mandatory
	DESCRIPTION
		"The port number of this port."
	::= { ol5208MTPPortEntry 2 }

ol5208MTPPortDipAdminState OBJECT-TYPE
	SYNTAX INTEGER {
		enabled(1),
		disabled(2)
		}
	ACCESS read-only
	STATUS mandatory
	DESCRIPTION
		"The state of this port as indicated by the port's dip 
		switches."		
	::= { ol5208MTPPortEntry 3 }

ol5208MTPPortStationType OBJECT-TYPE
	SYNTAX INTEGER {
		mac-present(1),
		mac-not-present(2)
		}
	ACCESS read-write
	STATUS mandatory
	DESCRIPTION
		"Determines whether the station connected to this port
		has a MAC address."
	::= { ol5208MTPPortEntry 4 }

ol5208MTPTrunkTable OBJECT-TYPE
	SYNTAX SEQUENCE OF Ol5208MTPTrunkEntry
	ACCESS not-accessible
	STATUS mandatory
	DESCRIPTION
		"A list of trunk-specific information about each trunk 
		for this module type."
	::= { ol5208MTP 3 }

ol5208MTPTrunkEntry OBJECT-TYPE
	SYNTAX Ol5208MTPTrunkEntry
	ACCESS not-accessible
	STATUS mandatory
	DESCRIPTION
		"A description of 5208M-TP trunk attributes."		
	INDEX { ol5208MTPTrunkSlotIndex, ol5208MTPTrunkIndex }
	::= { ol5208MTPTrunkTable 1 }

Ol5208MTPTrunkEntry ::= 
	SEQUENCE {
		ol5208MTPTrunkSlotIndex	
			INTEGER,
		ol5208MTPTrunkIndex
			INTEGER,	
		ol5208MTPTrunkDipAdminState
			INTEGER,
		ol5208MTPTrunkCableMon
			INTEGER,
		ol5208MTPTrunkDipCableMon
			INTEGER,
		ol5208MTPTrunkNetMapState
			INTEGER,
		ol5208MTPTrunkExtBcnRecovery
			INTEGER
		}

ol5208MTPTrunkSlotIndex OBJECT-TYPE
	SYNTAX INTEGER
	ACCESS read-only
	STATUS mandatory
	DESCRIPTION
		"A unique value that identifies a particular module.  Its
		value ranges between 1 and olModSlotNumber.  The module
		identified by a particular value of this index is the same
		module as indentified by the same value of 
		olTrunkSlotIndex."
	::= { ol5208MTPTrunkEntry 1 }


ol5208MTPTrunkIndex OBJECT-TYPE
	SYNTAX INTEGER
	ACCESS read-only
	STATUS mandatory
	DESCRIPTION
		"The trunk number for this trunk."
	::= { ol5208MTPTrunkEntry 2 }

ol5208MTPTrunkDipAdminState OBJECT-TYPE
	SYNTAX INTEGER {
		enabled(1),
		disabled(2)
		}
	ACCESS read-only
	STATUS mandatory
	DESCRIPTION
		"The state of this trunk as indicated by the trunk's dip 
		switches."		
	::= { ol5208MTPTrunkEntry 3 }

		
ol5208MTPTrunkCableMon OBJECT-TYPE
	SYNTAX INTEGER {
		enabled(1),
		disabled(2),
		notApplicable(3)	
	}
	ACCESS read-write
	STATUS mandatory
	DESCRIPTION
		"The cable monitor configuration for this trunk."
	::= { ol5208MTPTrunkEntry 4 }

ol5208MTPTrunkDipCableMon OBJECT-TYPE
	SYNTAX INTEGER {
		enabled(1),
		disabled(2),
		notApplicable(3)	
	}
	ACCESS read-only
	STATUS mandatory
	DESCRIPTION
		"The cable monitor configuration as indicated by this trunk's
		dip switches."
	::= { ol5208MTPTrunkEntry 5 }


ol5208MTPTrunkNetMapState OBJECT-TYPE
	SYNTAX INTEGER {
		notApplicable(1),
		internal(2),
		external(3)
	}
	ACCESS read-write
	STATUS mandatory
	DESCRIPTION
		"The map state of the copper ring-in trunk.  This
		should be set to external for ring-in trunks which
		connect to external hubs.  The mapping logic will not
		operate on trunks which are set to external.  This 
		prevents incorrect mapping which can occur when a 
		module in one hub detects the mapping signal from
		another hub. This attribute only applies to copper 
		ring-in trunks."
	::= { ol5208MTPTrunkEntry 6 }


ol5208MTPTrunkExtBcnRecovery OBJECT-TYPE
	SYNTAX INTEGER {
		exists(1),
		nonExists(2),
		notApplicable(3)
	}
	ACCESS read-write
	STATUS mandatory
	DESCRIPTION
		"Indicates whether the trunk is connected to a 
		segment that will perform beacon recovery.  This
		should be set to exists(1) for trunks which connect 
		to hubs which perform beacon recovery.  This attribute 
		is used to determine the fault domain when resolving a 
		beaconing condition.

		The beacon recovery process will resolve beaconing on 
		trunks with this attribute set to nonExists(2) before 
		trunks with the attribute set to exists(1) are resolved.
		For backplane trunks, setting to a value other than 
		notApplicable will return invalidData error.  The 
		default value is nonExists(2)."
	::= { ol5208MTPTrunkEntry 7 }


-- 
-- ONline Ethernet Fiber Per-Port Module
--

ol51nnMFPModTable OBJECT-TYPE
	SYNTAX SEQUENCE OF Ol51nnMFPModEntry
	ACCESS not-accessible
	STATUS mandatory
	DESCRIPTION
		"A list of module-specific information associated
		with a particular 51nnM-FP module in the concentrator."
  	::= { ol51nnMFP 1 }

ol51nnMFPModEntry OBJECT-TYPE
	SYNTAX Ol51nnMFPModEntry 
	ACCESS not-accessible
	STATUS mandatory
	DESCRIPTION
		"A list of module-specific information about a specific
		51nnM-FP module in the concentrator."
	INDEX { ol51nnMFPModSlotIndex }
	::= { ol51nnMFPModTable 1 }

Ol51nnMFPModEntry ::=
	SEQUENCE {
		ol51nnMFPModSlotIndex
			INTEGER
		}

ol51nnMFPModSlotIndex OBJECT-TYPE
	SYNTAX INTEGER
	ACCESS read-only
	STATUS mandatory
	DESCRIPTION
		"The slot number of this module."
	::= { ol51nnMFPModEntry 1 }

ol51nnMFPPortTable			 OBJECT-TYPE
	SYNTAX SEQUENCE OF Ol51nnMFPPortEntry
	ACCESS not-accessible
	STATUS mandatory
	DESCRIPTION
		"A table of port-specific information for each port of
		this module type."
	::= { ol51nnMFP 2 }

ol51nnMFPPortEntry OBJECT-TYPE
	SYNTAX Ol51nnMFPPortEntry 
	ACCESS not-accessible
	STATUS mandatory
	DESCRIPTION
		"A list of module-specific information about a specific
		51nnM-FP port in the concentrator."
	INDEX { ol51nnMFPPortSlotIndex, ol51nnMFPPortIndex }
	::= { ol51nnMFPPortTable 1 }

Ol51nnMFPPortEntry ::=
	SEQUENCE {
		ol51nnMFPPortSlotIndex
			INTEGER,			
		ol51nnMFPPortIndex
			INTEGER,
		ol51nnMFPPortAdminState
			INTEGER,
		ol51nnMFPPortBuddySlot
			INTEGER,
		ol51nnMFPPortBuddyPort
			INTEGER,
		ol51nnMFPPortDipAdminState
			INTEGER,
		ol51nnMFPPortDipNetwork
			INTEGER,
		ol51nnMFPPortLLW
			INTEGER,
		ol51nnMFPPortDipLLW
			INTEGER,
		ol51nnMFPPortHipwr
			INTEGER,
		ol51nnMFPPortDipHipwr
			INTEGER
		}

ol51nnMFPPortSlotIndex OBJECT-TYPE
	SYNTAX INTEGER
	ACCESS read-only
	STATUS mandatory
	DESCRIPTION
		"The slot number of this port's module."
	::= { ol51nnMFPPortEntry 1 }


ol51nnMFPPortIndex OBJECT-TYPE
	SYNTAX INTEGER
	ACCESS read-only
	STATUS mandatory
	DESCRIPTION
		"The port number of this port."
	::= { ol51nnMFPPortEntry 2 }

ol51nnMFPPortAdminState OBJECT-TYPE
	SYNTAX INTEGER {
		enabled(1),
		disabled(2),
		redundant-primary(3),
		redundant-backup(4)
		}
	ACCESS read-write
	STATUS mandatory
	DESCRIPTION
		"The desired state of this port.  Setting this port to 
		be redundant with invalid settings of buddy slot and
		buddy port will return the genError error."
	::= { ol51nnMFPPortEntry 3 }

ol51nnMFPPortBuddySlot OBJECT-TYPE
	SYNTAX INTEGER
	ACCESS read-write
	STATUS mandatory
	DESCRIPTION
		"The slot index of the redundant port's buddy.  To set
		a port to be redundant, the buddy's slot and port must 
		be set to valid values.

		The buddy is automatically set to be redundant to this port."
	::= { ol51nnMFPPortEntry 4 }

ol51nnMFPPortBuddyPort  OBJECT-TYPE
	SYNTAX INTEGER
	ACCESS read-write
	STATUS mandatory
	DESCRIPTION
		"The port index of the redundant port's buddy.  To set
		a port to be redundant, the buddy's slot and port must 
		be set to valid values.

		The buddy is automatically set to be redundant to this port."
	::= { ol51nnMFPPortEntry 5 }

ol51nnMFPPortDipAdminState OBJECT-TYPE
	SYNTAX INTEGER {
		enabled(1),
		disabled(2),
                redundant-primary(3),
                redundant-backup(4)
		}
	ACCESS read-only
	STATUS mandatory
	DESCRIPTION
		"The state of this port as indicated by the port's dip 
		switches."		
	::= { ol51nnMFPPortEntry 6 }

ol51nnMFPPortDipNetwork OBJECT-TYPE
	SYNTAX INTEGER {
		isolated(2),
		ethernet-1(6),
		ethernet-2(7),
		ethernet-3(8)
		}
	ACCESS read-only
	STATUS mandatory
	DESCRIPTION
		"The network indicated by the port's dip switches."
	::= { ol51nnMFPPortEntry 7 }	

ol51nnMFPPortLLW OBJECT-TYPE
	SYNTAX INTEGER {
		enabled(1),
		disabled(2)
		}
	ACCESS read-write
	STATUS mandatory
	DESCRIPTION
		"The current low light warning configuration for this port."
	::= { ol51nnMFPPortEntry 8 }

ol51nnMFPPortDipLLW OBJECT-TYPE
	SYNTAX INTEGER {
		enabled(1),
		disabled(2)
		}
	ACCESS read-only
	STATUS mandatory
	DESCRIPTION
		"The low light warning configuration indicated by this module's
		dip switches."
	::= { ol51nnMFPPortEntry 9 }
	
ol51nnMFPPortHipwr OBJECT-TYPE
	SYNTAX INTEGER {
		enabled(1),
		disabled(2)
		}
	ACCESS read-write
	STATUS mandatory
	DESCRIPTION
		"The current high power optic configuration for this port."
	::= { ol51nnMFPPortEntry 10 }

ol51nnMFPPortDipHipwr OBJECT-TYPE
	SYNTAX INTEGER {
		enabled(1),
		disabled(2)
		}
	ACCESS read-only
	STATUS mandatory
	DESCRIPTION
		"The high power optic configuration for this port as indicated
		by the port's dip switches."
	::= { ol51nnMFPPortEntry 11 }

-- 
-- ONline Ethernet 10BASE-F Per-Port Module
--

ol51nnMFBPModTable OBJECT-TYPE
	SYNTAX SEQUENCE OF Ol51nnMFBPModEntry
	ACCESS not-accessible
	STATUS mandatory
	DESCRIPTION
		"A list of module-specific information associated
		with a particular 51nnM-FBP module in the concentrator."
	::= { ol51nnMFBP 1 }

ol51nnMFBPModEntry OBJECT-TYPE
	SYNTAX Ol51nnMFBPModEntry 
	ACCESS not-accessible
	STATUS mandatory
	DESCRIPTION
		"A list of module-specific information about a specific
		51nnM-FBP module in the concentrator."
	INDEX { ol51nnMFBPModSlotIndex }
	::= { ol51nnMFBPModTable 1 }

Ol51nnMFBPModEntry ::=
	SEQUENCE {
		ol51nnMFBPModSlotIndex
			INTEGER
		}

ol51nnMFBPModSlotIndex OBJECT-TYPE
	SYNTAX INTEGER
	ACCESS read-only
	STATUS mandatory
	DESCRIPTION
		"The slot number of this module."
	::= { ol51nnMFBPModEntry 1 }

ol51nnMFBPPortTable			 OBJECT-TYPE
	SYNTAX SEQUENCE OF Ol51nnMFBPPortEntry
	ACCESS not-accessible
	STATUS mandatory
	DESCRIPTION
		"A table of port-specific information for each port of
		this module type."
	::= { ol51nnMFBP 2 }

ol51nnMFBPPortEntry OBJECT-TYPE
	SYNTAX Ol51nnMFBPPortEntry 
	ACCESS not-accessible
	STATUS mandatory
	DESCRIPTION
		"A list of module-specific information about a specific
		51nnM-FBP port in the concentrator."
	INDEX { ol51nnMFBPPortSlotIndex, ol51nnMFBPPortIndex }
	::= { ol51nnMFBPPortTable 1 }

Ol51nnMFBPPortEntry ::=
	SEQUENCE {
		ol51nnMFBPPortSlotIndex
			INTEGER,			
		ol51nnMFBPPortIndex
			INTEGER,
		ol51nnMFBPPortAdminState
			INTEGER,
		ol51nnMFBPPortBuddySlot
			INTEGER,
		ol51nnMFBPPortBuddyPort
			INTEGER,
		ol51nnMFBPPortDipAdminState
			INTEGER,
		ol51nnMFBPPortDipNetwork
			INTEGER,
		ol51nnMFBPPortLLW
			INTEGER,
		ol51nnMFBPPortDipLLW
			INTEGER,
		ol51nnMFBPPortHipwr
			INTEGER,
		ol51nnMFBPPortDipHipwr
			INTEGER
		}

ol51nnMFBPPortSlotIndex OBJECT-TYPE
	SYNTAX INTEGER
	ACCESS read-only
	STATUS mandatory
	DESCRIPTION
		"The slot number of this port's module."
	::= { ol51nnMFBPPortEntry 1 }


ol51nnMFBPPortIndex OBJECT-TYPE
	SYNTAX INTEGER
	ACCESS read-only
	STATUS mandatory
	DESCRIPTION
		"The port number of this port."
	::= { ol51nnMFBPPortEntry 2 }

ol51nnMFBPPortAdminState OBJECT-TYPE
	SYNTAX INTEGER {
		enabled(1),
		disabled(2),
		redundant-primary(3),
		redundant-backup(4)
		}
	ACCESS read-write
	STATUS mandatory
	DESCRIPTION
		"The desired state of this port.  Setting this port to 
		be redundant with invalid settings of buddy slot and
		buddy port will return the genError error."
	::= { ol51nnMFBPPortEntry 3 }

ol51nnMFBPPortBuddySlot OBJECT-TYPE
	SYNTAX INTEGER
	ACCESS read-write
	STATUS mandatory
	DESCRIPTION
		"The slot index of the redundant port's buddy.  To set
		a port to be redundant, the buddy's slot and port must 
		be set to valid values.

		The buddy is automatically set to be redundant to this port."
	::= { ol51nnMFBPPortEntry 4 }

ol51nnMFBPPortBuddyPort  OBJECT-TYPE
	SYNTAX INTEGER
	ACCESS read-write
	STATUS mandatory
	DESCRIPTION
		"The port index of the redundant port's buddy.  To set
		a port to be redundant, the buddy's slot and port must 
		be set to valid values.

		The buddy is automatically set to be redundant to this port."
	::= { ol51nnMFBPPortEntry 5 }

ol51nnMFBPPortDipAdminState OBJECT-TYPE
	SYNTAX INTEGER {
		enabled(1),
		disabled(2),
                redundant-primary(3),
                redundant-backup(4)
		}
	ACCESS read-only
	STATUS mandatory
	DESCRIPTION
		"The state of this port as indicated by the port's dip 
		switches."		
	::= { ol51nnMFBPPortEntry 6 }

ol51nnMFBPPortDipNetwork OBJECT-TYPE
	SYNTAX INTEGER {
		isolated(2),
		ethernet-1(6),
		ethernet-2(7),
		ethernet-3(8)
		}
	ACCESS read-only
	STATUS mandatory
	DESCRIPTION
		"The network indicated by the port's dip switches."
	::= { ol51nnMFBPPortEntry 7 }	

ol51nnMFBPPortLLW OBJECT-TYPE
	SYNTAX INTEGER {
		enabled(1),
		disabled(2)
		}
	ACCESS read-write
	STATUS mandatory
	DESCRIPTION
		"The current low light warning configuration for this port."
	::= { ol51nnMFBPPortEntry 8 }

ol51nnMFBPPortDipLLW OBJECT-TYPE
	SYNTAX INTEGER {
		enabled(1),
		disabled(2)
		}
	ACCESS read-only
	STATUS mandatory
	DESCRIPTION
		"The low light warning configuration indicated by this module's
		dip switches."
	::= { ol51nnMFBPPortEntry 9 }
	
ol51nnMFBPPortHipwr OBJECT-TYPE
	SYNTAX INTEGER {
		enabled(1),
		disabled(2)
		}
	ACCESS read-write
	STATUS mandatory
	DESCRIPTION
		"The current high power optic configuration for this port."
	::= { ol51nnMFBPPortEntry 10 }

ol51nnMFBPPortDipHipwr OBJECT-TYPE
	SYNTAX INTEGER {
		enabled(1),
		disabled(2)
		}
	ACCESS read-only
	STATUS mandatory
	DESCRIPTION
		"The high power optic configuration for this port as indicated
		by the port's dip switches."
	::= { ol51nnMFBPPortEntry 11 }

-- 
-- ONline Ethernet 10BASE-T Module
--

ol51nnMTPLModTable OBJECT-TYPE
	SYNTAX SEQUENCE OF Ol51nnMTPLModEntry
	ACCESS not-accessible
	STATUS mandatory
	DESCRIPTION
		"A list of module-specific information associated
		with a particular 51nnM-TPL module in the concentrator."
	::= { ol51nnMTPL 1 }

ol51nnMTPLModEntry OBJECT-TYPE
	SYNTAX Ol51nnMTPLModEntry 
	ACCESS not-accessible
	STATUS mandatory
	DESCRIPTION
		"A list of module-specific information about a specific
		51nnM-TPL module in the concentrator."
	INDEX { ol51nnMTPLModSlotIndex }
	::= { ol51nnMTPLModTable 1 }

Ol51nnMTPLModEntry ::=
	SEQUENCE {
		ol51nnMTPLModSlotIndex
			INTEGER,
		ol51nnMTPLModDipNetwork
			INTEGER
		}

ol51nnMTPLModSlotIndex OBJECT-TYPE
	SYNTAX INTEGER
	ACCESS read-only
	STATUS mandatory
	DESCRIPTION
		"The slot number of this module."
	::= { ol51nnMTPLModEntry 1 }

ol51nnMTPLModDipNetwork OBJECT-TYPE
	SYNTAX INTEGER {
		isolated(2),
		ethernet-1(6),
		ethernet-2(7),
		ethernet-3(8)
		}
	ACCESS read-only
	STATUS mandatory
	DESCRIPTION
		"The network indicated by the module's dip switches."
	::= { ol51nnMTPLModEntry 2 }	
	
ol51nnMTPLPortTable			 OBJECT-TYPE
	SYNTAX SEQUENCE OF Ol51nnMTPLPortEntry
	ACCESS not-accessible
	STATUS mandatory
	DESCRIPTION
		"A table of port-specific information for each port of
		this module type."
	::= { ol51nnMTPL 2 }

ol51nnMTPLPortEntry OBJECT-TYPE
	SYNTAX Ol51nnMTPLPortEntry 
	ACCESS not-accessible
	STATUS mandatory
	DESCRIPTION
		"A list of module-specific information about a specific
		51nnM-TPL port in the concentrator."
	INDEX { ol51nnMTPLPortSlotIndex, ol51nnMTPLPortIndex }
	::= { ol51nnMTPLPortTable 1 }

Ol51nnMTPLPortEntry ::=
	SEQUENCE {
		ol51nnMTPLPortSlotIndex
			INTEGER,			
		ol51nnMTPLPortIndex
			INTEGER,
		ol51nnMTPLPortAdminState
			INTEGER,
		ol51nnMTPLPortBuddySlot
			INTEGER,
		ol51nnMTPLPortBuddyPort
			INTEGER,
		ol51nnMTPLPortDipAdminState
			INTEGER,
		ol51nnMTPLPortLinkInteg
			INTEGER,
		ol51nnMTPLPortDipLinkInteg
			INTEGER,
		ol51nnMTPLPortSquelch
			INTEGER,
		ol51nnMTPLPortJabber
			INTEGER,
		ol51nnMTPLPortDipJabber
			INTEGER
		}

ol51nnMTPLPortSlotIndex OBJECT-TYPE
	SYNTAX INTEGER
	ACCESS read-only
	STATUS mandatory
	DESCRIPTION
		"The slot number of this port's module."	
	::= { ol51nnMTPLPortEntry 1 }


ol51nnMTPLPortIndex OBJECT-TYPE
	SYNTAX INTEGER
	ACCESS read-only
	STATUS mandatory
	DESCRIPTION
		"The port number of this port."
	::= { ol51nnMTPLPortEntry 2 }

ol51nnMTPLPortAdminState OBJECT-TYPE
	SYNTAX INTEGER {
		enabled(1),
		disabled(2),
		redundant-primary(3),
		redundant-backup(4),
		remote-diagnostics(8)
		}
	ACCESS read-write
	STATUS mandatory
	DESCRIPTION
                "The desired state of this port.  Setting this port to
                be redundant or for remote diagnostics with invalid settings
		of buddy slot and buddy port will return the genError error."
	::= { ol51nnMTPLPortEntry 3 }

ol51nnMTPLPortBuddySlot OBJECT-TYPE
	SYNTAX INTEGER
	ACCESS read-write
	STATUS mandatory
	DESCRIPTION
		"The slot index of the redundant port's buddy.  To set
		a port to be redundant, the buddy's slot and port must 
		be set to valid values.

		The buddy is automatically set to be redundant to this port.

		If the port is configured for remote diagnostics, then 
		this contains the slot index of the backup buddy port.
		To configure a port for remote diagnostics, the buddy's
		slot and port must be set to valid values."
	::= { ol51nnMTPLPortEntry 4 }

ol51nnMTPLPortBuddyPort  OBJECT-TYPE
	SYNTAX INTEGER
	ACCESS read-write
	STATUS mandatory
	DESCRIPTION
		"The port index of the redundant port's buddy.  To set
		a port to be redundant, the buddy's slot and port must 
		be set to valid values.

		The buddy is automatically set to be redundant to this port.

		If the port is configured for remote diagnostics, then 
		this contains the port index of the backup buddy port.
		To configure a port for remote diagnostics, the buddy's
		slot and port must be set to valid values."
	::= { ol51nnMTPLPortEntry 5 }

ol51nnMTPLPortDipAdminState OBJECT-TYPE
	SYNTAX INTEGER {
		enabled(1),
		disabled(2)
		}
	ACCESS read-only
	STATUS mandatory
	DESCRIPTION
		"The state of this port as indicated by the port's dip 
		switches."		
	::= { ol51nnMTPLPortEntry 6 }

ol51nnMTPLPortLinkInteg OBJECT-TYPE
	SYNTAX INTEGER {
		enabled(1),
		disabled(2)
		}
	ACCESS read-write
	STATUS mandatory
	DESCRIPTION
		"The current link integrity configuration for this port."
	::= { ol51nnMTPLPortEntry 7 }

ol51nnMTPLPortDipLinkInteg OBJECT-TYPE
	SYNTAX INTEGER {
		enabled(1),
		disabled(2)
		}
	ACCESS read-only
	STATUS mandatory
	DESCRIPTION
		"The link integrity configuration as indicated by this
		module's dip switches."
	::= { ol51nnMTPLPortEntry 8 }

ol51nnMTPLPortSquelch OBJECT-TYPE
	SYNTAX INTEGER {
		normal(1), -- high squelch
		low(2)
		}
	ACCESS read-write
	STATUS mandatory
	DESCRIPTION
		"The current squelch configuration for this port.  See
		the module's user's guide for more information."
	::= { ol51nnMTPLPortEntry 9 }

ol51nnMTPLPortJabber OBJECT-TYPE
	SYNTAX INTEGER {
		enabled(1),
		disabled(2)
		}
	ACCESS read-write
	STATUS mandatory
	DESCRIPTION
		"The current receive jabber configuration for this port."
	::= { ol51nnMTPLPortEntry 10 }

ol51nnMTPLPortDipJabber OBJECT-TYPE
	SYNTAX INTEGER {
		enabled(1),
		disabled(2)
		}
	ACCESS read-only
	STATUS mandatory
	DESCRIPTION
		"The receive jabber configuration as indicated by this
		module's dip switches."
	::= { ol51nnMTPLPortEntry 11 }


-- 
-- ONline Ethernet 10BASE-T Per-Port Module
--

ol51nnMTPPLModTable OBJECT-TYPE
 	SYNTAX SEQUENCE OF Ol51nnMTPPLModEntry
 	ACCESS not-accessible
	STATUS mandatory
	DESCRIPTION
		"A list of module-specific information about a specific
		51nnM-TPPL module in the concentrator."
	::= { ol51nnMTPPL 1 }

ol51nnMTPPLModEntry OBJECT-TYPE
	SYNTAX Ol51nnMTPPLModEntry 
	ACCESS not-accessible
	STATUS mandatory
	DESCRIPTION
		"A list of module-specific information about a specific
		51nnM-TPPL module in the concentrator."
	INDEX { ol51nnMTPPLModSlotIndex }
	::= { ol51nnMTPPLModTable 1 }

Ol51nnMTPPLModEntry ::=
	SEQUENCE {
		ol51nnMTPPLModSlotIndex
			INTEGER
		}

ol51nnMTPPLModSlotIndex OBJECT-TYPE
	SYNTAX INTEGER
	ACCESS read-only
	STATUS mandatory
	DESCRIPTION
		"The slot number of this module."
	::= { ol51nnMTPPLModEntry 1 }

ol51nnMTPPLPortTable			 OBJECT-TYPE
	SYNTAX SEQUENCE OF Ol51nnMTPPLPortEntry
	ACCESS not-accessible
	STATUS mandatory
	DESCRIPTION
		"A table of port-specific information for each port of
		this module type."
	::= { ol51nnMTPPL 2 }

ol51nnMTPPLPortEntry OBJECT-TYPE
	SYNTAX Ol51nnMTPPLPortEntry 
	ACCESS not-accessible
	STATUS mandatory
	DESCRIPTION
		"A list of module-specific information about a specific
		51nnM-TPPL port in the concentrator."
	INDEX { ol51nnMTPPLPortSlotIndex, ol51nnMTPPLPortIndex }
	::= { ol51nnMTPPLPortTable 1 }

Ol51nnMTPPLPortEntry ::=
	SEQUENCE {
		ol51nnMTPPLPortSlotIndex
			INTEGER,			
		ol51nnMTPPLPortIndex
			INTEGER,
		ol51nnMTPPLPortAdminState
			INTEGER,
		ol51nnMTPPLPortBuddySlot
			INTEGER,
		ol51nnMTPPLPortBuddyPort
			INTEGER,
		ol51nnMTPPLPortDipAdminState
			INTEGER,
		ol51nnMTPPLPortDipNetwork
			INTEGER,
		ol51nnMTPPLPortLinkInteg
			INTEGER,
		ol51nnMTPPLPortDipLinkInteg
			INTEGER,
		ol51nnMTPPLPortSquelch
			INTEGER,
		ol51nnMTPPLPortJabber
			INTEGER,
		ol51nnMTPPLPortDipJabber
			INTEGER
		}

ol51nnMTPPLPortSlotIndex OBJECT-TYPE
	SYNTAX INTEGER
	ACCESS read-only
	STATUS mandatory
	DESCRIPTION
		"The slot number of this port's module."
	::= { ol51nnMTPPLPortEntry 1 }


ol51nnMTPPLPortIndex OBJECT-TYPE
	SYNTAX INTEGER
	ACCESS read-only
	STATUS mandatory
	DESCRIPTION
		"The port number of this port."
	::= { ol51nnMTPPLPortEntry 2 }

ol51nnMTPPLPortAdminState OBJECT-TYPE
	SYNTAX INTEGER {
		enabled(1),
		disabled(2),
		redundant-primary(3),
		redundant-backup(4),
		remote-diagnostics(8)
		}
	ACCESS read-write
	STATUS mandatory
	DESCRIPTION
                "The desired state of this port.  Setting this port to
                be redundant or for remote diagnostics with invalid settings
		of buddy slot and buddy port will return the genError error."
	::= { ol51nnMTPPLPortEntry 3 }

ol51nnMTPPLPortBuddySlot OBJECT-TYPE
	SYNTAX INTEGER
	ACCESS read-write
	STATUS mandatory
	DESCRIPTION
		"The slot index of the redundant port's buddy.  To set
		a port to be redundant, the buddy's slot and port must 
		be set to valid values.

		The buddy is automatically set to be redundant to this port.

		If the port is configured for remote diagnostics, then 
		this contains the slot index of the backup buddy port.
		To configure a port for remote diagnostics, the buddy's
		slot and port must be set to valid values."

	::= { ol51nnMTPPLPortEntry 4 }

ol51nnMTPPLPortBuddyPort  OBJECT-TYPE
	SYNTAX INTEGER
	ACCESS read-write
	STATUS mandatory
	DESCRIPTION
		"The port index of the redundant port's buddy.  To set
		a port to be redundant, the buddy's slot and port must 
		be set to valid values.

		The buddy is automatically set to be redundant to this port.

		If the port is configured for remote diagnostics, then 
		this contains the port index of the backup buddy port.
		To configure a port for remote diagnostics, the buddy's
		slot and port must be set to valid values."
	::= { ol51nnMTPPLPortEntry 5 }

ol51nnMTPPLPortDipAdminState OBJECT-TYPE
	SYNTAX INTEGER {
		enabled(1),
		disabled(2)
		}
	ACCESS read-only
	STATUS mandatory
	DESCRIPTION
		"The state of this port as indicated by the port's dip 
		switches."		
	::= { ol51nnMTPPLPortEntry 6 }

ol51nnMTPPLPortDipNetwork OBJECT-TYPE
	SYNTAX INTEGER {
		isolated(2),
		ethernet-1(6),
		ethernet-2(7),
		ethernet-3(8)
		}
	ACCESS read-only
	STATUS mandatory
	DESCRIPTION
		"The network indicated by the port's dip switches."
	::= { ol51nnMTPPLPortEntry 7 }	

ol51nnMTPPLPortLinkInteg OBJECT-TYPE
	SYNTAX INTEGER {
		enabled(1),
		disabled(2)
		}
	ACCESS read-write
	STATUS mandatory
	DESCRIPTION
		"The current link integrity configuration for this port."
	::= { ol51nnMTPPLPortEntry 8 }

ol51nnMTPPLPortDipLinkInteg OBJECT-TYPE
	SYNTAX INTEGER {
		enabled(1),
		disabled(2)
		}
	ACCESS read-only
	STATUS mandatory
	DESCRIPTION
		"The link integrity configuration as indicated by this
		module's dip switches."
	::= { ol51nnMTPPLPortEntry 9 }

ol51nnMTPPLPortSquelch OBJECT-TYPE
	SYNTAX INTEGER {
		normal(1), -- high squelch
		low(2)
		}
	ACCESS read-write
	STATUS mandatory
	DESCRIPTION
		"The current squelch configuration for this port.  See
		the module's user's guide for more information."
	::= { ol51nnMTPPLPortEntry 10 }

ol51nnMTPPLPortJabber OBJECT-TYPE
	SYNTAX INTEGER {
		enabled(1),
		disabled(2)
		}
	ACCESS read-write
	STATUS mandatory
	DESCRIPTION
		"The current receive jabber configuration for this port."
	::= { ol51nnMTPPLPortEntry 11 }

ol51nnMTPPLPortDipJabber OBJECT-TYPE
	SYNTAX INTEGER {
		enabled(1),
		disabled(2)
		}
	ACCESS read-only
	STATUS mandatory
	DESCRIPTION
		"The receive jabber configuration as indicated by this
		module's dip switches."
	::= { ol51nnMTPPLPortEntry 12 }

--
-- ONline Token Ring Media Module
--
ol52nnMTPModTable OBJECT-TYPE
	SYNTAX SEQUENCE OF Ol52nnMTPModEntry
	ACCESS not-accessible
	STATUS mandatory
	DESCRIPTION
		"A list of module-specific information about a specific
		52nnM-TP module in the concentrator."
	::= { ol52nnMTP 1 }

ol52nnMTPModEntry OBJECT-TYPE
	SYNTAX Ol52nnMTPModEntry
	ACCESS not-accessible
	STATUS mandatory
	DESCRIPTION
		"A description of the 52nnM-TP module attributes."
	INDEX { ol52nnMTPModSlotIndex }
	::= { ol52nnMTPModTable 1 }

Ol52nnMTPModEntry ::= 
	SEQUENCE {
		ol52nnMTPModSlotIndex
			INTEGER,
		ol52nnMTPModRingSpeed
			INTEGER,
		ol52nnMTPModDipRingSpeed
			INTEGER,
		ol52nnMTPModCableImp
			INTEGER,
		ol52nnMTPModDipCableImp
			INTEGER
		}

ol52nnMTPModSlotIndex OBJECT-TYPE
	SYNTAX INTEGER
	ACCESS read-only
	STATUS mandatory
	DESCRIPTION	
		"A unique value that identifies a particular module.  Its
		value ranges between 1 and olModSlotNumber.  The module
		identified by a particular value of this index is the same
		module as indentified by the same value of
		olModSlotIndex."
	::= { ol52nnMTPModEntry 1 }

ol52nnMTPModRingSpeed OBJECT-TYPE
	SYNTAX INTEGER {
		fourMegabit(1),
		sixteenMegabit(2)
		}
	ACCESS read-write
	STATUS mandatory
	DESCRIPTION	
		"The ring's bandwidth."
	::= { ol52nnMTPModEntry 2 }

ol52nnMTPModDipRingSpeed OBJECT-TYPE
	SYNTAX INTEGER {
		fourMegabit(1),
		sixteenMegabit(2)
		}
	ACCESS read-only
	STATUS mandatory
	DESCRIPTION	
		"The dip switch setting for the ring's bandwidth."
	::= { ol52nnMTPModEntry 3 }

ol52nnMTPModCableImp OBJECT-TYPE
	SYNTAX INTEGER {
		ohm100(1),
		ohm150(2)
		}
	ACCESS read-write
	STATUS mandatory
	DESCRIPTION
		"The setting of this module's port impedance matching, with
		100 ohm	corresponding to unshielded twisted pair cabling and
		150 ohm	corresponding to shielded twisted pair cabling.
		This setting is valid for all ports on this module."
	::= { ol52nnMTPModEntry 4 }

ol52nnMTPModDipCableImp OBJECT-TYPE
	SYNTAX INTEGER {
		ohm100(1),
		ohm150(2)
		}
	ACCESS read-only
	STATUS mandatory
	DESCRIPTION
		"The dip switch setting for the module's port impedance
		matching."
	::= { ol52nnMTPModEntry 5 }

ol52nnMTPPortTable OBJECT-TYPE
	SYNTAX SEQUENCE OF Ol52nnMTPPortEntry
	ACCESS not-accessible
	STATUS mandatory
	DESCRIPTION
		"A table of port-specific information for each port of
		this module type."
	::= { ol52nnMTP 2 }

ol52nnMTPPortEntry OBJECT-TYPE
	SYNTAX Ol52nnMTPPortEntry
	ACCESS not-accessible
	STATUS mandatory
	DESCRIPTION
		"A description of 52nnM-TP port attributes."		
	INDEX { ol52nnMTPPortSlotIndex, ol52nnMTPPortIndex }
	::= { ol52nnMTPPortTable 1 }

Ol52nnMTPPortEntry ::= 
	SEQUENCE {
		ol52nnMTPPortSlotIndex	
			INTEGER,
		ol52nnMTPPortIndex
			INTEGER,	
		ol52nnMTPPortDipAdminState
			INTEGER,
		ol52nnMTPPortStationType
			INTEGER
		}

ol52nnMTPPortSlotIndex OBJECT-TYPE
	SYNTAX INTEGER
	ACCESS read-only
	STATUS mandatory
	DESCRIPTION
		"The slot number of this port's module."
	::= { ol52nnMTPPortEntry 1 }


ol52nnMTPPortIndex OBJECT-TYPE
	SYNTAX INTEGER
	ACCESS read-only
	STATUS mandatory
	DESCRIPTION
		"The port number of this port."
	::= { ol52nnMTPPortEntry 2 }

ol52nnMTPPortDipAdminState OBJECT-TYPE
	SYNTAX INTEGER {
		enabled(1),
		disabled(2)
		}
	ACCESS read-only
	STATUS mandatory
	DESCRIPTION
		"The state of this port as indicated by the port's dip 
		switches."		
	::= { ol52nnMTPPortEntry 3 }

ol52nnMTPPortStationType OBJECT-TYPE
	SYNTAX INTEGER {
		mac-present(1),
		mac-not-present(2)
		}
	ACCESS read-write
	STATUS mandatory
	DESCRIPTION
		"Determines whether the station connected to this port
		has a MAC address."
	::= { ol52nnMTPPortEntry 4 }

ol52nnMTPTrunkTable OBJECT-TYPE
	SYNTAX SEQUENCE OF Ol52nnMTPTrunkEntry
	ACCESS not-accessible
	STATUS mandatory
	DESCRIPTION
		"A list of trunk-specific information about each trunk 
		for this module type."
	::= { ol52nnMTP 3 }

ol52nnMTPTrunkEntry OBJECT-TYPE
	SYNTAX Ol52nnMTPTrunkEntry
	ACCESS not-accessible
	STATUS mandatory
	DESCRIPTION
		"A description of 52nnM-TP trunk attributes."		
	INDEX { ol52nnMTPTrunkSlotIndex, ol52nnMTPTrunkIndex }
	::= { ol52nnMTPTrunkTable 1 }

Ol52nnMTPTrunkEntry ::= 
	SEQUENCE {
		ol52nnMTPTrunkSlotIndex	
			INTEGER,
		ol52nnMTPTrunkIndex
			INTEGER,	
		ol52nnMTPTrunkDipAdminState
			INTEGER
		}

ol52nnMTPTrunkSlotIndex OBJECT-TYPE
	SYNTAX INTEGER
	ACCESS read-only
	STATUS mandatory
	DESCRIPTION
		"A unique value that identifies a particular module.  Its
		value ranges between 1 and olModSlotNumber.  The module
		identified by a particular value of this index is the same
		module as indentified by the same value of 
		olTrunkSlotIndex."
	::= { ol52nnMTPTrunkEntry 1 }


ol52nnMTPTrunkIndex OBJECT-TYPE
	SYNTAX INTEGER
	ACCESS read-only
	STATUS mandatory
	DESCRIPTION
		"The trunk number for this trunk."
	::= { ol52nnMTPTrunkEntry 2 }

ol52nnMTPTrunkDipAdminState OBJECT-TYPE
	SYNTAX INTEGER {
		enabled(1),
		disabled(2)
		}
	ACCESS read-only
	STATUS mandatory
	DESCRIPTION
		"The state of this trunk as indicated by the trunk's dip 
		switches."		
	::= { ol52nnMTPTrunkEntry 3 }

--
-- ONline Token Fiberoptic Repeater Module
--
ol52nnMFRModTable OBJECT-TYPE
	SYNTAX SEQUENCE OF Ol52nnMFRModEntry
	ACCESS not-accessible
	STATUS mandatory
	DESCRIPTION
		"A list of module-specific information about a specific
		52nnM-FR module in the concentrator."
	::= { ol52nnMFR 1 }

ol52nnMFRModEntry OBJECT-TYPE
	SYNTAX Ol52nnMFRModEntry
	ACCESS not-accessible
	STATUS mandatory
	DESCRIPTION
		"A description of the 52nnMFR module attributes."
	INDEX { ol52nnMFRModSlotIndex }
	::= { ol52nnMFRModTable 1 }

Ol52nnMFRModEntry ::= 
	SEQUENCE {
		ol52nnMFRModSlotIndex
			INTEGER,
		ol52nnMFRModRingSpeed
			INTEGER,
		ol52nnMFRModDipRingSpeed
			INTEGER
		}

ol52nnMFRModSlotIndex OBJECT-TYPE
	SYNTAX INTEGER
	ACCESS read-only
	STATUS mandatory
	DESCRIPTION	
		"The slot number of this module."
	::= { ol52nnMFRModEntry 1 }

ol52nnMFRModRingSpeed OBJECT-TYPE
	SYNTAX INTEGER {
		fourMegabit(1),
		sixteenMegabit(2)
		}
	ACCESS read-write
	STATUS mandatory
	DESCRIPTION	
		"The ring's bandwidth."
	::= { ol52nnMFRModEntry 2 }

ol52nnMFRModDipRingSpeed OBJECT-TYPE
	SYNTAX INTEGER {
		fourMegabit(1),
		sixteenMegabit(2)
		}
	ACCESS read-only
	STATUS mandatory
	DESCRIPTION	
		"The dip switch setting for the ring's bandwidth."
	::= { ol52nnMFRModEntry 3 }

ol52nnMFRPortTable OBJECT-TYPE
	SYNTAX SEQUENCE OF Ol52nnMFRPortEntry
	ACCESS not-accessible
	STATUS mandatory
	DESCRIPTION
		"A table of port-specific information for each port of
		this module type."
	::= { ol52nnMFR 2 }

ol52nnMFRPortEntry OBJECT-TYPE
	SYNTAX Ol52nnMFRPortEntry
	ACCESS not-accessible
	STATUS mandatory
	DESCRIPTION
		"A description of 52nnMFR port attributes."		
	INDEX { ol52nnMFRPortSlotIndex, ol52nnMFRPortIndex }
	::= { ol52nnMFRPortTable 1 }

Ol52nnMFRPortEntry ::= 
	SEQUENCE {
		ol52nnMFRPortSlotIndex	
			INTEGER,
		ol52nnMFRPortIndex
			INTEGER,	
		ol52nnMFRPortDipAdminState
			INTEGER,
		ol52nnMFRPortCableImp
			INTEGER,
		ol52nnMFRPortStationType
			INTEGER
		}

ol52nnMFRPortSlotIndex OBJECT-TYPE
	SYNTAX INTEGER
	ACCESS read-only
	STATUS mandatory
	DESCRIPTION
		"The slot number of this port's module."
	::= { ol52nnMFRPortEntry 1 }


ol52nnMFRPortIndex OBJECT-TYPE
	SYNTAX INTEGER
	ACCESS read-only
	STATUS mandatory
	DESCRIPTION
		"The port number of this port."
	::= { ol52nnMFRPortEntry 2 }

ol52nnMFRPortDipAdminState OBJECT-TYPE
	SYNTAX INTEGER {
		enabled(1),
		disabled(2)
		}
	ACCESS read-only
	STATUS mandatory
	DESCRIPTION
		"The state of this port as indicated by the port's dip 
		switches."		
	::= { ol52nnMFRPortEntry 3 }

ol52nnMFRPortCableImp OBJECT-TYPE
	SYNTAX INTEGER {
		ohm100(1),
		ohm150(2)
		}
	ACCESS read-only
	STATUS mandatory
	DESCRIPTION
		"The setting of this port's impedance matching, with 100 ohm
		corresponding to unshielded twisted pair cabling and 150 ohm
		corresponding to shielded twisted pair cabling."
	::= { ol52nnMFRPortEntry 4 }
		
ol52nnMFRPortStationType OBJECT-TYPE
	SYNTAX INTEGER {
		mac-present(1),
		mac-not-present(2)
		}
	ACCESS read-write
	STATUS mandatory
	DESCRIPTION
		"Determines whether the station connected to this port
		has a MAC address."
	::= { ol52nnMFRPortEntry 5 }

ol52nnMFRTrunkTable OBJECT-TYPE
	SYNTAX SEQUENCE OF Ol52nnMFRTrunkEntry
	ACCESS not-accessible
	STATUS mandatory
	DESCRIPTION
		"A list of trunk-specific information about each trunk 
		for this module type."
	::= { ol52nnMFR 3 }

ol52nnMFRTrunkEntry OBJECT-TYPE
	SYNTAX Ol52nnMFRTrunkEntry
	ACCESS not-accessible
	STATUS mandatory
	DESCRIPTION
		"A description of 52nnMFR trunk attributes."		
	INDEX { ol52nnMFRTrunkSlotIndex, ol52nnMFRTrunkIndex }
	::= { ol52nnMFRTrunkTable 1 }

Ol52nnMFRTrunkEntry ::= 
	SEQUENCE {
		ol52nnMFRTrunkSlotIndex	
			INTEGER,
		ol52nnMFRTrunkIndex
			INTEGER,	
		ol52nnMFRTrunkDipAdminState
			INTEGER,
		ol52nnMFRTrunkCableMon
			INTEGER,
		ol52nnMFRTrunkDipCableMon
			INTEGER,
		ol52nnMFRTrunkCompMode
			INTEGER,
		ol52nnMFRTrunkDipCompMode
			INTEGER,
		ol52nnMFRTrunkNetMapState
			INTEGER,
	        ol52nnMFRTrunkExtBcnRecovery
			INTEGER
		}

ol52nnMFRTrunkSlotIndex OBJECT-TYPE
	SYNTAX INTEGER
	ACCESS read-only
	STATUS mandatory
	DESCRIPTION
		"A unique value that identifies a particular module.  Its
		value ranges between 1 and olModSlotNumber.  The module
		identified by a particular value of this index is the same
		module as indentified by the same value of 
		olTrunkSlotIndex."
	::= { ol52nnMFRTrunkEntry 1 }


ol52nnMFRTrunkIndex OBJECT-TYPE
	SYNTAX INTEGER
	ACCESS read-only
	STATUS mandatory
	DESCRIPTION
		"The trunk number of this trunk."
	::= { ol52nnMFRTrunkEntry 2 }

ol52nnMFRTrunkDipAdminState OBJECT-TYPE
	SYNTAX INTEGER {
		enabled(1),
		disabled(2)
		}
	ACCESS read-only
	STATUS mandatory
	DESCRIPTION
		"The state of this trunk as indicated by the trunk's dip 
		switches."		
	::= { ol52nnMFRTrunkEntry 3 }

ol52nnMFRTrunkCableMon OBJECT-TYPE
	SYNTAX INTEGER {
		enabled(1),
		disabled(2),
		notApplicable(3)	
	}
	ACCESS read-write
	STATUS mandatory
	DESCRIPTION
		"The cable monitor configuration for this trunk. This
		does not apply to fiber trunks."
	::= { ol52nnMFRTrunkEntry 4 }

ol52nnMFRTrunkDipCableMon OBJECT-TYPE
	SYNTAX INTEGER {
		enabled(1),
		disabled(2),
		notApplicable(3)	
	}
	ACCESS read-only
	STATUS mandatory
	DESCRIPTION
		"The cable monitor configuration as indicated by this trunk's
		dip switches. This does not apply to fiber trunks."
	::= { ol52nnMFRTrunkEntry 5 }


ol52nnMFRTrunkCompMode OBJECT-TYPE
	SYNTAX INTEGER {
		enabled(1),
		disabled(2),
		notApplicable(3)	
	}
	ACCESS read-write
	STATUS mandatory
	DESCRIPTION
		"The compatibility mode for this trunk. This
		only applies to fiber trunks."
	::= { ol52nnMFRTrunkEntry 6 }

ol52nnMFRTrunkDipCompMode OBJECT-TYPE
	SYNTAX INTEGER {
		enabled(1),
		disabled(2),
		notApplicable(3)	
	}
	ACCESS read-only
	STATUS mandatory
	DESCRIPTION
		"The compatibility mode as indicated by this trunk's
		dip switches. This only applies to fiber trunks."
	::= { ol52nnMFRTrunkEntry 7 }


ol52nnMFRTrunkNetMapState OBJECT-TYPE
	SYNTAX INTEGER {
		notApplicable(1),
		internal(2),
		external(3)
	}
	ACCESS read-write
	STATUS mandatory
	DESCRIPTION
		"The map state of the copper ring-in trunk.  This
		should be set to external for ring-in trunks which
		connect to external hubs.  The mapping logic will not
		operate on trunks which are set to external.  This 
		prevents incorrect mapping which can occur when a 
		module in one hub detects the mapping signal from
		another hub. This attribute only applies to copper 
		ring-in trunks."
	::= { ol52nnMFRTrunkEntry 8 }


ol52nnMFRTrunkExtBcnRecovery OBJECT-TYPE
	SYNTAX INTEGER {
		exists(1),
		nonExists(2),
		notApplicable(3)
	}
	ACCESS read-write
	STATUS mandatory
	DESCRIPTION
		"Indicates whether the trunk is connected to a 
		segment that will perform beacon recovery.  This
		should be set to exists(1) for trunks which connect 
		to hubs which perform beacon recovery.  This attribute 
		is used to determine the fault domain when resolving a 
		beaconing condition.

		The beacon recovery process will resolve beaconing on 
		trunks with this attribute set to nonExists(2) before 
		trunks with the attribute set to exists(1) are resolved.
		For backplane trunks, setting to a value other than 
		notApplicable will return invalidData error.  The 
		default value is nonExists(2)."
	::= { ol52nnMFRTrunkEntry 9 }


--
-- ONline Ethernet Terminal Server Module
--


ol51nnMTSModTable OBJECT-TYPE
        SYNTAX SEQUENCE OF Ol51nnMTSModEntry
        ACCESS not-accessible
        STATUS mandatory
        DESCRIPTION
                "A table of module-specific information for each
                51nnM-TS module in the concentrator."
        ::= { ol51nnMTS 1 }

ol51nnMTSModEntry OBJECT-TYPE
       SYNTAX Ol51nnMTSModEntry
       ACCESS not-accessible
       STATUS mandatory
       DESCRIPTION
               "A list of module information for each 51nnMTS module
               in the concentrator."
       INDEX { ol51nnMTSModSlotIndex }
       ::= { ol51nnMTSModTable 1 }

Ol51nnMTSModEntry ::=
       SEQUENCE {
               ol51nnMTSModSlotIndex
                       INTEGER,
               ol51nnMTSModProtocols
                       DisplayString,
               ol51nnMTSModIpAddress
                       IpAddress,
               ol51nnMTSModTCPPort
                       INTEGER,
               ol51nnMTSModStationAddr
                       OCTET STRING,
               ol51nnMTSModDipNetwork
                       INTEGER,
               ol51nnMTSModCPURev
                       DisplayString
               }

ol51nnMTSModSlotIndex OBJECT-TYPE
       SYNTAX INTEGER
       ACCESS read-only
       STATUS mandatory
       DESCRIPTION
               "The slot number of this module."
       ::= { ol51nnMTSModEntry 1 }

ol51nnMTSModProtocols OBJECT-TYPE
        SYNTAX DisplayString
        ACCESS read-only
        STATUS mandatory
        DESCRIPTION
		"A textual description of the protocols supported by 
		this module"
        ::= { ol51nnMTSModEntry 2 }

ol51nnMTSModIpAddress OBJECT-TYPE
       SYNTAX IpAddress
       ACCESS read-only
       STATUS mandatory
       DESCRIPTION
               "The IP Address of the terminal terver."
       ::= { ol51nnMTSModEntry 3 }

ol51nnMTSModTCPPort OBJECT-TYPE
       SYNTAX INTEGER
       ACCESS read-only
       STATUS mandatory
       DESCRIPTION
               "The TCP port number of the the terminal server's remote
                console port."
       ::= { ol51nnMTSModEntry 4 }

ol51nnMTSModStationAddr OBJECT-TYPE
       SYNTAX OCTET STRING (SIZE(6))
       ACCESS read-only
       STATUS mandatory
       DESCRIPTION
               "A 6 octet address that uniquely identifies this module.
               The station address is the mac address of the terminal server."
       ::= { ol51nnMTSModEntry 5 }

ol51nnMTSModDipNetwork OBJECT-TYPE
       SYNTAX INTEGER {
               isolated(2),
               ethernet-1(6),
               ethernet-2(7),
               ethernet-3(8)
               }
       ACCESS read-only
       STATUS mandatory
       DESCRIPTION
               "The network indicated by the module's dip switches."
       ::= { ol51nnMTSModEntry 6 }

ol51nnMTSModCPURev OBJECT-TYPE
       SYNTAX DisplayString (SIZE(1..10))
       ACCESS read-only
       STATUS mandatory
       DESCRIPTION
               "The terminal server's CPU revision."
       ::= { ol51nnMTSModEntry 7 }


ol51nnMTSPortTable OBJECT-TYPE
       SYNTAX SEQUENCE OF Ol51nnMTSPortEntry
       ACCESS not-accessible
       STATUS mandatory
       DESCRIPTION
               "A table of information that contains port-specific
               information for each port on each 51nnMTS module."
       ::= { ol51nnMTS 2 }

ol51nnMTSPortEntry OBJECT-TYPE
       SYNTAX Ol51nnMTSPortEntry
       ACCESS not-accessible
       STATUS mandatory
       DESCRIPTION
               "A list of information about a specific port on a
               51nnMTS module."
       INDEX { ol51nnMTSPortSlotIndex, ol51nnMTSPortIndex }
       ::= { ol51nnMTSPortTable 1 }

Ol51nnMTSPortEntry ::=
       SEQUENCE {
               ol51nnMTSPortSlotIndex
                       INTEGER,
               ol51nnMTSPortIndex
                       INTEGER,
               ol51nnMTSPortAdminState
                       INTEGER,
               ol51nnMTSPortOperState
                       INTEGER
               }

       ol51nnMTSPortSlotIndex OBJECT-TYPE
       SYNTAX INTEGER
       ACCESS read-only
       STATUS mandatory
       DESCRIPTION
		"The slot number for this port."
       ::= { ol51nnMTSPortEntry 1 }

ol51nnMTSPortIndex OBJECT-TYPE
       SYNTAX INTEGER
       ACCESS read-only
       STATUS mandatory
       DESCRIPTION
		"The port number of this port."
       ::= { ol51nnMTSPortEntry 2 }

ol51nnMTSPortAdminState OBJECT-TYPE
       SYNTAX INTEGER {
               enabled(1),
               disabled(2),
               local(6),
               remote(7)
               }
       ACCESS read-write
       STATUS mandatory
       DESCRIPTION
               "The administrative state of this port."
       ::= { ol51nnMTSPortEntry 3 }

ol51nnMTSPortOperState OBJECT-TYPE
       SYNTAX INTEGER {
               idle(1),
               local(2),
               connected(3)
               }
       ACCESS read-only
       STATUS mandatory
       DESCRIPTION
               "The operational mode of this port."
       ::= { ol51nnMTSPortEntry 4 }


--
-- ONline Ethernet FOIRL MOdule
--


ol51nnMFLModTable OBJECT-TYPE
        SYNTAX SEQUENCE OF Ol51nnMFLModEntry
        ACCESS not-accessible
        STATUS mandatory
        DESCRIPTION
                "A table of module-specific information for each
                51nnM-FL module in the concentrator."
        ::= { ol51nnMFL 1 }

ol51nnMFLModEntry OBJECT-TYPE
        SYNTAX Ol51nnMFLModEntry
        ACCESS not-accessible
        STATUS mandatory
        DESCRIPTION
                "A list of module-specific information associated
                with a particular 51nnM-FL module in the concentrator."
        INDEX { ol51nnMFLModSlotIndex }
        ::= { ol51nnMFLModTable 1 }
 
Ol51nnMFLModEntry ::=
        SEQUENCE {
                ol51nnMFLModSlotIndex
                        INTEGER,
                ol51nnMFLModDipNetwork
                        INTEGER
                }
 
ol51nnMFLModSlotIndex OBJECT-TYPE
        SYNTAX INTEGER
        ACCESS read-only
        STATUS mandatory
        DESCRIPTION
		"The slot number of this module."
        ::= { ol51nnMFLModEntry 1 }
 
ol51nnMFLModDipNetwork OBJECT-TYPE
        SYNTAX INTEGER {
                isolated(2),
                ethernet-1(6),
                ethernet-2(7),
                ethernet-3(8)
                }
        ACCESS read-only
        STATUS mandatory
        DESCRIPTION
                "The network indicated by the module's dip switches."
        ::= { ol51nnMFLModEntry 2 }
 
ol51nnMFLPortTable OBJECT-TYPE
        SYNTAX SEQUENCE OF Ol51nnMFLPortEntry
        ACCESS not-accessible
        STATUS mandatory
        DESCRIPTION
                "A table of port-specific information for each port
                of each 51nnMFL module."
        ::= { ol51nnMFL 2 }
 
ol51nnMFLPortEntry OBJECT-TYPE
        SYNTAX Ol51nnMFLPortEntry
        ACCESS not-accessible
        STATUS mandatory
        DESCRIPTION
                "A list of information about a specific port on a
                51nnMFL module."
        INDEX { ol51nnMFLPortSlotIndex, ol51nnMFLPortIndex }
        ::= { ol51nnMFLPortTable 1 }
 
Ol51nnMFLPortEntry ::=
        SEQUENCE {
                ol51nnMFLPortSlotIndex
                        INTEGER,
                ol51nnMFLPortIndex
                        INTEGER,
                ol51nnMFLPortAdminState
                        INTEGER,
                ol51nnMFLPortBuddySlot
                        INTEGER,
                ol51nnMFLPortBuddyPort
                        INTEGER,
                ol51nnMFLPortDipAdminState
                        INTEGER
                }

        ol51nnMFLPortSlotIndex OBJECT-TYPE
        SYNTAX INTEGER
        ACCESS read-only
        STATUS mandatory
        DESCRIPTION
                "A unique value that identifies a particular module.  Its
                value ranges between 1 and olModSlotNumber.  The module
                identified by a particular value of this index is the same
                module as indentified by the same value of
                olPortSlotIndex."
        ::= { ol51nnMFLPortEntry 1 }
 
 
ol51nnMFLPortIndex OBJECT-TYPE
        SYNTAX INTEGER
        ACCESS read-only
        STATUS mandatory
        DESCRIPTION
		"The port number of this port."
        ::= { ol51nnMFLPortEntry 2 }
 
 
ol51nnMFLPortAdminState OBJECT-TYPE
        SYNTAX INTEGER {
                enabled(1),
                disabled(2),
                redundant-primary(3),
                redundant-backup(4),
		redundant-rfs(5)
                }
        ACCESS read-write
        STATUS mandatory
        DESCRIPTION
                "The desired state of this port.  Setting this port to
                be redundant with invalid settings of buddy slot and
                buddy port will return invalidData error. Remote
		Failure Signaling (RFS), is set on connected module 
		port to permit transmit error detection on local port.
		Port must be set to be RFS when connected port is set to
		be redundant"
        ::= { ol51nnMFLPortEntry 3 }
 
ol51nnMFLPortBuddySlot OBJECT-TYPE
        SYNTAX INTEGER
        ACCESS read-write
        STATUS mandatory
        DESCRIPTION
                "The slot index of the redundant port's buddy.   "
        ::= { ol51nnMFLPortEntry 4 }
 

ol51nnMFLPortBuddyPort  OBJECT-TYPE
        SYNTAX INTEGER
        ACCESS read-write
        STATUS mandatory
        DESCRIPTION
                "The port index of the redundant port's buddy."
        ::= { ol51nnMFLPortEntry 5 }
 
 
ol51nnMFLPortDipAdminState OBJECT-TYPE
        SYNTAX INTEGER {
                enabled(1),
                disabled(2),
                redundant-primary(3),
                redundant-backup(4),
		redundant-rfs(5)
                }
        ACCESS read-only
        STATUS mandatory
        DESCRIPTION
                "The state of this port as indicated by the port's dip
                switches."
        ::= { ol51nnMFLPortEntry 6 }
 


--
-- ONline Redundant Controller Module
--

ol50nnMRCTLModTable OBJECT-TYPE
	SYNTAX SEQUENCE OF Ol50nnMRCTLModEntry
	ACCESS not-accessible
	STATUS mandatory
	DESCRIPTION
		"A table that contains information about each 50nnMRCTL
		in the concentrator.  "
	::= { ol50nnMRCTL 1 }

ol50nnMRCTLModEntry OBJECT-TYPE
	SYNTAX Ol50nnMRCTLModEntry
	ACCESS not-accessible
	STATUS mandatory
	DESCRIPTION
		"A list of information for each 50nnMRCTL module
		in the concentrator."
	INDEX { ol50nnMRCTLModSlotIndex }
	::= { ol50nnMRCTLModTable 1 }

Ol50nnMRCTLModEntry ::= 
	SEQUENCE {
		ol50nnMRCTLModSlotIndex
			INTEGER,
		ol50nnMRCTLModOperState
			INTEGER,
		ol50nnMRCTLModClockStatus
			INTEGER,
		ol50nnMRCTLModTempStatus
			INTEGER
		}

ol50nnMRCTLModSlotIndex OBJECT-TYPE
	SYNTAX INTEGER
	ACCESS read-only
	STATUS mandatory
	DESCRIPTION
		"The slot number for this module."
	::= { ol50nnMRCTLModEntry 1 }

ol50nnMRCTLModOperState OBJECT-TYPE
	SYNTAX INTEGER {
		active(1),
		standby(2)
		}
	ACCESS read-only
	STATUS mandatory
	DESCRIPTION
		"The operational state of the 50nnMRCTL module.  Specifically,
		this is an indicator of whether the 50nnMRCTL module is
		providing clock signals to the backplane.  An active 50nnMRCTL
		module provides clock signals to the backplane while a standby 
		50nnMRCTL module does not.  Note that only one 50nnMRCTL
		module will be active at any given time; all other 50nnMRCTL
		modules in the concentrator will be in standby mode."
	::= { ol50nnMRCTLModEntry 2 }

ol50nnMRCTLModClockStatus OBJECT-TYPE
	SYNTAX INTEGER {
		okay(1),
		faulty(2)
		}
	ACCESS read-only
	STATUS mandatory
	DESCRIPTION
		"The current status of the on-board clocks on this module."
	::= { ol50nnMRCTLModEntry 3 }

ol50nnMRCTLModTempStatus OBJECT-TYPE
	SYNTAX INTEGER {
		okay(1),
		extremeTemp(2)
		}
	ACCESS read-only
	STATUS mandatory
	DESCRIPTION
		"The temperature as detected by the probe on this module."
	::= { ol50nnMRCTLModEntry 4 }

-- 
-- ONline Ethernet 10BASE-F Module
--

ol51nnMFBModTable OBJECT-TYPE
	SYNTAX SEQUENCE OF Ol51nnMFBModEntry
	ACCESS not-accessible
	STATUS mandatory
	DESCRIPTION
		"A list of module-specific information associated
		with a particular 51nnM-FB module in the concentrator."
	::= { ol51nnMFB 1 }

ol51nnMFBModEntry OBJECT-TYPE
	SYNTAX Ol51nnMFBModEntry 
	ACCESS not-accessible
	STATUS mandatory
	DESCRIPTION
		"A list of module-specific information about a specific
		51nnM-FB module in the concentrator."
	INDEX { ol51nnMFBModSlotIndex }
	::= { ol51nnMFBModTable 1 }

Ol51nnMFBModEntry ::=
	SEQUENCE {
		ol51nnMFBModSlotIndex
			INTEGER,
		ol51nnMFBModDipNetwork
			INTEGER,
                ol51nnMFBModLLW
                        INTEGER,
                ol51nnMFBModDipLLW
                        INTEGER
		}

ol51nnMFBModSlotIndex OBJECT-TYPE
	SYNTAX INTEGER
	ACCESS read-only
	STATUS mandatory
	DESCRIPTION
		"The slot number of this module."
	::= { ol51nnMFBModEntry 1 }

ol51nnMFBModDipNetwork OBJECT-TYPE
	SYNTAX INTEGER {
		isolated(2),
		ethernet-1(6),
		ethernet-2(7),
		ethernet-3(8)
		}
	ACCESS read-only
	STATUS mandatory
	DESCRIPTION
		"The network indicated by the module's dip switches."
	::= { ol51nnMFBModEntry 2 }	

ol51nnMFBModLLW OBJECT-TYPE
        SYNTAX INTEGER {
                enabled(1),
                disabled(2)
                }
        ACCESS read-write
        STATUS mandatory
        DESCRIPTION
                "The current state of this module's low light warning
                configuration.  Enabling this feature causes the module to
                check for low light and to issue a warning if low light is
                present.  Disabling low light has the advantage of faster
                redundancy switchover in the event of a port error."
        ::= { ol51nnMFBModEntry 3 }
 
ol51nnMFBModDipLLW OBJECT-TYPE
        SYNTAX INTEGER {
                enabled(1),
                disabled(2)
                }
        ACCESS read-only
        STATUS mandatory
        DESCRIPTION
                "The low light warning configuration indicated by this module's
                dip switches."
        ::= { ol51nnMFBModEntry 4 }
 
ol51nnMFBPortTable OBJECT-TYPE
	SYNTAX SEQUENCE OF Ol51nnMFBPortEntry
	ACCESS not-accessible
	STATUS mandatory
	DESCRIPTION
		"A table of port-specific information for each port of
		this module type."
	::= { ol51nnMFB 2 }

ol51nnMFBPortEntry OBJECT-TYPE
	SYNTAX Ol51nnMFBPortEntry 
	ACCESS not-accessible
	STATUS mandatory
	DESCRIPTION
		"A list of module-specific information about a specific
		51nnM-FB port in the concentrator."
	INDEX { ol51nnMFBPortSlotIndex, ol51nnMFBPortIndex }
	::= { ol51nnMFBPortTable 1 }

Ol51nnMFBPortEntry ::=
	SEQUENCE {
		ol51nnMFBPortSlotIndex
			INTEGER,			
		ol51nnMFBPortIndex
			INTEGER,
		ol51nnMFBPortAdminState
			INTEGER,
		ol51nnMFBPortBuddySlot
			INTEGER,
		ol51nnMFBPortBuddyPort
			INTEGER,
		ol51nnMFBPortDipAdminState
			INTEGER
		}

ol51nnMFBPortSlotIndex OBJECT-TYPE
	SYNTAX INTEGER
	ACCESS read-only
	STATUS mandatory
	DESCRIPTION
		"The slot number of this port's module."
	::= { ol51nnMFBPortEntry 1 }


ol51nnMFBPortIndex OBJECT-TYPE
	SYNTAX INTEGER
	ACCESS read-only
	STATUS mandatory
	DESCRIPTION
		"The port number of this port."
	::= { ol51nnMFBPortEntry 2 }

ol51nnMFBPortAdminState OBJECT-TYPE
	SYNTAX INTEGER {
		enabled(1),
		disabled(2),
		redundant-primary(3),
		redundant-backup(4)
		}
	ACCESS read-write
	STATUS mandatory
	DESCRIPTION
		"The desired state of this port.  Setting this port to 
		be redundant with invalid settings of buddy slot and
		buddy port will return the genError error."
	::= { ol51nnMFBPortEntry 3 }

ol51nnMFBPortBuddySlot OBJECT-TYPE
	SYNTAX INTEGER
	ACCESS read-write
	STATUS mandatory
	DESCRIPTION
		"The slot index of the redundant port's buddy.  To set
		a port to be redundant, the buddy's slot and port must 
		be set to valid values.

		The buddy is automatically set to be redundant to this port."
	::= { ol51nnMFBPortEntry 4 }

ol51nnMFBPortBuddyPort  OBJECT-TYPE
	SYNTAX INTEGER
	ACCESS read-write
	STATUS mandatory
	DESCRIPTION
		"The port index of the redundant port's buddy.  To set
		a port to be redundant, the buddy's slot and port must 
		be set to valid values.

		The buddy is automatically set to be redundant to this port."
	::= { ol51nnMFBPortEntry 5 }

ol51nnMFBPortDipAdminState OBJECT-TYPE
	SYNTAX INTEGER {
		enabled(1),
		disabled(2)
		}
	ACCESS read-only
	STATUS mandatory
	DESCRIPTION
		"The state of this port as indicated by the port's dip 
		switches."		
	::= { ol51nnMFBPortEntry 6 }



--
-- FDDI media module with ANSI MIC connector
--

ol53nnMFBMICModTable OBJECT-TYPE
	SYNTAX SEQUENCE OF Ol53nnMFBMICModEntry
	ACCESS not-accessible
	STATUS mandatory
	DESCRIPTION
		"A list of module attributes that apply to this model.
		To access an ol53nnMFBMICModTable entry, the 
		ol53nnMFBMICModSlotIndex attribute is used."
	::= { ol53nnMFBMIC 1 }

ol53nnMFBMICModEntry OBJECT-TYPE
	SYNTAX Ol53nnMFBMICModEntry 
	ACCESS not-accessible
	STATUS mandatory
	DESCRIPTION
		"A list of module-specific information about a specific
		53nnM-FBMIC module in the concentrator."
	INDEX { ol53nnMFBMICModSlotIndex }
	::= { ol53nnMFBMICModTable 1 }

Ol53nnMFBMICModEntry ::=
	SEQUENCE {
		ol53nnMFBMICModSlotIndex
			INTEGER,
		ol53nnMFBMICModDownStreamModule
			INTEGER,
		ol53nnMFBMICModUpStreamModule
			INTEGER,
		ol53nnMFBMICModDownStreamOperPath
			INTEGER,
		ol53nnMFBMICModUpStreamOperPath
			INTEGER,
		ol53nnMFBMICModRingInfo
			OCTET STRING
		}

ol53nnMFBMICModSlotIndex OBJECT-TYPE
	SYNTAX INTEGER
	ACCESS read-only
	STATUS mandatory
	DESCRIPTION
		"A unique value that identifies a particular module.  Its
		value ranges between 1 and olModSlotNumber.  The module
		identified by a particular value of this index is the same
		module as indentified by the same value of olModSlotIndex."
	::= { ol53nnMFBMICModEntry 1 }

ol53nnMFBMICModDownStreamModule OBJECT-TYPE
	SYNTAX INTEGER (1..16)
	ACCESS read-only
	STATUS mandatory
	DESCRIPTION
                "Down stream slot (transmit to)"
	::= { ol53nnMFBMICModEntry 2 }

ol53nnMFBMICModUpStreamModule OBJECT-TYPE
	SYNTAX INTEGER (1..16)
	ACCESS read-only
	STATUS mandatory
	DESCRIPTION
                "Up stream slot (receve from)"
	::= { ol53nnMFBMICModEntry 3 }

ol53nnMFBMICModDownStreamOperPath OBJECT-TYPE
	SYNTAX INTEGER {
                isolated(2),
                fddi-path-1(24),
                fddi-path-2(25),
                fddi-path-3(26),
                fddi-path-4(27),
                fddi-path-5(28),
                fddi-path-6(29),
                fddi-path-7(30),
                fddi-path-8(31)
                }
	ACCESS read-only
	STATUS mandatory
	DESCRIPTION
                "Transmit DBA  (debug only)"
	::= { ol53nnMFBMICModEntry 4 }

ol53nnMFBMICModUpStreamOperPath OBJECT-TYPE
	SYNTAX INTEGER  {
                isolated(2),
                fddi-path-1(24),
                fddi-path-2(25),
                fddi-path-3(26),
                fddi-path-4(27),
                fddi-path-5(28),
                fddi-path-6(29),
                fddi-path-7(30),
                fddi-path-8(31)
                }
        ACCESS read-only
	STATUS mandatory
	DESCRIPTION
                "Receive DBA (debug only)"
	::= { ol53nnMFBMICModEntry 5 }

ol53nnMFBMICModRingInfo OBJECT-TYPE
	SYNTAX OCTET STRING (SIZE(1..8))
	ACCESS read-only
	STATUS mandatory
	DESCRIPTION
                "An array which is indexed by DBA number. Each element
                 contains the slot number (1..16) which is assigned to
                 transmit on this DBA. (debug only)"
	::= { ol53nnMFBMICModEntry 6 }


-- port table

ol53nnMFBMICPortTable OBJECT-TYPE
	SYNTAX SEQUENCE OF Ol53nnMFBMICPortEntry
	ACCESS not-accessible
	STATUS mandatory
	DESCRIPTION
		"A table of port-specific information for each port of
		this module type."
	::= { ol53nnMFBMIC 2 }

ol53nnMFBMICPortEntry OBJECT-TYPE
	SYNTAX Ol53nnMFBMICPortEntry 
	ACCESS not-accessible
	STATUS mandatory
	DESCRIPTION
		"A list of module-specific information about a specific
		53nnM-FBMIC port in the concentrator."
	INDEX { ol53nnMFBMICPortSlotIndex, ol53nnMFBMICPortIndex }
	::= { ol53nnMFBMICPortTable 1 }

Ol53nnMFBMICPortEntry ::=
	SEQUENCE {
		ol53nnMFBMICPortSlotIndex
			INTEGER,			
		ol53nnMFBMICPortIndex
			INTEGER,
		ol53nnMFBMICPortConfig
			INTEGER,
		ol53nnMFBMICPortPcmState
			INTEGER,
		ol53nnMFBMICPortConnectState
			INTEGER,
		ol53nnMFBMICPortNeighbor
			INTEGER,
		ol53nnMFBMICPortRemoteMACIndicated
			INTEGER,
		ol53nnMFBMICPortBSFlag
			INTEGER,
		ol53nnMFBMICPortPCWithhold
			INTEGER,
		ol53nnMFBMICPortLerCondition
			INTEGER
		}

ol53nnMFBMICPortSlotIndex OBJECT-TYPE
	SYNTAX INTEGER
	ACCESS read-only
	STATUS mandatory
	DESCRIPTION
		"A unique value that identifies a particular module.  Its
		value ranges between 1 and olModSlotNumber.  The module
		identified by a particular value of this index is the same
		module as indentified by the same value of 
		olPortSlotIndex."
	::= { ol53nnMFBMICPortEntry 1 }


ol53nnMFBMICPortIndex OBJECT-TYPE
	SYNTAX INTEGER
	ACCESS read-only
	STATUS mandatory
	DESCRIPTION
		"A unique value that identifies a particular port within this
		module. Its value ranges between 1 and olModPortNumber.  
		The module identified by a particular value of this index is 
		the same module as indentified by the same value of 
		olPortIndex."
	::= { ol53nnMFBMICPortEntry 2 }

ol53nnMFBMICPortConfig OBJECT-TYPE
	SYNTAX INTEGER {
                slave(3),
                master(4)
		}
	ACCESS read-write
	STATUS mandatory
	DESCRIPTION
                "Specifies the FDDI port type. If the port is on an
                 FPM, the only allowed values are slave(3), and master(4).
                 In addition, there can only be one active slave port on any
                 concentrator FDDI network."
	::= { ol53nnMFBMICPortEntry 3 }

ol53nnMFBMICPortPcmState OBJECT-TYPE
	SYNTAX INTEGER {
                  pc0(1), -- Off
                  pc1(2), -- Break
                  pc2(3), -- Trace
                  pc3(4), -- Connect
                  pc4(5), -- Next
                  pc5(6), -- Signal
                  pc6(7), -- Join
                  pc7(8), -- Verify
                  pc8(9), -- Active
                  pc9(10) -- Maint
	}
	ACCESS read-only
	STATUS mandatory
	DESCRIPTION
                      "(refer to ANSI SMT 9.6.2)."
	::= { ol53nnMFBMICPortEntry 4 }

ol53nnMFBMICPortConnectState OBJECT-TYPE
	SYNTAX INTEGER {
          disabled(1),
          connecting(2),
          standby(3),
          active(4)
		}
	ACCESS read-only
	STATUS mandatory
	DESCRIPTION
             "An indication of the connect state of this PORT.
              Basically, this gives a higher level view of the
              state of the connection by grouping PCM states and
              the PC-Withhold flag state.  The supported values
              and their corresponding PCM states and PC-Withhold
              condition, when relevant, are:
                  disabled: (PC0:Off, PC9:Maint)
                  connecting: (PC1(Break) || PC3 (Connect) || PC4(next) ||
                               PC5 (Signal) || PC6(Join) || PC7 (Verify)) &&
                              (PC_Withhold = None)
                  standby: (PC_Withhold != None)
                  active: (PC2:Trace || PC8:Active)"
	::= { ol53nnMFBMICPortEntry 5 }

ol53nnMFBMICPortNeighbor OBJECT-TYPE
	SYNTAX INTEGER {
                a(1),
                b(2),
                slave(3),
                master(4),
                unknown(5)
		}
	ACCESS read-only
	STATUS mandatory
	DESCRIPTION
             "The type (PC_Neighbor) of the remote PORT that is
              determined in PC_Signaling in R_Val (1,2) (refer
              to ANSI SMT 9.6.3.2)."
	::= { ol53nnMFBMICPortEntry 6 }

ol53nnMFBMICPortRemoteMACIndicated OBJECT-TYPE
	SYNTAX INTEGER { true(1), false(2) }
	ACCESS read-only
	STATUS mandatory
	DESCRIPTION
          "The indication, in PC-Signaling that the remote
           partner intends to place a MAC in the output token
           PATH of this PORT.  Signaled as R_Val (9) (refer
           to ANSI SMT 9.6.3.2)."
	::= { ol53nnMFBMICPortEntry 7 }

ol53nnMFBMICPortBSFlag OBJECT-TYPE
	SYNTAX INTEGER { true(1), false(2) }
	ACCESS read-only
	STATUS mandatory
	DESCRIPTION
          "The Break State, BS_Flag (refer to ANSI SMT
           9.4.3.4)."
	::= { ol53nnMFBMICPortEntry 8 }

ol53nnMFBMICPortPCWithhold OBJECT-TYPE
	SYNTAX INTEGER  { none(1), m-m(2), other(3) }
	ACCESS read-only
	STATUS mandatory
	DESCRIPTION
           "PC_Withhold, (refer to ANSI SMT 9.4.1)."
	::= { ol53nnMFBMICPortEntry 9 }

ol53nnMFBMICPortLerCondition OBJECT-TYPE
	SYNTAX INTEGER  { bad(1), okay(2) }
	ACCESS read-only
	STATUS mandatory
	DESCRIPTION
           "This variable is set to true whenever LerEstimate
            is less than or equal to LerAlarm (the larger the number
            the smaller the value)."
	::= { ol53nnMFBMICPortEntry 10 }


-- Trunk Table
-- (only present for compatibility)

ol53nnMFBMICTrunkTable OBJECT-TYPE
	SYNTAX SEQUENCE OF Ol53nnMFBMICTrunkEntry
	ACCESS not-accessible
	STATUS mandatory
	DESCRIPTION
                "FDDI module specific trunk table variables.
                 At present there are none."
	::= { ol53nnMFBMIC 3 }

ol53nnMFBMICTrunkEntry OBJECT-TYPE
	SYNTAX Ol53nnMFBMICTrunkEntry
	ACCESS not-accessible
	STATUS mandatory
	DESCRIPTION
		"A description of 53nnM-FBMIC trunk attributes."		
	INDEX { ol53nnMFBMICTrunkSlotIndex, ol53nnMFBMICTrunkIndex }
	::= { ol53nnMFBMICTrunkTable 1 }

Ol53nnMFBMICTrunkEntry ::= 
	SEQUENCE {
		ol53nnMFBMICTrunkSlotIndex	
			INTEGER,
		ol53nnMFBMICTrunkIndex
			INTEGER
		}

ol53nnMFBMICTrunkSlotIndex OBJECT-TYPE
	SYNTAX INTEGER
	ACCESS read-only
	STATUS mandatory
	DESCRIPTION
		"A unique value that identifies a particular module.  Its
		value ranges between 1 and olModSlotNumber.  The module
		identified by a particular value of this index is the same
		module as indentified by the same value of 
		olTrunkSlotIndex."
	::= { ol53nnMFBMICTrunkEntry 1 }


ol53nnMFBMICTrunkIndex OBJECT-TYPE
	SYNTAX INTEGER
	ACCESS read-only
	STATUS mandatory
	DESCRIPTION
		"A unique value that identifies a particular trunk within this
		module. Its value ranges between 1 and olModTrunkNumber.  
		The module identified by a particular value of this index is 
		the same module as indentified by the same value of 
		olTrunkIndex."
	::= { ol53nnMFBMICTrunkEntry 2 }



--
-- FDDI media module with ST connector
--

ol53nnMFIBSTModTable OBJECT-TYPE
	SYNTAX SEQUENCE OF Ol53nnMFIBSTModEntry
	ACCESS not-accessible
	STATUS mandatory
	DESCRIPTION
		"A list of module attributes that apply to this model.
		To access an ol53nnMFIBSTModTable entry, the 
		ol53nnMFIBSTModSlotIndex attribute is used."
	::= { ol53nnMFIBST 1 }

ol53nnMFIBSTModEntry OBJECT-TYPE
	SYNTAX Ol53nnMFIBSTModEntry 
	ACCESS not-accessible
	STATUS mandatory
	DESCRIPTION
		"A list of module-specific information about a specific
		53nnM-FIBST module in the concentrator."
	INDEX { ol53nnMFIBSTModSlotIndex }
	::= { ol53nnMFIBSTModTable 1 }

Ol53nnMFIBSTModEntry ::=
	SEQUENCE {
		ol53nnMFIBSTModSlotIndex
			INTEGER,
		ol53nnMFIBSTModDownStreamModule
			INTEGER,
		ol53nnMFIBSTModUpStreamModule
			INTEGER,
		ol53nnMFIBSTModDownStreamOperPath
			INTEGER,
		ol53nnMFIBSTModUpStreamOperPath
			INTEGER,
		ol53nnMFIBSTModRingInfo
			OCTET STRING
		}

ol53nnMFIBSTModSlotIndex OBJECT-TYPE
	SYNTAX INTEGER
	ACCESS read-only
	STATUS mandatory
	DESCRIPTION
		"A unique value that identifies a particular module.  Its
		value ranges between 1 and olModSlotNumber.  The module
		identified by a particular value of this index is the same
		module as indentified by the same value of olModSlotIndex."
	::= { ol53nnMFIBSTModEntry 1 }

ol53nnMFIBSTModDownStreamModule OBJECT-TYPE
	SYNTAX INTEGER (1..16)
	ACCESS read-only
	STATUS mandatory
	DESCRIPTION
                "Down stream slot (transmit to)"
	::= { ol53nnMFIBSTModEntry 2 }

ol53nnMFIBSTModUpStreamModule OBJECT-TYPE
	SYNTAX INTEGER (1..16)
	ACCESS read-only
	STATUS mandatory
	DESCRIPTION
                "Up stream slot (receve from)"
	::= { ol53nnMFIBSTModEntry 3 }

ol53nnMFIBSTModDownStreamOperPath OBJECT-TYPE
	SYNTAX INTEGER  {
                isolated(2),
                fddi-path-1(24),
                fddi-path-2(25),
                fddi-path-3(26),
                fddi-path-4(27),
                fddi-path-5(28),
                fddi-path-6(29),
                fddi-path-7(30),
                fddi-path-8(31)
                }
	ACCESS read-only
	STATUS mandatory
	DESCRIPTION
                "Transmit DBA (debug only)"
	::= { ol53nnMFIBSTModEntry 4 }

ol53nnMFIBSTModUpStreamOperPath OBJECT-TYPE
	SYNTAX INTEGER  {
                isolated(2),
                fddi-path-1(24),
                fddi-path-2(25),
                fddi-path-3(26),
                fddi-path-4(27),
                fddi-path-5(28),
                fddi-path-6(29),
                fddi-path-7(30),
                fddi-path-8(31)
                }
	ACCESS read-only
	STATUS mandatory
	DESCRIPTION
                "Receive DBA (debug only)"
	::= { ol53nnMFIBSTModEntry 5 }

ol53nnMFIBSTModRingInfo OBJECT-TYPE
	SYNTAX OCTET STRING (SIZE(1..8))
	ACCESS read-only
	STATUS mandatory
	DESCRIPTION
                "An array which is indexed by DBA number. Each element
                 contains the slot number (1..16) which is assigned to
                 transmit on this DBA. (debug only)"
	::= { ol53nnMFIBSTModEntry 6 }


-- port table

ol53nnMFIBSTPortTable OBJECT-TYPE
	SYNTAX SEQUENCE OF Ol53nnMFIBSTPortEntry
	ACCESS not-accessible
	STATUS mandatory
	DESCRIPTION
		"A table of port-specific information for each port of
		this module type."
	::= { ol53nnMFIBST 2 }

ol53nnMFIBSTPortEntry OBJECT-TYPE
	SYNTAX Ol53nnMFIBSTPortEntry 
	ACCESS not-accessible
	STATUS mandatory
	DESCRIPTION
		"A list of module-specific information about a specific
		53nnM-FIBST port in the concentrator."
	INDEX { ol53nnMFIBSTPortSlotIndex, ol53nnMFIBSTPortIndex }
	::= { ol53nnMFIBSTPortTable 1 }

Ol53nnMFIBSTPortEntry ::=
	SEQUENCE {
		ol53nnMFIBSTPortSlotIndex
			INTEGER,			
		ol53nnMFIBSTPortIndex
			INTEGER,
		ol53nnMFIBSTPortConfig
			INTEGER,
		ol53nnMFIBSTPortPcmState
			INTEGER,
		ol53nnMFIBSTPortConnectState
			INTEGER,
		ol53nnMFIBSTPortNeighbor
			INTEGER,
		ol53nnMFIBSTPortRemoteMACIndicated
			INTEGER,
		ol53nnMFIBSTPortBSFlag
			INTEGER,
		ol53nnMFIBSTPortPCWithhold
			INTEGER,
		ol53nnMFIBSTPortLerCondition
			INTEGER
		}

ol53nnMFIBSTPortSlotIndex OBJECT-TYPE
	SYNTAX INTEGER
	ACCESS read-only
	STATUS mandatory
	DESCRIPTION
		"A unique value that identifies a particular module.  Its
		value ranges between 1 and olModSlotNumber.  The module
		identified by a particular value of this index is the same
		module as indentified by the same value of 
		olPortSlotIndex."
	::= { ol53nnMFIBSTPortEntry 1 }


ol53nnMFIBSTPortIndex OBJECT-TYPE
	SYNTAX INTEGER
	ACCESS read-only
	STATUS mandatory
	DESCRIPTION
		"A unique value that identifies a particular port within this
		module. Its value ranges between 1 and olModPortNumber.  
		The module identified by a particular value of this index is 
		the same module as indentified by the same value of 
		olPortIndex."
	::= { ol53nnMFIBSTPortEntry 2 }

ol53nnMFIBSTPortConfig OBJECT-TYPE
	SYNTAX INTEGER {
                slave(3),
                master(4)
		}
	ACCESS read-write
	STATUS mandatory
	DESCRIPTION
                "Specifies the FDDI port type. If the port is on an
                 FPM, the only allowed values are slave(3) and master(4).
                 In addition, there can only be one active slave port on any
                 concentrator FDDI network."
	::= { ol53nnMFIBSTPortEntry 3 }

ol53nnMFIBSTPortPcmState OBJECT-TYPE
	SYNTAX INTEGER {
                  pc0(1), -- Off
                  pc1(2), -- Break
                  pc2(3), -- Trace
                  pc3(4), -- Connect
                  pc4(5), -- Next
                  pc5(6), -- Signal
                  pc6(7), -- Join
                  pc7(8), -- Verify
                  pc8(9), -- Active
                  pc9(10) -- Maint
	}
	ACCESS read-only
	STATUS mandatory
	DESCRIPTION
                      "(refer to ANSI SMT 9.6.2)."
	::= { ol53nnMFIBSTPortEntry 4 }

ol53nnMFIBSTPortConnectState OBJECT-TYPE
	SYNTAX INTEGER {
          disabled(1),
          connecting(2),
          standby(3),
          active(4)
		}
	ACCESS read-only
	STATUS mandatory
	DESCRIPTION
             "An indication of the connect state of this PORT.
              Basically, this gives a higher level view of the
              state of the connection by grouping PCM states and
              the PC-Withhold flag state.  The supported values
              and their corresponding PCM states and PC-Withhold
              condition, when relevant, are:
                  disabled: (PC0:Off, PC9:Maint)
                  connecting: (PC1(Break) || PC3 (Connect) || PC4(next) ||
                               PC5 (Signal) || PC6(Join) || PC7 (Verify)) &&
                              (PC_Withhold = None)
                  standby: (PC_Withhold != None)
                  active: (PC2:Trace || PC8:Active)"
	::= { ol53nnMFIBSTPortEntry 5 }

ol53nnMFIBSTPortNeighbor OBJECT-TYPE
	SYNTAX INTEGER {
                a(1),
                b(2),
                slave(3),
                master(4),
                unknown(5)
		}
	ACCESS read-only
	STATUS mandatory
	DESCRIPTION
             "The type (PC_Neighbor) of the remote PORT that is
              determined in PC_Signaling in R_Val (1,2) (refer
              to ANSI SMT 9.6.3.2)."
	::= { ol53nnMFIBSTPortEntry 6 }

ol53nnMFIBSTPortRemoteMACIndicated OBJECT-TYPE
	SYNTAX INTEGER { true(1), false(2) }
	ACCESS read-only
	STATUS mandatory
	DESCRIPTION
          "The indication, in PC-Signaling that the remote
           partner intends to place a MAC in the output token
           PATH of this PORT.  Signaled as R_Val (9) (refer
           to ANSI SMT 9.6.3.2)."
	::= { ol53nnMFIBSTPortEntry 7 }

ol53nnMFIBSTPortBSFlag OBJECT-TYPE
	SYNTAX INTEGER { true(1), false(2) }
	ACCESS read-only
	STATUS mandatory
	DESCRIPTION
          "The Break State, BS_Flag (refer to ANSI SMT
           9.4.3.4)."
	::= { ol53nnMFIBSTPortEntry 8 }

ol53nnMFIBSTPortPCWithhold OBJECT-TYPE
	SYNTAX INTEGER  { none(1), m-m(2), other(3) }
	ACCESS read-only
	STATUS mandatory
	DESCRIPTION
           "PC_Withhold, (refer to ANSI SMT 9.4.1)."
	::= { ol53nnMFIBSTPortEntry 9 }

ol53nnMFIBSTPortLerCondition OBJECT-TYPE
	SYNTAX INTEGER  { bad(1), okay(2) }
	ACCESS read-only
	STATUS mandatory
	DESCRIPTION
           "This variable is set to true whenever LerEstimate
            is less than or equal to LerAlarm (the larger the number
            the smaller the value)."
	::= { ol53nnMFIBSTPortEntry 10 }



-- Trunk Table
-- (only present for compatibility)

ol53nnMFIBSTTrunkTable OBJECT-TYPE
	SYNTAX SEQUENCE OF Ol53nnMFIBSTTrunkEntry
	ACCESS not-accessible
	STATUS mandatory
	DESCRIPTION
                "FDDI module specific trunk table variables.
                 At present there are none."
	::= { ol53nnMFIBST 3 }

ol53nnMFIBSTTrunkEntry OBJECT-TYPE
	SYNTAX Ol53nnMFIBSTTrunkEntry
	ACCESS not-accessible
	STATUS mandatory
	DESCRIPTION
		"A description of 53nnM-FIBST trunk attributes."		
	INDEX { ol53nnMFIBSTTrunkSlotIndex, ol53nnMFIBSTTrunkIndex }
	::= { ol53nnMFIBSTTrunkTable 1 }

Ol53nnMFIBSTTrunkEntry ::= 
	SEQUENCE {
		ol53nnMFIBSTTrunkSlotIndex	
			INTEGER,
		ol53nnMFIBSTTrunkIndex
			INTEGER
		}

ol53nnMFIBSTTrunkSlotIndex OBJECT-TYPE
	SYNTAX INTEGER
	ACCESS read-only
	STATUS mandatory
	DESCRIPTION
		"A unique value that identifies a particular module.  Its
		value ranges between 1 and olModSlotNumber.  The module
		identified by a particular value of this index is the same
		module as indentified by the same value of 
		olTrunkSlotIndex."
	::= { ol53nnMFIBSTTrunkEntry 1 }


ol53nnMFIBSTTrunkIndex OBJECT-TYPE
	SYNTAX INTEGER
	ACCESS read-only
	STATUS mandatory
	DESCRIPTION
		"A unique value that identifies a particular trunk within this
		module. Its value ranges between 1 and olModTrunkNumber.  
		The module identified by a particular value of this index is 
		the same module as indentified by the same value of 
		olTrunkIndex."
	::= { ol53nnMFIBSTTrunkEntry 2 }


--
-- FDDI media module with coper connector
--

ol53nnMSTPModTable OBJECT-TYPE
	SYNTAX SEQUENCE OF Ol53nnMSTPModEntry
	ACCESS not-accessible
	STATUS mandatory
	DESCRIPTION
		"A list of module attributes that apply to this model.
		To access an ol53nnMSTPModTable entry, the 
		ol53nnMSTPModSlotIndex attribute is used."
	::= { ol53nnMSTP 1 }

ol53nnMSTPModEntry OBJECT-TYPE
	SYNTAX Ol53nnMSTPModEntry 
	ACCESS not-accessible
	STATUS mandatory
	DESCRIPTION
		"A list of module-specific information about a specific
		53nnM-FIBSTP module in the concentrator."
	INDEX { ol53nnMSTPModSlotIndex }
	::= { ol53nnMSTPModTable 1 }

Ol53nnMSTPModEntry ::=
	SEQUENCE {
		ol53nnMSTPModSlotIndex
			INTEGER,
		ol53nnMSTPModDownStreamModule
			INTEGER,
		ol53nnMSTPModUpStreamModule
			INTEGER,
		ol53nnMSTPModDownStreamOperPath
			INTEGER,
		ol53nnMSTPModUpStreamOperPath
			INTEGER,
		ol53nnMSTPModRingInfo
			OCTET STRING
		}

ol53nnMSTPModSlotIndex OBJECT-TYPE
	SYNTAX INTEGER
	ACCESS read-only
	STATUS mandatory
	DESCRIPTION
		"A unique value that identifies a particular module.  Its
		value ranges between 1 and olModSlotNumber.  The module
		identified by a particular value of this index is the same
		module as indentified by the same value of olModSlotIndex."
	::= { ol53nnMSTPModEntry 1 }

ol53nnMSTPModDownStreamModule OBJECT-TYPE
	SYNTAX INTEGER (1..16)
	ACCESS read-only
	STATUS mandatory
	DESCRIPTION
                "Down stream slot (transmit to)"
	::= { ol53nnMSTPModEntry 2 }

ol53nnMSTPModUpStreamModule OBJECT-TYPE
	SYNTAX INTEGER (1..16)
	ACCESS read-only
	STATUS mandatory
	DESCRIPTION
                "Down stream slot (receve from)"
	::= { ol53nnMSTPModEntry 3 }

ol53nnMSTPModDownStreamOperPath OBJECT-TYPE
	SYNTAX INTEGER  {
                isolated(2),
                fddi-path-1(24),
                fddi-path-2(25),
                fddi-path-3(26),
                fddi-path-4(27),
                fddi-path-5(28),
                fddi-path-6(29),
                fddi-path-7(30),
                fddi-path-8(31)
                }
	ACCESS read-only
	STATUS mandatory
	DESCRIPTION
                "transmit DBA  (debug only)"
	::= { ol53nnMSTPModEntry 4 }

ol53nnMSTPModUpStreamOperPath OBJECT-TYPE
	SYNTAX INTEGER  {
                isolated(2),
                fddi-path-1(24),
                fddi-path-2(25),
                fddi-path-3(26),
                fddi-path-4(27),
                fddi-path-5(28),
                fddi-path-6(29),
                fddi-path-7(30),
                fddi-path-8(31)
                }
	ACCESS read-only
	STATUS mandatory
	DESCRIPTION
                "receive DBA  (debug only)"
	::= { ol53nnMSTPModEntry 5 }

ol53nnMSTPModRingInfo OBJECT-TYPE
	SYNTAX OCTET STRING (SIZE(1..8))
	ACCESS read-only
	STATUS mandatory
	DESCRIPTION
                "An array which is indexed by DBA number. Each element
                 contains the slot number (1..16) which is assigned to
                 transmit on this DBA. (debug only)"
	::= { ol53nnMSTPModEntry 6 }


-- port table

ol53nnMSTPPortTable OBJECT-TYPE
	SYNTAX SEQUENCE OF Ol53nnMSTPPortEntry
	ACCESS not-accessible
	STATUS mandatory
	DESCRIPTION
		"A table of port-specific information for each port of
		this module type."
	::= { ol53nnMSTP 2 }

ol53nnMSTPPortEntry OBJECT-TYPE
	SYNTAX Ol53nnMSTPPortEntry 
	ACCESS not-accessible
	STATUS mandatory
	DESCRIPTION
		"A list of module-specific information about a specific
		53nnM-STP port in the concentrator."
	INDEX { ol53nnMSTPPortSlotIndex, ol53nnMSTPPortIndex }
	::= { ol53nnMSTPPortTable 1 }

Ol53nnMSTPPortEntry ::=
	SEQUENCE {
		ol53nnMSTPPortSlotIndex
			INTEGER,			
		ol53nnMSTPPortIndex
			INTEGER,
		ol53nnMSTPPortConfig
			INTEGER,
		ol53nnMSTPPortPcmState
			INTEGER,
		ol53nnMSTPPortConnectState
			INTEGER,
		ol53nnMSTPPortNeighbor
			INTEGER,
		ol53nnMSTPPortRemoteMACIndicated
			INTEGER,
		ol53nnMSTPPortBSFlag
			INTEGER,
		ol53nnMSTPPortPCWithhold
			INTEGER,
		ol53nnMSTPPortLerCondition
			INTEGER,
		ol53nnMSTPPortPersonality
			INTEGER
		}

ol53nnMSTPPortSlotIndex OBJECT-TYPE
	SYNTAX INTEGER
	ACCESS read-only
	STATUS mandatory
	DESCRIPTION
		"A unique value that identifies a particular module.  Its
		value ranges between 1 and olModSlotNumber.  The module
		identified by a particular value of this index is the same
		module as indentified by the same value of 
		olPortSlotIndex."
	::= { ol53nnMSTPPortEntry 1 }


ol53nnMSTPPortIndex OBJECT-TYPE
	SYNTAX INTEGER
	ACCESS read-only
	STATUS mandatory
	DESCRIPTION
		"A unique value that identifies a particular port within this
		module. Its value ranges between 1 and olModPortNumber.  
		The module identified by a particular value of this index is 
		the same module as indentified by the same value of 
		olPortIndex."
	::= { ol53nnMSTPPortEntry 2 }

ol53nnMSTPPortConfig OBJECT-TYPE
	SYNTAX INTEGER {
                slave(3),
                master(4)
		}
	ACCESS read-write
	STATUS mandatory
	DESCRIPTION
                "Specifies the FDDI port type. If the port is on an
                 FPM, the only allowed values are slave(3) and master(4).
                 In addition, there can only be one active slave port on any
                 concentrator FDDI network."
	::= { ol53nnMSTPPortEntry 3 }

ol53nnMSTPPortPcmState OBJECT-TYPE
	SYNTAX INTEGER {
                  pc0(1), -- Off
                  pc1(2), -- Break
                  pc2(3), -- Trace
                  pc3(4), -- Connect
                  pc4(5), -- Next
                  pc5(6), -- Signal
                  pc6(7), -- Join
                  pc7(8), -- Verify
                  pc8(9), -- Active
                  pc9(10) -- Maint
	}
	ACCESS read-only
	STATUS mandatory
	DESCRIPTION
                      "(refer to ANSI SMT 9.6.2)."
	::= { ol53nnMSTPPortEntry 4 }

ol53nnMSTPPortConnectState OBJECT-TYPE
	SYNTAX INTEGER {
          disabled(1),
          connecting(2),
          standby(3),
          active(4)
		}
	ACCESS read-only
	STATUS mandatory
	DESCRIPTION
             "An indication of the connect state of this PORT.
              Basically, this gives a higher level view of the
              state of the connection by grouping PCM states and
              the PC-Withhold flag state.  The supported values
              and their corresponding PCM states and PC-Withhold
              condition, when relevant, are:
                  disabled: (PC0:Off, PC9:Maint)
                  connecting: (PC1(Break) || PC3 (Connect) || PC4(next) ||
                               PC5 (Signal) || PC6(Join) || PC7 (Verify)) &&
                              (PC_Withhold = None)
                  standby: (PC_Withhold != None)
                  active: (PC2:Trace || PC8:Active)"
	::= { ol53nnMSTPPortEntry 5 }

ol53nnMSTPPortNeighbor OBJECT-TYPE
	SYNTAX INTEGER {
                a(1),
                b(2),
                slave(3),
                master(4),
                unknown(5)
		}
	ACCESS read-only
	STATUS mandatory
	DESCRIPTION
             "The type (PC_Neighbor) of the remote PORT that is
              determined in PC_Signaling in R_Val (1,2) (refer
              to ANSI SMT 9.6.3.2)."
	::= { ol53nnMSTPPortEntry 6 }

ol53nnMSTPPortRemoteMACIndicated OBJECT-TYPE
	SYNTAX INTEGER { true(1), false(2) }
	ACCESS read-only
	STATUS mandatory
	DESCRIPTION
          "The indication, in PC-Signaling that the remote
           partner intends to place a MAC in the output token
           PATH of this PORT.  Signaled as R_Val (9) (refer
           to ANSI SMT 9.6.3.2)."
	::= { ol53nnMSTPPortEntry 7 }

ol53nnMSTPPortBSFlag OBJECT-TYPE
	SYNTAX INTEGER { true(1), false(2) }
	ACCESS read-only
	STATUS mandatory
	DESCRIPTION
          "The Break State, BS_Flag (refer to ANSI SMT
           9.4.3.4)."
	::= { ol53nnMSTPPortEntry 8 }

ol53nnMSTPPortPCWithhold OBJECT-TYPE
	SYNTAX INTEGER  { none(1), m-m(2), other(3) }
	ACCESS read-only
	STATUS mandatory
	DESCRIPTION
           "PC_Withhold, (refer to ANSI SMT 9.4.1)."
	::= { ol53nnMSTPPortEntry 9 }

ol53nnMSTPPortLerCondition OBJECT-TYPE
	SYNTAX INTEGER  { bad(1), okay(2) }
	ACCESS read-only
	STATUS mandatory
	DESCRIPTION
           "This variable is set to true whenever LerEstimate
            is less than or equal to LerAlarm (the larger the number
            the smaller the value)."
	::= { ol53nnMSTPPortEntry 10 }


ol53nnMSTPPortPersonality OBJECT-TYPE
	SYNTAX INTEGER {
                sddi(1),
                tpddi(2)
		}
	ACCESS read-write
	STATUS mandatory
	DESCRIPTION
                "Specifies the physical signaling used by the port, the only 
		 valid values are sddi(3) and tpddi(4)."
	::= { ol53nnMSTPPortEntry 11 }


-- Trunk Table
-- (only present for compatibility)

ol53nnMSTPTrunkTable OBJECT-TYPE
	SYNTAX SEQUENCE OF Ol53nnMSTPTrunkEntry
	ACCESS not-accessible
	STATUS mandatory
	DESCRIPTION
                "FDDI module specific trunk table variables.
                 At present there are none."
	::= { ol53nnMSTP 3 }

ol53nnMSTPTrunkEntry OBJECT-TYPE
	SYNTAX Ol53nnMSTPTrunkEntry
	ACCESS not-accessible
	STATUS mandatory
	DESCRIPTION
		"A description of 53nnM-STP trunk attributes."		
	INDEX { ol53nnMSTPTrunkSlotIndex, ol53nnMSTPTrunkIndex }
	::= { ol53nnMSTPTrunkTable 1 }

Ol53nnMSTPTrunkEntry ::= 
	SEQUENCE {
		ol53nnMSTPTrunkSlotIndex	
			INTEGER,
		ol53nnMSTPTrunkIndex
			INTEGER
		}

ol53nnMSTPTrunkSlotIndex OBJECT-TYPE
	SYNTAX INTEGER
	ACCESS read-only
	STATUS mandatory
	DESCRIPTION
		"A unique value that identifies a particular module.  Its
		value ranges between 1 and olModSlotNumber.  The module
		identified by a particular value of this index is the same
		module as indentified by the same value of 
		olTrunkSlotIndex."
	::= { ol53nnMSTPTrunkEntry 1 }


ol53nnMSTPTrunkIndex OBJECT-TYPE
	SYNTAX INTEGER
	ACCESS read-only
	STATUS mandatory
	DESCRIPTION
		"A unique value that identifies a particular trunk within this
		module. Its value ranges between 1 and olModTrunkNumber.  
		The module identified by a particular value of this index is 
		the same module as indentified by the same value of 
		olTrunkIndex."
	::= { ol53nnMSTPTrunkEntry 2 }


-- 
-- ONline Ethernet 10BASE-T Per-Connector Module
--

ol51nnMTPCLModTable OBJECT-TYPE
 	SYNTAX SEQUENCE OF Ol51nnMTPCLModEntry
 	ACCESS not-accessible
	STATUS mandatory
	DESCRIPTION
		"A list of module-specific information about a specific
		51nnM-TPCL module in the concentrator."
	::= { ol51nnMTPCL 1 }

ol51nnMTPCLModEntry OBJECT-TYPE
	SYNTAX Ol51nnMTPCLModEntry 
	ACCESS not-accessible
	STATUS mandatory
	DESCRIPTION
		"A list of module-specific information about a specific
		51nnM-TPCL module in the concentrator."
	INDEX { ol51nnMTPCLModSlotIndex }
	::= { ol51nnMTPCLModTable 1 }

Ol51nnMTPCLModEntry ::=
	SEQUENCE {
		ol51nnMTPCLModSlotIndex
			INTEGER,
		ol51nnMTPCLModMonitorConn
			INTEGER,
		ol51nnMTPCLModConn1Network
			INTEGER,
		ol51nnMTPCLModConn2Network
			INTEGER,
		ol51nnMTPCLModConn1DipNetwork
			INTEGER,
		ol51nnMTPCLModConn2DipNetwork
			INTEGER,
		ol51nnMTPCLModAutoPartition
			INTEGER
		}

ol51nnMTPCLModSlotIndex OBJECT-TYPE
	SYNTAX INTEGER
	ACCESS read-only
	STATUS mandatory
	DESCRIPTION
		"The slot number of this module."
	::= { ol51nnMTPCLModEntry 1 }

ol51nnMTPCLModMonitorConn OBJECT-TYPE
	SYNTAX INTEGER {
		connector-1(1),
		connector-2(2)
		}
	ACCESS read-write
	STATUS mandatory
	DESCRIPTION
		"When both connectors are on the same network:

		   Setting this object to connector-1 allows the EMM to 
                   monitor the port statistics of port 1-12 on a per-port 
                   basis, and the port statistics of port 13-24 are summed
                   and are reported through port 13.  

                   Setting this object to connector-2 allows the EMM to 
                   monitor the port statistics of port 12-24 on a per-port
                   basis, and the port statistics of port 1-12 are summed 
                   and are reported through port 13.

	         Note: when the 2 connectors are on different networks,
	   	 setting this object to the value connector-1 or 
                 connector-2 will not have any effect.  The port counters 
                 will be cleared whenever the value of this object is 
                 changed."
	::= { ol51nnMTPCLModEntry 2 }

ol51nnMTPCLModConn1Network OBJECT-TYPE
	SYNTAX INTEGER {
		ethernet-1(6),
		ethernet-2(7),
		ethernet-3(8), 
		isolated-1(21),
		isolated-2(22)
		}
	ACCESS read-write
	STATUS mandatory
	DESCRIPTION
		"The network that this connector is attached to."
	::= { ol51nnMTPCLModEntry 3 }

ol51nnMTPCLModConn2Network OBJECT-TYPE
	SYNTAX INTEGER {
		ethernet-1(6),
		ethernet-2(7),
		ethernet-3(8),
		isolated-1(21),
		isolated-2(22)
		}
	ACCESS read-write
	STATUS mandatory
	DESCRIPTION
		"The network that this connector is attached to."

	::= { ol51nnMTPCLModEntry 4 }

ol51nnMTPCLModConn1DipNetwork OBJECT-TYPE
	SYNTAX INTEGER {
		ethernet-1(6),
		ethernet-2(7),
		ethernet-3(8),
		isolated-1(21),
		isolated-2(22)
		}
	ACCESS read-only
	STATUS mandatory
	DESCRIPTION
		"The network indicated by the connector dip switch."
	::= { ol51nnMTPCLModEntry 5 }

ol51nnMTPCLModConn2DipNetwork OBJECT-TYPE
	SYNTAX INTEGER {
		ethernet-1(6),
		ethernet-2(7),
		ethernet-3(8),
		isolated-1(21),
		isolated-2(22)
		}
	ACCESS read-only
	STATUS mandatory
	DESCRIPTION
		"The network indicated by the connector dip switch."
	::= { ol51nnMTPCLModEntry 6 }

ol51nnMTPCLModAutoPartition OBJECT-TYPE
	SYNTAX INTEGER {
		collisions-31(1),
		collisions-63(2),
		collisions-127(3),
		collisions-255(4)
		}
	ACCESS read-write
	STATUS mandatory
	DESCRIPTION
		"This object holds the consecutive collision count 
                 limit value.  The module goes into the auto-partition 
                 mode whenever the consecutive collision count exceeds
                 the consecutive collision limit count."	
	::= { ol51nnMTPCLModEntry 7 }

ol51nnMTPCLPortTable OBJECT-TYPE
	SYNTAX SEQUENCE OF Ol51nnMTPCLPortEntry
	ACCESS not-accessible
	STATUS mandatory
	DESCRIPTION
		"A table of port-specific information for each port of
		this module type."
	::= { ol51nnMTPCL 2 }

ol51nnMTPCLPortEntry OBJECT-TYPE
	SYNTAX Ol51nnMTPCLPortEntry 
	ACCESS not-accessible
	STATUS mandatory
	DESCRIPTION
		"A list of module-specific information about a specific
		51nnM-TPCL port in the concentrator."
	INDEX { ol51nnMTPCLPortSlotIndex, ol51nnMTPCLPortIndex }
	::= { ol51nnMTPCLPortTable 1 }

Ol51nnMTPCLPortEntry ::=
	SEQUENCE {
		ol51nnMTPCLPortSlotIndex
			INTEGER,			
		ol51nnMTPCLPortIndex
			INTEGER,
		ol51nnMTPCLPortAdminState
			INTEGER,
		ol51nnMTPCLPortBuddySlot
			INTEGER,
		ol51nnMTPCLPortBuddyPort
			INTEGER,
		ol51nnMTPCLPortDipAdminState
			INTEGER,
		ol51nnMTPCLPortLinkInteg
			INTEGER,
		ol51nnMTPCLPortDipLinkInteg
			INTEGER
		}

ol51nnMTPCLPortSlotIndex OBJECT-TYPE
	SYNTAX INTEGER
	ACCESS read-only
	STATUS mandatory
	DESCRIPTION
		"The slot number of this port's module."
	::= { ol51nnMTPCLPortEntry 1 }


ol51nnMTPCLPortIndex OBJECT-TYPE
	SYNTAX INTEGER
	ACCESS read-only
	STATUS mandatory
	DESCRIPTION
		"The port number of this port."
	::= { ol51nnMTPCLPortEntry 2 }

ol51nnMTPCLPortAdminState OBJECT-TYPE
	SYNTAX INTEGER {
		enabled(1),
		disabled(2),
		redundant-primary(3),
		redundant-backup(4),
		remote-diagnostics(8)
		}
	ACCESS read-write
	STATUS mandatory
	DESCRIPTION
                "The desired state of this port.  Setting this port to
                be redundant or for remote diagnostics with invalid settings
		of buddy slot and buddy port will return the genError error."
	::= { ol51nnMTPCLPortEntry 3 }

ol51nnMTPCLPortBuddySlot OBJECT-TYPE
	SYNTAX INTEGER
	ACCESS read-write
	STATUS mandatory
	DESCRIPTION
		"The slot index of the redundant port's buddy.  To set
		a port to be redundant, the buddy's slot and port must 
		be set to valid values.

		The buddy is automatically set to be redundant to this port.

		If the port is configured for remote diagnostics, then 
		this contains the slot index of the backup buddy port.
		To configure a port for remote diagnostics, the buddy's
		slot and port must be set to valid values."
	::= { ol51nnMTPCLPortEntry 4 }

ol51nnMTPCLPortBuddyPort  OBJECT-TYPE
	SYNTAX INTEGER
	ACCESS read-write
	STATUS mandatory
	DESCRIPTION
		"The port index of the redundant port's buddy.  To set
		a port to be redundant, the buddy's slot and port must 
		be set to valid values.

		The buddy is automatically set to be redundant to this port.

		If the port is configured for remote diagnostics, then 
		this contains the port index of the backup buddy port.
		To configure a port for remote diagnostics, the buddy's
		slot and port must be set to valid values."
	::= { ol51nnMTPCLPortEntry 5 }

ol51nnMTPCLPortDipAdminState OBJECT-TYPE
	SYNTAX INTEGER {
		enabled(1),
		disabled(2)
		}
	ACCESS read-only
	STATUS mandatory
	DESCRIPTION
		"The state of this port as indicated by the port's dip 
		switches."		
	::= { ol51nnMTPCLPortEntry 6 }

ol51nnMTPCLPortLinkInteg OBJECT-TYPE
	SYNTAX INTEGER {
		enabled(1),
		disabled(2)
		}
	ACCESS read-write
	STATUS mandatory
	DESCRIPTION
		"The current link integrity configuration for this port."
	::= { ol51nnMTPCLPortEntry 7 }

ol51nnMTPCLPortDipLinkInteg OBJECT-TYPE
	SYNTAX INTEGER {
		enabled(1),
		disabled(2)
		}
	ACCESS read-only
	STATUS mandatory
	DESCRIPTION
		"The link integrity configuration as indicated by this
		dip switch."
	::= { ol51nnMTPCLPortEntry 8 }


--
-- ONline Token Ring to Token Ring Bridge Module
--

ol52nnBTTModTable OBJECT-TYPE
        SYNTAX SEQUENCE OF Ol52nnBTTModEntry
        ACCESS not-accessible
        STATUS mandatory
        DESCRIPTION
                "A table of module-specific information for each
                52nnB-TT module in the concentrator."
        ::= { ol52nnBTT 1 }

ol52nnBTTModEntry OBJECT-TYPE
        SYNTAX Ol52nnBTTModEntry
        ACCESS not-accessible
        STATUS mandatory
        DESCRIPTION
                "A list of module-specific information about a specific
                52nnB-TT module in the concentrator."
        INDEX { ol52nnBTTModSlotIndex }
        ::= {ol52nnBTTModTable 1 }

Ol52nnBTTModEntry ::=
        SEQUENCE {
                ol52nnBTTModSlotIndex
                        INTEGER,
                ol52nnBTTModBridgeType
                        INTEGER,
                ol52nnBTTModSoftwareVersion
                        DisplayString,
                ol52nnBTTModSRBridgeNo
                        INTEGER,
		ol52nnBTTModNetworkStatus
			INTEGER
        }
                
ol52nnBTTModSlotIndex OBJECT-TYPE
        SYNTAX INTEGER
        ACCESS read-only
        STATUS mandatory
        DESCRIPTION
                "The slot number of this module."
        ::= { ol52nnBTTModEntry 1 }
        
ol52nnBTTModBridgeType OBJECT-TYPE
        SYNTAX INTEGER {
                  bridge-type-sr(1),
                  bridge-type-srt(2)
                }
        ACCESS read-only
        STATUS mandatory
        DESCRIPTION
                "Whether the bridge is a source-routing bridge or a
                source-routing-transparent bridge."
        ::= { ol52nnBTTModEntry 2 }

ol52nnBTTModSoftwareVersion OBJECT-TYPE
       SYNTAX DisplayString (SIZE(1..10))
       ACCESS read-only
       STATUS mandatory
       DESCRIPTION
               "The version number of the software loaded into the
		module's flash chips."
       ::= { ol52nnBTTModEntry 3 }

ol52nnBTTModSRBridgeNo OBJECT-TYPE
        SYNTAX INTEGER
        ACCESS read-only
        STATUS mandatory
        DESCRIPTION
                "The module's source routing bridge number."
        ::= { ol52nnBTTModEntry 4 }

ol52nnBTTModNetworkStatus OBJECT-TYPE
	SYNTAX INTEGER {
		okay(1),
		closed(2),
		beaconing(3)
		}
	ACCESS read-only
	STATUS mandatory
	DESCRIPTION
		"The status of the ring containing this module."
	::= {ol52nnBTTModEntry 5}

ol52nnBTTPortTable OBJECT-TYPE
        SYNTAX SEQUENCE OF Ol52nnBTTPortEntry
        ACCESS not-accessible
        STATUS mandatory
        DESCRIPTION
                "A table of port-specific for each port of each
                52nnB-TT module i the concentrator."
        ::= { ol52nnBTT 2 }

ol52nnBTTPortEntry OBJECT-TYPE
        SYNTAX Ol52nnBTTPortEntry
        ACCESS not-accessible
        STATUS mandatory
        DESCRIPTION
                "A list of port-specific information about a specific
                52nnB-TT port in the concentrator."
        INDEX { ol52nnBTTPortSlotIndex, ol52nnBTTPortIndex }
        ::= { ol52nnBTTPortTable 1 }

Ol52nnBTTPortEntry ::=
        SEQUENCE {
                ol52nnBTTPortSlotIndex
                        INTEGER,
                ol52nnBTTPortIndex
                        INTEGER,
                ol52nnBTTPortConnector
                        INTEGER,
                ol52nnBTTPortSTAPState
                        INTEGER,
                ol52nnBTTPortIpAddress
                        IpAddress,
                ol52nnBTTPortMACAddress
                        OCTET STRING,
                ol52nnBTTPortThroughput
                        Gauge,
                ol52nnBTTPortForwarding
                        Gauge,
                ol52nnBTTPortSRRingNo
                        INTEGER,
                ol52nnBTTPortRingSpeed
                        INTEGER
                }

ol52nnBTTPortSlotIndex OBJECT-TYPE
        SYNTAX INTEGER
        ACCESS read-only
        STATUS mandatory
        DESCRIPTION
                "The slot number for this port's module."
        ::= { ol52nnBTTPortEntry 1 }

ol52nnBTTPortIndex OBJECT-TYPE
        SYNTAX INTEGER
        ACCESS read-only
        STATUS mandatory
        DESCRIPTION
                "The port number for this port within this slot."
        ::= { ol52nnBTTPortEntry 2 }
                
ol52nnBTTPortConnector OBJECT-TYPE
        SYNTAX INTEGER {
                backPlane(1),   -- connects directly to backplane
                rj45(8),        -- unshielded
                db-9(10)        -- shielded
                }
        ACCESS read-write
        STATUS mandatory
        DESCRIPTION
                "The port connector. Notice that setting port connector 
                 available only for the front pannel port."
        ::= { ol52nnBTTPortEntry 3 }

ol52nnBTTPortSTAPState OBJECT-TYPE
        SYNTAX INTEGER {
                disabled (1),	-- receive and process frames
		blocking (2),	-- receive and process frames 
		listening (3),  -- receive and process frames
		learning (4),	-- receive and process frames
		forwarding (5),	-- receive, process and forward frames
		off (6)		-- receive and discard frames
                }
        ACCESS read-only
        STATUS mandatory
        DESCRIPTION
                "The port connector. Notice that setting port connector
                 available only for the front pannel port."
        ::= { ol52nnBTTPortEntry 4 }


ol52nnBTTPortIpAddress OBJECT-TYPE
        SYNTAX IpAddress
        ACCESS read-only
        STATUS mandatory
        DESCRIPTION
                "The IP address associated with this port."
        ::= { ol52nnBTTPortEntry 5 }
                
ol52nnBTTPortMACAddress OBJECT-TYPE
        SYNTAX OCTET STRING (SIZE(6))
        ACCESS read-only
        STATUS mandatory
        DESCRIPTION
                "A 6 octet address that uniquely identifies this port."
        ::= { ol52nnBTTPortEntry 6 }
                
ol52nnBTTPortThroughput OBJECT-TYPE
        SYNTAX Gauge
        ACCESS read-only
        STATUS mandatory
        DESCRIPTION
                "Port throughput measured in Kbytes per second."
        ::= { ol52nnBTTPortEntry 7 }
                
ol52nnBTTPortForwarding OBJECT-TYPE
        SYNTAX Gauge
        ACCESS read-only
        STATUS mandatory
        DESCRIPTION
                "Port forwarding rate measured in frames per second."
        ::= { ol52nnBTTPortEntry 8 }
                
ol52nnBTTPortSRRingNo OBJECT-TYPE
        SYNTAX INTEGER
        ACCESS read-only
        STATUS mandatory
        DESCRIPTION
                "The port's source routing ring number."
        ::= { ol52nnBTTPortEntry 9 }

ol52nnBTTPortRingSpeed OBJECT-TYPE
        SYNTAX INTEGER {
                fourMegabit(1),
                sixteenMegabit(2)
                }
        ACCESS read-write
        STATUS mandatory
        DESCRIPTION     
                "The ring's bandwidth."
        ::= { ol52nnBTTPortEntry 10 }
                
                
--
-- Trunk table is for compatibility purposes only
--
 
ol52nnBTTTrunkTable  OBJECT-TYPE 
        SYNTAX SEQUENCE OF Ol52nnBTTTrunkEntry 
        ACCESS not-accessible
        STATUS mandatory 
        DESCRIPTION 
                "A table that contains trunk-specific information for 
                each trunk on each 52nnB-TT in the concentrator." 
        ::= {ol52nnBTT 3} 
 
ol52nnBTTTrunkEntry  OBJECT-TYPE 
        SYNTAX Ol52nnBTTTrunkEntry 
        ACCESS not-accessible 
        STATUS mandatory 
        DESCRIPTION 
                "A list of information about a specific Trunk on a 
                52nnB-TT module in the concentrator." 
        INDEX {ol52nnBTTTrunkSlotIndex, ol52nnBTTTrunkIndex} 
        ::= {ol52nnBTTTrunkTable 1} 
 
Ol52nnBTTTrunkEntry ::= 
        SEQUENCE { 
                ol52nnBTTTrunkSlotIndex 
                        INTEGER, 
                ol52nnBTTTrunkIndex 
                        INTEGER
                } 
 
ol52nnBTTTrunkSlotIndex OBJECT-TYPE 
        SYNTAX INTEGER 
        ACCESS read-only 
        STATUS mandatory 
        DESCRIPTION 
                "The slot number of this module. Its value ranges 
                between 1 and olConcNumSlots."
        ::= {ol52nnBTTTrunkEntry 1} 
  
ol52nnBTTTrunkIndex OBJECT-TYPE
        SYNTAX INTEGER 
        ACCESS read-only 
        STATUS mandatory 
        DESCRIPTION 
                "The trunk number of this module. Its value ranges 
                between 1 and olModNumTrunks." 
        ::= {ol52nnBTTTrunkEntry 2} 


--
-- Token ring management module
--

ol52nnMMGTModTable  OBJECT-TYPE
	SYNTAX SEQUENCE OF Ol52nnMMGTModEntry
	ACCESS not-accessible
	STATUS mandatory
	DESCRIPTION
		"A table that contains module information about
		each 52nnM-MGT in the concentrator."
	::= {ol52nnMMGT 1}

ol52nnMMGTModEntry  OBJECT-TYPE
	SYNTAX Ol52nnMMGTModEntry
	ACCESS not-accessible
	STATUS mandatory
	DESCRIPTION
		"A list of module information for each 52nnM-MGT
		in the concentrator."
	INDEX {ol52nnMMGTModSlotIndex}
	::= {ol52nnMMGTModTable 1}

Ol52nnMMGTModEntry ::=
	SEQUENCE {
		ol52nnMMGTModSlotIndex
			INTEGER,
		ol52nnMMGTModMasterPriority
			INTEGER,
		ol52nnMMGTModMasterStatus
			INTEGER,
		ol52nnMMGTModStationAddr
			OCTET STRING,
		ol52nnMMGTModRingSpeed
			INTEGER,
		ol52nnMMGTModNetworkStatus
			INTEGER
		}

ol52nnMMGTModSlotIndex OBJECT-TYPE
	SYNTAX INTEGER
	ACCESS read-only
	STATUS mandatory
	DESCRIPTION
		"The slot number of this module. Its value ranges
		between 1 and olConcNumSlots."
	::= {ol52nnMMGTModEntry 1}

ol52nnMMGTModMasterPriority OBJECT-TYPE
	SYNTAX INTEGER {
		one(1),
		two(2),
		three(3),
		four(4),
		five(5),
		six(6),
		seven(7),
		eight(8),
		nine(9),
		ten(10)
		}
	ACCESS read-write
	STATUS mandatory
	DESCRIPTION
		"The mastership priority of this agent. Ten is the
		highest and one is the lowest. Priority is only
		used when an election occurs. Mastership is not
		preemptive unless the reset mastership command is used."
	::= {ol52nnMMGTModEntry 2}

ol52nnMMGTModMasterStatus OBJECT-TYPE
	SYNTAX INTEGER {
		master(1),
		non-master(2),
		electing(3)
		}
	ACCESS read-only
	STATUS mandatory
	DESCRIPTION
		"The mastership status of this agent."
	::= {ol52nnMMGTModEntry 3}

ol52nnMMGTModStationAddr OBJECT-TYPE
	SYNTAX OCTET STRING
	ACCESS read-only
	STATUS mandatory
	DESCRIPTION
		"A 6 octet address that uniquely identifies this module.
		The station address is the MAC address of port 1."
	::= {ol52nnMMGTModEntry 4}

ol52nnMMGTModRingSpeed OBJECT-TYPE
	SYNTAX INTEGER {
		fourMegabit(1),
		sixteenMegabit(2)
		}
	ACCESS read-write
	STATUS mandatory
	DESCRIPTION
		"The ring's bandwidth."
	::= {ol52nnMMGTModEntry 5}

ol52nnMMGTModNetworkStatus OBJECT-TYPE
	SYNTAX INTEGER {
		okay(1),
		closed(2),
		beaconing(3)
		}
	ACCESS read-only
	STATUS mandatory
	DESCRIPTION
		"The status of the ring containing this module."
	::= {ol52nnMMGTModEntry 6}


ol52nnMMGTPortTable  OBJECT-TYPE
	SYNTAX SEQUENCE OF Ol52nnMMGTPortEntry
	ACCESS not-accessible
	STATUS mandatory
	DESCRIPTION
		"A table that contains port-specific information for
		each port on each 52nnM-MGT in the concentrator."
	::= {ol52nnMMGT 2}

ol52nnMMGTPortEntry  OBJECT-TYPE
	SYNTAX Ol52nnMMGTPortEntry
	ACCESS not-accessible
	STATUS mandatory
	DESCRIPTION
		"A list of information about a specific port on a
		52nnM-MGT module in the concentrator."
	INDEX {ol52nnMMGTPortSlotIndex, ol52nnMMGTPortIndex}
	::= {ol52nnMMGTPortTable 1}

Ol52nnMMGTPortEntry ::=
	SEQUENCE {
		ol52nnMMGTPortSlotIndex
			INTEGER,
		ol52nnMMGTPortIndex
			INTEGER,
		ol52nnMMGTPortIpAddress
			IpAddress
		}

ol52nnMMGTPortSlotIndex OBJECT-TYPE
	SYNTAX INTEGER
	ACCESS read-only
	STATUS mandatory
	DESCRIPTION
		"The slot number of this port's module."
	::= {ol52nnMMGTPortEntry 1}

ol52nnMMGTPortIndex OBJECT-TYPE
	SYNTAX INTEGER
	ACCESS read-only
	STATUS mandatory
	DESCRIPTION
		"The port number of this port."
	::= {ol52nnMMGTPortEntry 2}

ol52nnMMGTPortIpAddress  OBJECT-TYPE
	SYNTAX IpAddress
	ACCESS read-write
	STATUS mandatory
	DESCRIPTION
		"The IP address associated with this port."
	::= {ol52nnMMGTPortEntry 3}

ol52nnMMGTTrunkTable  OBJECT-TYPE
	SYNTAX SEQUENCE OF Ol52nnMMGTTrunkEntry
	ACCESS not-accessible
	STATUS mandatory
	DESCRIPTION
		"A table that contains trunk-specific information for
		each trunk on each 52nnM-MGT in the concentrator."
	::= {ol52nnMMGT 3}

ol52nnMMGTTrunkEntry  OBJECT-TYPE
	SYNTAX Ol52nnMMGTTrunkEntry
	ACCESS not-accessible
	STATUS mandatory
	DESCRIPTION
		"A list of information about a specific Trunk on a
		52nnM-MGT module in the concentrator."
	INDEX {ol52nnMMGTTrunkSlotIndex, ol52nnMMGTTrunkIndex}
	::= {ol52nnMMGTTrunkTable 1}

Ol52nnMMGTTrunkEntry ::=
	SEQUENCE {
		ol52nnMMGTTrunkSlotIndex
			INTEGER,
		ol52nnMMGTTrunkIndex
			INTEGER,
		ol52nnMMGTTrunkCableMon
			INTEGER,
		ol52nnMMGTTrunkNetMapState
			INTEGER,
	        ol52nnMMGTTrunkExtBcnRecovery
			INTEGER
		}

ol52nnMMGTTrunkSlotIndex OBJECT-TYPE
	SYNTAX INTEGER
	ACCESS read-only
	STATUS mandatory
	DESCRIPTION
		"The slot number of this module. Its value ranges
		between 1 and olConcNumSlots."
	::= {ol52nnMMGTTrunkEntry 1}

ol52nnMMGTTrunkIndex OBJECT-TYPE
	SYNTAX INTEGER
	ACCESS read-only
	STATUS mandatory
	DESCRIPTION
		"The slot number of this module. Its value ranges
		between 1 and olModNumTrunks."
	::= {ol52nnMMGTTrunkEntry 2}

ol52nnMMGTTrunkCableMon OBJECT-TYPE
	SYNTAX INTEGER {
		enable(1),
		disable(2),
		notApplicable(3)
		}
	ACCESS read-write
	STATUS mandatory
	DESCRIPTION
		"The cable monitor configuration for this trunk."
	::= {ol52nnMMGTTrunkEntry 3}

ol52nnMMGTTrunkNetMapState OBJECT-TYPE
	SYNTAX INTEGER {
		notApplicable(1),
		internal(2),
		external(3)
		}
	ACCESS read-write
	STATUS mandatory
	DESCRIPTION
		"The map state of the copper ring-in trunk. This
		should be set to external for ring-in trunks which
		connect to external hubs. The mapping logic will not
		operate on trunks which are set to external. This
		prevents incorrect mapping which can occur when a
		module in one hub detects the mapping signal from
		another hub. This attribute only applies to copper
		ring-in trunks."
	::= {ol52nnMMGTTrunkEntry 4}


ol52nnMMGTTrunkExtBcnRecovery OBJECT-TYPE
	SYNTAX INTEGER {
		exists(1),
		nonExists(2),
		notApplicable(3)
	}
	ACCESS read-write
	STATUS mandatory
	DESCRIPTION
		"Indicates whether the trunk is connected to a 
		segment that will perform beacon recovery.  This
		should be set to exists(1) for trunks which connect 
		to hubs which perform beacon recovery.  This attribute 
		is used to determine the fault domain when resolving a 
		beaconing condition.

		The beacon recovery process will resolve beaconing on 
		trunks with this attribute set to nonExists(2) before 
		trunks with the attribute set to exists(1) are resolved.
		For backplane trunks, setting to a value other than 
		notApplicable will return invalidData error.  The 
		default value is nonExists(2)."
	::= { ol52nnMMGTTrunkEntry 5 }



--
-- ONline Ethernet Interconnect Module
--

ol51nnIxModTable OBJECT-TYPE
	SYNTAX SEQUENCE OF Ol51nnIxModEntry
	ACCESS not-accessible
	STATUS mandatory
	DESCRIPTION
		"A table of module-specific information for
		each 51nnI-x module in the concentrator."
	::= { ol51nnIx 1 }

ol51nnIxModEntry OBJECT-TYPE
	SYNTAX Ol51nnIxModEntry
	ACCESS not-accessible
	STATUS mandatory
	DESCRIPTION
		"A list of module-specific information about a specific
		51nnI-x module in the concentrator."
	INDEX { ol51nnIxModSlotIndex }
	::= { ol51nnIxModTable 1 }

Ol51nnIxModEntry ::= 
	SEQUENCE {
		ol51nnIxModSlotIndex
			INTEGER,	
		ol51nnIxModSwType
			INTEGER,
		ol51nnIxModStationAddr
			OCTET STRING,
		ol51nnIxModDipPromDefaults
			INTEGER,
		ol51nnIxModProtocols
			DisplayString
		}

ol51nnIxModSlotIndex OBJECT-TYPE
	SYNTAX INTEGER
	ACCESS read-only
	STATUS mandatory
	DESCRIPTION
		"The slot number of this module."
	::= { ol51nnIxModEntry 1 }

ol51nnIxModSwType OBJECT-TYPE
	SYNTAX INTEGER {
		bridge(1),
		switch(2),
		router(3)
		}
	ACCESS read-only
	STATUS mandatory
	DESCRIPTION
		"The software currently loaded and executing has the
                module operating as a Bridge, Switch or Router."
	::= { ol51nnIxModEntry 2 }

ol51nnIxModStationAddr OBJECT-TYPE
	SYNTAX OCTET STRING (SIZE(6))
	ACCESS read-only
	STATUS mandatory
	DESCRIPTION
		"A 6 octet address that uniquely identifies this module.
		The station address is the mac address of port 1."
	::= { ol51nnIxModEntry 3 }

ol51nnIxModDipPromDefaults OBJECT-TYPE
	SYNTAX INTEGER {
		true(1),
		false(2)
		}
	ACCESS read-only
	STATUS mandatory
	DESCRIPTION
		"The current module configuration with respect to 
		default PROM values as specified by dip switches."
	::= { ol51nnIxModEntry 4 }


ol51nnIxModProtocols OBJECT-TYPE
	SYNTAX DisplayString
	ACCESS read-only
	STATUS mandatory
	DESCRIPTION
		"A textual description of the protocols supported by 
		this module"
	::= { ol51nnIxModEntry 5 }
		
	
ol51nnIxPortTable	OBJECT-TYPE
	SYNTAX SEQUENCE OF Ol51nnIxPortEntry
	ACCESS not-accessible
	STATUS mandatory
	DESCRIPTION
		"A table of port-specific information for each port of
                each 51nnI-x module in the concentrator."
	::= { ol51nnIx 2 }


ol51nnIxPortEntry OBJECT-TYPE
	SYNTAX Ol51nnIxPortEntry
	ACCESS not-accessible
	STATUS mandatory
	DESCRIPTION
		"A list of port-specific information about a specific
		51nnI-x port in the concentrator."
        INDEX { ol51nnIxPortSlotIndex, ol51nnIxPortIndex }
	::= { ol51nnIxPortTable 1 }

Ol51nnIxPortEntry ::= 
	SEQUENCE {
		ol51nnIxPortSlotIndex
			INTEGER,
		ol51nnIxPortIndex
			INTEGER,
		ol51nnIxPortDipAdminState
			INTEGER,
		ol51nnIxPortSTAPState
			INTEGER,
		ol51nnIxPortIpAddress
			IpAddress,
		ol51nnIxPortDipNetwork
			INTEGER,
		ol51nnIxPortDefNetwork
			INTEGER
		}

ol51nnIxPortSlotIndex OBJECT-TYPE
	SYNTAX INTEGER
	ACCESS read-only
	STATUS mandatory
	DESCRIPTION
		"The slot number for this port's module."
	::= { ol51nnIxPortEntry 1 }

ol51nnIxPortIndex OBJECT-TYPE
	SYNTAX INTEGER
	ACCESS read-only
	STATUS mandatory
	DESCRIPTION
		"The port number for this port within this slot."
	::= { ol51nnIxPortEntry 2 }

ol51nnIxPortDipAdminState OBJECT-TYPE
        SYNTAX INTEGER {
                enabled(1),
                disabled(2)
                }
        ACCESS read-only
        STATUS mandatory
        DESCRIPTION
                "The state of this port as indicated by the port's dip
                switches."
        ::= { ol51nnIxPortEntry 3 }
 
ol51nnIxPortSTAPState OBJECT-TYPE
        SYNTAX INTEGER {
                disabled (1),	-- receive and process frames
		blocking (2),	-- receive and process frames 
		listening (3),  -- receive and process frames
		learning (4),	-- receive and process frames
		forwarding (5),	-- receive, process and forward frames
		off (6),	-- receive SNMP frames, others discarded
		unknown(7)      -- not currently reporting STAP state
                }
        ACCESS read-only
        STATUS mandatory
        DESCRIPTION
                "The current IEEE 802.1d Spanning Tree Algorithm and Protocol
		 state (STAP) of this port."
        ::= { ol51nnIxPortEntry 4 }

ol51nnIxPortIpAddress OBJECT-TYPE
	SYNTAX IpAddress
	ACCESS read-only
	STATUS mandatory
	DESCRIPTION
		"The IP Address associated with this port."
	::= { ol51nnIxPortEntry 5 }

ol51nnIxPortDipNetwork OBJECT-TYPE
	SYNTAX INTEGER {
		isolated(2),
		front-panel(5),
		ethernet-1(6),
		ethernet-2(7),
		ethernet-3(8)
		}
	ACCESS read-only
	STATUS mandatory
	DESCRIPTION
		"The network for this port as specified by this port's
		dip switches."
	::= { ol51nnIxPortEntry 6 }

ol51nnIxPortDefNetwork OBJECT-TYPE
	SYNTAX INTEGER {
		isolated(2),
		front-panel(5),
		ethernet-1(6),
		ethernet-2(7),
		ethernet-3(8)
		}
	ACCESS read-only
	STATUS mandatory
	DESCRIPTION
		"The network for this port as specified by the OEIM's
		non-volatile storage."
	::= { ol51nnIxPortEntry 7 }



--
-- FDDI Management Module
--

ol53nnMMGTModTable OBJECT-TYPE
	SYNTAX SEQUENCE OF Ol53nnMMGTModEntry
	ACCESS not-accessible
	STATUS mandatory
	DESCRIPTION
		"A list of module attributes that apply to this model.
		To access an ol53nnMMGTModTable entry, the 
		ol53nnMMGTModSlotIndex attribute is used."
	::= { ol53nnMMGT 1 }

ol53nnMMGTModEntry OBJECT-TYPE
	SYNTAX Ol53nnMMGTModEntry 
	ACCESS not-accessible
	STATUS mandatory
	DESCRIPTION
		"A list of module-specific information about a specific
		53nnM-MGT module in the concentrator."
	INDEX { ol53nnMMGTModSlotIndex }
	::= { ol53nnMMGTModTable 1 }

Ol53nnMMGTModEntry ::=
	SEQUENCE {
		ol53nnMMGTModSlotIndex
			INTEGER,
		ol53nnMMGTModMasterPriority
			INTEGER,
		ol53nnMMGTModMasterStatus
			INTEGER,
		ol53nnMMGTModStationAddr
			OCTET STRING,
		ol53nnMMGTModIpAddress
			IpAddress,
		ol53nnMMGTModDownStreamMAC
			OCTET STRING,
		ol53nnMMGTModUpStreamMAC
			OCTET STRING,
                ol53nnMMGTModfddiMACPath
                        INTEGER,
		ol53nnMMGTModDownStreamModule
			INTEGER,
		ol53nnMMGTModUpStreamModule
			INTEGER,
		ol53nnMMGTModDownStreamOperPath
			INTEGER,
		ol53nnMMGTModUpStreamOperPath
			INTEGER,
		ol53nnMMGTModRingInfo
			OCTET STRING
		}

ol53nnMMGTModSlotIndex OBJECT-TYPE
	SYNTAX INTEGER
	ACCESS read-only
	STATUS mandatory
	DESCRIPTION
		"A unique value that identifies a particular module.  Its
		value ranges between 1 and olModSlotNumber.  The module
		identified by a particular value of this index is the same
		module as indentified by the same value of olModSlotIndex."
	::= { ol53nnMMGTModEntry 1 }

ol53nnMMGTModMasterPriority OBJECT-TYPE
	SYNTAX INTEGER {
		one(1),
		two(2),
		three(3),
		four(4),
		five(5),
		six(6),
		seven(7),
		eight(8),
		nine(9),
		ten(10)
		}
	ACCESS read-write
	STATUS mandatory
	DESCRIPTION
		"The mastership priority of this agent. Ten is the
		highest and one is the lowest. Priority is only
		used when an election occurs. Mastership is not
		preemptive unless the reset mastership command is used."
	::= {ol53nnMMGTModEntry 2 }

ol53nnMMGTModMasterStatus OBJECT-TYPE
	SYNTAX INTEGER {
		master(1),
		non-master(2),
		electing(3)
		}
	ACCESS read-only
	STATUS mandatory
	DESCRIPTION
		"The mastership status of this agent."
	::= {ol53nnMMGTModEntry 3 }

ol53nnMMGTModStationAddr OBJECT-TYPE
	SYNTAX OCTET STRING (SIZE (6))
	ACCESS read-only
	STATUS mandatory
	DESCRIPTION
		"A 6 octet address that uniquely identifies this module.
		The station address is the MAC address of port 1."
	::= {ol53nnMMGTModEntry 4 }

ol53nnMMGTModIpAddress  OBJECT-TYPE
	SYNTAX IpAddress
	ACCESS read-write
	STATUS mandatory
	DESCRIPTION
		"The IP address associated with this module."
	::= {ol53nnMMGTModEntry 5 }

ol53nnMMGTModDownStreamMAC OBJECT-TYPE
	SYNTAX OCTET STRING (SIZE (6))
	ACCESS read-only
	STATUS mandatory
	DESCRIPTION
                "Down stream MAC"
	::= { ol53nnMMGTModEntry 6 }

ol53nnMMGTModUpStreamMAC OBJECT-TYPE
	SYNTAX OCTET STRING (SIZE (6))
	ACCESS read-only
	STATUS mandatory
	DESCRIPTION
                "Up stream MAC"
	::= { ol53nnMMGTModEntry 7 }

ol53nnMMGTModfddiMACPath OBJECT-TYPE
        SYNTAX INTEGER {
                primary(1),
                secondary(2)
                }
        ACCESS read-write
        STATUS mandatory
        DESCRIPTION
                "The FDDI path which should be inserted into the MAC"
        ::= { ol53nnMMGTModEntry 8 }

ol53nnMMGTModDownStreamModule OBJECT-TYPE
	SYNTAX INTEGER (1..16)
	ACCESS read-only
	STATUS mandatory
	DESCRIPTION
                "Down stream slot (transmit to)"
	::= { ol53nnMMGTModEntry 9 }

ol53nnMMGTModUpStreamModule OBJECT-TYPE
	SYNTAX INTEGER (1..16)
	ACCESS read-only
	STATUS mandatory
	DESCRIPTION
                "Up stream slot (receve from)"
	::= { ol53nnMMGTModEntry 10 }

ol53nnMMGTModDownStreamOperPath OBJECT-TYPE
	SYNTAX INTEGER {
                isolated(2),
                fddi-path-1(24),
                fddi-path-2(25),
                fddi-path-3(26),
                fddi-path-4(27),
                fddi-path-5(28),
                fddi-path-6(29),
                fddi-path-7(30),
                fddi-path-8(31)
                }
	ACCESS read-only
	STATUS mandatory
	DESCRIPTION
                "Transmit DBA  (debug only)"
	::= { ol53nnMMGTModEntry 11 }

ol53nnMMGTModUpStreamOperPath OBJECT-TYPE
	SYNTAX INTEGER  {
                isolated(2),
                fddi-path-1(24),
                fddi-path-2(25),
                fddi-path-3(26),
                fddi-path-4(27),
                fddi-path-5(28),
                fddi-path-6(29),
                fddi-path-7(30),
                fddi-path-8(31)
                }
        ACCESS read-only
	STATUS mandatory
	DESCRIPTION
                "Receive DBA (debug only)"
	::= { ol53nnMMGTModEntry 12 }

ol53nnMMGTModRingInfo OBJECT-TYPE
	SYNTAX OCTET STRING (SIZE(1..8))
	ACCESS read-only
	STATUS mandatory
	DESCRIPTION
                "An array which is indexed by DBA number. Each element
                 contains the slot number (1..16) which is assigned to
                 transmit on this DBA. (debug only)"
	::= { ol53nnMMGTModEntry 13 }


-- port table

ol53nnMMGTPortTable OBJECT-TYPE
	SYNTAX SEQUENCE OF Ol53nnMMGTPortEntry
	ACCESS not-accessible
	STATUS mandatory
	DESCRIPTION
		"A table of port-specific information for each port of
		this module type."
	::= { ol53nnMMGT 2 }

ol53nnMMGTPortEntry OBJECT-TYPE
	SYNTAX Ol53nnMMGTPortEntry 
	ACCESS not-accessible
	STATUS mandatory
	DESCRIPTION
		"A list of module-specific information about a specific
		53nnM-MGT port in the concentrator."
	INDEX { ol53nnMMGTPortSlotIndex, ol53nnMMGTPortIndex }
	::= { ol53nnMMGTPortTable 1 }

Ol53nnMMGTPortEntry ::=
	SEQUENCE {
		ol53nnMMGTPortSlotIndex
			INTEGER,			
		ol53nnMMGTPortIndex
			INTEGER,
		ol53nnMMGTPortConfig
			INTEGER,
		ol53nnMMGTPortPcmState
			INTEGER,
		ol53nnMMGTPortConnectState
			INTEGER,
		ol53nnMMGTPortNeighbor
			INTEGER,
		ol53nnMMGTPortRemoteMACIndicated
			INTEGER,
		ol53nnMMGTPortBSFlag
			INTEGER,
		ol53nnMMGTPortPCWithhold
			INTEGER,
		ol53nnMMGTPortLerCondition
			INTEGER
		}

ol53nnMMGTPortSlotIndex OBJECT-TYPE
	SYNTAX INTEGER
	ACCESS read-only
	STATUS mandatory
	DESCRIPTION
		"A unique value that identifies a particular module.  Its
		value ranges between 1 and olModSlotNumber.  The module
		identified by a particular value of this index is the same
		module as indentified by the same value of 
		olPortSlotIndex."
	::= { ol53nnMMGTPortEntry 1 }


ol53nnMMGTPortIndex OBJECT-TYPE
	SYNTAX INTEGER
	ACCESS read-only
	STATUS mandatory
	DESCRIPTION
		"A unique value that identifies a particular port within this
		module. Its value ranges between 1 and olModPortNumber.  
		The module identified by a particular value of this index is 
		the same module as indentified by the same value of 
		olPortIndex."
	::= { ol53nnMMGTPortEntry 2 }

ol53nnMMGTPortConfig OBJECT-TYPE
	SYNTAX INTEGER {
                a(1),
                b(2)
		}
	ACCESS read-only
	STATUS mandatory
	DESCRIPTION
                "Specifies the FDDI port type (a or b)."
	::= { ol53nnMMGTPortEntry 3 }

ol53nnMMGTPortPcmState OBJECT-TYPE
	SYNTAX INTEGER {
                  pc0(1), -- Off
                  pc1(2), -- Break
                  pc2(3), -- Trace
                  pc3(4), -- Connect
                  pc4(5), -- Next
                  pc5(6), -- Signal
                  pc6(7), -- Join
                  pc7(8), -- Verify
                  pc8(9), -- Active
                  pc9(10) -- Maint
	}
	ACCESS read-only
	STATUS mandatory
	DESCRIPTION
                      "(refer to ANSI SMT 9.6.2)."
	::= { ol53nnMMGTPortEntry 4 }

ol53nnMMGTPortConnectState OBJECT-TYPE
	SYNTAX INTEGER {
          disabled(1),
          connecting(2),
          standby(3),
          active(4)
		}
	ACCESS read-only
	STATUS mandatory
	DESCRIPTION
             "An indication of the connect state of this PORT.
              Basically, this gives a higher level view of the
              state of the connection by grouping PCM states and
              the PC-Withhold flag state.  The supported values
              and their corresponding PCM states and PC-Withhold
              condition, when relevant, are:
                  disabled: (PC0:Off, PC9:Maint)
                  connecting: (PC1(Break) || PC3 (Connect) || PC4(next) ||
                               PC5 (Signal) || PC6(Join) || PC7 (Verify)) &&
                              (PC_Withhold = None)
                  standby: (PC_Withhold != None)
                  active: (PC2:Trace || PC8:Active)"
	::= { ol53nnMMGTPortEntry 5 }

ol53nnMMGTPortNeighbor OBJECT-TYPE
	SYNTAX INTEGER {
                a(1),
                b(2),
                slave(3),
                master(4),
                unknown(5)
		}
	ACCESS read-only
	STATUS mandatory
	DESCRIPTION
             "The type (PC_Neighbor) of the remote PORT that is
              determined in PC_Signaling in R_Val (1,2) (refer
              to ANSI SMT 9.6.3.2)."
	::= { ol53nnMMGTPortEntry 6 }

ol53nnMMGTPortRemoteMACIndicated OBJECT-TYPE
	SYNTAX INTEGER { true(1), false(2) }
	ACCESS read-only
	STATUS mandatory
	DESCRIPTION
          "The indication, in PC-Signaling that the remote
           partner intends to place a MAC in the output token
           PATH of this PORT.  Signaled as R_Val (9) (refer
           to ANSI SMT 9.6.3.2)."
	::= { ol53nnMMGTPortEntry 7 }

ol53nnMMGTPortBSFlag OBJECT-TYPE
	SYNTAX INTEGER { true(1), false(2) }
	ACCESS read-only
	STATUS mandatory
	DESCRIPTION
          "The Break State, BS_Flag (refer to ANSI SMT
           9.4.3.4)."
	::= { ol53nnMMGTPortEntry 8 }

ol53nnMMGTPortPCWithhold OBJECT-TYPE
	SYNTAX INTEGER  { none(1), m-m(2), other(3) }
	ACCESS read-only
	STATUS mandatory
	DESCRIPTION
           "PC_Withhold, (refer to ANSI SMT 9.4.1)."
	::= { ol53nnMMGTPortEntry 9 }

ol53nnMMGTPortLerCondition OBJECT-TYPE
	SYNTAX INTEGER  { bad(1), okay(2) }
	ACCESS read-only
	STATUS mandatory
	DESCRIPTION
           "This variable is set to true whenever LerEstimate
            is less than or equal to LerAlarm (the larger the number
            the smaller the value)."
	::= { ol53nnMMGTPortEntry 10 }


-- Trunk Table
-- (only present for compatibility)

ol53nnMMGTTrunkTable OBJECT-TYPE
	SYNTAX SEQUENCE OF Ol53nnMMGTTrunkEntry
	ACCESS not-accessible
	STATUS mandatory
	DESCRIPTION
                "FDDI module specific trunk table variables.
                 At present there are none."
	::= { ol53nnMMGT 3 }

ol53nnMMGTTrunkEntry OBJECT-TYPE
	SYNTAX Ol53nnMMGTTrunkEntry
	ACCESS not-accessible
	STATUS mandatory
	DESCRIPTION
		"A description of 53nnM-MGT trunk attributes."		
	INDEX { ol53nnMMGTTrunkSlotIndex, ol53nnMMGTTrunkIndex }
	::= { ol53nnMMGTTrunkTable 1 }

Ol53nnMMGTTrunkEntry ::= 
	SEQUENCE {
		ol53nnMMGTTrunkSlotIndex	
			INTEGER,
		ol53nnMMGTTrunkIndex
			INTEGER
		}

ol53nnMMGTTrunkSlotIndex OBJECT-TYPE
	SYNTAX INTEGER
	ACCESS read-only
	STATUS mandatory
	DESCRIPTION
		"A unique value that identifies a particular module.  Its
		value ranges between 1 and olModSlotNumber.  The module
		identified by a particular value of this index is the same
		module as indentified by the same value of 
		olTrunkSlotIndex."
	::= { ol53nnMMGTTrunkEntry 1 }


ol53nnMMGTTrunkIndex OBJECT-TYPE
	SYNTAX INTEGER
	ACCESS read-only
	STATUS mandatory
	DESCRIPTION
		"A unique value that identifies a particular trunk within this
		module. Its value ranges between 1 and olModTrunkNumber.  
		The module identified by a particular value of this index is 
		the same module as indentified by the same value of 
		olTrunkIndex."
	::= { ol53nnMMGTTrunkEntry 2 }



--
-- ONline Hidden Controller Module
--

ol50nnMHCTLModTable OBJECT-TYPE
	SYNTAX SEQUENCE OF Ol50nnMHCTLModEntry
	ACCESS not-accessible
	STATUS mandatory
	DESCRIPTION
		"A table that contains information about each 50nnM-HCTL
		in the concentrator.  "
	::= { ol50nnMHCTL 1 }

ol50nnMHCTLModEntry OBJECT-TYPE
	SYNTAX Ol50nnMHCTLModEntry
	ACCESS not-accessible
	STATUS mandatory
	DESCRIPTION
		"A list of information for each 50nnM-HCTL module
		in the concentrator."
	INDEX { ol50nnMHCTLModSlotIndex }
	::= { ol50nnMHCTLModTable 1 }

Ol50nnMHCTLModEntry ::= 
	SEQUENCE {
		ol50nnMHCTLModSlotIndex
			INTEGER,
		ol50nnMHCTLModOperState
			INTEGER,
		ol50nnMHCTLModClockStatus
			INTEGER,
		ol50nnMHCTLModTempStatus
			INTEGER,
		ol50nnMHCTLModPDBStatus
			INTEGER,
		ol50nnMHCTLModDipCh1ActCol
			INTEGER,
		ol50nnMHCTLModDipCh2ActCol
			INTEGER,
		ol50nnMHCTLModDipCh3ActCol
			INTEGER
		}

ol50nnMHCTLModSlotIndex OBJECT-TYPE
	SYNTAX INTEGER
	ACCESS read-only
	STATUS mandatory
	DESCRIPTION
		"The slot number for this module.  The value should be 7."
	::= { ol50nnMHCTLModEntry 1 }

ol50nnMHCTLModOperState OBJECT-TYPE
	SYNTAX INTEGER {
		active(1),
		standby(2)
		}
	ACCESS read-only
	STATUS mandatory
	DESCRIPTION
		"The operational state of the 50nnM-HCTL module.  Specifically,
		this is an indicator of whether the 50nnM-HCTL module is
		providing clock signals to the backplane.  An active 50nnM-HCTL
		module provides clock signals to the backplane while a standby 
		50nnM-HCTL module does not.  Note that only one 50nnM-HCTL
		module will be active at any given time; all other 50nnM-HCTL/
		50nnMRCTL modules in the concentrator will be in standby mode."
	::= { ol50nnMHCTLModEntry 2 }

ol50nnMHCTLModClockStatus OBJECT-TYPE
	SYNTAX INTEGER {
		okay(1),
		faulty(2)
		}
	ACCESS read-only
	STATUS mandatory
	DESCRIPTION
		"The current status of the on-board clocks on this module."
	::= { ol50nnMHCTLModEntry 3 }

ol50nnMHCTLModTempStatus OBJECT-TYPE
	SYNTAX INTEGER {
		okay(1),
		extremeTemp(2)
		}
	ACCESS read-only
	STATUS mandatory
	DESCRIPTION
		"The temperature as detected by the probe on this module."
	::= { ol50nnMHCTLModEntry 4 }

ol50nnMHCTLModPDBStatus OBJECT-TYPE
	SYNTAX INTEGER {
		present(1),
		notPresent(2)
		}
	ACCESS read-only
	STATUS mandatory
	DESCRIPTION
		"Indicates whether this 6-slot concentrator contains a power
		distribution board that supports powersupply redundancy."
	::= { ol50nnMHCTLModEntry 5 }

ol50nnMHCTLModDipCh1ActCol OBJECT-TYPE
	SYNTAX INTEGER {
		enabled(1),
		disabled(2)
		}
	ACCESS read-only
	STATUS mandatory
	DESCRIPTION
		"The Ethernet channel 1 activity/collision LED configuration
		as indicated by this module's dip switches."
	::= { ol50nnMHCTLModEntry 6 }

ol50nnMHCTLModDipCh2ActCol OBJECT-TYPE
	SYNTAX INTEGER {
		enabled(1),
		disabled(2)
		}
	ACCESS read-only
	STATUS mandatory
	DESCRIPTION
		"The Ethernet channel 2 activity/collision LED configuration
		as indicated by this module's dip switches."
	::= { ol50nnMHCTLModEntry 7 }

ol50nnMHCTLModDipCh3ActCol OBJECT-TYPE
	SYNTAX INTEGER {
		enabled(1),
		disabled(2)
		}
	ACCESS read-only
	STATUS mandatory
	DESCRIPTION
		"The Ethernet channel 3 activity/collision LED configuration
		as indicated by this module's dip switches."
	::= { ol50nnMHCTLModEntry 8 }























--
-- olModSummary
--
-- This group was designed to enhance the performance of retrievals of 
-- module related information.  It is specifically targeted for use by
-- closely designed management applications.  It is NOT designed for use 
-- by off the shelf applications and is documented here only for completeness.
-- 
-- The summary group encodes the module information into an octet string
-- that includes the values of each object in the module, port and trunk
-- tables.  This allows fast retrieval of a large amount of information
-- within no more that 17 Get operations, rather than utilizing 17 operations
-- (max) for the modules, and 17 x Number of Ports (max) for the port 
-- information, and 17 x Number of Trunks (max) for the trunk information.
--
-- Users should be aware that this table requires the application to 
-- parse out information and therefore, applications should be sensitive to 
-- the positioning of information within the summary string.
--



olModSummaryTable OBJECT-TYPE
	SYNTAX SEQUENCE OF OlModSummaryEntry
	ACCESS not-accessible
	STATUS mandatory
	DESCRIPTION
		"A table of condensed module information."
	::= { olModules 5 }

olModSummaryEntry OBJECT-TYPE
	SYNTAX OlModSummaryEntry
	ACCESS not-accessible
	STATUS mandatory
	DESCRIPTION
		"A summary of all the generic and value added information
		associated with this module."
	INDEX { olModSummarySlotIndex }
	::= { olModSummaryTable 1 }

OlModSummaryEntry ::= 
	SEQUENCE {
		olModSummarySlotIndex
			INTEGER,
		olModSummaryInfo
			OCTET STRING
		}

olModSummarySlotIndex OBJECT-TYPE
	SYNTAX INTEGER
	ACCESS read-only
	STATUS mandatory
	DESCRIPTION
		"The slot number of this module that this summary
		pertains to."
	::= { olModSummaryEntry 1 }

olModSummaryInfo OBJECT-TYPE
	SYNTAX OCTET STRING (SIZE(0..512))
	ACCESS read-only
	STATUS mandatory
	DESCRIPTION
		"A summary of all information relating to this module in 
		condensed format.  The condensed format is only as large
		as needed to hence the largest value which usually is one
		octet.  The TCP port for the terminal server, however,
		uses 4 octets.

		The summary consists of a header, a module portion, a port
		portion, and a trunk portion.  Each portion consists of 
		generic information and module specific information. 
		For example, the module information consists of the 
		olModTable entry for this slot and the olSpecMods module
		table information for this module type for this slot.


		---------------------------------------------------
		The header consists of the following octets:
			Version of structure : 1

			Number of octets in generic module 
			Number of octets in specific module
			Number of octets in generic port
			Number of octets in specific port
			Number of octets in generic trunk
			Number of octets in specific trunk

		The format of the data portion is as follows:
		
			Some of the olModTable:
				olModType
				olModClass
				olModDescr
				olModVersion
				olModNetwork
				olModNetworkType
				olModStatus

				olModNumPorts
				olModNumTrunks

			olSpecMods module table (for this module)
				Not including slot number.

		For each port:
			Some of the olPortTable:
				olPortType
				olPortConnector
				olPortStatus  
				olPortAdminState
				olPortNetwork
				olPortNetworkType
	
			olSpecMods port table (for this port's module)
				Not including slot and port number.

		For each trunk:
			Some of the olTrunkTable:
				olTrunkType
				olTrunkConnector
				olTrunkStatus
				olTrunkAdminState
				olTrunkWrapState
				olTrunkNeighbor

			olSpecMods trunk table (for this trunk's module)
				Not including slot and trunk number.



		In all of the above, the index for all of these tables
		is condensed out of the summary. "
	::= { olModSummaryEntry 2 }



-- The olNet Group

-- This group represents information about ONline networks in general.

olNetDPTable OBJECT-TYPE
	SYNTAX SEQUENCE OF OlNetDPEntry
	ACCESS not-accessible
	STATUS mandatory
	DESCRIPTION
		"A table that contains information linking 
		physical backplane allocation to logical
		networks. This information is useful:

			(1) to determine the physical allocation 
			of networks on the backplane, and 

			(2) to determine the remaining capacity of
			the backplane for future network growth.
	
		Since unknown modules are managed via dip
		switches, this is useful in order to set the
		dips to the appropriate settings.

		Ethernet is a bus architecture.  Once a path is
		allocated, all modules and ports can access that
		path.

		Token Ring and FDDI are ring architectures.  
		Each module on a ring requires a path.  Therefore,
		4 paths could be used to link 4 modules together
		on one ring, or 2 modules on 2 separate rings.
		It is possible to have a module allocated to 
		a ring (and thus a data path) without linking
		to another module.  

		These rules can be used to determine the remaining
		capacity for network growth."
	::= { olNet 1 }

olNetDPEntry OBJECT-TYPE
	SYNTAX OlNetDPEntry
	ACCESS not-accessible
	STATUS mandatory
	DESCRIPTION
		"A list of information about each data path in the
		concentrator."
	INDEX { olNetDPDataPath }
	::= { olNetDPTable 1 }

OlNetDPEntry ::= 
	SEQUENCE {
		olNetDPDataPath
			INTEGER,
		olNetDPNetID
			INTEGER
		}

olNetDPDataPath OBJECT-TYPE
	SYNTAX INTEGER {
		ethernet-path-1(6), -- channel 1
		ethernet-path-2(7), -- channel 2
		ethernet-path-3(8), -- channel 3
		token-ring-path-1(9),
		token-ring-path-2(10),
		token-ring-path-3(11),
		token-ring-path-4(12),
		token-ring-path-5(13),
		token-ring-path-6(14),
		token-ring-path-7(15),
		token-ring-path-8(16),
		token-ring-path-9(17),
		token-ring-path-10(18),
		token-ring-path-11(19),
		token-ring-path-12(20),
		token-ring-path-13(21),
		token-ring-path-14(22),
		token-ring-path-15(23),
		fddi-path-1(24),		
		fddi-path-2(25),		
		fddi-path-3(26),		
		fddi-path-4(27),		
		fddi-path-5(28),		
		fddi-path-6(29),		
		fddi-path-7(30),		
		fddi-path-8(31)
		}
	ACCESS read-only
	STATUS mandatory
	DESCRIPTION
		"The data path on the backplane.  Data paths between
		different protocols overlap.  That is, an ethernet data
		path will overlap with multiple token ring and fddi data
		paths. "
	::= { olNetDPEntry 1 }

olNetDPNetID OBJECT-TYPE
	SYNTAX INTEGER {
		notUsed(1),		-- available for use
		otherProto(2),		-- another protocol is using
					-- these resources
		ethernet-1(6),		
		ethernet-2(7),
		ethernet-3(8),
		token-ring-1(9),
		token-ring-2(10),
		token-ring-3(11),
		token-ring-4(12),
		token-ring-5(13),
		token-ring-6(14),
		token-ring-7(15),
		fddi-1(16),
		fddi-2(17),
		fddi-3(18),
		fddi-4(19)
		}
	ACCESS	read-only
	STATUS mandatory
	DESCRIPTION
		"The network that this data path corresponds to.  
		If the data path is not being used at all, notUsed(1)
		is the return value.  If the data path is being used
		by another protocol, then otherProto(2) is the
		return value."
	::= { olNetDPEntry 2 }


--
-- The following objects comprise the oldest style of security.
-- They are left here for backward compatibility with existing
-- applications; however, this group will not be enhanced.
--
olNetSecurityMACTable OBJECT-TYPE
	SYNTAX SEQUENCE OF OlNetSecurityMACEntry
	ACCESS not-accessible
	STATUS mandatory
	DESCRIPTION
		"A table of security configuration parameters and MAC
		addresses associated with every port with security
		configured in the concentrator."
	::= { olNet 2 }

olNetSecurityMACEntry OBJECT-TYPE
	SYNTAX OlNetSecurityMACEntry
	ACCESS not-accessible
	STATUS mandatory
	DESCRIPTION
		"A list of security configuration parameters and MAC
		addresses associated with each port with security
		configured in the concentrator."
	INDEX { olNetSecurityMACSlotIndex, olNetSecurityMACPortIndex,
		olNetSecurityMACAddress }
	::= { olNetSecurityMACTable 1 }

OlNetSecurityMACEntry ::=
	SEQUENCE {
		olNetSecurityMACSlotIndex
			INTEGER,
		olNetSecurityMACPortIndex
			INTEGER,
		olNetSecurityMACAddress
		  	MacAddress,
		olNetSecurityMACMode
			INTEGER,
		olNetSecurityMACStatus
			INTEGER
		 }

olNetSecurityMACSlotIndex OBJECT-TYPE
	 SYNTAX INTEGER
	 ACCESS read-only
	 STATUS mandatory
	 DESCRIPTION
		 "The slot number that contains this port."
	 ::= { olNetSecurityMACEntry 1 }

olNetSecurityMACPortIndex OBJECT-TYPE
	 SYNTAX INTEGER
	 ACCESS read-only
	 STATUS mandatory
	 DESCRIPTION
		 "The port number within this slot."
	 ::= { olNetSecurityMACEntry 2 }

olNetSecurityMACAddress OBJECT-TYPE
	 SYNTAX MacAddress
	 ACCESS read-write
	 STATUS mandatory
	 DESCRIPTION
		 "The security MAC address assigned to this port."
	 ::= { olNetSecurityMACEntry 3 }

olNetSecurityMACMode OBJECT-TYPE
	SYNTAX INTEGER {
		enabled(1),
		disabled(2)
		}
	ACCESS read-write
	STATUS mandatory
	DESCRIPTION
		"The desired security mode for this port/address."
--	DEFVAL {disabled(2)}
	::= { olNetSecurityMACEntry 4 }

olNetSecurityMACStatus OBJECT-TYPE
	SYNTAX INTEGER {
		valid(1),
		invalid(2)
		}
	ACCESS read-write
	STATUS mandatory
	DESCRIPTION
		"Each instance of the olNetSecurityMACTable associated
		with this olNetSecurityMACEntry (slot, port, and address)
		will be deleted by the agent if this olNetSecurityMACEntry
		is not equal to valid(1).  Initial creation of instances
		occurs via a set operation on a specific slot/port/address."
--	DEFVAL {valid(1)}
	::= { olNetSecurityMACEntry 5 }









-- The olEnet Group

-- This group represents information about Ethernet networks.

olEnetStatsTable OBJECT-TYPE
	SYNTAX SEQUENCE OF OlEnetStatsEntry
	ACCESS not-accessible
	STATUS mandatory
	DESCRIPTION
		"A table that contains statistical information about
		Ethernet (IEEE 802.3) networks."
	::= { olEnet 1 }

olEnetStatsEntry OBJECT-TYPE
	SYNTAX OlEnetStatsEntry
	ACCESS not-accessible
	STATUS mandatory
	DESCRIPTION
		"A list of statistical information about each Ethernet
		(IEEE 802.3) network in the concentrator."
	INDEX { olEnetStatsNetID }
	::= { olEnetStatsTable 1 }

OlEnetStatsEntry ::=
	SEQUENCE {
		olEnetStatsNetID
			INTEGER,
		olEnetStatsFramesRcvdOks
			Counter,
		olEnetStatsOctetsRcvdOks
			Counter,
		olEnetStatsMcastRcvdOks
			Counter,
		olEnetStatsBcastRcvdOks
			Counter,
		olEnetStatsFrameTooLongs
			Counter,
		olEnetStatsAlignmentErrors
			Counter,
		olEnetStatsFCSErrors
			Counter,
		olEnetStatsRunts
			Counter,
		olEnetStatsLocalColls
			Counter
		}

olEnetStatsNetID OBJECT-TYPE
	SYNTAX INTEGER {
		ethernet-1(6), -- corresponds to ifIndex
		ethernet-2(7),
		ethernet-3(8)
		}
	ACCESS read-only
	STATUS mandatory
	DESCRIPTION
		"The network index that uniquely identifies this network.
		One of ethernet-1, ethernet-2, or ethernet-3."
	::= { olEnetStatsEntry 1 }

olEnetStatsFramesRcvdOks OBJECT-TYPE
	SYNTAX Counter
	ACCESS read-only
	STATUS mandatory
	DESCRIPTION
		"The count of frames that were successfully received by this
		network.  This counter does not include frames received 
		in error."
	::= { olEnetStatsEntry 2 }

olEnetStatsOctetsRcvdOks OBJECT-TYPE
	SYNTAX Counter
	ACCESS read-only
	STATUS mandatory
	DESCRIPTION
		"The count of the number of octets that were successfully 
		received by this network.  This counter does not include 
		octets that were part of frames that were received in error."
	::= { olEnetStatsEntry 3 }

olEnetStatsMcastRcvdOks OBJECT-TYPE
	SYNTAX Counter
	ACCESS read-only
	STATUS mandatory
	DESCRIPTION
		"The count of the number of multicast frames successfully
		received by this network."
	::= { olEnetStatsEntry 4 }

olEnetStatsBcastRcvdOks OBJECT-TYPE
	SYNTAX Counter
	ACCESS read-only
	STATUS mandatory
	DESCRIPTION
		"The count of the number of broadcast frames successfully
		received by this network."
	::= { olEnetStatsEntry 5 }

olEnetStatsFrameTooLongs OBJECT-TYPE
	SYNTAX Counter
	ACCESS read-only
	STATUS mandatory
	DESCRIPTION
		"The count of the number of frames received by this network
		that exceeds the maximum permitted Ethernet (802.3) frame
		size."
	::= { olEnetStatsEntry 6 }

olEnetStatsAlignmentErrors OBJECT-TYPE
	SYNTAX Counter
	ACCESS read-only
	STATUS mandatory
	DESCRIPTION
		"The count of the number of frames received by this network
		that did not pass the frame check sequence (FCS) check
		and that are not an integral number of octets.  These
		frames are not counted in olEnetStatsFCSErrors."
	::= { olEnetStatsEntry 7 }

olEnetStatsFCSErrors OBJECT-TYPE
	SYNTAX Counter
	ACCESS read-only
	STATUS mandatory
	DESCRIPTION
		"The count of the number of frames received by this network
		that did not pass the frame check sequence (FCS) check
		and are an integral number of octets."
	::= { olEnetStatsEntry 8 }

olEnetStatsRunts OBJECT-TYPE
	SYNTAX Counter
	ACCESS read-only
	STATUS mandatory
	DESCRIPTION
		"The count of the number of frames received by this network
		 that are less than 512 bits long.  "
	::= { olEnetStatsEntry 9 }

olEnetStatsLocalColls OBJECT-TYPE
	SYNTAX Counter
	ACCESS read-only
	STATUS mandatory
	DESCRIPTION
		"The count of the number of times that two or more ports 
		within this concentrator have received traffic simultaneously."
	::= { olEnetStatsEntry 10 }




olEnetStatsModTable OBJECT-TYPE
	SYNTAX SEQUENCE OF OlEnetStatsModEntry
	ACCESS not-accessible
	STATUS mandatory
	DESCRIPTION
		"A table of statistical information counted for each module
		in each Ethernet (IEEE 802.3) network."
	::= { olEnet 2 }

olEnetStatsModEntry OBJECT-TYPE
	SYNTAX OlEnetStatsModEntry
	ACCESS not-accessible
	STATUS mandatory
	DESCRIPTION
		"A list of statistical information for each port
		on each Ethernet (IEEE 802.3) network in the concentrator."
	INDEX { olEnetStatsModNetID, olEnetStatsModSlotIndex }
	::= { olEnetStatsModTable 1 }

OlEnetStatsModEntry ::=
	SEQUENCE {
		olEnetStatsModNetID
			INTEGER,
		olEnetStatsModSlotIndex
			INTEGER,
		olEnetStatsModFramesRcvdOks
			Counter,
		olEnetStatsModOctetsRcvdOks
			Counter,
		olEnetStatsModMcastRcvdOks
			Counter,
		olEnetStatsModBcastRcvdOks
			Counter,
		olEnetStatsModFrameTooLongs
			Counter,
		olEnetStatsModAlignmentErrors
			Counter,
		olEnetStatsModFCSErrors
			Counter,
		olEnetStatsModRunts
			Counter
		}

olEnetStatsModNetID OBJECT-TYPE
	SYNTAX INTEGER {
		ethernet-1(6), -- corresponds to ifIndex
		ethernet-2(7),
		ethernet-3(8)
		}
	ACCESS read-only
	STATUS mandatory
	DESCRIPTION
		"The unique identifier for this network.  
		One of ethernet-1, ethernet-2, or ethernet-3."
	::= { olEnetStatsModEntry 1 }

olEnetStatsModSlotIndex OBJECT-TYPE
	SYNTAX INTEGER
	ACCESS read-only
	STATUS mandatory
	DESCRIPTION
		"The slot number that contains this module."
	::= { olEnetStatsModEntry 2 }

olEnetStatsModFramesRcvdOks OBJECT-TYPE
	SYNTAX Counter
	ACCESS read-only
	STATUS mandatory
	DESCRIPTION
		"The count of frames that were successfully received by this
		module.  This counter does not include frames received in 
		error."
	::= { olEnetStatsModEntry 3 }

olEnetStatsModOctetsRcvdOks OBJECT-TYPE
	SYNTAX Counter
	ACCESS read-only
	STATUS mandatory
	DESCRIPTION
		"The count of the number of octets that were successfully 
		received by this module.  This counter does not include 
		octets that were part of frames that were received in error."
	::= { olEnetStatsModEntry 4 }

olEnetStatsModMcastRcvdOks OBJECT-TYPE
	SYNTAX Counter
	ACCESS read-only
	STATUS mandatory
	DESCRIPTION
		"The count of the number of multicast frames successfully
		received by this module."
	::= { olEnetStatsModEntry 5 }

olEnetStatsModBcastRcvdOks OBJECT-TYPE
	SYNTAX Counter
	ACCESS read-only
	STATUS mandatory
	DESCRIPTION
		"The count of the number of broadcast frames successfully
		received by this module."
	::= { olEnetStatsModEntry 6 }

olEnetStatsModFrameTooLongs OBJECT-TYPE
	SYNTAX Counter
	ACCESS read-only
	STATUS mandatory
	DESCRIPTION
		"The count of the number of frames received by this module
		that exceeds the maximum permitted Ethernet (802.3) frame
		size."
	::= { olEnetStatsModEntry 7 }

olEnetStatsModAlignmentErrors OBJECT-TYPE
	SYNTAX Counter
	ACCESS read-only
	STATUS mandatory
	DESCRIPTION
		"The count of the number of frames received by this module
		that did not pass the frame check sequence (FCS) check
		and that are not an integral number of octets.  These
		frames are not counted in olEnetStatsModFCSErrors."
	::= { olEnetStatsModEntry 8 }

olEnetStatsModFCSErrors OBJECT-TYPE
	SYNTAX Counter
	ACCESS read-only
	STATUS mandatory
	DESCRIPTION
		"The count of the number of frames received by this module
		that did not pass the frame check sequence (FCS) check
		and are an integral number of octets."
	::= { olEnetStatsModEntry 9 }

olEnetStatsModRunts OBJECT-TYPE
	SYNTAX Counter
	ACCESS read-only
	STATUS mandatory
	DESCRIPTION
		"The count of the number of frames received by 
		this module that are less than 512 bits long.  "
	::= { olEnetStatsModEntry 10 }



olEnetStatsPortTable OBJECT-TYPE
	SYNTAX SEQUENCE OF OlEnetStatsPortEntry
	ACCESS not-accessible
	STATUS mandatory
	DESCRIPTION
		"A table of statistical information counted for each port
		in each Ethernet (IEEE 802.3) network."
	::= { olEnet 3 }

olEnetStatsPortEntry OBJECT-TYPE
	SYNTAX OlEnetStatsPortEntry
	ACCESS not-accessible
	STATUS mandatory
	DESCRIPTION
		"A list of statistical information for each port
		on each Ethernet (IEEE 802.3) network in the concentrator."
	INDEX { olEnetStatsPortSlotIndex, olEnetStatsPortIndex }
	::= { olEnetStatsPortTable 1 }

OlEnetStatsPortEntry ::=
	SEQUENCE {
		olEnetStatsPortNetID
			INTEGER,
		olEnetStatsPortSlotIndex
			INTEGER,
		olEnetStatsPortIndex
			INTEGER,
		olEnetStatsPortFramesRcvdOks
			Counter,
		olEnetStatsPortOctetsRcvdOks
			Counter,
		olEnetStatsPortMcastRcvdOks
			 Counter,
		 olEnetStatsPortBcastRcvdOks
			 Counter,
		 olEnetStatsPortFrameTooLongs
			 Counter,
		 olEnetStatsPortAlignmentErrors
			 Counter,
		 olEnetStatsPortFCSErrors
			 Counter,
		 olEnetStatsPortRunts
			 Counter,
		 olEnetStatsPortSrcAddrChanges
			 Counter,
		 olEnetStatsPortLastSrcAddr
			 OCTET STRING (SIZE(6)),
		 olEnetStatsPortLastErrAddr
			 OCTET STRING (SIZE(6))
		 }

olEnetStatsPortNetID OBJECT-TYPE
	 SYNTAX INTEGER {
		 ethernet-1(6), -- corresponds to ifIndex
		 ethernet-2(7),
		 ethernet-3(8)
		 }
	 ACCESS read-only
	 STATUS mandatory
	 DESCRIPTION
		 "The unique identifier for this network.  
		 One of ethernet-1, ethernet-2, or ethernet-3."
	 ::= { olEnetStatsPortEntry 1 }

olEnetStatsPortSlotIndex OBJECT-TYPE
	 SYNTAX INTEGER
	 ACCESS read-only
	 STATUS mandatory
	 DESCRIPTION
		 "The slot number that contains this port."
	 ::= { olEnetStatsPortEntry 2 }

olEnetStatsPortIndex OBJECT-TYPE
	 SYNTAX INTEGER
	 ACCESS read-only
	 STATUS mandatory
	 DESCRIPTION
		 "The port number within this slot."
	 ::= { olEnetStatsPortEntry 3 }

olEnetStatsPortFramesRcvdOks OBJECT-TYPE
	 SYNTAX Counter
	 ACCESS read-only
	 STATUS mandatory
	 DESCRIPTION
		 "The count of frames that were successfully received by this
		 port.  This counter does not include frames received in error."
	 ::= { olEnetStatsPortEntry 4 }

olEnetStatsPortOctetsRcvdOks OBJECT-TYPE
	 SYNTAX Counter
	 ACCESS read-only
	 STATUS mandatory
	 DESCRIPTION
		 "The count of the number of octets that were successfully 
		 received by this port.  This counter does not include 
		 octets that were part of frames that were received in error."
	 ::= { olEnetStatsPortEntry 5 }

olEnetStatsPortMcastRcvdOks OBJECT-TYPE
	 SYNTAX Counter
	 ACCESS read-only
	 STATUS mandatory
	 DESCRIPTION
		 "The count of the number of multicast frames successfully
		 received by this port."
	 ::= { olEnetStatsPortEntry 6 }

olEnetStatsPortBcastRcvdOks OBJECT-TYPE
	 SYNTAX Counter
	 ACCESS read-only
	 STATUS mandatory
	 DESCRIPTION
		 "The count of the number of broadcast frames successfully
		 received by this port."
	 ::= { olEnetStatsPortEntry 7 }

olEnetStatsPortFrameTooLongs OBJECT-TYPE
	 SYNTAX Counter
	 ACCESS read-only
	 STATUS mandatory
	 DESCRIPTION
		 "The count of the number of frames received by this port
		 that exceeds the maximum permitted Ethernet (802.3) frame
		 size."
	 ::= { olEnetStatsPortEntry 8 }

olEnetStatsPortAlignmentErrors OBJECT-TYPE
	 SYNTAX Counter
	 ACCESS read-only
	 STATUS mandatory
	 DESCRIPTION
		 "The count of the number of frames received by this port
		 that did not pass the frame check sequence (FCS) check
		 and that are not an integral number of octets.  These
		 frames are not counted in olEnetStatsPortFCSErrors."
	 ::= { olEnetStatsPortEntry 9 }

olEnetStatsPortFCSErrors OBJECT-TYPE
	 SYNTAX Counter
	 ACCESS read-only
	 STATUS mandatory
	 DESCRIPTION
		 "The count of the number of frames received by this port
		 that did not pass the frame check sequence (FCS) check
		 and are an integral number of octets."
	 ::= { olEnetStatsPortEntry 10 }

olEnetStatsPortRunts OBJECT-TYPE
	 SYNTAX Counter
	 ACCESS read-only
	 STATUS mandatory
	 DESCRIPTION
		 "The count of the number of frames received by this port that
		 are less than 512 bits long.  "
	 ::= { olEnetStatsPortEntry 11 }


olEnetStatsPortSrcAddrChanges OBJECT-TYPE
	 SYNTAX Counter
	 ACCESS read-only
	 STATUS mandatory
	 DESCRIPTION
		 "The count of the number of times that 
		 olEnetStatsPortLastSourceAddr 
		{ olEnetStatsPortEntry 11 } has changed."
	 ::= { olEnetStatsPortEntry 12 }

olEnetStatsPortLastSrcAddr OBJECT-TYPE
	 SYNTAX OCTET STRING (SIZE(6))
	 ACCESS read-only
	 STATUS mandatory
	 DESCRIPTION
		 "The last source address seen on this port for this
		 network for the last successfully received frame."
	 ::= { olEnetStatsPortEntry 13 }

olEnetStatsPortLastErrAddr OBJECT-TYPE
	 SYNTAX OCTET STRING (SIZE(6))
	 ACCESS read-only
	 STATUS mandatory
	 DESCRIPTION
		 "The value stored in the source address portion of
		 a frame received in error (alignment, FCS, or too long).
		 Since the frame was received in error, there is no
		 guarantee that this is an actual valid address."
	 ::= { olEnetStatsPortEntry 14 }

olEnetMapTable OBJECT-TYPE
	 SYNTAX SEQUENCE OF OlEnetMapEntry
	 ACCESS not-accessible
	 STATUS mandatory
	 DESCRIPTION
		 "A table that contains a cache of information relating
		 an Ethernet source address with a specific port for
		 a given network.  An indication of this source's utilization
		 of the network is also provided."
	 ::= { olEnet 4 }

olEnetMapEntry OBJECT-TYPE
	 SYNTAX OlEnetMapEntry
	 ACCESS not-accessible
	 STATUS mandatory
	 DESCRIPTION
		 "A list of information that tracks a source address to
		 a specific port for each network."
	 INDEX { olEnetMapNetID, olEnetMapAddress }
	 ::= { olEnetMapTable 1 }

OlEnetMapEntry ::= 
	 SEQUENCE {
		 olEnetMapNetID
			 INTEGER,
		 olEnetMapAddress
			 OCTET STRING,
		 olEnetMapSlotIndex
			 INTEGER,
		 olEnetMapPortIndex
			 INTEGER,
		 olEnetMapFrames
			 Counter,
		 olEnetMapOctets
			 Counter,
		 olEnetMapTime		
			 TimeTicks
		 }

olEnetMapNetID OBJECT-TYPE
	 SYNTAX INTEGER {
		 ethernet-1(6),  -- corresponds to ifIndex
		 ethernet-2(7),
		 ethernet-3(8)
		 }	
	 ACCESS read-only
	 STATUS mandatory
	 DESCRIPTION
		 "The network index that uniquely identifies this network.
		 One of ethernet-1, ethernet-2, ethernet-3."
	 ::= { olEnetMapEntry 1 }

olEnetMapAddress OBJECT-TYPE
	 SYNTAX OCTET STRING (SIZE(6))
	 ACCESS read-only
	 STATUS mandatory
	 DESCRIPTION
		 "An Ethernet source address received by this port on this
		 network."
	 ::= { olEnetMapEntry 2 }

olEnetMapSlotIndex OBJECT-TYPE
	 SYNTAX INTEGER
	 ACCESS read-only
	 STATUS mandatory
	 DESCRIPTION
		 "The slot number of the port that received this address."
	 ::= { olEnetMapEntry 3 }


olEnetMapPortIndex OBJECT-TYPE
	 SYNTAX INTEGER
	 ACCESS read-only
	 STATUS mandatory
	 DESCRIPTION
		 "The port number within olEnetMapSlotIndex's slot that
		 received this address."
	 ::= { olEnetMapEntry 4 }

olEnetMapFrames OBJECT-TYPE
	 SYNTAX Counter
	 ACCESS read-only
	 STATUS mandatory
	 DESCRIPTION
		 "An estimated count of the number of frames generated by this
		 address.  This count should be interpreted as an
		 indicator, not a true frame count."
	 ::= { olEnetMapEntry 5 }

olEnetMapOctets OBJECT-TYPE
	 SYNTAX Counter
	 ACCESS read-only
	 STATUS mandatory
	 DESCRIPTION
		 "An estimated count of the number of octets generated by this
		 address.  This count should be interpreted as an
		 indicator, not a true octet count."
	 ::= { olEnetMapEntry 6 }

olEnetMapTime OBJECT-TYPE
	 SYNTAX TimeTicks
	 ACCESS read-only
	 STATUS mandatory
	 DESCRIPTION
		 "The time in in hundredths of a second since this address 
		 was last seen.  For example, if olEnetMapTime is 500 
		 ticks, then this adddress was seen 5 seconds ago."
	 ::= { olEnetMapEntry 7 }









 -- The olTRnet Group

 -- This group represents information about Token Ring networks.

olTRnetMapState OBJECT-TYPE
	 SYNTAX INTEGER {
		 changing(1),
		 notChanging(2)
		 }
	 ACCESS read-only
	 STATUS mandatory
	 DESCRIPTION
		"The state of the inter-module token ring map. If the map
		is being updated, then the state of the map is changing."
	 ::= { olTRnet 1 }


olTRnetStatsTable OBJECT-TYPE
	SYNTAX SEQUENCE OF OlTRnetStatsEntry
	ACCESS not-accessible
	STATUS mandatory
	DESCRIPTION
		"A list of Token Ring statistics entries counted
		for each network."
	::= { olTRnet 2 }

olTRnetStatsEntry OBJECT-TYPE
	SYNTAX OlTRnetStatsEntry
	ACCESS not-accessible
	STATUS mandatory
	DESCRIPTION
		"A collection of statistics kept for a particular 
		Token Ring interface."	
	INDEX { olTRnetStatsNetID }
	::= { olTRnetStatsTable 1 }

OlTRnetStatsEntry ::=
	SEQUENCE {
		olTRnetStatsNetID
			INTEGER,
		olTRnetStatsLineErrors
			Counter,
		olTRnetStatsBurstErrors
			Counter,
		olTRnetStatsACErrors
			Counter,
		olTRnetStatsLostFrameErrors
			Counter,
		olTRnetStatsCongestionErrors
			Counter,
		olTRnetStatsFrameCopiedErrors
			Counter,
		olTRnetStatsTokenErrors
			Counter,
		olTRnetStatsDuplicateAddresses
			Counter,
		olTRnetStatsBeaconEvents
			Counter,
		olTRnetStatsLastBeaconSender
			OCTET STRING,
		olTRnetStatsLastBeaconNAUN
			OCTET STRING,
		olTRnetStatsLastBeaconTime
			TimeTicks,
		olTRnetStatsLastBeaconAction
			INTEGER,
		olTRnetStatsTotalStations
			INTEGER,
		olTRnetStatsConcStations
			INTEGER,
		olTRnetStatsTotalPorts
			INTEGER,
		olTRnetStatsEnabledPorts
			INTEGER,
		olTRnetStatsActivePorts
			INTEGER
		}

olTRnetStatsNetID OBJECT-TYPE
	SYNTAX INTEGER {
		isolated(2),
		token-ring-1(9),
		token-ring-2(10),
		token-ring-3(11),
		token-ring-4(12),
		token-ring-5(13),
		token-ring-6(14),
		token-ring-7(15)
		}
	ACCESS read-only
	STATUS mandatory
	DESCRIPTION
		"The network index that uniquely identifies this network.
		One of token-ring-1 through token-ring-7 or isolated."
	::= { olTRnetStatsEntry 1 }

olTRnetStatsLineErrors OBJECT-TYPE
	SYNTAX Counter
	ACCESS read-only
	STATUS mandatory
	DESCRIPTION
		"The total number of line errors reported in
		error reporting packets detected by the TRMM."
	::= { olTRnetStatsEntry 2 }

olTRnetStatsBurstErrors OBJECT-TYPE
	SYNTAX Counter
	ACCESS read-only
	STATUS mandatory
	DESCRIPTION
		"The total number of burst errors reported in
		error reporting packets detected by the TRMM."
	::= { olTRnetStatsEntry 3 }

olTRnetStatsACErrors OBJECT-TYPE
	SYNTAX Counter
	ACCESS read-only
	STATUS mandatory
	DESCRIPTION
		"The total number of AC (Address Copied) errors 
		reported in error reporting packets detected by 
		the TRMM."
	::= { olTRnetStatsEntry 4 }

olTRnetStatsLostFrameErrors OBJECT-TYPE
	SYNTAX Counter
	ACCESS read-only
	STATUS mandatory
	DESCRIPTION
		"The total number of lost frame errors reported
		in error reporting packets detected by the TRMM."
	::= { olTRnetStatsEntry 5 }

olTRnetStatsCongestionErrors OBJECT-TYPE
	SYNTAX Counter
	ACCESS read-only
	STATUS mandatory
	DESCRIPTION
		"The total number of receive congestion errors 
		reported in error reporting packets detected by 
		the TRMM."
	::= { olTRnetStatsEntry 6 }

olTRnetStatsFrameCopiedErrors OBJECT-TYPE
	SYNTAX Counter
	ACCESS read-only
	STATUS mandatory
	DESCRIPTION
		"The total number of frame copied errors
		reported in error reporting packets detected by
		the TRMM."
	::= { olTRnetStatsEntry 7 }

olTRnetStatsTokenErrors OBJECT-TYPE
	SYNTAX Counter
	ACCESS read-only
	STATUS mandatory
	DESCRIPTION
		"The total number of token errors reported in
		error reporting packets detected by the TRMM."
	::= { olTRnetStatsEntry 8 }

olTRnetStatsDuplicateAddresses OBJECT-TYPE
	SYNTAX Counter
	ACCESS read-only
	STATUS mandatory
	DESCRIPTION
		"The total number of token errors reported in
		error reporting packets detected by the TRMM."
	::= { olTRnetStatsEntry 9 }

olTRnetStatsBeaconEvents OBJECT-TYPE
	SYNTAX Counter
	ACCESS read-only
	STATUS mandatory
	DESCRIPTION
		"The total number of times that the ring enters
		the beaconing state."
	::= { olTRnetStatsEntry 10 }

olTRnetStatsLastBeaconSender OBJECT-TYPE
	SYNTAX OCTET STRING (SIZE(6))
	ACCESS read-only
	STATUS mandatory
	DESCRIPTION
		"The address of the sender of the last beacon frame
		received on this ring. If no beacon frames have been
		received, this object will be six zero octets."
	::= { olTRnetStatsEntry 11 }

olTRnetStatsLastBeaconNAUN OBJECT-TYPE
	SYNTAX OCTET STRING (SIZE(6))
	ACCESS read-only
	STATUS mandatory
	DESCRIPTION
		"The address of the NAUN in the last beacon frame
		received on this ring. If no beacon frames have been
		received, this object will be six zero octets."
	::= { olTRnetStatsEntry 12 }

olTRnetStatsLastBeaconTime OBJECT-TYPE
	SYNTAX TimeTicks
	ACCESS read-only
	STATUS mandatory
	DESCRIPTION
		"The time in in hundredths of a second since the last 
		beacon event occurred.  For example, if the time  is 500 
		ticks, then this event was seen 5 seconds ago. If no
		beacon events have occurred, then this will be equal
		to the sysUpTime."
	::= { olTRnetStatsEntry 13 }

olTRnetStatsLastBeaconAction OBJECT-TYPE
	SYNTAX INTEGER {
		noAction (1),
		portDisable (2),
		trunkDisable (3),
		moduleIsolate (4)
		}
	ACCESS read-only
	STATUS mandatory
	DESCRIPTION
		"The action (if any) taken to correct the last beacon
		event on the ring."
	::= { olTRnetStatsEntry 14 }

olTRnetStatsTotalStations OBJECT-TYPE
	SYNTAX INTEGER (1..255)
	ACCESS read-only
	STATUS mandatory
	DESCRIPTION
		"The number of stations currently participating in the 802.5 
		MAC protocol on the ring."
	::= { olTRnetStatsEntry 15 }

olTRnetStatsConcStations OBJECT-TYPE
	SYNTAX INTEGER (1..255)
	ACCESS read-only
	STATUS mandatory
	DESCRIPTION
		"The number of stations currently participating in the 802.5 
		MAC protocol on the ring which are connected to ports in
		this concentrator."
	::= { olTRnetStatsEntry 16}

olTRnetStatsTotalPorts OBJECT-TYPE
	SYNTAX INTEGER
	ACCESS read-only
	STATUS mandatory
	DESCRIPTION
		"The total number of ports within this concentrator and
		on this ring regardless of their admin state or status."
	::= { olTRnetStatsEntry 17 }

olTRnetStatsEnabledPorts OBJECT-TYPE
	SYNTAX INTEGER
	ACCESS read-only
	STATUS mandatory
	DESCRIPTION
		"The number of ports within this concentrator and on this ring
		which have olPortAdminState set to enabled."
	::= { olTRnetStatsEntry 18 }

olTRnetStatsActivePorts OBJECT-TYPE
	SYNTAX INTEGER
	ACCESS read-only
	STATUS mandatory
	DESCRIPTION
		"The number of ports within this concentrator and on this ring
		which have olPortAdminState set to enabled and whose 
		olPortStatus has a status of okay."
	::= { olTRnetStatsEntry 19 }

olTRnetStatsStationTable OBJECT-TYPE
	SYNTAX SEQUENCE OF OlTRnetStatsStationEntry
	ACCESS not-accessible
	STATUS mandatory
	DESCRIPTION
		"A list of ring statistics entries."
	::= { olTRnet 3 }

olTRnetStatsStationEntry OBJECT-TYPE
	SYNTAX OlTRnetStatsStationEntry
	ACCESS not-accessible
	STATUS mandatory
	DESCRIPTION
		"A collection of statistics for a particular station
		that has been discovered on a a ring monitored by 
		this device."
	INDEX { olTRnetStatsStationNetID, olTRnetStatsStationAddr }
	::= { olTRnetStatsStationTable 1 }

OlTRnetStatsStationEntry ::= 
	SEQUENCE {
		olTRnetStatsStationNetID
			INTEGER,
		olTRnetStatsStationAddr
			OCTET STRING,
		olTRnetStatsStationSlotIndex
			INTEGER,
		olTRnetStatsStationPortIndex
			INTEGER,
		olTRnetStatsStationNAUNAddress
			OCTET STRING,
		olTRnetStatsStationLineErrors
			Counter,
		olTRnetStatsStationBurstErrors
			Counter,
		olTRnetStatsStationACErrors
			Counter,
		olTRnetStatsStationLostFrameErrors
			Counter,
		olTRnetStatsStationCongestionErrors
			Counter,
		olTRnetStatsStationFrameCopiedErrors
			Counter,
		olTRnetStatsStationTokenErrors
			Counter,
		olTRnetStatsStationDuplicateAddresses
			Counter
		}

olTRnetStatsStationNetID OBJECT-TYPE
	SYNTAX INTEGER {
		isolated(2),
		token-ring-1(9),
		token-ring-2(10),
		token-ring-3(11),
		token-ring-4(12),
		token-ring-5(13),
		token-ring-6(14),
		token-ring-7(15)
		}	
	ACCESS read-only
	STATUS mandatory
	DESCRIPTION
		"The network index that uniquely identifies this network.
		One of token-ring-1 through token-ring-7 or isolated."
	::= { olTRnetStatsStationEntry 1 }

olTRnetStatsStationAddr OBJECT-TYPE
	SYNTAX OCTET STRING (SIZE(6))
	ACCESS read-only
	STATUS mandatory
	DESCRIPTION
		"The physical address of this station."
	::= { olTRnetStatsStationEntry 2 }

olTRnetStatsStationSlotIndex OBJECT-TYPE
	SYNTAX INTEGER {
		slot-1(1),
		slot-2(2),
		slot-3(3),
		slot-4(4),
		slot-5(5),
		slot-6(6),
		slot-7(7),
		slot-8(8),
		slot-9(9),
		slot-10(10),
		slot-11(11),
		slot-12(12),
		slot-13(13),
		slot-14(14),
		slot-15(15),
		slot-16(16),
		slot-17(17),
		external(255)
		}
	ACCESS read-only
	STATUS mandatory
	DESCRIPTION
		"The slot number of the station with this address.
		Addresses with a slot value of external(255) are
		not in this concentrator."
	::= { olTRnetStatsStationEntry 3 }

olTRnetStatsStationPortIndex OBJECT-TYPE
	SYNTAX INTEGER
	ACCESS read-only
	STATUS mandatory
	DESCRIPTION
		"The port number within olTRnetStatsStationSlotIndex's
		slot that received this address. If 
		olTRnetStatsStationSlotIndex has a value of 
		external(255), then the port address will be 255."
	::= { olTRnetStatsStationEntry 4 }

olTRnetStatsStationNAUNAddress OBJECT-TYPE
	SYNTAX OCTET STRING (SIZE(6))
	ACCESS read-only
	STATUS mandatory
	DESCRIPTION
		"The physical address of the nearest active upstream
		neighbor of this station."
	::= { olTRnetStatsStationEntry 5 }

olTRnetStatsStationLineErrors OBJECT-TYPE
	SYNTAX Counter
	ACCESS read-only
	STATUS mandatory
	DESCRIPTION
		"The total number of Line Errors pertaining to this station 
		reported in error reporting packets detected by the TRMM."
	::= { olTRnetStatsStationEntry 6 }

olTRnetStatsStationBurstErrors OBJECT-TYPE
	SYNTAX Counter
	ACCESS read-only
	STATUS mandatory
	DESCRIPTION
		"The total number of burst errors pertaining to this station 
		reported in error reporting packets detected by the TRMM."
	::= { olTRnetStatsStationEntry 7 }

olTRnetStatsStationACErrors OBJECT-TYPE
	SYNTAX Counter
	ACCESS read-only
	STATUS mandatory
	DESCRIPTION
		"The total number of AC (Address Copied)
		errors pertaining to this station reported in
		error reporting packets detected by the TRMM."
	::= { olTRnetStatsStationEntry 8 }

olTRnetStatsStationLostFrameErrors OBJECT-TYPE
	SYNTAX Counter
	ACCESS read-only
	STATUS mandatory
	DESCRIPTION
		"The total number of lost frame errors pertaining to 
		this station reported in error reporting packets
		detected by the TRMM."
	::= { olTRnetStatsStationEntry 9 }

olTRnetStatsStationCongestionErrors OBJECT-TYPE
	SYNTAX Counter
	ACCESS read-only
	STATUS mandatory
	DESCRIPTION
		"The total number of congestion errors pertaining
		to this station reported in error reporting
		packets detected by the TRMM."
	::= { olTRnetStatsStationEntry 10 }

olTRnetStatsStationFrameCopiedErrors OBJECT-TYPE
	SYNTAX Counter
	ACCESS read-only
	STATUS mandatory
	DESCRIPTION
		"The total number of frame copied errors pertaining 
		to this station reported in error reporting packets
		detected by the TRMM."
	::= { olTRnetStatsStationEntry 11 }

olTRnetStatsStationTokenErrors OBJECT-TYPE
	SYNTAX Counter
	ACCESS read-only
	STATUS mandatory
	DESCRIPTION
		"The total number of token errors pertaining to this
		station reported in error reporting packets detected
		by the TRMM."
	::= { olTRnetStatsStationEntry 12 }

olTRnetStatsStationDuplicateAddresses OBJECT-TYPE
	SYNTAX Counter
	ACCESS read-only
	STATUS mandatory
	DESCRIPTION
		"The number of times this station experienced
		a duplicate address error."
	::= { olTRnetStatsStationEntry 13 }


olTRnetStatsPortTable OBJECT-TYPE
	SYNTAX SEQUENCE OF OlTRnetStatsPortEntry
	ACCESS not-accessible
	STATUS mandatory
	DESCRIPTION
		"A list of statistic entries, for ports within the 
		concentrator."
	::= { olTRnet 4 }

olTRnetStatsPortEntry OBJECT-TYPE
	SYNTAX OlTRnetStatsPortEntry
	ACCESS not-accessible
	STATUS mandatory
	DESCRIPTION
		"A collection of statistics for a particular station
		that has been discovered on a a ring monitored by 
		this device."
	INDEX {olTRnetStatsPortSlotIndex, olTRnetStatsPortIndex }
	::= { olTRnetStatsPortTable 1 }

OlTRnetStatsPortEntry ::= 
	SEQUENCE {
		olTRnetStatsPortSlotIndex
			INTEGER,
		olTRnetStatsPortIndex
			INTEGER,
		olTRnetStatsPortNetID
			INTEGER,
		olTRnetStatsPortTotalStations
			INTEGER,
		olTRnetStatsPortAddress
			OCTET STRING,
		olTRnetStatsPortLineErrors
			Counter,
		olTRnetStatsPortBurstErrors
			Counter,
		olTRnetStatsPortACErrors
			Counter,
		olTRnetStatsPortLostFrameErrors
			Counter,
		olTRnetStatsPortCongestionErrors
			Counter,
		olTRnetStatsPortFrameCopiedErrors
			Counter,
		olTRnetStatsPortTokenErrors
			Counter,
		olTRnetStatsPortDuplicateAddresses
			Counter
		}

olTRnetStatsPortSlotIndex OBJECT-TYPE
	SYNTAX INTEGER 
	ACCESS read-only
	STATUS mandatory
	DESCRIPTION
		"The port slot number." 
	::= { olTRnetStatsPortEntry 1 }

olTRnetStatsPortIndex OBJECT-TYPE
	SYNTAX INTEGER
	ACCESS read-only
	STATUS mandatory
	DESCRIPTION
		"The port number within olTRnetStatsPortSlotIndex's slot."
	::= { olTRnetStatsPortEntry 2 }

olTRnetStatsPortNetID OBJECT-TYPE
	SYNTAX INTEGER {
		isolated(2),
		token-ring-1(9),
		token-ring-2(10),
		token-ring-3(11),
		token-ring-4(12),
		token-ring-5(13),
		token-ring-6(14),
		token-ring-7(15)
		}	
	ACCESS read-only
	STATUS mandatory
	DESCRIPTION
		"The network index that uniquely identifies this network.
		One of token-ring-1 through token-ring-7 or isolated."
	::= { olTRnetStatsPortEntry 3 }

olTRnetStatsPortTotalStations OBJECT-TYPE
	SYNTAX INTEGER 
	ACCESS read-only
	STATUS mandatory
	DESCRIPTION
		"The total number of stations attached to this port."
	::= { olTRnetStatsPortEntry 4 }

olTRnetStatsPortAddress OBJECT-TYPE
	SYNTAX OCTET STRING (SIZE(6))
	ACCESS read-only
	STATUS mandatory
	DESCRIPTION
		"The mac address of the station connected to this
		If there are multiple mac addresses for this port,
		then this object will contain the last mac address."
	::= { olTRnetStatsPortEntry 5 }

olTRnetStatsPortLineErrors OBJECT-TYPE
	SYNTAX Counter
	ACCESS read-only
	STATUS mandatory
	DESCRIPTION
		"The total number of Line Errors pertaining to
		this port reported in error reporting
		packets detected by the TRMM."
	::= { olTRnetStatsPortEntry 6 }

olTRnetStatsPortBurstErrors OBJECT-TYPE
	SYNTAX Counter
	ACCESS read-only
	STATUS mandatory
	DESCRIPTION
		"The total number of burst errors pertaining
		to this port reported in error reporting 
		packets detected by the TRMM."
	::= { olTRnetStatsPortEntry 7 }

olTRnetStatsPortACErrors OBJECT-TYPE
	SYNTAX Counter
	ACCESS read-only
	STATUS mandatory
	DESCRIPTION
		"The total number of AC (Address Copied)
		errors pertaining to this port reported in
		error reporting packets detected by the TRMM."
	::= { olTRnetStatsPortEntry 8 }

olTRnetStatsPortLostFrameErrors OBJECT-TYPE
	SYNTAX Counter
	ACCESS read-only
	STATUS mandatory
	DESCRIPTION
		"The total number of lost frame errors pertaining to 
		this port reported in error reporting packets
		detected by the TRMM."
	::= { olTRnetStatsPortEntry 9 }

olTRnetStatsPortCongestionErrors OBJECT-TYPE
	SYNTAX Counter
	ACCESS read-only
	STATUS mandatory
	DESCRIPTION
		"The total number of congestion errors pertaining
		to this port reported in error reporting
		packets detected by the TRMM."
	::= { olTRnetStatsPortEntry 10 }

olTRnetStatsPortFrameCopiedErrors OBJECT-TYPE
	SYNTAX Counter
	ACCESS read-only
	STATUS mandatory
	DESCRIPTION
		"The total number of frame copied errors pertaining 
		to this port reported in error reporting packets
		detected by the TRMM."
	::= { olTRnetStatsPortEntry 11 }

olTRnetStatsPortTokenErrors OBJECT-TYPE
	SYNTAX Counter
	ACCESS read-only
	STATUS mandatory
	DESCRIPTION
		"The total number of token errors pertaining to this
		station reported in error reporting packets detected
		by the TRMM."
	::= { olTRnetStatsPortEntry 12 }

olTRnetStatsPortDuplicateAddresses OBJECT-TYPE
	SYNTAX Counter
	ACCESS read-only
	STATUS mandatory
	DESCRIPTION
		"The number of times this port experienced
		a duplicate address error."
	::= { olTRnetStatsPortEntry 13 }

olTRnetMapSummary 	OBJECT IDENTIFIER ::= { olTRnet 5 }

olTRnetMapSummaryLogicalState OBJECT-TYPE
	SYNTAX INTEGER {
		changing(1),
		notChanging(2)
		}
	ACCESS read-only
	STATUS mandatory
	DESCRIPTION
		"The state of the token ring summary table. If the summary
		is being updated, then the state of the summary is changing."
	::= { olTRnetMapSummary 1 }

olTRnetMapSummaryLogicalLock OBJECT-TYPE
	SYNTAX INTEGER {
		lock(1),
		unlock(2)
		}
	ACCESS read-write
	STATUS mandatory
	DESCRIPTION
		"A semaphore for locking the token ring summary table.
		When locked, updates to the summary will pend until the 
		semaphore is unlocked, so that a valid summary can be read.
		This cannot be set to unlock if olTRnetSummaryLogicalState is 
                changing.
		For complete accuracy, this should be read after being set to
		ensure that the map was not changing when the lock was
		attempted. After the summary information has been recorded,
		the semaphore should be set to unlock to allow changes to
		occur."
	::= { olTRnetMapSummary 2 }

olTRnetMapSummaryTable OBJECT-TYPE
	SYNTAX SEQUENCE OF OlTRnetMapSummaryEntry
	ACCESS not-accessible
	STATUS mandatory
	DESCRIPTION
		"A logical map of the token ring network, starting from the
		agent's specified token ring interface. Each station on the
		map is represented by it's MAC address, slot number and port
		number (8 octets per station). If the port is external
		to the concentrator, the slot number will be 255 and the
		port number will be 0. The map is ordered in the same 
		direction as the token flow. The MAC addresses
		are concatonated into groups of up to 32 addresses per entry.
		The last entry has all-zero MAC addresses padded on the end
		of the entry. All entries before the last one have 32 valid
		addresses. This table supports up to 256 stations."
	::= { olTRnetMapSummary 3 }

olTRnetMapSummaryEntry OBJECT-TYPE
	SYNTAX OlTRnetMapSummaryEntry
	ACCESS not-accessible
	STATUS mandatory
	DESCRIPTION
		"A group of MAC addresses associated with a Token Ring map."
	INDEX { olTRnetMapSummaryNetID, olTRnetMapSummaryIndex }
	::= { olTRnetMapSummaryTable 1 }

OlTRnetMapSummaryEntry ::=
	SEQUENCE {
		olTRnetMapSummaryNetID
			INTEGER,
		olTRnetMapSummaryIndex
			INTEGER,
		olTRnetMapSummary32Stations
			OCTET STRING
		}

olTRnetMapSummaryNetID OBJECT-TYPE
	SYNTAX INTEGER {
		isolated(2),		-- corresponds to ifIndex
		token-ring-1(9),
		token-ring-2(10),
		token-ring-3(11),
		token-ring-4(12),
		token-ring-5(13),
		token-ring-6(14),
		token-ring-7(15)
		}
	ACCESS read-only
	STATUS mandatory
	DESCRIPTION
		"The network index that uniquely identifies this network.
		It can be isolated from the backplane, or on one of seven
		possible backplane token ring networks."
	::= { olTRnetMapSummaryEntry 1 }

olTRnetMapSummaryIndex OBJECT-TYPE
	SYNTAX INTEGER
	ACCESS read-only
	STATUS mandatory
	DESCRIPTION
		"The index into the map array. Possible values are 1 through 8.
		The MAC address of this agent is the first MAC address in
		olTRnetMapSummary32Stations indexed by a 1 in this entry."
	::= { olTRnetMapSummaryEntry 2 }

olTRnetMapSummary32Stations OBJECT-TYPE
	SYNTAX OCTET STRING (SIZE(8..256))
	ACCESS read-only
	STATUS mandatory
	DESCRIPTION
		"A concatonated group of MAC addresses and their associated
		slot and port of stations on the ring. Each entry has the
		eight octets. The first six octets are the MAC address.
		The seventh octet is the slot ID (or 255 if it is external
		to the concentrator). The eighth is the port ID (or 255
		if it is external to the concentrator).
		The MAC addresses are in the same order as the token flow."
	::= { olTRnetMapSummaryEntry 3 }

--
--  Network Traffic
--

olTRTrafTable OBJECT-TYPE
    SYNTAX SEQUENCE OF OlTRTrafEntry
    ACCESS not-accessible
    STATUS mandatory
    DESCRIPTION
	"A list of Token Ring network traffic (non-error) statistics entries.  
	Note that all of the frame and octet counters in this table
	include error frames that have valid length;
	all octet counters exclude framing bits but include FCS octets."
    ::= { olTRnet 6 }

olTRTrafEntry OBJECT-TYPE
    SYNTAX OlTRTrafEntry
    ACCESS not-accessible
    STATUS mandatory
    DESCRIPTION
	"A collection of statistics kept for a particular
	Token Ring interface.
	Note that all of the frame and octet counters in this table
	include error frames that have valid length;
	all octet counters exclude framing bits but include FCS octets."
    INDEX { olTRTrafNetID }
    ::= { olTRTrafTable 1 }

OlTRTrafEntry ::= SEQUENCE {
  olTRTrafNetID			INTEGER,
  olTRTrafTokenRotationTime	INTEGER,
  olTRTrafDropEvents		Counter,
  olTRTrafOctets		Counter,
  olTRTrafFrames		Counter,
  olTRTrafMacOctets		Counter,
  olTRTrafMacFrames		Counter,
  olTRTrafBroadcastFrames	Counter,
  olTRTrafMulticastFrames	Counter,
  olTRTrafFrames18to63Octets    Counter,
  olTRTrafFrames64to127Octets   Counter,
  olTRTrafFrames128to255Octets  Counter,
  olTRTrafFrames256to511Octets  Counter,
  olTRTrafFrames512to1023Octets Counter,
  olTRTrafFrames1024to2047Octets Counter,
  olTRTrafFrames2048to4095Octets Counter,
  olTRTrafFrames4096to8191Octets Counter,
  olTRTrafFrames8192to18000Octets Counter,
  olTRTrafFramesGreaterThan18000Octets	Counter
}

olTRTrafNetID OBJECT-TYPE
        SYNTAX INTEGER {
                isolated(2),
                token-ring-1(9),
                token-ring-2(10),
                token-ring-3(11),
                token-ring-4(12),
                token-ring-5(13),
                token-ring-6(14),
                token-ring-7(15)
                }
        ACCESS read-only
        STATUS mandatory
        DESCRIPTION
                "The network index that uniquely identifies this network.
                One of token-ring-1 through token-ring-7 or isolated."
        ::= { olTRTrafEntry 1 }

olTRTrafTokenRotationTime OBJECT-TYPE
    SYNTAX INTEGER
    ACCESS read-only
    STATUS mandatory
    DESCRIPTION
        "An estimate of the time (in microseconds) that it takes for the
	token to complete a single rotation around the ring."
    ::= { olTRTrafEntry 2 }

olTRTrafDropEvents OBJECT-TYPE
    SYNTAX Counter
    ACCESS read-only
    STATUS mandatory
    DESCRIPTION
        "The total number of events in which frames
        were dropped by the TRMM due to lack of resources.
        Note that this number is not necessarily the number of
        frames dropped; it is just the number of times this
        condition has been detected."
    ::= { olTRTrafEntry 3 }

olTRTrafOctets OBJECT-TYPE
    SYNTAX Counter
    ACCESS read-only
    STATUS mandatory
    DESCRIPTION
        "The total number of octets of data received on the network."
    ::= { olTRTrafEntry 4 }

olTRTrafFrames OBJECT-TYPE
    SYNTAX Counter
    ACCESS read-only
    STATUS mandatory
    DESCRIPTION
        "The total number of frames received."
    ::= { olTRTrafEntry 5 }

olTRTrafMacOctets OBJECT-TYPE
    SYNTAX Counter
    ACCESS read-only
    STATUS mandatory
    DESCRIPTION
        "The total number of octets of data in MAC frames
        received on the network."
    ::= { olTRTrafEntry 6 }

olTRTrafMacFrames OBJECT-TYPE
    SYNTAX Counter
    ACCESS read-only
    STATUS mandatory
    DESCRIPTION
        "The total number of MAC frames received."
    ::= { olTRTrafEntry 7 }

olTRTrafBroadcastFrames OBJECT-TYPE
    SYNTAX Counter
    ACCESS read-only
    STATUS mandatory
    DESCRIPTION
        "The total number of non-MAC frames received that were
        directed to a broadcast address (0xFFFFFFFFFFFF or 0xC000FFFFFFFF)."
    ::= { olTRTrafEntry 8 }

olTRTrafMulticastFrames OBJECT-TYPE
    SYNTAX Counter
    ACCESS read-only
    STATUS mandatory
    DESCRIPTION
        "The total number of non-MAC frames received that were
        directed to a local or global multicast or functional address.
	Note that this number does not include frames directed to
	a broadcast address."
    ::= { olTRTrafEntry 9 }

olTRTrafFrames18to63Octets OBJECT-TYPE
    SYNTAX Counter
    ACCESS read-only
    STATUS mandatory
    DESCRIPTION
	"The total number of non-MAC frames received that were between
	18 and 63 octets in length inclusive."
    ::= { olTRTrafEntry 10 }

olTRTrafFrames64to127Octets OBJECT-TYPE
    SYNTAX Counter
    ACCESS read-only
    STATUS mandatory
    DESCRIPTION
	"The total number of non-MAC frames received that were between
	64 and 127 octets in length inclusive."
    ::= { olTRTrafEntry 11 }

olTRTrafFrames128to255Octets OBJECT-TYPE
    SYNTAX Counter
    ACCESS read-only
    STATUS mandatory
    DESCRIPTION
	"The total number of non-MAC frames received that were between
	128 and 255 octets in length inclusive."
    ::= { olTRTrafEntry 12 }

olTRTrafFrames256to511Octets OBJECT-TYPE
    SYNTAX Counter
    ACCESS read-only
    STATUS mandatory
    DESCRIPTION
	"The total number of non-MAC frames received that were between
	256 and 511 octets in length inclusive."
    ::= { olTRTrafEntry 13 }

olTRTrafFrames512to1023Octets OBJECT-TYPE
    SYNTAX Counter
    ACCESS read-only
    STATUS mandatory
    DESCRIPTION
	"The total number of non-MAC frames received that were between
	512 and 1023 octets in length inclusive."
    ::= { olTRTrafEntry 14 }

olTRTrafFrames1024to2047Octets OBJECT-TYPE
    SYNTAX Counter
    ACCESS read-only
    STATUS mandatory
    DESCRIPTION
	"The total number of non-MAC frames received that were between
	1024 and 2047 octets in length inclusive."
    ::= { olTRTrafEntry 15 }

olTRTrafFrames2048to4095Octets OBJECT-TYPE
    SYNTAX Counter
    ACCESS read-only
    STATUS mandatory
    DESCRIPTION
	"The total number of non-MAC frames received that were between
	2048 and 4095 octets in length inclusive."
    ::= { olTRTrafEntry 16 }

olTRTrafFrames4096to8191Octets OBJECT-TYPE
    SYNTAX Counter
    ACCESS read-only
    STATUS mandatory
    DESCRIPTION
	"The total number of non-MAC frames received that were between
	4096 and 8191 octets in length inclusive."
    ::= { olTRTrafEntry 17 }

olTRTrafFrames8192to18000Octets OBJECT-TYPE
    SYNTAX Counter
    ACCESS read-only
    STATUS mandatory
    DESCRIPTION
	"The total number of non-MAC frames received that were between
	8192 and 18000 octets in length inclusive."
    ::= { olTRTrafEntry 18 }

olTRTrafFramesGreaterThan18000Octets OBJECT-TYPE
    SYNTAX Counter
    ACCESS read-only
    STATUS mandatory
    DESCRIPTION
	"The total number of non-MAC frames received that were
	greater than or equal to 18000 octets in length."
    ::= { olTRTrafEntry 19 }



-- Station and Port Traffic


-- The OlTRTrafControl, OlTRTrafStation, OlTRTrafPort, OlTRTrafTopN, and
-- OlTRTrafTopNSummary Groups

--
-- New stations on the token ring network are discovered by
-- keeping a list of source and destination MAC Addresses seen
-- in good frames.  For each of these addresses, a set of statistics
-- is maintained.  The OlTRTrafStation, OlTRTrafPort, OlTRTrafTopN,
-- and OlTRTrafTopNSummary Groups provide four different ways
-- to retrieve this information.
--
-- Note that the list of stations will include
--	- stations internal to the concentrator on the local ring
--	- stations external to the concentrator on the local ring
-- 	- stations on remote rings
--
-- If the list is full, the least recently used entries not on the local ring
-- will be deleted first, as needed.

-- The olTRTrafStationTable contains entries for each address
-- discovered on a particular interface.  Each entry
-- contains statistical data about that station.  This table
-- is indexed by Network ID and the MAC address of the station.

-- The olTRTrafPortTable contains data in the same format as the
-- olTRTrafStationTable, and contains the same set of stations
-- except that stations external to the concentrator or not on the local ring
-- are omitted.  The olTRTrafPortTable is
-- indexed by Network ID, SlotIndex and PortIndex.

-- The olTRTrafTopNTable is composed of 7 sublists, one for each statistic.
-- Each sublist contains the same set of stations as
-- olTRTrafStationTable.  The stations in each sublist are sorted by
-- the statistic specified in olTRTrafTopNStatistic.
-- The olTRTrafTopNTable is indexed by olTRTrafTopNNetID,
-- by olTRTrafTopNStatistic to identify the sublist,
-- and by olTRTrafTopNIndex (1..N) with index 1 referring to
-- the entry with the highest value of the specifed counter.
-- (See description of olTRTrafTopNTable)

-- The olTRTrafTopNSummaryTable contains the same information as
-- olTRTrafTopNTable, but in a condensed format.

-- Note that table entries may be added, deleted, or resorted at any time.
-- There are three methods available for a management station to address this.

-- METHOD 1
-- Each of the 4 tables has an associated "-LastChangeTime" entry in
-- olTRTrafControlTable.  A management station should read the
-- associated "-LastChangeTime" entry before and after reading a group of
-- table entries.  If the before and after "-LastChangeTimes differ then the
-- management station should repeat the reading of table entries.

-- METHOD 2
-- Use olTRTrafControlLogicalLock and olTRTrafControlLogicalState to ensure
-- that changes don't occur while retrieving table entries.
-- (see description below)

-- METHOD 3
-- Don't worry about table entry changes.  Probably they won't happen while
-- you are reading the table.  The worst that would happen is you might miss
-- a few stations or see the same station twice in the list.




olTRTrafControlTable OBJECT-TYPE
    SYNTAX SEQUENCE OF OlTRTrafControlEntry
    ACCESS not-accessible
    STATUS mandatory
    DESCRIPTION
	"A list entries containing information about 
	olTRTrafStationTable, olTRTrafPortTable, olTRTrafTopNTable, and
	olTRTrafTopNSummaryTable"
    ::= { olTRnet 7 }

olTRTrafControlEntry OBJECT-TYPE
    SYNTAX OlTRTrafControlEntry
    ACCESS not-accessible
    STATUS mandatory
    DESCRIPTION
	"A collection of information about 
	olTRTrafStationTable, olTRTrafPortTable, olTRTrafTopNTable, and
	olTRTrafTopNSummaryTable"
    INDEX { olTRTrafControlNetID }
    ::= { olTRTrafControlTable 1 }

OlTRTrafControlEntry ::= SEQUENCE {
  olTRTrafControlNetID			INTEGER,
  olTRTrafControlLogicalState		INTEGER,
  olTRTrafControlLogicalLock		INTEGER,
  olTRTrafControlClear			INTEGER,
  olTRTrafControlLastClearTime		TimeTicks,
  olTRTrafControlTotalStations		INTEGER,
  olTRTrafControlStationLastChangeTime	TimeTicks,
  olTRTrafControlPortTotalStations	INTEGER,
  olTRTrafControlPortLastChangeTime	TimeTicks,
  olTRTrafControlTopNMaxStations	INTEGER,
  olTRTrafControlTopNTotalStations	INTEGER,
  olTRTrafControlTopNLastChangeTime	TimeTicks,
  olTRTrafControlTopNInterval		INTEGER
}

olTRTrafControlNetID OBJECT-TYPE
        SYNTAX INTEGER {
                isolated(2),
                token-ring-1(9),
                token-ring-2(10),
                token-ring-3(11),
                token-ring-4(12),
                token-ring-5(13),
                token-ring-6(14),
                token-ring-7(15)
                }
        ACCESS read-only
        STATUS mandatory
        DESCRIPTION
                "The network index that uniquely identifies this network.
                One of token-ring-1 through token-ring-7 or isolated."
        ::= { olTRTrafControlEntry 1 }

olTRTrafControlLogicalState OBJECT-TYPE
        SYNTAX INTEGER {
                changing(1),
                notChanging(2)
                }
        ACCESS read-only
        STATUS mandatory
        DESCRIPTION
                "The state of the token ring station traffic tables:
		olTRTrafStationTable, olTRTrafPortTable, olTRTrafTopNTable
		and olTRTrafTopNSummaryTable. If any of the tables associated
		with this olTRTrafControlEntry are being updated,
		then the state is changing(1)."
        ::= { olTRTrafControlEntry 2 }

olTRTrafControlLogicalLock OBJECT-TYPE
        SYNTAX INTEGER {
                lock(1),
                unlock(2)
                }
        ACCESS read-write
        STATUS mandatory
        DESCRIPTION
                "A semaphore for locking the token ring station traffic
		tables: olTRTrafStationTable, olTRTrafPortTable,
		olTRTrafTopNTable, and olTRTrafTopNSummaryTable.
		When the semaphore is locked, adds, deletes, and re-sorting
		the traffic tables associated with this 
		olTRTrafControlEntry will pend until the
                semaphore is unlocked, so that a valid set of entries
		can be read.  Note that the normal incrementing of the traffic
		counters are not affected by the setting of this semaphore.
                This cannot be set to unlock if olTRTrafControlLogicalState is
                changing.
                For complete accuracy, this semaphore
		should be read after being set to
                ensure that the tables were not changing when the lock was
                attempted. After the table information has been recorded,
                the semaphore should be set to unlock to allow changes to
                occur."
        ::= { olTRTrafControlEntry 3 }


olTRTrafControlClear OBJECT-TYPE
  SYNTAX INTEGER {
	  normal(1),
	  clear(2)
  }
  ACCESS read-write
  STATUS mandatory
  DESCRIPTION
	"When the value of this object is set to clear,
	all entries in the token ring station traffic
	tables (olTRTrafStationTable, olTRTrafPortTable,
	olTRTrafTopNTable, and olTRTrafTopNSummaryTable) are cleared."
    ::= { olTRTrafControlEntry 4 }

olTRTrafControlLastClearTime OBJECT-TYPE
  SYNTAX TimeTicks
  ACCESS read-only
  STATUS mandatory
  DESCRIPTION
	"The value of sysUpTime when the token ring station traffic
	tables (olTRTrafStationTable, olTRTrafPortTable,
	olTRTrafTopNTable and olTRTrafTopNSummaryTable) were cleared.
	If never cleared, this value shall be zero (and the token ring
	station traffic tables will contain information collected since
	the XMM was started up)."
    ::= { olTRTrafControlEntry 5 }

olTRTrafControlTotalStations OBJECT-TYPE
  SYNTAX INTEGER
  ACCESS read-only
  STATUS mandatory
  DESCRIPTION
	"The number of stations in the portion of the olTRTrafStationTable
	associated with this olTRTrafControlEntry."
    ::= { olTRTrafControlEntry 6 }

olTRTrafControlStationLastChangeTime OBJECT-TYPE
  SYNTAX TimeTicks
  ACCESS read-only
  STATUS mandatory
  DESCRIPTION
      "The value of sysUpTime when the last entry
      was added to or deleted (or re-sorted)
      from the portion of the olTRTrafStationTable
      associated with this olTRTrafControlEntry.  If no
      additions or deletions have occurred, this value shall be zero."
    ::= { olTRTrafControlEntry 7 }

olTRTrafControlPortTotalStations OBJECT-TYPE
  SYNTAX INTEGER
  ACCESS read-only
  STATUS mandatory
  DESCRIPTION
	"The number of stations in the portion of the olTRTrafPortTable
	associated with this olTRTrafControlEntry."
    ::= { olTRTrafControlEntry 8 }

olTRTrafControlPortLastChangeTime OBJECT-TYPE
  SYNTAX TimeTicks
  ACCESS read-only
  STATUS mandatory
  DESCRIPTION
      "The value of sysUpTime when the last entry
      was added to or deleted (or re-sorted)
      from the portion of the olTRTrafPortTable
      associated with this olTRTrafControlEntry.  If no
      additions or deletions have occurred, this value shall be zero."
    ::= { olTRTrafControlEntry 9 }

olTRTrafControlTopNMaxStations OBJECT-TYPE
  SYNTAX INTEGER
  ACCESS read-write
  STATUS mandatory
  DESCRIPTION
	"Specifies a maximum value for olTRTrafControlTopNTotalStations
	in this olTRTrafControlEntry.  If this value is zero then no  
	maximum value for olTRTrafControlTopNTotalStations is specified."
--	DEFVAL { 0 }
    ::= { olTRTrafControlEntry 10 }

olTRTrafControlTopNTotalStations OBJECT-TYPE
  SYNTAX INTEGER
  ACCESS read-only
  STATUS mandatory
  DESCRIPTION
	"The number of stations (for each statistic) in the portion of 
	the olTRTrafTopNTable and olTRTrafTopNSummaryTable associated
	with this olTRTrafControlEntry.  If olTRTrafControlTopNMaxStations
	is zero or is not less than olTRTrafControlTotalStations then
	olTRTrafControlTopNTotalStations will have the same value as
	olTRTrafControlTotalStations.  Otherwise
	olTRTrafControlTopNTotalStations will
	have the same value as olTRTrafControlTopNMaxStations." 
    ::= { olTRTrafControlEntry 11 }

olTRTrafControlTopNLastChangeTime OBJECT-TYPE
  SYNTAX TimeTicks
  ACCESS read-only
  STATUS mandatory
  DESCRIPTION
      "The value of sysUpTime when the last entry
      was added to or deleted (or re-sorted)
      from the portion of the olTRTrafTopNTable and olTRTrafTopNSummaryTable
      associated with this olTRTrafControlEntry.  
      This is equivalent to the time when 
      the last TopN data collection period ended.
      If no additions or deletions have occurred, this value shall be zero."
    ::= { olTRTrafControlEntry 12 }

olTRTrafControlTopNInterval OBJECT-TYPE
  SYNTAX INTEGER
  ACCESS read-write
  STATUS mandatory
  DESCRIPTION
      "Specifies the length of the TopN data collection period in seconds.
      Minimum length is 5 seconds; maximum is 86400 seconds (24 hours).
      When this value is modified, all associated entries in 
      olTRTrafTopNTable and olTRTrafTopNSummaryTable are deleted and a new
      TopN data collection period is started."
--      DEFVAL {30}
    ::= { olTRTrafControlEntry 13 }



olTRTrafStationTable OBJECT-TYPE
  SYNTAX SEQUENCE OF OlTRTrafStationEntry
  ACCESS not-accessible
  STATUS mandatory
  DESCRIPTION
      "A list of Token Ring station traffic statistics entries
      indexed by Network ID and MAC address.  The table has 
      olTRTrafTotalStations entries.
	Note that all of the frame and octet counters in this table
	include error frames that have valid length;
	all octet counters exclude framing bits but include FCS octets."
  ::= { olTRnet 8 }

olTRTrafStationEntry OBJECT-TYPE
  SYNTAX OlTRTrafStationEntry
  ACCESS not-accessible
  STATUS mandatory
  DESCRIPTION
      "A collection of station statistics for a particular station
      that has been discovered on an interface of this
      device.
	Note that all of the frame and octet counters in this table
	include error frames that have valid length;
	all octet counters exclude framing bits but include FCS octets."
  INDEX { olTRTrafStationNetID,
		olTRTrafStationAddress }
  ::= { olTRTrafStationTable 1 }

OlTRTrafStationEntry ::= SEQUENCE {
  olTRTrafStationNetID			INTEGER,
  olTRTrafStationAddress		MacAddress,
  olTRTrafStationSlotIndex		INTEGER,
  olTRTrafStationPortIndex		INTEGER,
  olTRTrafStationInFrames		Counter,
  olTRTrafStationOutFrames		Counter,
  olTRTrafStationInOctets		Counter,
  olTRTrafStationOutOctets		Counter,
  olTRTrafStationOutErrors		Counter,
  olTRTrafStationOutBroadcastFrames	Counter,
  olTRTrafStationOutMulticastFrames	Counter
}

olTRTrafStationNetID OBJECT-TYPE
        SYNTAX INTEGER {
                isolated(2),
                token-ring-1(9),
                token-ring-2(10),
                token-ring-3(11),
                token-ring-4(12),
                token-ring-5(13),
                token-ring-6(14),
                token-ring-7(15)
                }
        ACCESS read-only
        STATUS mandatory
        DESCRIPTION
                "The network index that uniquely identifies this network.
                One of token-ring-1 through token-ring-7 or isolated."
        ::= { olTRTrafStationEntry 1 }

olTRTrafStationAddress OBJECT-TYPE
  SYNTAX MacAddress
  ACCESS read-only
  STATUS mandatory
  DESCRIPTION
      "The physical address of this station."
  ::= { olTRTrafStationEntry 2 }

olTRTrafStationSlotIndex OBJECT-TYPE
	SYNTAX INTEGER {
		slot-1(1),
		slot-2(2),
		slot-3(3),
		slot-4(4),
		slot-5(5),
		slot-6(6),
		slot-7(7),
		slot-8(8),
		slot-9(9),
		slot-10(10),
		slot-11(11),
		slot-12(12),
		slot-13(13),
		slot-14(14),
		slot-15(15),
		slot-16(16),
		slot-17(17),
		remote-ring(254),
		external(255)
		}
	ACCESS read-only
	STATUS mandatory
	DESCRIPTION
		"The slot number of the station with this address.
		Addresses with a slot value of remote-ring(254) are
		not in this ring.
		Addresses with a slot value of external(255) are
		not in this concentrator."
  ::= { olTRTrafStationEntry 3 }

olTRTrafStationPortIndex OBJECT-TYPE
	SYNTAX INTEGER
	ACCESS read-only
	STATUS mandatory
	DESCRIPTION
		"The port number within olTRTrafSlotIndex's
		slot that received this address.
		If olTRTrafSlotIndex has a value of 
		remote-ring(254), then the port address will be 254.
		If olTRTrafSlotIndex has a value of 
		external(255), then the port address will be 255."
  ::= { olTRTrafStationEntry 4 }

olTRTrafStationInFrames OBJECT-TYPE
  SYNTAX Counter
  ACCESS read-only
  STATUS mandatory
  DESCRIPTION
      "The number of frames transmitted to this address since it was
      added to this table."
  ::= { olTRTrafStationEntry 5 }

olTRTrafStationOutFrames OBJECT-TYPE
  SYNTAX Counter
  ACCESS read-only
  STATUS mandatory
  DESCRIPTION
      "The number of frames transmitted by this address since it was
      added to this table."
  ::= { olTRTrafStationEntry 6 }

olTRTrafStationInOctets OBJECT-TYPE
  SYNTAX Counter
  ACCESS read-only
  STATUS mandatory
  DESCRIPTION
      "The number of octets transmitted to this address since it was
      added to this table."
  ::= { olTRTrafStationEntry 7 }

olTRTrafStationOutOctets OBJECT-TYPE
  SYNTAX Counter
  ACCESS read-only
  STATUS mandatory
  DESCRIPTION
      "The number of octets transmitted by this address since it was
      added to this table."
  ::= { olTRTrafStationEntry 8 }

olTRTrafStationOutErrors OBJECT-TYPE
  SYNTAX Counter
  ACCESS read-only
  STATUS mandatory
  DESCRIPTION
      "The number of error frames transmitted by this
      address since it was added to this table.  Only isolating errors
      (LineErrors, BurstErrors, ACErrors, InternalErrors, and AbortErrors)
      and CongestionErrors are counted."
  ::= { olTRTrafStationEntry 9 }

olTRTrafStationOutBroadcastFrames OBJECT-TYPE
  SYNTAX Counter
  ACCESS read-only
  STATUS mandatory
  DESCRIPTION
      "The number of frames transmitted by this address
      that were directed to the broadcast address since it was
      added to this table."
  ::= { olTRTrafStationEntry 10 }

olTRTrafStationOutMulticastFrames OBJECT-TYPE
  SYNTAX Counter
  ACCESS read-only
  STATUS mandatory
  DESCRIPTION
      "The number of frames transmitted by this address
      that were directed to a multicast address since it was
      added to this table.
      Note that this number does not include frames
      directed to the broadcast address."
  ::= { olTRTrafStationEntry 11 }



olTRTrafPortTable OBJECT-TYPE
  SYNTAX SEQUENCE OF OlTRTrafPortEntry
  ACCESS not-accessible
  STATUS mandatory
  DESCRIPTION
      "A list of Token Ring station traffic statistics entries
      indexed by slot number, and port number.  Note that stations external
      to this concentrator or on another ring are excluded from this table.
	Note that all of the frame and octet counters in this table
	include error frames that have valid length;
	all octet counters exclude framing bits but include FCS octets."
  ::= { olTRnet 9 }

olTRTrafPortEntry OBJECT-TYPE
  SYNTAX OlTRTrafPortEntry
  ACCESS not-accessible
  STATUS mandatory
  DESCRIPTION
      "A collection of station statistics for a particular station
      that has been discovered on an interface of this
      device.
	Note that all of the frame and octet counters in this table
	include error frames that have valid length;
	all octet counters exclude framing bits but include FCS octets.
	include error frames; all octet counters exclude framing bits
	but include FCS octets."
  INDEX { olTRTrafPortSlotIndex, olTRTrafPortPortIndex }
  ::= { olTRTrafPortTable 1 }

OlTRTrafPortEntry ::= SEQUENCE {
  olTRTrafPortSlotIndex           INTEGER,
  olTRTrafPortPortIndex           INTEGER,
  olTRTrafPortNetID               INTEGER,
  olTRTrafPortAddress             MacAddress,
  olTRTrafPortInFrames              Counter,
  olTRTrafPortOutFrames             Counter,
  olTRTrafPortInOctets            Counter,
  olTRTrafPortOutOctets           Counter,
  olTRTrafPortOutErrors           Counter,
  olTRTrafPortOutBroadcastFrames    Counter,
  olTRTrafPortOutMulticastFrames    Counter
}

olTRTrafPortSlotIndex OBJECT-TYPE
	SYNTAX INTEGER
	ACCESS read-only
	STATUS mandatory
	DESCRIPTION
		"The slot number of the station with this address."
  ::= { olTRTrafPortEntry 1 }

olTRTrafPortPortIndex OBJECT-TYPE
	SYNTAX INTEGER
	ACCESS read-only
	STATUS mandatory
	DESCRIPTION
		"The port number within olTRTrafPortSlotIndex's
		slot that received this address."
  ::= { olTRTrafPortEntry 2 }

olTRTrafPortNetID OBJECT-TYPE
        SYNTAX INTEGER {
                isolated(2),
                token-ring-1(9),
                token-ring-2(10),
                token-ring-3(11),
                token-ring-4(12),
                token-ring-5(13),
                token-ring-6(14),
                token-ring-7(15)
                }
        ACCESS read-only
        STATUS mandatory
        DESCRIPTION
                "The network index that uniquely identifies this network.
                One of token-ring-1 through token-ring-7 or isolated."
        ::= { olTRTrafPortEntry 3 }

olTRTrafPortAddress OBJECT-TYPE
  SYNTAX MacAddress
  ACCESS read-only
  STATUS mandatory
  DESCRIPTION
      "The physical address of this station."
  ::= { olTRTrafPortEntry 4 }

olTRTrafPortInFrames OBJECT-TYPE
  SYNTAX Counter
  ACCESS read-only
  STATUS mandatory
  DESCRIPTION
      "The number of frames transmitted to this address since it was
      added to this table."
  ::= { olTRTrafPortEntry 5 }

olTRTrafPortOutFrames OBJECT-TYPE
  SYNTAX Counter
  ACCESS read-only
  STATUS mandatory
  DESCRIPTION
      "The number of frames transmitted by this address since it was
      added to this table."
  ::= { olTRTrafPortEntry 6 }

olTRTrafPortInOctets OBJECT-TYPE
  SYNTAX Counter
  ACCESS read-only
  STATUS mandatory
  DESCRIPTION
      "The number of octets transmitted to this address since it was
      added to this table."
  ::= { olTRTrafPortEntry 7 }

olTRTrafPortOutOctets OBJECT-TYPE
  SYNTAX Counter
  ACCESS read-only
  STATUS mandatory
  DESCRIPTION
      "The number of octets transmitted by this address since it was
      added to this table."
  ::= { olTRTrafPortEntry 8 }

olTRTrafPortOutErrors OBJECT-TYPE
  SYNTAX Counter
  ACCESS read-only
  STATUS mandatory
  DESCRIPTION
      "The number of error frames transmitted by this
      address since it was added to this table.  Only isolating errors
      (LineErrors, BurstErrors, ACErrors, InternalErrors, and AbortErrors)
      and CongestionErrors are counted."
  ::= { olTRTrafPortEntry 9 }

olTRTrafPortOutBroadcastFrames OBJECT-TYPE
  SYNTAX Counter
  ACCESS read-only
  STATUS mandatory
  DESCRIPTION
      "The number of frames transmitted by this address
      that were directed to the broadcast address since it was
      added to this table."
  ::= { olTRTrafPortEntry 10 }

olTRTrafPortOutMulticastFrames OBJECT-TYPE
  SYNTAX Counter
  ACCESS read-only
  STATUS mandatory
  DESCRIPTION
      "The number of frames transmitted by this address
      that were directed to a multicast address since it was
      added to this table.
      Note that this number does not include frames
      directed to the broadcast address."
  ::= { olTRTrafPortEntry 11 }



olTRTrafTopNTable OBJECT-TYPE
  SYNTAX SEQUENCE OF OlTRTrafTopNEntry
  ACCESS not-accessible
  STATUS mandatory
  DESCRIPTION
      "A list of Token Ring station traffic statistics entries indexed by
	olTRTrafTopNNetID, olTRTrafTopNStatistic, and olTRTrafTopNIndex.
	For each Network, the list contains 7 logical sublists - one for 
	each statistic.
	Each of the sublists has olTRTrafControlTopNTotalStations entries.
	For eack Network, the table has 7 times
	olTRTrafTopNControlTotalStations entries.
	All of the counters in this table reflect activity during the last 
	completed TopN data collection period 
	(olTRTrafControlTopNInterval seconds).
	Note that this table will contain no entries 
	if a TopN data collection period has not yet completed since
	olTRTrafControlTopNInterval was modified or since startup.
	Note that all of the frame and octet counters in this table
	include error frames that have valid length;
	all octet counters exclude framing bits but include FCS octets."
  ::= { olTRnet 10 }

olTRTrafTopNEntry OBJECT-TYPE
  SYNTAX OlTRTrafTopNEntry
  ACCESS not-accessible
  STATUS mandatory
  DESCRIPTION
      "A collection of station statistics for a particular station
      that has been discovered on an interface of this
      device.
	Note that all of the frame and octet counters in this table
	include error frames that have valid length;
	all octet counters exclude framing bits but include FCS octets."
  INDEX { olTRTrafTopNNetID,
		olTRTrafTopNStatistic,
		olTRTrafTopNIndex }
  ::= { olTRTrafTopNTable 1 }

OlTRTrafTopNEntry ::= SEQUENCE {
  olTRTrafTopNNetID               INTEGER,
  olTRTrafTopNStatistic		  INTEGER,
  olTRTrafTopNIndex               INTEGER,
  olTRTrafTopNAddress             MacAddress,
  olTRTrafTopNSlotIndex           INTEGER,
  olTRTrafTopNPortIndex           INTEGER,
  olTRTrafTopNInFrames              Counter,
  olTRTrafTopNOutFrames             Counter,
  olTRTrafTopNInOctets            Counter,
  olTRTrafTopNOutOctets           Counter,
  olTRTrafTopNOutErrors           Counter,
  olTRTrafTopNOutBroadcastFrames    Counter,
  olTRTrafTopNOutMulticastFrames    Counter
}

olTRTrafTopNNetID OBJECT-TYPE
        SYNTAX INTEGER {
                isolated(2),
                token-ring-1(9),
                token-ring-2(10),
                token-ring-3(11),
                token-ring-4(12),
                token-ring-5(13),
                token-ring-6(14),
                token-ring-7(15)
                }
        ACCESS read-only
        STATUS mandatory
        DESCRIPTION
                "The network index that uniquely identifies this network.
                One of token-ring-1 through token-ring-7 or isolated."
        ::= { olTRTrafTopNEntry 1 }

olTRTrafTopNStatistic OBJECT-TYPE
  SYNTAX INTEGER {
	  olTRTrafTopNInFrames(1),
	  olTRTrafTopNOutFrames(2),
	  olTRTrafTopNInOctets(3),
	  olTRTrafTopNOutOctets(4),
	  olTRTrafTopNOutErrors(5),
	  olTRTrafTopNOutBroadcastFrames(6),
	  olTRTrafTopNOutMulticastFrames(7)
  }
  ACCESS read-write
  STATUS mandatory
  DESCRIPTION
      "The object representing the statistic for each station that this
      portion of the olTRTrafTopNTable is sorted on."
    ::= { olTRTrafTopNEntry 2 }

olTRTrafTopNIndex OBJECT-TYPE
  SYNTAX INTEGER
  ACCESS read-only
  STATUS mandatory
  DESCRIPTION
      "An index that uniquely identifies an entry in
      the olTRTrafTopN table among those in the same network
      and for the same olTRTrafTopNStatistic.
      This index is between 1 and N, where N is the value of
      olTRTrafControlTopNTotalStations.  Increasing values
      of olTRTrafTopNIndex shall be assigned to entries with
      decreasing values of the object referenced by olTRTrafTopNStatistic."
  ::= { olTRTrafTopNEntry 3 }

olTRTrafTopNAddress OBJECT-TYPE
  SYNTAX MacAddress
  ACCESS read-only
  STATUS mandatory
  DESCRIPTION
      "The physical address of this station."
  ::= { olTRTrafTopNEntry 4 }

olTRTrafTopNSlotIndex OBJECT-TYPE
	SYNTAX INTEGER {
		slot-1(1),
		slot-2(2),
		slot-3(3),
		slot-4(4),
		slot-5(5),
		slot-6(6),
		slot-7(7),
		slot-8(8),
		slot-9(9),
		slot-10(10),
		slot-11(11),
		slot-12(12),
		slot-13(13),
		slot-14(14),
		slot-15(15),
		slot-16(16),
		slot-17(17),
		remote-ring(254),
		external(255)
		}
	ACCESS read-only
	STATUS mandatory
	DESCRIPTION
		"The slot number of the station with this address.
		Addresses with a slot value of remote-ring(254) are
		not in this ring.
		Addresses with a slot value of external(255) are
		not in this concentrator."
  ::= { olTRTrafTopNEntry 5 }

olTRTrafTopNPortIndex OBJECT-TYPE
	SYNTAX INTEGER
	ACCESS read-only
	STATUS mandatory
	DESCRIPTION
		"The port number within olTRTrafTopNSlotIndex's
		slot that received this address.
		If olTRTrafTopNSlotIndex has a value of 
		remote-ring(254), then the port address will be 254.
		If olTRTrafTopNSlotIndex has a value of 
		external(255), then the port address will be 255."
  ::= { olTRTrafTopNEntry 6 }

olTRTrafTopNInFrames OBJECT-TYPE
  SYNTAX Counter
  ACCESS read-only
  STATUS mandatory
  DESCRIPTION
      "The number of frames transmitted to this address
      during the last TopN data collection period."
  ::= { olTRTrafTopNEntry 7 }

olTRTrafTopNOutFrames OBJECT-TYPE
  SYNTAX Counter
  ACCESS read-only
  STATUS mandatory
  DESCRIPTION
      "The number of frames transmitted by this address 
      during the last TopN data collection period."
  ::= { olTRTrafTopNEntry 8 }

olTRTrafTopNInOctets OBJECT-TYPE
  SYNTAX Counter
  ACCESS read-only
  STATUS mandatory
  DESCRIPTION
      "The number of octets transmitted to this address 
      during the last TopN data collection period."
  ::= { olTRTrafTopNEntry 9 }

olTRTrafTopNOutOctets OBJECT-TYPE
  SYNTAX Counter
  ACCESS read-only
  STATUS mandatory
  DESCRIPTION
      "The number of octets transmitted by this address 
      during the last TopN data collection period."
  ::= { olTRTrafTopNEntry 10 }

olTRTrafTopNOutErrors OBJECT-TYPE
  SYNTAX Counter
  ACCESS read-only
  STATUS mandatory
  DESCRIPTION
      "The number of error frames transmitted by this address
      during the last TopN data collection period.  Only isolating errors
      (LineErrors, BurstErrors, ACErrors, InternalErrors, and AbortErrors)
      and CongestionErrors are counted."
  ::= { olTRTrafTopNEntry 11 }

olTRTrafTopNOutBroadcastFrames OBJECT-TYPE
  SYNTAX Counter
  ACCESS read-only
  STATUS mandatory
  DESCRIPTION
      "The number of frames transmitted by this address
      that were directed to the broadcast address 
      during the last TopN data collection period."
  ::= { olTRTrafTopNEntry 12 }

olTRTrafTopNOutMulticastFrames OBJECT-TYPE
  SYNTAX Counter
  ACCESS read-only
  STATUS mandatory
  DESCRIPTION
      "The number of frames transmitted by this address
      that were directed to a multicast address 
      during the last TopN data collection period.
      Note that this number does not include frames
      directed to the broadcast address."
  ::= { olTRTrafTopNEntry 13 }



olTRTrafTopNSummaryTable OBJECT-TYPE
  SYNTAX SEQUENCE OF OlTRTrafTopNSummaryEntry
  ACCESS not-accessible
  STATUS mandatory
  DESCRIPTION
      "A list containing information from olTRTrafTopNTable
	provided for the convenience of network management stations
	that wish to obtain this information in condensed form."
  ::= { olTRnet 11 }

olTRTrafTopNSummaryEntry OBJECT-TYPE
  SYNTAX OlTRTrafTopNSummaryEntry
  ACCESS not-accessible
  STATUS mandatory
  DESCRIPTION
      "A segment of the Top N list for a particular statistic."
  INDEX { olTRTrafTopNSummaryNetID,
		olTRTrafTopNSummaryStatistic,
		olTRTrafTopNSummaryIndex }
  ::= { olTRTrafTopNSummaryTable 1 }

OlTRTrafTopNSummaryEntry ::= SEQUENCE {
  olTRTrafTopNSummaryNetID               INTEGER,
  olTRTrafTopNSummaryStatistic		  INTEGER,
  olTRTrafTopNSummaryIndex               INTEGER,
  olTRTrafTopNSummaryStations		OCTET STRING
}

olTRTrafTopNSummaryNetID OBJECT-TYPE
        SYNTAX INTEGER {
                isolated(2),
                token-ring-1(9),
                token-ring-2(10),
                token-ring-3(11),
                token-ring-4(12),
                token-ring-5(13),
                token-ring-6(14),
                token-ring-7(15)
                }
        ACCESS read-only
        STATUS mandatory
        DESCRIPTION
                "The network index that uniquely identifies this network.
                One of token-ring-1 through token-ring-7 or isolated."
        ::= { olTRTrafTopNSummaryEntry 1 }

olTRTrafTopNSummaryStatistic OBJECT-TYPE
  SYNTAX INTEGER {
	  olTRTrafTopNSummaryInFrames(1),
	  olTRTrafTopNSummaryOutFrames(2),
	  olTRTrafTopNSummaryInOctets(3),
	  olTRTrafTopNSummaryOutOctets(4),
	  olTRTrafTopNSummaryOutErrors(5),
	  olTRTrafTopNSummaryOutBroadcastFrames(6),
	  olTRTrafTopNSummaryOutMulticastFrames(7)
  }
  ACCESS read-write
  STATUS mandatory
  DESCRIPTION
      "The object representing the statistic for each station that this
      portion of the olTRTrafTopNSummaryTable is sorted on."
    ::= { olTRTrafTopNSummaryEntry 2 }

olTRTrafTopNSummaryIndex OBJECT-TYPE
  SYNTAX INTEGER
  ACCESS read-only
  STATUS mandatory
  DESCRIPTION
	"An index that uniquely identifies an entry in
	the olTRTrafTopNSummary table among those in the same network
	and for the same olTRTrafTopNSummaryStatistic.
	The number of entries for this portion of olTRTrafTopNSummaryTable
	is number of entries for the corresponding portion of
	olTRTrafTopNTable divided by 12 (rounded up to the next integer)."
  ::= { olTRTrafTopNSummaryEntry 3 }

olTRTrafTopNSummaryStations OBJECT-TYPE
        SYNTAX OCTET STRING
        ACCESS read-only
        STATUS mandatory
        DESCRIPTION
                "A concatonated list of (up to 12) MAC addresses,
		their associated slot and port, and a statistic value
		for traffic associated with stations on the ring.  Each entry
		has 36 octets. The first 6 octets are the MAC address.
                The 7th octet is the slot ID (or 255 if it is external
                to the concentrator or 254 if it is on a remote ring).
		The 8th is the port ID (or 255 if it is external to the
		concentrator or 254 if it is on a remote ring).
                The 9th through 36th octets contain the values of the
		statistics olTRTrafTopNInFrames, olTRTrafTopNOutFrames,
		olTRTrafTopNInOctets, olTRTrafTopNOutOctets,
		olTRTrafTopNOutErrors, olTRTrafTopNOutBroadcastFrames,
		and olTRTrafTopNOutMulticastFrames.  Each statistic is
		represented in 4 octets, most significant octet first.
                The stations are in order of decreasing values of the
		statistic referenced by olTRTrafTopNStatistic."
        ::= { olTRTrafTopNSummaryEntry 4 }




-- The olFDDInet Group				

olFDDIStatsModTable OBJECT-TYPE
	SYNTAX SEQUENCE OF OlFDDIStatsModEntry
	ACCESS not-accessible
	STATUS mandatory
	DESCRIPTION
		"A table of statistical information counted for each module
		in each FDDI network."
	::= { olFDDInet 2 }

olFDDIStatsModEntry OBJECT-TYPE
	SYNTAX OlFDDIStatsModEntry
	ACCESS not-accessible
	STATUS mandatory
	DESCRIPTION
		"A list of statistical information for each module
		on each FDDI network in the concentrator."
	INDEX { olFDDIStatsModSlotIndex }
	::= { olFDDIStatsModTable 1 }

OlFDDIStatsModEntry ::=
	SEQUENCE {
		olFDDIStatsModSlotIndex
			INTEGER,
		olFDDIStatsModMgtRcvErrs
			Counter,
		olFDDIStatsModMgtXmitErrs
			Counter,
		olFDDIStatsModBackplaneErrs
			Counter,
		olFDDIStatsModPllUnlockErrs
			Counter
		}

olFDDIStatsModSlotIndex OBJECT-TYPE
	SYNTAX INTEGER
	ACCESS read-only
	STATUS mandatory
	DESCRIPTION
		"The slot number that contains this module."
	::= { olFDDIStatsModEntry 1 }

olFDDIStatsModMgtRcvErrs OBJECT-TYPE
	SYNTAX Counter
	ACCESS read-only
	STATUS mandatory
	DESCRIPTION
                "The number of errors encountered while receiving data
                 on the Management Channel."
	::= { olFDDIStatsModEntry 2 }

olFDDIStatsModMgtXmitErrs OBJECT-TYPE
	SYNTAX Counter
	ACCESS read-only
	STATUS mandatory
	DESCRIPTION
                "The number of errors encountered while transmitting data
                 on the Management Channel."
	::= { olFDDIStatsModEntry 3 }

olFDDIStatsModBackplaneErrs OBJECT-TYPE
	SYNTAX Counter
	ACCESS read-only
	STATUS mandatory
	DESCRIPTION
                "The number of errors while receiving and transmitting 
                 network data on the backplane."
	::= { olFDDIStatsModEntry 4 }

olFDDIStatsModPllUnlockErrs OBJECT-TYPE
	SYNTAX Counter
	ACCESS read-only
	STATUS mandatory
	DESCRIPTION
                "The number of times the phased lock loop on the
                 backplane network data channel was lost."
	::= { olFDDIStatsModEntry 5 }


-- Port table

olFDDIStatsPortTable OBJECT-TYPE
	SYNTAX SEQUENCE OF OlFDDIStatsPortEntry
	ACCESS not-accessible
	STATUS mandatory
	DESCRIPTION
		"A table of statistical information counted for each Port
		in each FDDI network."
	::= { olFDDInet 3 }

olFDDIStatsPortEntry OBJECT-TYPE
	SYNTAX OlFDDIStatsPortEntry
	ACCESS not-accessible
	STATUS mandatory
	DESCRIPTION
		"A list of statistical information for each Port
		on each FDDI network in the concentrator."
	INDEX { olFDDIStatsPortSlotIndex, olFDDIStatsPortIndex }
	::= { olFDDIStatsPortTable 1 }

OlFDDIStatsPortEntry ::=
	SEQUENCE {
		olFDDIStatsPortSlotIndex
			INTEGER,
		olFDDIStatsPortIndex
			INTEGER,
		olFDDIStatsPortLCTFailCts
			Counter,
		olFDDIStatsPortLerEstimate
			Counter,
		olFDDIStatsPortLemRejectCts
			Counter,
		olFDDIStatsPortLemCts
			Counter
		}

olFDDIStatsPortSlotIndex OBJECT-TYPE
	SYNTAX INTEGER
	ACCESS read-only
	STATUS mandatory
	DESCRIPTION
		"The slot number that contains this Port."
	::= { olFDDIStatsPortEntry 1 }

olFDDIStatsPortIndex OBJECT-TYPE
	SYNTAX INTEGER
	ACCESS read-only
	STATUS mandatory
	DESCRIPTION
		"The Port number of this port"
	::= { olFDDIStatsPortEntry 2 }

olFDDIStatsPortLCTFailCts OBJECT-TYPE
	SYNTAX Counter
	ACCESS read-only
	STATUS mandatory
	DESCRIPTION
           "The count of the consecutive times the link
            confidence test (LCT) has failed during connection
            management. Once the connection has been established,
            the count is zeroed. (refer to ANSI 9.4.1)."
	::= { olFDDIStatsPortEntry 3 }

olFDDIStatsPortLerEstimate OBJECT-TYPE
	SYNTAX Gauge
	ACCESS read-only
	STATUS mandatory
	DESCRIPTION
            "A long term average link error rate.  It ranges
             from 10**-4 to 10**-15 and is reported as the
             absolute value of the exponent of the estimate
             (the larger the number, the smaller the value)."
	::= { olFDDIStatsPortEntry 4 }

olFDDIStatsPortLemRejectCts OBJECT-TYPE
	SYNTAX Counter
	ACCESS read-only
	STATUS mandatory
	DESCRIPTION
            "A link error monitoring count of the times that a
             link has been removed from the ring due to the
             LerCutOff threshold being exceeded."
	::= { olFDDIStatsPortEntry 5 }

olFDDIStatsPortLemCts OBJECT-TYPE
	SYNTAX Counter
	ACCESS read-only
	STATUS mandatory
	DESCRIPTION
            "The aggregate link error monitor error count, set
             to zero only on station power up. This variable's
             long term rate average is lerEstimate."
	::= { olFDDIStatsPortEntry 6 }


olFDDInetStatsTable OBJECT-TYPE
        SYNTAX SEQUENCE OF OlFDDInetStatsEntry
        ACCESS not-accessible
        STATUS mandatory
        DESCRIPTION
                "A table of statistical information counted for each FDDI
                network in the concentrator"
        ::= { olFDDInet 4 }
 
olFDDInetStatsEntry OBJECT-TYPE
        SYNTAX OlFDDInetStatsEntry
        ACCESS not-accessible
        STATUS mandatory
        DESCRIPTION
                "A list of statistical information for each FDDI
                network in the concentrator."
        INDEX { olFDDInetStatsNetID }
        ::= { olFDDInetStatsTable 1 }
 
OlFDDInetStatsEntry ::=
        SEQUENCE {
                olFDDInetStatsNetID
                        INTEGER,
                olFDDInetStatsRingOpCounts
                        Counter,
                olFDDInetStatsFrameCounts
                        Counter,
                olFDDInetStatsErrorCounts
                        Counter,
                olFDDInetStatsLostCounts
                        Counter,
                olFDDInetStatsFrameErrorRatio
                        INTEGER
        }
 
olFDDInetStatsNetID OBJECT-TYPE
        SYNTAX INTEGER {
                isolated(2), 
                fddi-1(16), 
                fddi-2(17), 
                fddi-3(18),
                fddi-4(19)
                } 
        ACCESS read-only
        STATUS mandatory
        DESCRIPTION
                "The network index that uniquely identifies this network.
                One of isolated, fddi-1, fddi-2, fddi-3, or fddi-4."
        ::= { olFDDInetStatsEntry 1 }
 
olFDDInetStatsRingOpCounts OBJECT-TYPE
        SYNTAX Counter
        ACCESS read-only
        STATUS mandatory
        DESCRIPTION
                "The number times the ring transitioned to operational."
        ::= { olFDDInetStatsEntry 2 }

olFDDInetStatsFrameCounts OBJECT-TYPE
        SYNTAX Counter
        ACCESS read-only
        STATUS mandatory
        DESCRIPTION
                "Frame_Ct (refer to ANSI MAC 2.2.1)."
        ::= { olFDDInetStatsEntry 3 }

olFDDInetStatsErrorCounts OBJECT-TYPE
        SYNTAX Counter
        ACCESS read-only
        STATUS mandatory
        DESCRIPTION
                "Error_Ct (refer to ANSI MAC 2.2.1)."
        ::= { olFDDInetStatsEntry 4 }

olFDDInetStatsLostCounts OBJECT-TYPE
        SYNTAX Counter
        ACCESS read-only
        STATUS mandatory
        DESCRIPTION
                "Lost_Ct (refer to ANSI MAC 2.2.1)."
        ::= { olFDDInetStatsEntry 5 }

olFDDInetStatsFrameErrorRatio OBJECT-TYPE
        SYNTAX INTEGER (1..65535)
        ACCESS read-only
        STATUS mandatory
        DESCRIPTION
                "This attribute is the actual ratio, ((delta
                 snmpFddiMACLostCt + delta snmpFddiMACErrorCt) /
                 (delta snmpFddiMACFrameCt + delta
                 snmpFddiMACLostCt)) x 2**16."
        ::= { olFDDInetStatsEntry 6 }







-- The olGroups group

-- These objects define ports which have been assigned to groups and actions
-- which can be performed on the groups.  To add ports to a group, 
-- olGroupSetAction should be set to add-ports(1) and the port(s) defined
-- by olGroupSetSlotIndex and olGroupSetPortIndex will be added to the group 
-- olGroupSetGroupID, if the port exists and is not a logical port.  To remove 
-- ports from a group, olGroupSetAction should be set to delete-ports(2) and 
-- the port(s) defined by olGroupSetSlotIndex and olGroupSetPortIndex will be 
-- removed from the group olGroupSetGroupID.   To change the admin state of 
-- all ports in the group, olGroupSetAction should be set to 
-- set-admin-state(3) and the ports in group olGroupSetGroupID will be set 
-- to the state defined in olGroupSetAdminState.

olGroupPortTable OBJECT-TYPE
	SYNTAX SEQUENCE OF OlGroupPortEntry
	ACCESS not-accessible
	STATUS mandatory
	DESCRIPTION
		"A list of groups that each port is in. Each port can
		can be in 0, 1, or many groups."
	::= { olGroups 1 }

olGroupPortEntry OBJECT-TYPE
	SYNTAX OlGroupPortEntry
	ACCESS not-accessible
	STATUS mandatory
	DESCRIPTION
		"The groups corresponding to a particular port."
	INDEX { olGroupPortSlotIndex, olGroupPortIndex }
	::= { olGroupPortTable 1 }

OlGroupPortEntry ::=
	SEQUENCE {
		olGroupPortSlotIndex
			INTEGER,
		olGroupPortIndex
			INTEGER,
		olGroupPortGroupID
			OCTET STRING
		}

olGroupPortSlotIndex OBJECT-TYPE
	SYNTAX INTEGER 
	ACCESS read-only
	STATUS mandatory
	DESCRIPTION
		"The slot number that contains this port."
	::= { olGroupPortEntry 1 }

olGroupPortIndex OBJECT-TYPE
	SYNTAX INTEGER 
	ACCESS read-only
	STATUS mandatory
	DESCRIPTION
		"The port number within this slot. Logical ports
		can not be put into groups."
	::= { olGroupPortEntry 2 }

olGroupPortGroupID OBJECT-TYPE
	SYNTAX OCTET STRING (SIZE(0..8))
	ACCESS read-only
	STATUS mandatory
	DESCRIPTION
		"The group(s) to which the port has been assigned." 
	::= { olGroupPortEntry 3 }


olGroupSummaryTable OBJECT-TYPE
	SYNTAX SEQUENCE OF OlGroupSummaryEntry
	ACCESS not-accessible
	STATUS mandatory
	DESCRIPTION
		"A table of condensed group information listing all the ports
		in each group."
	::= { olGroups 2 }

olGroupSummaryEntry OBJECT-TYPE
	SYNTAX OlGroupSummaryEntry
	ACCESS not-accessible
	STATUS mandatory
	DESCRIPTION
		"The summary of all the ports in a particular group."
	INDEX { olGroupSummaryGroupID, olGroupSummaryIndex }
	::= { olGroupSummaryTable 1 }

OlGroupSummaryEntry ::=
	SEQUENCE {
		olGroupSummaryGroupID
			INTEGER,
		olGroupSummaryIndex
			INTEGER,
		olGroupSummaryPorts
			OCTET STRING
		}

olGroupSummaryGroupID OBJECT-TYPE
	SYNTAX INTEGER {
		group-1(1),
		group-2(2),
		group-3(3),
		group-4(4),
		group-5(5),
		group-6(6),
		group-7(7),
		group-8(8)
		}
	ACCESS read-only
	STATUS mandatory
	DESCRIPTION
		"The group to which the ports have been assigned. A port
		can be in one or more groups."
	::= { olGroupSummaryEntry 1 }

olGroupSummaryIndex OBJECT-TYPE
	SYNTAX INTEGER
	ACCESS read-only
	STATUS mandatory
	DESCRIPTION 
		"The index into the summary array. Up to 256 ports will be shown
		in olGroupSummaryPorts for each value in this entry."
	::= { olGroupSummaryEntry 2 }

olGroupSummaryPorts OBJECT-TYPE
	SYNTAX OCTET STRING (SIZE(0..1400))
	ACCESS read-only
	STATUS mandatory
	DESCRIPTION 
		"A condensed list of all the ports in this group. The summary
		is in the format: Slotx PortX SlotY PortY ..."
	::= { olGroupSummaryEntry 3 }		 

		
olGroupSet	OBJECT IDENTIFIER ::= { olGroups 3 }


olGroupSetAction OBJECT-TYPE
	SYNTAX INTEGER {
		add-ports(1),
		clear-ports(2),
		set-admin-state(3)
	}
	ACCESS read-write
	STATUS mandatory
	DESCRIPTION
		"This object specifies the action that we apply on
		 a group. add-ports(1) adds port(s) to a group, 
		 clear-ports(2) clears (delete) port(s) from a group,
		 and set-admin-state sets the Admin State of 
		 the group."
	::= { olGroupSet 1 }


olGroupSetGroupID OBJECT-TYPE
	SYNTAX INTEGER {
		group-1(1),
		group-2(2),
		group-3(3),
		group-4(4),
		group-5(5),
		group-6(6),
		group-7(7),
		group-8(8),
		all-groups(255) -- only valid for olGroupSetAction of 
 				-- clear-ports(2)
		}
	ACCESS read-write
	STATUS mandatory
	DESCRIPTION
		"A group index that uniquely identifies this group. A port
		can be in zero, one, or more groups."
	::= { olGroupSet 2 }


olGroupSetSlotIndex OBJECT-TYPE
	SYNTAX INTEGER 
	ACCESS read-write
	STATUS mandatory
	DESCRIPTION
		"This object specifies the slot number of the port(s) that 
		are to be added/cleared to/from the group. This object should 
		be set whenever add-ports(1) or clear-ports(2) are selected 
		for olGroupSetAction.  Value 254 refers to all non-existing 
		ports, and value 255 refers to all slots which are only valid 
		when olGroupSetAction is clear-ports(2)."
 	::= { olGroupSet 3 }

olGroupSetPortIndex OBJECT-TYPE
	SYNTAX INTEGER 
	ACCESS read-write
	STATUS mandatory
	DESCRIPTION
		"This object specifies the port number of the port(s) that 
		are to be added/cleared to/from the group. This object should 
		be set whenever add-ports(1) or clear-ports(2) are selected 
		for olGroupSetAction. Value 255 refers to all ports."
	::= { olGroupSet 4 }


olGroupSetAdminState OBJECT-TYPE
	SYNTAX INTEGER {
		enabled(1),
		disabled(2)
	}
	ACCESS read-write
	STATUS mandatory
	DESCRIPTION
		"This object specifies the Admin State that all the ports in 
		the group defined by olGroupSetGroupID should be set to. 
		This object should be set whenever set-admin-state(3) is 
		selected for olGroupSetAction."
	::= { olGroupSet 5 }


--  Threshold Group

--	This group provides access to agent thresholding.
--	If the agent does not support thresholding, then
--	olThreshTable will have no entries.


olThreshTotalEntries OBJECT-TYPE
  SYNTAX INTEGER
  ACCESS read-only
  STATUS mandatory
  DESCRIPTION
	"The number of entries currently in olThreshTable."
    ::= { olThreshControl 1 }

olThreshMaxEntries OBJECT-TYPE
  SYNTAX INTEGER
  ACCESS read-only
  STATUS mandatory
  DESCRIPTION
	"The maximum number of entries in olThreshTable supported by
	this agent."
    ::= { olThreshControl 2 }

olThreshLastCreatedIndex OBJECT-TYPE
  SYNTAX INTEGER
  ACCESS read-only
  STATUS mandatory
  DESCRIPTION
	"The index of the last entry in olThreshTable created via index 255
	(see olThreshMode).  If none, this value will be zero."
    ::= { olThreshControl 3 }

olThreshAllMode OBJECT-TYPE
        SYNTAX INTEGER {
                enable(1),
                disable(2),
		clear(3)
                }
        ACCESS read-write
        STATUS mandatory
        DESCRIPTION
                "Provides the management station with a convenient way to set
		olThreshMode for all of the entries in ThreshTable.
		Setting olThreshAllMode to enable(1) or disable(2)
		will not cause new entries to be created; this
		will only affect entries that have presiously been created.
		Getting olThreshAllMode will always yield clear(3)."
        ::= { olThreshControl 4 }

olThreshTable OBJECT-TYPE
    SYNTAX SEQUENCE OF OlThreshEntry
    ACCESS not-accessible
    STATUS mandatory
    DESCRIPTION
	"A list of thresholding entries."
    ::= { olThresh 2 }

olThreshEntry OBJECT-TYPE
    SYNTAX OlThreshEntry
    ACCESS not-accessible
    STATUS mandatory
    DESCRIPTION
	"A collection of variables for controlling and monitoring a
	specific threshold."
    INDEX { olThreshIndex }
    ::= { olThreshTable 1 }

OlThreshEntry ::= SEQUENCE {
    olThreshIndex		INTEGER,
    olThreshMode		INTEGER,
    olThreshDescription		DisplayString,
    olThreshObjectIdentifier	OBJECT IDENTIFIER,
    olThreshStatCategory	INTEGER,
    olThreshStatType		INTEGER,
    olThreshStatNetID		INTEGER,
    olThreshStatSlotIndex	INTEGER,
    olThreshStatPortIndex	INTEGER,
    olThreshStatStationAddr	MacAddress,
    olThreshInterval		INTEGER,
    olThreshCondition		INTEGER,
    olThreshValue		INTEGER,
    olThreshCurrentValue	INTEGER,
    olThreshStatus		INTEGER,
    olThreshTimeSinceLastTriggered	TimeTicks,
    olThreshActionType		INTEGER,
    olThreshActionData		INTEGER,
    olThreshActionPriority	INTEGER
}

olThreshIndex OBJECT-TYPE
  SYNTAX INTEGER
  ACCESS read-only
  STATUS mandatory
  DESCRIPTION
	"An index that uniquely identifies an entry in
	the olThresh table.  The number of entries in olTRThreshTable
	is olThreshTotalEntries.  A new entry is created when a value is
	written to any object within the entry.  An entry is removed when 
	olThreshMode is set to clear(3).
	Index 255 references a 'pseudo entry' that allows
	the management station to create a new entry without having to 
	search for a clear entry.
	When olThreshMode for entry 255 is set to disable or enable, 
	if there is no available (clear) entry, then the SNMP set-response will
	indicate a bad value error, otherwise the agent does the following:
	    - set the value of olThreshLastCreatedIndex to the index
		of the available entry
	    - copy the values currently in entry 255 to the available entry
	    - clear out entry 255."
  ::= { olThreshEntry 1 }

olThreshMode OBJECT-TYPE
        SYNTAX INTEGER {
                enable(1),
                disable(2),
		clear(3)
                }
        ACCESS read-write
        STATUS mandatory
        DESCRIPTION
                "The mode for this threshold.
		enable(1) indicates that this entry
		is in use and thresholding will be done.
		disable(2) indicates that this entry
		is in use but will no thresholding will be done.
		Setting olThreshMode to clear(3)  will cause this entry to be
		removed from the table."
--      DEFVAL {disable(2)}
        ::= { olThreshEntry 2 }

olThreshDescription OBJECT-TYPE
        SYNTAX DisplayString (SIZE(0..40))
        ACCESS read-write
        STATUS mandatory
        DESCRIPTION
		"Description of the threshold to be sent with the
		chipAboveThreshold trap."
        ::= { olThreshEntry 3 }

olThreshObjectIdentifier OBJECT-TYPE
        SYNTAX OBJECT IDENTIFIER
        ACCESS read-write
        STATUS mandatory
        DESCRIPTION
                "The object identifier that specifies the statistic to be
		thresholded.  The statistic to be thresholded can be 
		specified either by setting olThreshObjectIdentifier
		or by setting values of the olThreshStat group of variables.
		When olThreshObjectIdentifier is set, the agent changes
		the values of the olThreshStat group of variables
		to refer to the new statistic to be thresholded.
		Similarly, when a olThreshStat variable is set, the agent
		changes olThreshObjectIdentifier to refer to the new statistic
		to be thresholded.  A null object identifier (0.0) is used
		when no statistic is specified."
        ::= { olThreshEntry 4 }

olThreshStatCategory OBJECT-TYPE
        SYNTAX INTEGER {
		other(1),
		network(2),
		port(3),
		station(4)
	}
        ACCESS read-write
        STATUS mandatory
        DESCRIPTION
                "Specifies the category of statistic to be thresholded.
		When olThreshStatCategory is network(2) or station(4),
		olThreshStatNetID may also be specified.
		When olThreshStatCategory is station(4),
		olThreshStatStation must be specified.
		When olThreshStatCategory is port(3), olThreshStatSlotIndex
		and olThreshStatPortIndex must be specified."

--      DEFVAL {network(2)}
        ::= { olThreshEntry 5 }

olThreshStatType OBJECT-TYPE
        SYNTAX INTEGER {
		other(1),
		frames(2),
		octets(3),
		broadcast-frames(4),
		multicast-frames(5),
		error-frames(6),
		tr-net-soft-errors(7),
		tr-net-hard-errors(8)
	}
        ACCESS read-write
        STATUS mandatory
        DESCRIPTION
                "Specifies the type of statistic to be thresholded.
		error-frames(6) is valid only when olThreshStatCategory is
		port(3) or station(4).  tr-net-soft-errors(7) or
		tr-net-hard-errors(8) is valid only when olThreshStatCategory
		is network(2).  Note that tr-net-soft-errors(7) and 
		tr-net-hard-errors(8) refer to dot5StatsSoftErrors
		and dot5StatsHardErrors, respectively.  The other choices
		refer for items in the olTRTraf tables."
--      DEFVAL {frames(2)}
        ::= { olThreshEntry 6 }

olThreshStatNetID OBJECT-TYPE
        SYNTAX INTEGER {
		other(1),
		isolated(2),
		token-ring-1(9),
		token-ring-2(10),
		token-ring-3(11),
		token-ring-4(12),
		token-ring-5(13),
		token-ring-6(14),
		token-ring-7(15),
		agent-network(255)
	}
        ACCESS read-write
        STATUS mandatory
        DESCRIPTION
                "When olThreshStatCategory is network(2) or station(4),
		specifies the network of statistic to be thresholded.  
		If the agent is capable of collecting statistics only for
		the network that it is attached to, olThreshStatNetID can
		be set to agent-network(255); the agent will change
		olThreshStatNetID to reflect the network that the agent
		is currently attached to.  If olThreshStatType is
		tr-net-soft-errors(7) or tr-net-hard-errors(8) the
		agent will change olThreshStatNetID to other(1)."
--      DEFVAL {agent-network(255)}
        ::= { olThreshEntry 7 }

olThreshStatSlotIndex OBJECT-TYPE
        SYNTAX INTEGER
        ACCESS read-write
        STATUS mandatory
        DESCRIPTION
                "When olThreshStatCategory is port(3), specifies the
		slot index of the port of statistic to be thresholded."
        ::= { olThreshEntry 8 }

olThreshStatPortIndex OBJECT-TYPE
        SYNTAX INTEGER
        ACCESS read-write
        STATUS mandatory
        DESCRIPTION
                "When olThreshStatCategory is port(3), specifies the
		port index of the port of statistic to be thresholded."
        ::= { olThreshEntry 9 }

olThreshStatStationAddr OBJECT-TYPE
        SYNTAX MacAddress
        ACCESS read-write
        STATUS mandatory
        DESCRIPTION
                "When olThreshStatCategory is station(4), specifies the
		MAC address of the station of statistic to be thresholded."
        ::= { olThreshEntry 10 }

olThreshInterval OBJECT-TYPE
        SYNTAX INTEGER
        ACCESS read-write
        STATUS mandatory
        DESCRIPTION
                "Specifies the length of the thresholding period in seconds.
		Minimum length is 5 seconds; maximum is 86400 seconds
		(24 hours)."
--      DEFVAL {60}
        ::= { olThreshEntry 11 }

olThreshCondition OBJECT-TYPE
        SYNTAX INTEGER {
		delta-above(1)
	}
        ACCESS read-write
        STATUS mandatory
        DESCRIPTION
                "Specifies the type of conditional comparison for the
		threshold."
--	  Possible future values for olThreshCondition: delta-below,
--	  absolute-above, absolute-below
--      DEFVAL {delta-above(1)}
        ::= { olThreshEntry 12 }

olThreshValue OBJECT-TYPE
        SYNTAX INTEGER
        ACCESS read-write
        STATUS mandatory
        DESCRIPTION
            "At the end of each thresholding interval (olThreshInterval
	    seconds), olThreshCurrentValue is compared against
	    olThreshValue (unsigned).
	    When olThreshType is delta-above(1):
		If olThreshStatus is valid(4), and olThreshCurrentValue is
		above olThreshValue, and olThreshMode is enabled,
		then a chipAboveThreshold trap will be sent.
		Another chipAboveThreshold trap will not be sent until
		olThreshCurrentValue drops to less than or equal to
		olThreshValue and then again exceeds it."
--      DEFVAL { 0 }
        ::= { olThreshEntry 13 }

olThreshCurrentValue OBJECT-TYPE
        SYNTAX INTEGER
        ACCESS read-only
        STATUS mandatory
        DESCRIPTION
	    "When olThreshType is delta-exceed(1):
		The most recent delta value of olThreshStatObjectIdentifier
		(i.e. value of olThreshStatObjectIdentifier at the end of
		the interval minus the value of olThreshStatObjectIdentifier
		at the beginning of the interval).
	    If olThreshStatus is not valid(4), olThreshCurrentValue will be 0."
        ::= { olThreshEntry 14 }

olThreshStatus OBJECT-TYPE
        SYNTAX INTEGER {
		no-statistic-specified(1),
		statistic-not-accessible(2),
		not-yet-available(3),
		valid(4)
	}
        ACCESS read-only
        STATUS mandatory
        DESCRIPTION
	    "When olThreshType is delta-exceed(1):
		If olThreshStatObjectIdentifier has not yet been specified,
		olThreshStatus will be no-statistic-specified(1).
		If the first interval has not yet completed,
		olThreshStatus will be not-yet-available(2).
		If object referenced by olThreshStatObjectIdentifier is not
		accessible, olThreshStatus will be not-accessible(3).
		Otherwise olThreshStatus will be valid(4)."
        ::= { olThreshEntry 15 }

olThreshTimeSinceLastTriggered OBJECT-TYPE
  SYNTAX TimeTicks
  ACCESS read-only
  STATUS mandatory
  DESCRIPTION
	"Time in TimeTicks that has elapsed since a chipAboveThreshold trap 
	associated with this ThreshEntry was last sent.
	If never sent, this value shall be zero."
    ::= { olThreshEntry 16 }

olThreshActionType OBJECT-TYPE
        SYNTAX INTEGER {
		trap-only(1)
	}
        ACCESS read-write
        STATUS mandatory
        DESCRIPTION
		"The action to be performed when the threshold is triggered."
--	  Possible future olThreshActionTypes: log, execute-script
--      DEFVAL {trap-only(1)}
    ::= { olThreshEntry 17 }

olThreshActionData OBJECT-TYPE
        SYNTAX INTEGER
        ACCESS read-write
        STATUS mandatory
        DESCRIPTION
		"Additional information to be sent with the
		chipAboveThreshold trap.  Provided for use by the
		network management station (NMS) - not interpreted by
		the agent.  A network management station (NMS)
		could use olThreshActionData to specify an action to be
		performed by the NMS when the chipAboveThreshold trap
		is received."
--	  Possible future use: specify which script to execute
    ::= { olThreshEntry 18 }

olThreshActionPriority OBJECT-TYPE
        SYNTAX INTEGER {
		low(1),
		medium(2),
		high(3)
	}
        ACCESS read-write
        STATUS mandatory
        DESCRIPTION
		"The priority for this entry.  Provided for use by the
		network management station (NMS) - not interpreted by
		the agent."
--      DEFVAL {low(1)}
    ::= { olThreshEntry 19 }








-- The chipTTY Group:
-- 
-- The following group is used to manage agent terminal ports.
--
-- 

chipTTYNumber OBJECT-TYPE
	SYNTAX INTEGER
	ACCESS read-only
	STATUS mandatory
	DESCRIPTION
		"The number of terminal ports on this agent product."
	::= { chipTTY 1 }

chipTTYTable OBJECT-TYPE
	SYNTAX  SEQUENCE OF ChipTTYEntry
	ACCESS  not-accessible
	STATUS  mandatory
	DESCRIPTION
		"A table of TTY specific information associated with 
                this agent."
	::= { chipTTY 2 }

chipTTYEntry OBJECT-TYPE
	SYNTAX  ChipTTYEntry
	ACCESS  not-accessible
	STATUS  mandatory
	DESCRIPTION
		"A profile of a specific TTY interface associated with 
		this agent."
	INDEX 	{ chipTTYIndex }
	::= { chipTTYTable 1 }

ChipTTYEntry ::=
	SEQUENCE {
		chipTTYIndex
			INTEGER,
		chipTTYBaud
			INTEGER,
		chipTTYParity
			INTEGER,
		chipTTYStop
			INTEGER,
		chipTTYData
			INTEGER,
		chipTTYTimeout
			INTEGER,
		chipTTYPrompt
			DisplayString,
		chipTTYDTR
			INTEGER,
                chipTTYTerminalType
			DisplayString
		}

chipTTYIndex 	OBJECT-TYPE
	SYNTAX	INTEGER
	ACCESS  read-only
	STATUS	mandatory
	DESCRIPTION
		"The TTY to which this entry refers."
	::= { chipTTYEntry 1 }	

chipTTYBaud 	OBJECT-TYPE
	SYNTAX	INTEGER {
		one-hundred-ten(110),
		three-hundred(300),
		twelve-hundred(1200),
		twenty-four-hundred(2400),
		forty-eight-hundred(4800),
		ninety-six-hundred(9600),	
		nineteen-two-hundred(19200),
		thirty-eight-thousand-four-hundred(38400)
		}
	ACCESS  read-write
	STATUS	mandatory
	DESCRIPTION
		"The baud rate for this TTY. It should be noted that all
		 serial ports do not support all of the above baud rates."
	::= { chipTTYEntry 2 }	

chipTTYParity 	OBJECT-TYPE
	SYNTAX	INTEGER {
		odd(1),
		even(2),
		none(3)
		}
	ACCESS  read-write
	STATUS	mandatory
	DESCRIPTION
		"The parity setting for this TTY."
	::= { chipTTYEntry 3 }	

chipTTYStop 	OBJECT-TYPE
	SYNTAX	INTEGER {
		one(1),
		two(2)
		}
	ACCESS  read-write
	STATUS	mandatory
	DESCRIPTION
		"The number of stop bits for this TTY."
	::= { chipTTYEntry 4 }	

chipTTYData 	OBJECT-TYPE
	SYNTAX	INTEGER {
		seven(7),	
		eight(8)
		}		
	ACCESS  read-write
	STATUS	mandatory
	DESCRIPTION
		"The number of data bits for this TTY."
	::= { chipTTYEntry 5 }	

chipTTYTimeout 	OBJECT-TYPE
	SYNTAX	INTEGER
	ACCESS  read-write
	STATUS	mandatory
	DESCRIPTION
		"The number of minutes to wait before this agent logs out
		an inactive login session on this TTY.
		NOTE: In some implementations, this is a single variable 
                      that is used by all of the terminal and telnet 
                      sessions."
	::= { chipTTYEntry 6 }	

chipTTYPrompt 	OBJECT-TYPE
	SYNTAX	DisplayString (SIZE(0..15))
	ACCESS  read-write
	STATUS	mandatory
	DESCRIPTION
		"The terminal prompt to display on this TTY.
		NOTE: In some implementations, this is a single variable 
                      that is used by all of the terminal and telnet 
                      sessions."
	::= { chipTTYEntry 7 }	

chipTTYDTR 	OBJECT-TYPE
	SYNTAX	INTEGER {
			asserted(1),
			deasserted(2)
		}
	ACCESS  read-write
	STATUS	mandatory
	DESCRIPTION
		"This value dictates the behavior of the RS-232 Data
		Terminal Ready (DTR) signal at the time a session ends
		due to a logout, timeout, or shutdown.  This is used by
		some modems as an indication that they should hangup.
                This variable is only support if the RS-232 port has a 
                DTR signal."
	::= { chipTTYEntry 8 }	

chipTTYTerminalType   OBJECT-TYPE
      SYNTAX  DisplayString (SIZE(1..40))
      ACCESS  read-write
      STATUS  mandatory
      DESCRIPTION
              "A string which indicates the type of terminal that
              is attached to the serial port. It should be noted that
              the string is passed to a telnet server whenever the server
              issues the IAC DO TERMINAL-TYPE command (see rfc884)."
      ::= { chipTTYEntry 9 }

-- The chipTFTP Group
--
-- Implementation of the chipTFTP group is mandatory for all agent
-- products that support TFTP file transfers.
-- 
-- The chipTFTP Group is used by a station to initiate a TFTP transfer
-- from a TFTP server to this agent (the TFTP client).  
--
-- In order to initiate a TFTP file transfer, the client must know
-- the following information:
--
-- 1. The operation to perform, either a get or a put (chipTFTPStart).
-- 2. What station is acting as the TFTP server (chipTFTPIpAddress).
-- 3. The file name (chipTFTPFileName) and the file type (chipTFTPFileType).
--        The file name can be a pathname.  The file type indicates to
--	  the agent what kind of information is being transferred.
-- 4. What module should receive the file (chipTFTPSlot).
--
--
-- For example, if one wished to inband download flash code to this agent,
-- one would set:
--
-- File type 	= Flash code
-- Slot number 	= This agent (255).
-- File name    = Pathname on the server where the file is located.
-- IP Address   = The IP of the TFTP file server.
-- TFTP Start   = get - retrieve the file from the server.
--
-- After setting the start object, the transfer takes place.  The  
-- chipTFTPResult object contains the result of the last TFTP transfer
-- attempted.
-- 

chipTFTPStart OBJECT-TYPE
	SYNTAX INTEGER {
		tftpNoTransfer(1),
		tftpGet(2),	-- download to agent
		tftpPut(3)	-- upload to server
		}
	ACCESS read-write
	STATUS mandatory
	DESCRIPTION
		"Setting chipTFTPStart to tftpGet(2) initiates a file
		transfer to the agent (download); tftpPut(3) initiates
		a file transfer to the server (upload)."
	::= { chipTFTP 1 }

chipTFTPSlot OBJECT-TYPE
	SYNTAX INTEGER {
		slot-1(1),
		slot-2(2),
		slot-3(3),
		slot-4(4),
		slot-5(5),
		slot-6(6),
		slot-7(7),
		slot-8(8),
		slot-9(9),
		slot-10(10),
		slot-11(11),
		slot-12(12),
		slot-13(13),
		slot-14(14),
		slot-15(15),
		slot-16(16),
		slot-17(17),
		agent-slot(255)
	}
	ACCESS	read-write
	STATUS 	mandatory
	DESCRIPTION
		"The slot number of the module that is to be involved 
		in the TFTP transfer with the TFTP server (chipTFTPIpAddress)."
	::= { chipTFTP 2 }
		
chipTFTPIpAddress OBJECT-TYPE
	SYNTAX IpAddress
	ACCESS read-write
	STATUS mandatory
	DESCRIPTION
		"The IP Address of the TFTP server."
	::= { chipTFTP 3 }

chipTFTPFileName OBJECT-TYPE
	SYNTAX DisplayString (SIZE(0..128))
	ACCESS read-write
	STATUS mandatory
	DESCRIPTION
		"The file name of the file to retrieve (tftpGet), or the 
		name of	the file to create (tftpPut). "
	::= { chipTFTP 4 }


chipTFTPFileType OBJECT-TYPE
	SYNTAX INTEGER {
		flashCode(1),
		bootCode(2)
		}
	ACCESS read-write
	STATUS mandatory
	DESCRIPTION
		"The type of file image to upload/download.  The file
		type indicates to the agent what kind of file it is
		receiving.  flashCode(1) indicates a code upgrade of
		the operational proms.  bootCode(2) indicates a code
		upgrade of the boot proms."
	::= { chipTFTP 5 }


chipTFTPResult OBJECT-TYPE
	SYNTAX INTEGER {
		clear(1),--not initialized
		xferInProgress(2),
		okay(3),
		otherTFTPError(4),
		fileNotFound(5),-- check for valid file name
		accessError(6),
		diskFull(7),-- server disk is full
 		illegalTFTPOperation(8),
		invalidTFTPTransactionID(9),
		noResponse(10),-- check valid server IP address 
		invalidDownloadKey(11),
		invalidSlot(12),
		invalidNetwork(13),
		fepromErase(14),
		fepromProg(15),
		xferError(16),
		decodeError(17)
		}	
	ACCESS read-only
	STATUS mandatory
	DESCRIPTION
		"The result of the last TFTP operation."
	::= { chipTFTP 6 }




-- chipDownload Group
--
-- To begin an in_band download through SNMP the following mib objects 
-- along with the chipTFTP objects must be completed with the correct
-- information.  
--
-- Before download is allowed to begin, the agent will verify the
-- Software Key.  If the Software Key is found to be valid, download
-- will follow.  Otherwise, chipTFTPResult is set to (9)invalidDown-
-- loadKey.


chipDownloadUDKSerial OBJECT-TYPE
	SYNTAX DisplayString (SIZE(0..8))
     	ACCESS read-write
     	STATUS mandatory
     	DESCRIPTION
		"A string representing the serial number of the
		 Upgrade Distribution Kit."
	::= { chipDownload 1 }

chipDownloadKey OBJECT-TYPE
	SYNTAX DisplayString (SIZE(0..8))
	ACCESS read-write
	STATUS mandatory
	DESCRIPTION
		"The key code provided by your VAR. Available by
		 calling technical support at +1 508 460 6195."
	::= { chipDownload 2 }

chipDownloadDateTime OBJECT-TYPE
	SYNTAX DisplayString (SIZE(0..20))
	ACCESS read-only
	STATUS mandatory
	DESCRIPTION
		"The date of the last successful download in the 
		 format hh:mm day DD Mon YY"
	::= { chipDownload 3 }








	








-- Chipcom Traps for use by agents.

-- Traps are defined using the conventions in RFC 1215.

chipHello TRAP-TYPE
	ENTERPRISE 	chipcom
--	VARIABLES	{ sysObjectID }
	DESCRIPTION
		"A chipHello trap is sent every minute by an agent with
		the hello trap enabled.  The hello trap will discontinue
		being sent when either the agent receives an authenticate
		SNMP request, or after 255 minutes."
	::= 1

chipSlotDown TRAP-TYPE
	ENTERPRISE 	chipcom
	VARIABLES	{ olModSlotIndex }
	DESCRIPTION
		"This trap indicates that the module in the indicated
		slot is down.  Usually, this trap is sent when the module
		has been removed. 

		Sometimes, this trap is sent when management communications
		with this module have been broken.  In this case, it may not
		be possible to distinguish between a removed and a failed 
		module.  The module type (olModType) and the module 
		description (olModDescr) are also provided in this case."
	::= 2

chipSlotUp TRAP-TYPE
	ENTERPRISE 	chipcom
	VARIABLES	{ olModSlotIndex }
	DESCRIPTION
		"This trap indicates that a blade in the indicated slot
		is up.  Usually, this trap is sent when the module is
		inserted into the hub.  

		Sometimes, this trap is sent when management communications 
		have been restored to a module where they had previously 
		been broken.  In this case, it may not be possible to 
		distinguish between a module that has just be inserted 
		and a module that has just the.  The module type (olModType)
		and the module description (olModDescr) are also provided
		in this case."
	::= 3

chipEnvironment TRAP-TYPE
	ENTERPRISE 	chipcom
	DESCRIPTION
		"A chipEnvironment trap indicates a change in the 
		concentrator's environment has occurred.  The variables
		supplied indicate what exactly changed."
	::= 4

chipHardware TRAP-TYPE
	ENTERPRISE 	chipcom
	DESCRIPTION
		"A chipHardware trap indicates that a soft hardware
		failure has been detected.  An example of a soft
		hardware failure is too many writes to non-vatile
		storage.  This is an indication to get the unit serviced."
	::= 5

chipSoftware TRAP-TYPE
	ENTERPRISE 	chipcom
	DESCRIPTION
		"A chipSoftware trap indicates that a soft software
		failure has been detected.  This is an indication
		to get the unit serviced."
	::= 6

chipChange TRAP-TYPE
	ENTERPRISE 	chipcom
	DESCRIPTION
		"A chipChange trap is used to indicate that a configuration
		change has occurred.  The actual variables that changed
		are included in the variables section of the PDU."
	::= 7

chipFatal TRAP-TYPE
	ENTERPRISE 	chipcom
	DESCRIPTION
		"A chipFatal trap is used to indicate that a fatal 
		error has occurred.  This is an indication to get
		the unit serviced."
	::= 8

chipTrunkDown TRAP-TYPE
	ENTERPRISE 	chipcom
	VARIABLES 	{ olTrunkSlotIndex,
			  olTrunkIndex,
			  olTrunkAdminState, 
			  olTrunkStatus }
	DESCRIPTION
		"A chipTrunkDown trap indicates that trunk's status
		has changed to an error condition.  Multiple chipTrunkDown
		traps may be sent if the trunk's status changes from
		one error to another."
	::= 9

chipTrunkUp TRAP-TYPE
	ENTERPRISE 	chipcom
	VARIABLES 	{ olTrunkSlotIndex,
			  olTrunkIndex,
			  olTrunkAdminState, 
			  olTrunkStatus }
	DESCRIPTION
		"A chipTrunkUp trap indicates that a trunk's status
		has changed to a non-error (okay or warning) condition."

	::= 10

chipPortDown TRAP-TYPE
	ENTERPRISE 	chipcom
	VARIABLES	{ olPortSlotIndex, 
			  olPortIndex,
			  olPortAdminState, 
			  olPortStatus }
	DESCRIPTION
		"A chipPortDown trap indicates that a port's status
		has changed to an error condition.  Multiple chipPortDown
		traps may be sent if the port's status changes from
		one error to another."
	::= 11

chipPortUp TRAP-TYPE
	ENTERPRISE 	chipcom
	VARIABLES	{ olPortSlotIndex, 
			  olPortIndex,
			  olPortAdminState, 
			  olPortStatus }
	DESCRIPTION
		"A chipPortUp trap indicates that a port's status
		has changed to a non-error (okay or warning) condition."
	::= 12

chipPing TRAP-TYPE
	ENTERPRISE	chipcom
	VARIABLES	{ chipEchoAddr, chipEchoNumber, chipEchoResponseCounts }
	DESCRIPTION
		"A chipPing trap is sent after the SNMP initiated PING
		command is completed.  After the last echo request packet
		is sent, this trap is sent indicating the ping address,
		the number of requests sent, and the number of responses
		received at the time the trap was generated."
	::= 13

chipAboveThreshd TRAP-TYPE
	ENTERPRISE	chipcom
	DESCRIPTION
                "A chipAboveThreshd trap indicates that a Counter or 
                 Gauge variable has exceeded its threshd. The variable
                 which is above its threshd is the only variable in
                 the varBind list. Its value is taken at the time the
                 threshd calculation is performed and therefore may be
                 greater than the actual threshd value. Another above 
                 threshd trap will not be sent until a below 
                 threshd trap is sent."
	::= 14

chipBelowThreshd TRAP-TYPE
	ENTERPRISE	chipcom
	DESCRIPTION
                "A chipBelowThreshd trap indicates that a Counter or 
                 Gauge variable had exceeded its threshd but is now 
                 below its threshd. The variable which is below its 
                 threshd is the only variable in the varBind list. 
                 Its value is taken at the time the threshd calculation
                 is performed and therefore may be less than the 
                 actual threshd value. Another below threshd trap 
                 will not be sent until an above threshd trap is sent."
	::= 15




END
