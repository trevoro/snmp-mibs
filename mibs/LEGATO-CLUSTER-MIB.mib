LEGATO-CLUSTER-MIB DEFINITIONS ::= BEGIN

  IMPORTS
	TRAP-TYPE FROM RFC-1215
    enterprises, IpAddress, Counter, Gauge
      FROM RFC1155-SMI
    OBJECT-TYPE
      FROM RFC-1212;
  --
  -- Legato Cluster Mib - originated 09/21/98
  --
  -- Last Modification:
  --


  DisplayString ::= OCTET STRING


  legatoSoftware   OBJECT IDENTIFIER ::= { enterprises 1676 }
  products    	     OBJECT IDENTIFIER ::= { legatoSoftware 1 }
  legatoCluster    OBJECT IDENTIFIER ::= { products 4 }

  clusterMessage     OBJECT IDENTIFIER ::= { legatoCluster 1 }


  -- msg Group
  trapSeverity OBJECT-TYPE
    SYNTAX  INTEGER 		{
				info(1),
				warning(2),
				severe(3)
				}
    ACCESS  read-only
    STATUS  mandatory
    DESCRIPTION
      "The severity level of the current trap."
    ::= { clusterMessage 1 }

  trapText OBJECT-TYPE
    SYNTAX  DisplayString  (SIZE (0..255))
    ACCESS  read-only
    STATUS  mandatory
    DESCRIPTION
      "The text of the current trap."
    ::= { clusterMessage 2 }


-- Traps
-- The enterprise used for for this trap mib is enterprises.LegatoSoftware.products.LegatoCluster

  legatoClusterUserTrap TRAP-TYPE
    ENTERPRISE legatoCluster
    VARIABLES {trapText, trapSeverity }
    DESCRIPTION
      "A trap was received from a Legato Cluster Rule."
    ::= 1
   

END
