-- *****************************************************************************
-- Unisphere-Data-VRRP-CONF
--
-- SNMP Agent Capabilities definitions for the VRRP MIB.
--
-- Copyright (c) 2002 Unisphere Networks, Inc.  All rights reserved.
-- *****************************************************************************

Unisphere-Data-VRRP-CONF DEFINITIONS ::= BEGIN

IMPORTS
    MODULE-IDENTITY
        FROM SNMPv2-SMI
    AGENT-CAPABILITIES
        FROM SNMPv2-CONF
    vrrpOperGroup, vrrpStatsGroup, vrrpTrapGroup, vrrpNotificationGroup
        FROM VRRP-MIB
    usDataAgents
        FROM Unisphere-Data-Agents;

usdVrrpAgent MODULE-IDENTITY
    LAST-UPDATED "200201241520Z"  -- 24-Jan-02 10:20 AM EST
    ORGANIZATION "Unisphere Networks, Inc."
    CONTACT-INFO
        "       Unisphere Networks, Inc.
        Postal: 10 Technology Park Drive
                Westford, MA 01886
                USA
        Tel:    +1 978 589 5800
        E-mail: mib@UnisphereNetworks.com"
    DESCRIPTION
        "The agent capabilities definitions for the Virtual Router Redundancy
        Protocol (VRRP) component of the SNMP agent in the Unisphere Routing
        Switch family of products."
    -- Revision History
    REVISION    "200201241520Z"  -- 24-Jan-02 10:20 AM EST  - RX 3.4
    DESCRIPTION
        "The initial release of this management information module."
    ::= { usDataAgents 53 }

usdVrrpAgentV1 AGENT-CAPABILITIES
    PRODUCT-RELEASE
        "Version 1 of the VRRP component of the Unisphere Routing Switch SNMP
        agent.  This version of the VRRP component is supported in the Unisphere
        RX 3.4 and subsequent system releases."
    STATUS      current
    DESCRIPTION
        "The MIB supported by the SNMP agent for the VRRP application in the
        Unisphere Routing Switch."
    SUPPORTS    VRRP-MIB
        INCLUDES  {
            vrrpOperGroup,
            vrrpStatsGroup,
            vrrpTrapGroup,
            vrrpNotificationGroup }
    ::= { usdVrrpAgent 1 }

END
