-- ****************************************************************************
--                             nms553.mib
-- ****************************************************************************

-- Copyright 1995 General DataComm Inc., All Rights Reserved.
--
-- Reproduction of this document is authorized on condition that the
-- foregoing copyright notice is included. This General DataComm, GDC,
-- SNMP Management Information Base Specification embodies GDCs'
-- confidential and proprietary intellectual property. GDC retains all
-- title and ownership in the Specification, including any revisions.
--
-- It is GDCs intent to encourage the widespread use of this Specification
-- in connection with the management of GDC's products. GDC grants vendors,
-- end-users, and other interested parties a non-exclusive license to use
-- this Specification in connection with the management of GDC's products.
--
-- This Specification is supplied "AS IS," and GDC makes no warranty,
-- either expressed or implied, as to the use operation, condition, or
-- performance of the Specification.

-- This MIB module uses the extended OBJECT-TYPE macro as
-- defined in RFC 1212.

-- Note:  All rows in all tables defined within this MIB module are
-- virtual.  They can neither be created or deleted by management
-- operations.



-- ****************************************************************************
--                        Revision History
-- ****************************************************************************

-- Version   Date	Name

-- 1.00A     17-Jan-96  R. Prasad     Initial Revision
-- 1.00B     21-Feb-96  D. Baylis     Added nms553DiagTestStatus to Nms553DiagEntry 
-- 1.00C     28-Feb-96  D. Baylis     Split nms553NetworkInbandLoopCfg into:
--					1) nms553NetworkInbandFrame 
--					2) nms553NetworkLoopbackConfig
-- 1.00D     06-Mar-96  D.Baylis      Removed octet 3 from nms553DteStat
-- 1.00E     12-Mar-96  D.Baylis      Removed 2 entries from alarm table:
--					1) nms553MbiLock
--					2) nms553LocalPwrFail	
-- 1.00F     18-Mar-96  D.Baylis      Removed enum: none(1)
--                                    from nms553DS0AlloctionInbandDccMode  
-- 1.00G     19-Mar-96  D.Baylis      Add enum: 
--					1) none(1) back to 	   					
--                                   	nms553DS0AlloctionInbandDccMode  
--					2) object nms553ConfigurationSave
-- 1.00H     03-Apr-96  D.Baylis      1) Merged 2 objects:
--					a) nms553DiagSendCode 
--					b) nms553DiagBeginSelfTest (old)
--					   into new: nms553DiagBeginSelfTest
--				      2) Changed nms553ConfigurationSave enums to:
--          				network(1),	write-only
--          				channel(2),	write-only
--          				both(3),	write-only
--          				norm(4)        	read-only
--	
-- 1.00J     09-Apr-96 D. Baylis      Add nolooptestrunning(4) enum to
--                                    nms553DiagBeginLoopTest object
--
-- 1.00K     10-Apr-96 D. Baylis      Change nms553PowerUpAlm Type to Informational
--                                    (was major)
-- 1.00M     29-Apr-96 D. Baylis      Changed nms553NetworkFallbackClockSource
--				      to have only 2 enums: internal and receive
-- ****************************************************************************


-- ****************************************************************************
--                       mib definitions begin
-- ****************************************************************************


NMS-553-MIB DEFINITIONS ::= BEGIN

IMPORTS	
        Gauge				FROM RFC1155-SMI
	OBJECT-TYPE			FROM RFC-1212
	DisplayString			FROM RFC1213-MIB
	gdc				FROM GDCCMN-MIB
	SCinstance			FROM GDCMACRO-MIB;

dsx1                   OBJECT IDENTIFIER ::= { gdc 6 }
nms553                 OBJECT IDENTIFIER ::= { dsx1 7 }

nms553Version          OBJECT IDENTIFIER ::= { nms553 1 }
nms553DS0Allocation    OBJECT IDENTIFIER ::= { nms553 2 }
nms553Configuration    OBJECT IDENTIFIER ::= { nms553 3 }
nms553DteStatus        OBJECT IDENTIFIER ::= { nms553 4 }
nms553Diagnostics      OBJECT IDENTIFIER ::= { nms553 5 }
nms553Maintenance      OBJECT IDENTIFIER ::= { nms553 6 }
nms553Alarms           OBJECT IDENTIFIER ::= { nms553 7 }
nms553AlarmHistory     OBJECT IDENTIFIER ::= { nms553 8 }
nms553Performance      OBJECT IDENTIFIER ::= { nms553 9 }




-- ****************************************************************************
--                       NMS 553 MIB TREE
-- ****************************************************************************
 
--        /-  nms553Version             nms553MIBversion(1)
--        |      (1)              	nms553VersionTable(2) 
--        |
--        |-  nms553DS0Allocation       nms553DS0AllocationConfigTable(1)
--        |
--        |
--        |-  nms553Configuration       nms553ChannelConfigTable(1)
--        |      (3)                    nms553NetworkConfigTable(2)
--        |                             nms553ConfigurationSave(3)
--        |
--        |
--        |-  nms553DteStatus       	nms553DteStatusTable(1)
--        |      (4)
--        |
--        |-  nms553Diagnostics     	nms553DiagTable(1)
--        |      (5)
--        |
--        |-  nms553Maintenance     	nms553MaintenanceTable(1)
--        |      (6)
--        |
--nms553- |
--(6.7)   |
--        |
--        |-  nms553Alarms         	nms553AlarmData(1)
--        |      (7)                    nms553AlarmConfigTable(2)
--        |
--        |-  nms553AlarmHistory    	nms553AlarmHistoryTable(1)
--        |      (8)                    nms553AlarmMaintenanceTable(2)
--        |
--        |
--        \-  nms553Performance         nms553CurrentTable(1)
--               (9)                    nms553IntervalTable(2)
--                                      nms553TotalTable(3)

-- ****************************************************************************


nms553MIBversion OBJECT-TYPE
    SYNTAX DisplayString (SIZE (5))
    ACCESS read-only
    STATUS mandatory
    DESCRIPTION
        "Identifies the version of the MIB. The format of the version
        is x.yzT, where 'x' identifies the major revision number, 'y'
        identifies the minor revision number, 'z' identifies the
        typographical revision, and T identifies the test revision.
        Upon formal release, no designation for the test revision will
        be present. Acceptable values for the individual revision
        components are as follows:
        x: 1 - 9,    y: 0 - 9,    z: 0 - 9,    T: A - Z"
    ::= { nms553Version 1 }




-- ****************************************************************************
--                                Version Table
-- ****************************************************************************


nms553VersionTable OBJECT-TYPE
    SYNTAX SEQUENCE OF Nms553VersionEntry
    ACCESS not-accessible
    STATUS mandatory
    DESCRIPTION " "
    ::= { nms553Version 2  }

nms553VersionEntry OBJECT-TYPE
    SYNTAX Nms553VersionEntry
    ACCESS not-accessible
    STATUS mandatory
    DESCRIPTION
        "An entry in the GDC NMS 553 Version Table."
    INDEX	{ nms553VersionIndex }
    ::= { nms553VersionTable 1 }

Nms553VersionEntry ::=
    SEQUENCE {
        nms553VersionIndex    SCinstance,
        nms553FirmwareRev     DisplayString
    }

nms553VersionIndex OBJECT-TYPE
    SYNTAX SCinstance
    ACCESS read-only
    STATUS mandatory
    DESCRIPTION
        "Identifies Version parameters associated with the managed object."
    ::= { nms553VersionEntry 1 }


nms553FirmwareRev OBJECT-TYPE
    SYNTAX DisplayString (SIZE(2))
    ACCESS read-only
    STATUS mandatory
    DESCRIPTION
        "The version number of the firmware, to allow products to know which
        revision is installed.  The released version number is sequenced from
        --, A-, ... AA, ... ZZ.  Test versions are numerical from 01 to 99."
    ::= { nms553VersionEntry 2 }



-- ****************************************************************************
--                     DS0 Allocation tables
-- ****************************************************************************


-- ----------------------------------------------------------------------------
--         
--                     DS0 Allocation Scheme table
-- ----------------------------------------------------------------------------


nms553DS0AllocationSchemeTable OBJECT-TYPE
    SYNTAX SEQUENCE OF Nms553DS0AllocationSchemeEntry
    ACCESS not-accessible
    STATUS mandatory
    DESCRIPTION
        "The GDC NMS 553 DS0 allocation table"
    ::= { nms553DS0Allocation 1 }


nms553DS0AllocationSchemeEntry OBJECT-TYPE
    SYNTAX Nms553DS0AllocationSchemeEntry
    ACCESS not-accessible
    STATUS mandatory
    DESCRIPTION
        "The GDC NMS 553 Configuration table entry."
    INDEX { nms553DS0AllocationSchemeIndex }
    ::= { nms553DS0AllocationSchemeTable 1 }


Nms553DS0AllocationSchemeEntry ::=
    SEQUENCE {
        nms553DS0AllocationSchemeIndex SCinstance,
        nms553DS0AllocationScheme INTEGER
    }
 
nms553DS0AllocationSchemeIndex OBJECT-TYPE
    SYNTAX SCinstance
    ACCESS read-only
    STATUS mandatory
    DESCRIPTION
        "The index value which uniquely identifies the DSU  to
        which this entry is applicable.  This has the form of a
        SCinstance which defines the slot, line, drop, and
        sub-identifier.
 
        The sub-identifier for this SC instance is the DSU."
    ::= { nms553DS0AllocationSchemeEntry 1 }
 
nms553DS0AllocationScheme OBJECT-TYPE
    SYNTAX INTEGER {
        consecutive(1),                 -- consecutive DS0's allocation scheme
        alternate(2)                    -- alternate DS0's allocation scheme
    }
    ACCESS read-write
    STATUS mandatory
    DESCRIPTION
        "Identifies the DSU DS0 allocation scheme.The value consecutive(2) 
        indicates that bundles of DS0s are allocated to channels consecutively 
        from the starting DS0. The value of alternate(3) indicates that bundles 
        of DS0s are allocated to channels alternatly, or every other DS0 from
        the starting DS0. The unused DS0s are forced to marks.
 
        Note that DS0 bundles cannot be split across frames (wrap around
        from the highest numbered DS0 of one frame to DS0 1 of the next
        frame. For example, on a T1 frame using consecutive DS0 allocation,
        a channel configuration of starting DS0 = 20 and number of
        DS0s = 5 is an illegal channel configuration because the DS0 bundle
        wraps from DS0 #24 of 1 frame to DS0 #1 of the next."
    ::= { nms553DS0AllocationSchemeEntry 2 }
 

-- ----------------------------------------------------------------------------
--         
--                     DS0 Allocation Configuration table
-- ----------------------------------------------------------------------------


nms553DS0AllocationConfigTable OBJECT-TYPE
    SYNTAX SEQUENCE OF Nms553DS0AllocationConfigEntry
    ACCESS not-accessible
    STATUS mandatory
    DESCRIPTION
        "The GDC DS0 Allocation Configuration table.  Information in the
        entries of this table define the configuration of DS0 allocation for
        channels.  There are entries in this table for each channel of
        the associated DSU."
    ::= { nms553DS0Allocation 2 }
 
nms553DS0AllocationConfigEntry OBJECT-TYPE
    SYNTAX Nms553DS0AllocationConfigEntry
    ACCESS not-accessible
    STATUS mandatory
    DESCRIPTION
        "The GDC DS0 Allocation Configuration table entry."
    INDEX { nms553DS0AllocationConfigIndex }
    ::= { nms553DS0AllocationConfigTable 1 }
 
Nms553DS0AllocationConfigEntry ::=
    SEQUENCE {
        nms553DS0AllocationConfigIndex SCinstance,
        nms553DS0AllocationBaseRate INTEGER,
        nms553DS0AllocationStartingDS0 INTEGER,
        nms553DS0AllocationNumberOfDS0s INTEGER,
        nms553DS0AllocationInbandDccMode INTEGER
    }

nms553DS0AllocationConfigIndex OBJECT-TYPE
    SYNTAX SCinstance
    ACCESS read-only
    STATUS mandatory
    DESCRIPTION
        "The index value which uniquely identifies the channel to
        which this entry is applicable.  This has the form of a
        SCinstance which defines the slot, line, drop, and
        sub-identifier.
 
        The sub-indentifier for this SCinstance is the channel."
    ::= { nms553DS0AllocationConfigEntry 1 }
 
nms553DS0AllocationBaseRate OBJECT-TYPE
    SYNTAX INTEGER {
        nx56k(1),                       -- N X 56K rate
        nx64k(2)                        -- N X 64K rate
    }
    ACCESS read-write
    STATUS mandatory
    DESCRIPTION
        "Indicates the DS0 base rate: either 56K or 64K bits per second.
        This is used in conjunction with the number of DS0s to determine
        the bandwidth of the channel.
 
        Note that base rate of 64K defines the DS0 as clear channel in
        which all 8 bits of the DS0 are used. A base rate of 56K defines
        the DS0 as non-clear in which bits 1-7 are used for channel data
        and the 8th bit is either unused and forced to marks or used to
        pass signaling information."
    ::= { nms553DS0AllocationConfigEntry 2 }
 
nms553DS0AllocationStartingDS0 OBJECT-TYPE
    SYNTAX INTEGER (0..24)
    ACCESS read-write
    STATUS mandatory
    DESCRIPTION
        "Indicates the starting DS0 number for the bundle of DS0s used for
        the channel. DS0 bundles are allocated starting at the DS0 defined by
        this integer.
 
        When this integer is set to 0, the channel is disabled and no DS0s
        are allocated to the channel.
 
        Note that DS0 bundles cannot be split across frames (wrap around
        from the highest numbered DS0 of one frame to DS0 1 of the next
        frame. For example, on a T1 frame using consecutive DS0 allocation,
        a channel configuration of starting DS0 = 20 and number of
        DS0s = 5 is an illegal channel configuration because the DS0 bundle
        wraps from DS0 #24 of 1 frame to DS0 #1 of the next."
    ::= { nms553DS0AllocationConfigEntry 3 }
 
nms553DS0AllocationNumberOfDS0s OBJECT-TYPE
    SYNTAX INTEGER (1..24)
    ACCESS read-write
    STATUS mandatory
    DESCRIPTION
        "Indicates the number of DS0s for the bundle allocated to the
        channel. The number of DS0s, in conjunction with the DS0 base
        rate, also determines the bandwidth of the channel.
 
        Note that DS0 bundles cannot be split across frames (wrap around
        from the highest numbered DS0 of one frame to DS0 1 of the next
        frame. For example, on a T1 frame using consecutive DS0 allocation,
        a channel configuration of starting DS0 = 20 and number of
        DS0s = 5 is an illegal channel configuration because the DS0 bundle
        wraps from DS0 #24 of 1 frame to DS0 #1 of the next."
    ::= { nms553DS0AllocationConfigEntry 4 }
 
 
nms553DS0AllocationInbandDccMode OBJECT-TYPE
    SYNTAX INTEGER {
	none(1),
        embedded(2),
        dccDs0(3)
    }
    ACCESS read-write
    STATUS mandatory
    DESCRIPTION
        "The mode of propagation of inband Diagnostics Communication Channel to
        the dedicated remote NMS553 unit. None specifies no inband DCC. Embedded
        is an allowed value when the mib object nms553DS0BaseRate is set to Nx56K,
        and specifies that DCC is propagated in the 8th bit of the assigned DS0's.
        dccDs0 specifies that a DS0 is used for propagation of DCC, this value
        would be selected if the nms553DS0BaseRate is Nx64k (clear channel) since
        all data bits are used for user data,  a minimum of two DS0's must be
        assigned to this device in this mode, the last ds0 should be set as the
        nms553DccDs0 when using this mode."
    ::= { nms553DS0AllocationConfigEntry 5 }




-- ****************************************************************************
--                        Configuration table
-- ****************************************************************************


-- ----------------------------------------------------------------------------
--
--                     Channel Configuration table
-- ----------------------------------------------------------------------------


nms553ChannelConfigTable OBJECT-TYPE
    SYNTAX SEQUENCE OF Nms553ChannelConfigEntry
    ACCESS not-accessible
    STATUS mandatory
    DESCRIPTION
    "The GDC 553 Channel Configuration table."
    ::= { nms553Configuration 1 }


nms553ChannelConfigEntry OBJECT-TYPE
    SYNTAX Nms553ChannelConfigEntry
    ACCESS not-accessible
    STATUS mandatory
    DESCRIPTION
    "The nms553 Channel Configuration table entry."
    INDEX { nms553ChannelConfigIndex }
    ::= { nms553ChannelConfigTable 1 }


Nms553ChannelConfigEntry ::=
    SEQUENCE {
        nms553ChannelConfigIndex       SCinstance,
        nms553ChannelSplitTiming INTEGER,
        nms553ChannelChannelType INTEGER,
        nms553ChannelClockInvert INTEGER,
        nms553ChannelDataInvert INTEGER,
        nms553ChannelLocalDCD INTEGER,
        nms553ChannelLocalDSR INTEGER,
        nms553ChannelFlowControl INTEGER,
        nms553ChannelRTSCTSControl INTEGER,
        nms553ChannelEIAtestLeads INTEGER,
        nms553ChannelInbandLoop INTEGER,
        nms553ChannelInbandLoopCode INTEGER,
        nms553ChannelInbandLoopdown INTEGER,
        nms553ChannelControlModeIdle INTEGER
    }

nms553ChannelConfigIndex OBJECT-TYPE
    SYNTAX SCinstance
    ACCESS read-only
    STATUS mandatory
    DESCRIPTION
        "The index value which uniquely identifies the channel to
        which this entry is applicable.  This has the form of a
        SCinstance which defines the slot, line, drop, and
        sub-identifier.
 
        The sub-indentifier for this SCinstance is the channel."
    ::= { nms553ChannelConfigEntry 1 }

nms553ChannelSplitTiming OBJECT-TYPE
    SYNTAX INTEGER {
        disabled(1),                    -- split timing disabled
        enabled(2)                      -- split timing enabled
    }
    ACCESS read-write
    STATUS mandatory
    DESCRIPTION
        "Indicates whether or not to use split timing. The value disabled(1)
        indicates that channel's transmit timing is provided by the DSU.
        The value enabled(2) indicates that the channel's transmit timing
        is provided by the customer business equipment (ext Tx Clk).
 
        Split timing refers to the activation of elastic storage to allow
        the channel interface to receive data using the customer business
        equipment's timing source (ext Tx Clk) and transmit that same data
        to the network using the networks timing source."
    ::= { nms553ChannelConfigEntry 2 }
 
nms553ChannelChannelType OBJECT-TYPE
    SYNTAX INTEGER {
        none(1),                        -- no channel interface
        v35(2),                         -- V.35 interface
        eia530(3)                       -- 530 EIA interface
    }
    ACCESS read-only
    STATUS mandatory
    DESCRIPTION
        "The channel interface type. The value none(1) indicates that 
        there is no channel interface for the index. The value v35(2) 
        indicates the channel interface is standard V.35 and the value 
        eia530(3) indicates the channel interface is standard EIA 530."
    ::= { nms553ChannelConfigEntry 3 }

nms553ChannelClockInvert OBJECT-TYPE
    SYNTAX INTEGER {
        txClockNormRxClockNorm(1),      -- Tx and Rx clock normal
        txClockNormRxClockInvert(2),    -- Tx clock normal, Rx clock inverted
        txClockInvertRxClockNorm(3),    -- Tx clock inv, Rx clock normal
        txClockInvertRxClockInvert(4)   -- Tx and Rx clock inverted
     }
    ACCESS read-write
    STATUS mandatory
    DESCRIPTION
    "Clock invert option"
    ::= { nms553ChannelConfigEntry 4 }
 
nms553ChannelDataInvert OBJECT-TYPE
    SYNTAX INTEGER {
        txDataNormRxDataNorm(1),        -- Tx and Rx data normal
        txDataNormRxDataInvert(2),      -- Tx data normal, Rx data inverted
        txDataInvertRxDataNorm(3),      -- Tx data inverted, Rx data normal
        txDataInvertRxDataInvert(4)    -- Tx and Rx data inverted
    }
    ACCESS read-write
    STATUS mandatory
    DESCRIPTION
    "Data invert option"
    ::= { nms553ChannelConfigEntry 5 }
 
nms553ChannelLocalDCD OBJECT-TYPE
    SYNTAX INTEGER {
        followsSignal(1),               -- local DCD follows inband CMI
        forcedOn(2)                     -- local DCD forced on
    }
    ACCESS read-write
    STATUS mandatory
    DESCRIPTION
        "Controls the operation of Data Carrier Detect (DCD) signal.
        The value followsSignal(1) indicates that the channel's DCD follows
        the inband control mode idle (CMI). The value forcedOn(2) indicates
        that DCD is forced on."
    ::= { nms553ChannelConfigEntry 6 }
 
nms553ChannelLocalDSR OBJECT-TYPE
    SYNTAX INTEGER {
        followsSignal(1),               -- local DSR follows inband CMI
        forcedOn(2)                     -- local DSR forced on
    }
    ACCESS read-write
    STATUS mandatory
    DESCRIPTION
        "Controls the operation of the Data Set Ready (DSR) signal.
        The value followsSignal(1) indicates that the channel's DSR follows
        the inband control mode idle (CMI). The value forcedOn(2) indicates
        that DSR is forced on."
    ::= { nms553ChannelConfigEntry 7 }
 
nms553ChannelFlowControl OBJECT-TYPE
    SYNTAX INTEGER {
        txRtsRxDcd(1),                 -- Tx is RTS, Rx is DCD
        txRtsRxDsr(2),                 -- Tx is RTS, Rx is DSR
        txDtrRxDcd(3),                 -- Tx is DTR, Rx is DCD
        txDtrRxDsr(4)                  -- Tx is DTR, Rx is DSR
    }
    ACCESS read-write
    STATUS mandatory
    DESCRIPTION
        "Flow Control Option. This object is valid only when the control mode idle
         object nms553ChannelControlModeIdle is set to enabled(2)."
    ::= { nms553ChannelConfigEntry 8 }
 
nms553ChannelRTSCTSControl OBJECT-TYPE
    SYNTAX INTEGER {
        ctsDelay10ms(1),                -- CTS delay 10 ms
        ctsOn(2),                       -- CTS forced on
        ctsDelayStandard(3)             -- CTS standard delay
    }
    ACCESS read-write
    STATUS mandatory
    DESCRIPTION
        "Controls the function of the channel's Request To Send (RTS)
         and Clear To Send signals used for flow control.
 
        The value of ctsDelay10ms(1) indicates that CTS is to
        respond to RTS after a 10ms delay. The value of ctsOn(2)
        indicates that CTS is forced on at all times. The value of
        ctsDelayStandard(3) indicates that CTS is to respond to RTS
        after the standard delay of 40 bits times.
 
        For 56Kbps applications using CMI flow control, this object
        must be set for ctsDelayStandard(3)."
    ::= { nms553ChannelConfigEntry 9 }
 
nms553ChannelEIAtestLeads OBJECT-TYPE
    SYNTAX INTEGER {
        disabled(1),                    -- EIA test leads disabled
        enabled(2)                      -- EIA test leads enabled
    }
    ACCESS read-write
    STATUS mandatory
    DESCRIPTION
        "Controls the channel's EIA test leads. The EIA test leads allow
        customer business equipment to initiate diagnostic tests through
        the assertion of the EIA test leads RDL, LL, and ST.
 
        When this object is enabled(1), then the assertion of these leads
        is recognized and acted upon by the DSU.  When this object is
        disabled(2), then the assertion of these leads is ignored by the DSU."
    ::= { nms553ChannelConfigEntry 10 }
 
nms553ChannelInbandLoop OBJECT-TYPE
    SYNTAX INTEGER {
        disable(1),                     -- disable detection of in-band loop code
        enabled(2)                      -- enable detection of in-band loop code
    }
    ACCESS read-write
    STATUS mandatory
    DESCRIPTION
        "In-band loopcode enable/disable. The value disabled(1) indicates
        the channel does not enter an RDL loop when an inband RDL code is detected.
        The value enable(2) indicates the channel does enter an RDL loop when
        an inband RDL code is detected."
    ::= { nms553ChannelConfigEntry 11 }
 
nms553ChannelInbandLoopCode OBJECT-TYPE
    SYNTAX INTEGER {
        pn127(1)                       -- PN127 random code
    }
    ACCESS read-only
    STATUS mandatory
    DESCRIPTION
        "In-band RDL code to send and/or receive by the channel. The
        value pn127(1) indicates that the in-band code sent/received is in
        accordance with CCITT V.54 PN-127 scrambled codes."
    ::= { nms553ChannelConfigEntry 12 }
 
nms553ChannelInbandLoopdown OBJECT-TYPE
    SYNTAX INTEGER {
        inhibit(1),                    -- timeout disabled
        enable10Min(2)                 -- timeout value of 10 minutes
    }
    ACCESS read-write
    STATUS mandatory
    DESCRIPTION
        "The time limit in seconds before terminating a channel's RDL.
        The value inhibit(1) indicates that the loopdown time is disabled and
        the loopback will only terminate by the in-band loopdown code.

        The value enable10Min(2) indicates the time before terminating
        the RDL in the event the loopdown code is never received."
    ::= { nms553ChannelConfigEntry 13 }
 
nms553ChannelControlModeIdle OBJECT-TYPE
    SYNTAX INTEGER {
        disabled(1),                    -- CMI disabled
        enabled(2)                      -- CMI enabled
    }
    ACCESS read-write
    STATUS mandatory
    DESCRIPTION
        "Control Mode Idle (CMI) enable/disable. When the channel
        application is Nx56k and RTS/CTS delay is standard, then
        this object defines the the use of CMI to provide flow control.
 
        The value disabled(1) indicates the channel using CMI to pass
        control flow information.
 
        The value enabled(2) indicates the channel is using the DDS
        secondary channel CMI format to pass flow control information."
    ::= { nms553ChannelConfigEntry 14 }

-- ----------------------------------------------------------------------------
--
--                     Network Configuration table
-- ----------------------------------------------------------------------------


nms553NetworkConfigTable OBJECT-TYPE
    SYNTAX SEQUENCE OF Nms553NetworkConfigEntry
    ACCESS not-accessible
    STATUS mandatory
    DESCRIPTION
    "The GDC 553 Network Configuration table."
    ::= { nms553Configuration 2 }
 
 
nms553NetworkConfigEntry OBJECT-TYPE
    SYNTAX Nms553NetworkConfigEntry
    ACCESS not-accessible
    STATUS mandatory
    DESCRIPTION
    "The nms553 Network Configuration table entry."
    INDEX { nms553NetworkConfigIndex }
    ::= { nms553NetworkConfigTable 1 }
 
 
Nms553NetworkConfigEntry ::=
    SEQUENCE {
        nms553NetworkConfigIndex SCinstance,
        nms553NetworkAdminLineType INTEGER,
        nms553NetworkOperLineType INTEGER,
        nms553NetworkInterfaceType INTEGER,
        nms553NetworkPreequalization INTEGER,
        nms553NetworkAdminLineBuildout INTEGER,
        nms553NetworkOperLineBuildout INTEGER,
        nms553NetworkOnesDensity INTEGER,
        nms553NetworkTransmitClockSource INTEGER,
        nms553NetworkFallbackClockSource INTEGER,
        nms553NetworkFDLdcc INTEGER,
        nms553NetworkAISLoopdown INTEGER,
        nms553NetworkInbandFrame INTEGER,
        nms553NetworkLoopbackConfig INTEGER,
        nms553NetworkLineCoding INTEGER,
        nms553NetworkFdl INTEGER 
    }





nms553NetworkConfigIndex OBJECT-TYPE
     SYNTAX SCinstance
     ACCESS read-only
     STATUS mandatory
     DESCRIPTION
         "The index value which uniquely identifies the interface to
         which this entry is applicable.  This has the form of a
         SCinstance which defines the slot, line, drop, and sub-identifier."
     ::= { nms553NetworkConfigEntry 1 }
 
nms553NetworkAdminLineType OBJECT-TYPE
    SYNTAX INTEGER {
        auto(1),
        manEsf(2),
        manD4(3),
        unframed(4)
    }
    ACCESS  read-write
    STATUS  mandatory
    DESCRIPTION
        "The values, in sequence, describe:
 
        'auto' indicates the unit will determine framing.
 
        'manEsf' indicates manual selection of extended superframe format.
 
        'manD4'indicates manual selection of D4 framing format.
 
        'unframed' indicates manual selection of unframed format."
    ::= { nms553NetworkConfigEntry 2 }

nms553NetworkOperLineType OBJECT-TYPE
    SYNTAX INTEGER {
        manEsf(1),
        manD4(2),
        unframed(3)
    }
    ACCESS  read-only
    STATUS  mandatory
    DESCRIPTION
        "The values, in sequence, describe:
 
        'manEsf' indicates the current setting of Line type.
 
        'manD4'indicates the current setting of Line type.
 
        'unframed' indicates the current setting of Line type."
    ::= { nms553NetworkConfigEntry 3 }
 
nms553NetworkInterfaceType OBJECT-TYPE
     SYNTAX INTEGER {
         ds1(1),                        -- DS1 mode
         dsx1(2)                        -- DSX-1 mode
     }
     ACCESS read-write
     STATUS mandatory
     DESCRIPTION
         "The operating mode of the interface.  Setting the value of
         this object to ds1(1) configures the interface as
         standard DS1.  Setting the value of this object to
         dsx1(2) configures the interface to operate as a standard
         cross-connect DSX-1.
 
         This object interoperates with the nms553NetworkPreequalization
         object.  When this object is set to ds1(1), then the value of
         nms553NetworkPreequalization does not apply.
 
         This object interoperates with the nms553NetworkAdminLineBuildout object.
         When this object is set to dsx1(2), then the value of
         nms553NetworkLineBuildout does not apply."
     ::= { nms553NetworkConfigEntry 4 }
 
nms553NetworkPreequalization OBJECT-TYPE
     SYNTAX INTEGER {
         none(1),               -- no preequalization
         preeq130(2),           -- preequalization for 0 < 130 feet
         preeq260(3),           -- preequalization for 130 < 260 feet
         preeq390(4),           -- preequalization for 260 < 390 feet
         preeq530(5),           -- preequalization for 390 < 530 feet
         preeq655(6)            -- preequalization for 530 < 655 feet
     }
     ACCESS read-write
     STATUS mandatory
     DESCRIPTION
         "Is the preequalization of the transmitter of the interface.
 
         This object interoperates with the object
         nms553NetworkInterfaceType.  When the value of nms553NetworkInterfaceType
         is ds1(2) then this value is not applicable."
     ::= { nms553NetworkConfigEntry 5 }
 
nms553NetworkAdminLineBuildout OBJECT-TYPE
    SYNTAX INTEGER {
        auto(1),
        man00dB(2),
        man75dB(3),
        man150dB(4)
    }
    ACCESS read-write
    STATUS mandatory
    DESCRIPTION
        "This variable is used to set the Transmit Ntwk
        Build-Out value on the network side and is only
        valid if the nms553NetworkInterfaceType is set for ds1(1).
        The values, in sequence, describe:

        auto(1) indicates auto detection of receive level to
        determine the appropriate Ntwk build out without controller intervention

        man00dB(2) indicates manual selection of 0.0 dB transmit Ntwk build out

        man75dB(3) indicates manual selection of -7.5 dB transmit Ntwk build out

        man150dB(4) indicates manual selection of -15.0 dB transmit Ntwk build out"
    ::= { nms553NetworkConfigEntry 6 }
 
nms553NetworkOperLineBuildout OBJECT-TYPE
    SYNTAX INTEGER {
        tx00dB(1),
        tx75dB(2),
        tx150dB(3)
    }
    ACCESS read-only
    STATUS mandatory
    DESCRIPTION
        "This variable is used to report the current Ntwk
        build-out setting if the nms553NetworkInterfaceType is set for ds1(1).
 
       tx00dB(1) indicates the unit is set for 0.0 dB of attenuation
       when the nms553NetworkAdminLineBuildout is set for auto (1) or man00dB (2)

       tx75dB(2) indicates the unit is set for -7.5 dB of attenuation
       when the nms553NetworkAdminLineBuildout is set for auto (1) or man75dB (3)

       tx150dB(3) indicates the unit is set for -15.0 dB of attenuation
       when the nms553NetworkAdminLineBuildout is set for auto (1) or man150dB (4)"
    ::= { nms553NetworkConfigEntry 7 }

nms553NetworkOnesDensity OBJECT-TYPE
     SYNTAX INTEGER {
         inhibit(1),                    -- no minimum ones density
         max15zeros(2),                 -- maximum 15 zeros
         max39zeros(3),                 -- maximum 39 zeros
         restrict8XNplus1(4),           -- minimum of N ones per 8(N+1) bits
         min1in8(5)                     -- minimum of 1 one per 8 bits
     }
     ACCESS read-write
     STATUS mandatory
     DESCRIPTION
         "The ones density restriction for the interface.  The values
         of this object define the ones density restriction that is
         enforced on the interface.
 
         The value inhibit(1) indicates that no ones density restriction
         is enforced.
 
         The value max15zeros(2) indicates that a maximum of 15 zeros
         are transmitted to the network before a one is inserted.
 
         The value max39zeros(3) indicates that a maximum of 39 zeros
         are transmitted to the network before a one is inserted.
 
         The value restrict8nX1(4) indicates a minimum of N ones per
         8(N+1) bits, where N is in the range 1 to 24.
 
         The value min1in8(5) indicates a minimum of 1 one per 8 bits.
         With this value, pulse density violations are enforced but not
         recorded."
     ::= { nms553NetworkConfigEntry 8 }
 
nms553NetworkTransmitClockSource OBJECT-TYPE
     SYNTAX INTEGER {
         receive(1),                    -- receive transmit clock source
         cascade(2),                    -- cascade transmit clock source
         internal(3),                   -- internal transmit clock source
         station(4),                    -- station transmit clock source
         extChannelClkA(5),             -- channel transmit clock source, ClockA
         extChannelClkB(6),             -- channel transmit clock source, ClockB
         extChannelClkC(7),             -- channel transmit clock source, ClockC
         composite(8)                   -- composite transmit clock source
     }
     ACCESS read-write
     STATUS mandatory
     DESCRIPTION
         ""
     ::= { nms553NetworkConfigEntry 9 }
 
nms553NetworkFallbackClockSource OBJECT-TYPE
     SYNTAX INTEGER {
         receive(1),                    -- receive transmit clock source
         internal(2)                    -- internal transmit clock source
     }
     ACCESS read-write
     STATUS mandatory
     DESCRIPTION
         ""
    ::= { nms553NetworkConfigEntry 10 }
 
nms553NetworkFDLdcc OBJECT-TYPE
     SYNTAX INTEGER {
         enabled(1),
         disabled(2)
     }
     ACCESS read-write
     STATUS mandatory
     DESCRIPTION
         "Controls whether or not the DCC uses the FDL as its
         transport.  The FDL is only available when the DS1 line type
         is ESF, a full DS1 interface is being used, and transportation
         of the FDL completely through the network is supported.
 
         The value enabled(1) enables the transportation of the DCC
         using the FDL.  The value disabled(2) disables the use of the
         FDL to transport the DCC, which implies that the DCC is
         transported by some other means.
 
         This object interoperates with the nms553NetworkLineType object.  The
         value of this object can be set to enabled(1) only when the
         value of the nms553NetworkLineType is one of the ESF values."
     ::= { nms553NetworkConfigEntry 11 }
 
nms553NetworkAISLoopdown OBJECT-TYPE
     SYNTAX INTEGER (4..60)             -- 4, 5..60 seconds
     ACCESS read-write
     STATUS mandatory
     DESCRIPTION
         "The time in seconds when receiving a continuous AIS signal
         before a remotely initiated loopback is terminated.  When this
         object has the value 4, then there is no time limit and the
         loop must be terminated by remotely issued in-band loopdown
         codes.  When the object has a value between 5 and 60, then
         this is time in seconds of continuous AIS signal before
         the loopback is terminated."
     ::= { nms553NetworkConfigEntry 12 }
 
nms553NetworkInbandFrame OBJECT-TYPE
    SYNTAX INTEGER {
        framed(1),
        unframed(2)
    }
    ACCESS read-write
    STATUS mandatory
    DESCRIPTION
        "This variable is used to set the
        In-Band DS1 Loopback Code Detection.

        Framed(1) framing is done upon recognition of 
	he inband loopback code.
 
        Unframed(2) no framing is done upon recognition 
	of the inband loopback code."

    ::= { nms553NetworkConfigEntry 13 }
 
nms553NetworkLoopbackConfig OBJECT-TYPE
    SYNTAX INTEGER {
        none(1),
        payload(2),
        lineloop(3)
    }
    ACCESS read-write
    STATUS mandatory
    DESCRIPTION
        "This variable is used to set the
        In-Band DS1 Loopback Code Detection.
 
        none(1) refers to when the in-band
        loopback codes are ignored.
 
        payload(2) designates a payload loopback is done 
	upon recognition of the inband loopback code.
 
        lineloop(3) designates a line loopback is done 
	upon recognition of the inband loopback code."

    ::= { nms553NetworkConfigEntry 14 }
 


nms553NetworkLineCoding OBJECT-TYPE
    SYNTAX  INTEGER {
        nms553B8ZS (1),
        nms553AMI (2)
    }
    ACCESS  read-write
    STATUS  mandatory
    DESCRIPTION
        "This variable describes the  variety  of  Zero
        Code  Suppression  used  on  the link, which in
        turn affects a number of its characteristics.

        nms553B8ZS refers to the use of a specified  pat-
        tern  of  normal  bits  and  bipolar violations
        which are used to replace a sequence  of  eight
        zero bits.

        nms553AMI refers to a mode wherein no  zero  code
        suppression  is  present  and the line encoding
        does not solve the problem directly.   In  this
        application, the higher layer must provide data
        which meets or exceeds the  pulse  density  re-
        quirements, such as inverting HDLC data."
    ::= { nms553NetworkConfigEntry 15 }

nms553NetworkFdl OBJECT-TYPE
    SYNTAX  INTEGER {
        nms553Fdl-none(1),
        nms553Ansi-T1-403(2),
        nms553Att-54016(3)
    }
    ACCESS  read-write
    STATUS  mandatory
    DESCRIPTION
        "This bitmap describes the use of  the  facili-
        ties data link, and is the sum of the capabili-
        ties:

        nms553Fdl-none(1) indicates that the device  does
        not use the FDL.
 
        nms553Ansi-T1-403(2) refers to the  FDL  exchange
        recommended by ANSI.
 
        nms553Att-54016(3) refers to ESF FDL exchanges."
     ::= { nms553NetworkConfigEntry 16 }
 

-- ----------------------------------------------------------------------------
--
--                    Network/ Channel Save
-- ----------------------------------------------------------------------------





nms553ConfigurationSave OBJECT-TYPE
    SYNTAX INTEGER {
          network(1),		-- write-only
          channel(2),		-- write-only
          both(3),		-- write-only
          norm(4)        	-- read-only
    }
    ACCESS read-write
    STATUS mandatory
    DESCRIPTION
        "This variable is used to set the update status flag for saving 
	network and channel configuration settings.
        
	Management can only set to network(1), channel(2), or both(3)

	A norm(4) will always be read.

	Both Network configuration and Channel configuration are saved
	at the same time on both(3).
	
	Configuration settings are not saved to network element by default.
	This permits the configuration of several objects before saving.  
	After all objects are set-up, a (1),(2) or (3) must be sent.  This will
	enable and save the new configuration(s).
	
 	"

    ::= { nms553Configuration 3 }
 








-- ****************************************************************************
--                      Dte Status table
-- ****************************************************************************


nms553DteStatusTable OBJECT-TYPE
    SYNTAX SEQUENCE OF Nms553DteStatusEntry
    ACCESS not-accessible
    STATUS mandatory
    DESCRIPTION
    "The nms553 DTE Signal Status table. Information in the
    entries of this table define the status of DSU channel
    interface leads.  There are entries in this table for each
    channel of the associated DSU."
    ::= { nms553DteStatus 1 }


nms553DteStatusEntry OBJECT-TYPE
    SYNTAX Nms553DteStatusEntry
    ACCESS not-accessible
    STATUS mandatory
    DESCRIPTION
    "The nms553 DTE Signal Status table entry."
    INDEX { nms553DteStatusIndex }
    ::= { nms553DteStatusTable 1 }


Nms553DteStatusEntry ::=
    SEQUENCE {
        nms553DteStatusIndex SCinstance,
        nms553DteStat OCTET STRING 
    }


nms553DteStatusIndex OBJECT-TYPE
    SYNTAX SCinstance
    ACCESS read-only
    STATUS mandatory
    DESCRIPTION
    "The index value: slot, line, drop, and interface"
    ::= { nms553DteStatusEntry 1 }

nms553DteStat OBJECT-TYPE
        SYNTAX  OCTET STRING (SIZE(2))
        ACCESS  read-only
        STATUS  mandatory
        DESCRIPTION
        "Returns a bitwise snapshot of the DTE signals.

        Octet 1 bit 7 - not used
                bit 6 - CTS     (1:ON; 0:OFF)
                bit 5 - RTS     (1:ON; 0:OFF)
                bit 4 - DTR     (1:ON; 0:OFF)
                bit 3 - DSR     (1:ON; 0:OFF)
                bit 2 - future use 
                bit 1 - DCD     (1:ON; 0:OFF)
                bit 0 - future use
 
        Octet 2 bit 7 - not used
                bit 6 - RXC     (1:Transitions)
                bit 5 - DCD     (1:Transitions)
                bit 4 - RTS     (1:Transitions)
                bit 3 - CTS     (1:Transitions)
                bit 2 - RXD     (1:Transitions)
                bit 1 - TXC     (1:Transitions)
                bit 0 - TXD     (1:Transitions)"
    ::= { nms553DteStatusEntry 2 }



-- ****************************************************************************
--                        Diagnostics table
-- ****************************************************************************

nms553DiagTable OBJECT-TYPE
    SYNTAX SEQUENCE OF Nms553DiagEntry
    ACCESS not-accessible
    STATUS mandatory
    DESCRIPTION
        "The NMS 553 Diagnostics table."
    ::= { nms553Diagnostics 1 }
 
nms553DiagEntry OBJECT-TYPE
    SYNTAX Nms553DiagEntry
    ACCESS not-accessible
    STATUS mandatory
    DESCRIPTION
        "The SNMP553S Diagnostics table entry."
    INDEX { nms553DiagIndex }
    ::= { nms553DiagTable 1 }
 
Nms553DiagEntry ::=
    SEQUENCE {
        nms553DiagIndex SCinstance,
        nms553DiagTestDuration INTEGER,
        nms553DiagProgPattern INTEGER,
        nms553DiagBeginSelfTest INTEGER,
        nms553DiagBeginLoopTest INTEGER,
        nms553DiagTestResults INTEGER,
        nms553DiagResetTestToNormal INTEGER,
	nms553DiagTestStatus INTEGER
 }

nms553DiagIndex OBJECT-TYPE
    SYNTAX SCinstance
    ACCESS read-only
    STATUS mandatory
    DESCRIPTION
        "The index value which uniquely identifies the interface to
        which this entry is applicable.  This has the form of a
        SCinstance which defines the slot, line, drop, and sub-identifier,
        which in this case is a network interface."
    ::= { nms553DiagEntry 1 }
 
nms553DiagTestDuration OBJECT-TYPE
    SYNTAX INTEGER     {
	testTime30Secs(1),
        testTime1Min(2),
        testTime2Mins(3),
        testTime3Mins(4),
        testTime4Mins(5),
        testTime5Mins(6),
        testTime6Mins(7),
        testTime7Mins(8),
        testTime8Mins(9),
        testTime9Mins(10),
        testTime10Mins(11),
        testTime15Mins(12),
        testTime20Mins(13),
        testTime25Mins(14),
        testTime30Mins(15),
        noLimit(16)
    }
    ACCESS read-write
    STATUS mandatory
    DESCRIPTION
        "Selects the duration to run a diagnostic test.  The value(1)
        noLimit signifies that the test should run indefinitely until
        explicitly terminated."

    ::= { nms553DiagEntry 2 }




nms553DiagProgPattern OBJECT-TYPE
     SYNTAX INTEGER (0..'ffff'h)
     ACCESS read-write
     STATUS mandatory
     DESCRIPTION
        "The 16 bit user programmable test pattern.  This object
        works with the  nms553DiagSendCode object in that when nms553DiagSendCode
        is set to sendProgPattern(4), the the value of this object is
        used as the 16 bit user programmable test pattern.
 
        This object is used for all tests defined in both the GDC
        dsx1 mib."
 
     ::= { nms553DiagEntry 3}



nms553DiagBeginSelfTest OBJECT-TYPE
    SYNTAX INTEGER {
	unit511Pattern(1),		-- UNIT (both ch and nw i/f) w/511
	unit2047Pattern(2),		-- UNIT (both ch and nw i/f) w/2047
	unitQRSPattern(3),		-- UNIT (both ch and nw i/f) w/QRS
	unitProgPattern(4),		-- UNIT (both ch and nw i/f) w/Prog.
	dsu511Pattern(5),		-- DSU  (only ch i/f) w/511
	dsu2047Pattern(6),		-- DSU  (only ch i/f) w/2047
	dsuQRSPattern(7),		-- DSU  (only ch i/f) w/QRS
	dsuProgPattern(8), 		-- DSU  (only ch i/f) w/Prog. 
	noselftestrunning(9)		-- read only
    }
    ACCESS read-write
    STATUS mandatory
    DESCRIPTION "A set of 1-8 will start the selected test with 
	the indicated pattern. A 9 cannot be set by management.
	A read will always return a 9.
	"
    ::= { nms553DiagEntry 4 }


nms553DiagBeginLoopTest OBJECT-TYPE
    SYNTAX INTEGER {
	localLoopback(1),		-- Channel digital loopback
	digitalLoopback(2),		-- back out T1 
	remoteDigitalLoopback(3),	-- (na)
        nolooptestrunning(4)		-- read only	
    }
    ACCESS read-write
    STATUS mandatory
    DESCRIPTION "A set will start the selected test.
	"
    ::= { nms553DiagEntry 5 }



nms553DiagTestResults OBJECT-TYPE
    SYNTAX INTEGER     		
    ACCESS read-only
    STATUS mandatory
    DESCRIPTION
    "The results of the last diagnostic test. This can be the
    current test running or the last completed test.
 
    The units of the value of this object depend on the type of
    diagnostic test run.  For all cases except a network delay
    measurement, the units of the value of this object is the
    number of bit errors that occurred. Bit errors can be read at any
    time during the duration of the test.  The valid range for bit
    errors is 0 to 4,095.  65,535 will be returned if for any reason
    the test was terminated early.  32,770 will be returned if the
    number of bit errors exceeds 4,095. For a network delay measurement,
    the units of the value of this test are milliseconds.  If the test
    is terminated early then 65,535 will be returned and if the delay
    is greater than 4,095 then 32,770 will be returned."
    ::= { nms553DiagEntry 6 }

nms553DiagResetTestToNormal OBJECT-TYPE
    SYNTAX INTEGER {
        normal(1),      -- read only
        resetTest(2)    -- write only
    }
    ACCESS read-write
    STATUS mandatory
    DESCRIPTION
        "This object will halt the execution of any and all
        diagnostic test that may be running with the exception
        of the Network Delay Test."
    ::= { nms553DiagEntry 7 }


nms553DiagTestStatus OBJECT-TYPE
    SYNTAX INTEGER {
	noTestinProgress(1),		-- No test in progress
	unitSelfTest(2),		-- UNIT (both ch and nw i/f)
	dsuSelfTest(3),			-- DSU  (only ch i/f)
  	localLoopback(4),		-- Channel digital loopback
	digitalLoopback(5)		-- back out T1   
   }
    ACCESS read-only
    STATUS mandatory
    DESCRIPTION
        "This object will return the test current test in progress, if any."
    ::= { nms553DiagEntry 8 }

-- ****************************************************************************
--                        Maintenance Table
-- ****************************************************************************


nms553MaintenanceTable OBJECT-TYPE
    SYNTAX SEQUENCE OF Nms553MaintenanceEntry
    ACCESS not-accessible
    STATUS mandatory
    DESCRIPTION
    "The table describes the maintenance functions for the nms553. "
    ::= { nms553Maintenance 1 }


nms553MaintenanceEntry OBJECT-TYPE
    SYNTAX Nms553MaintenanceEntry
    ACCESS not-accessible
    STATUS mandatory
    DESCRIPTION
    "An entry in the GDC maintenance Table"
    INDEX { nms553MaintenanceIndex }
    ::= { nms553MaintenanceTable 1 }


Nms553MaintenanceEntry ::=
SEQUENCE {
	nms553MaintenanceIndex      SCinstance,
	nms553LedStatus             OCTET STRING,
        nms553SoftReset             INTEGER,
	nms553DefaultInit           INTEGER,
	nms553FrontPanel            INTEGER,
        nms553ProductType           INTEGER,
        nms553ResetStatistics       INTEGER,
        nms553ValidIntervals        INTEGER,
        nms553CascadePresent        INTEGER,
        nms553ReceiveLevel          INTEGER
 }


nms553MaintenanceIndex OBJECT-TYPE
    SYNTAX SCinstance
    ACCESS read-only
    STATUS mandatory
    DESCRIPTION
     "The index value: slot, line, drop, and interface"
    ::= { nms553MaintenanceEntry 1 }


nms553LedStatus OBJECT-TYPE
    SYNTAX OCTET STRING (SIZE(3))
    ACCESS read-only
    STATUS mandatory
    DESCRIPTION
   "Returns a bitwise snapshot of the front panel LED state and front panel switches.
 		Octet 1         bit 7 - not used
				bit 6 - ON           (0:LED inactive   1:LED active)
				bit 5 - DSX1
				bit 4 - NMSRSP
				bit 3 - NMSDAT
				bit 2 - ER
				bit 1 - DSX OOF
				bit 0 - DSX LOS

		Octet 2         bit 7 - not used
				bit 6 - NET OOF
				bit 5 - NET LOS
				bit 4 - NET BPV
				bit 3 - NET AIS
				bit 2 - TM/ALM
				bit 1 - LBK
				bit 0 - future use

		Octet 3         bit 7 - not used
				bit 6 - CHA SD
				bit 5 - CHA RD
				bit 4 - CHB SD
				bit 3 - CHB RD 
				bit 2 - CHC SD
				bit 1 - CHC RD
				bit 0 - future use"
    ::= { nms553MaintenanceEntry 2 }


nms553SoftReset	OBJECT-TYPE
     SYNTAX INTEGER
     {
          reset(1),			-- write-only
          norm(2)           		-- read-only
     }
     ACCESS read-write
     STATUS mandatory
     DESCRIPTION
     "Supports the action of soft resetting the unit.  When this
     object is set to reset(1), then the unit performs a soft reset.
     The value norm will be returned when the reset is complete.
     The value of norm can not be set by management."
     ::= { nms553MaintenanceEntry 3 }

nms553DefaultInit OBJECT-TYPE
     SYNTAX INTEGER
     {
         factoryDefault(1),		-- write-only
         normal(2)			-- read-only
     }
     ACCESS read-write
     STATUS mandatory
     DESCRIPTION
     "This is used to allow the NonVolatile Configuration to be set to
     a factory default state.  When this value is set to factoryDefault,
     the unit will reset to the default configuration. The value of normal
     will be returned when the initialization is complete. The value normal
     can not be set by management."
     ::= { nms553MaintenanceEntry 4 }


nms553FrontPanel OBJECT-TYPE
     SYNTAX INTEGER
     {
         inhibit(1),
         enable(2)
     }
     ACCESS read-write
     STATUS mandatory
     DESCRIPTION
     "This variable is used to indicate whether the front
     panel switches are operational or not."
     ::= { nms553MaintenanceEntry 5 }

nms553ProductType OBJECT-TYPE
    SYNTAX INTEGER {
        nms553d1(1),
        nms553d1ifp(2),
        nms553d3ifp(3),
        nms553c(4),
        nms553cifp(5)
    }
    ACCESS read-only
    STATUS mandatory
    DESCRIPTION
        "Indicates the product type of the unit."
    ::= { nms553MaintenanceEntry 6 }

nms553ResetStatistics OBJECT-TYPE
    SYNTAX  INTEGER {
        norm(1),
        reset(2)
    }
    ACCESS  read-write
    STATUS  mandatory
    DESCRIPTION
        "Supports the action of soft resetting the nms553ValidIntervals
        object.  When this object is set to reset(2), then the unit
        will reset the nms553ValidIntervals object to zero.
        The value of norm(1) can not be set by management."
    ::= { nms553MaintenanceEntry 7 }

nms553ValidIntervals OBJECT-TYPE
    SYNTAX  INTEGER (0..96)
    ACCESS  read-only
    STATUS  mandatory
    DESCRIPTION
        "The number of  previous  intervals  for  which
        valid data was collected.  The value will be 96
        unless the interface was brought on-line within
        the last 24 hours, in which case the value will
        be the number of complete 15  minute  intervals
        the since interface has been online."
    ::= { nms553MaintenanceEntry 8 }
 
nms553CascadePresent OBJECT-TYPE
    SYNTAX INTEGER {
        notPresent(1),                  -- cascade interface not present
        present(2)                      -- cascade interface present
    }
    ACCESS read-only
    STATUS mandatory
    DESCRIPTION
        "Identifies whether or not the cascade interface cards
        are installed."
    ::= { nms553MaintenanceEntry 9 }

nms553ReceiveLevel    OBJECT-TYPE
    SYNTAX INTEGER (0..43)
        ACCESS read-only
        STATUS mandatory
        DESCRIPTION
            "This variable reports the absolute value of the network relative
            receive level of -40dB to +3dB when the nms553networkInterfaceType is set
            for ds1(1). 
            
            Values 1 thru 40 are to be interpreted as negative values,
            example a value 10 equals -10dB.
           
            Values 41,42,43 are to be interpreted as +1,+2 and +3dB respectively."
      ::= { nms553MaintenanceEntry 10 }
 


-- ****************************************************************************
--                     Alarm Tables
-- ****************************************************************************

-- ----------------------------------------------------------------------------
--
--                     Alarm Object Identifier Definitions
-- ----------------------------------------------------------------------------


nms553AlarmData	              OBJECT IDENTIFIER ::= { nms553Alarms 1 }

nms553NoResponseAlm           OBJECT IDENTIFIER ::= { nms553AlarmData 1 }
nms553DiagRxErrAlm            OBJECT IDENTIFIER ::= { nms553AlarmData 2 }
nms553PowerUpAlm              OBJECT IDENTIFIER ::= { nms553AlarmData 3 }
nms553NvRamCorrupt            OBJECT IDENTIFIER ::= { nms553AlarmData 4 }
nms553UnitFailure             OBJECT IDENTIFIER ::= { nms553AlarmData 5 }
nms553TimingLoss              OBJECT IDENTIFIER ::= { nms553AlarmData 6 }
nms553StatusChange            OBJECT IDENTIFIER ::= { nms553AlarmData 7 }
nms553UnsolicitedTest         OBJECT IDENTIFIER ::= { nms553AlarmData 8  }
nms553LossOfSignal            OBJECT IDENTIFIER ::= { nms553AlarmData 9  }
nms553LossOfFrame             OBJECT IDENTIFIER ::= { nms553AlarmData 10 }
nms553AlarmIndicationSignal   OBJECT IDENTIFIER ::= { nms553AlarmData 11 }
nms553ReceivedYellow          OBJECT IDENTIFIER ::= { nms553AlarmData 12 }
nms553UnavailableSignalState  OBJECT IDENTIFIER ::= { nms553AlarmData 13 }
nms553ExcessiveZeros          OBJECT IDENTIFIER ::= { nms553AlarmData 14 }
nms553LowAverageDensity       OBJECT IDENTIFIER ::= { nms553AlarmData 15 }
nms553ControlledSlips         OBJECT IDENTIFIER ::= { nms553AlarmData 16 }
nms553BipolarViolations       OBJECT IDENTIFIER ::= { nms553AlarmData 17 }
nms553CrcErrors               OBJECT IDENTIFIER ::= { nms553AlarmData 18 }


 -- The following Table provides a description of the alarms on the nms 553.

 -- The index sub-identifier for each alarm on an interface basis is:
 --
 --                     system sub-identifier = 0
 --                     net    sub-identifier = 1
 --                     casc   sub-identifier = 2
 --                     chA    sub-identifier = 3
 --                     chB    sub-identifier = 4
 --                     chC    sub-identifier = 5
 --
 -- ALARM                       Maskable   Valid interfaces   win/thres Type
 -- ============================================================================
 -- nms553NoResponseAlm           no         system             no        major
 -- nms553DiagRxErrAlm            ?????????????????????????????????????????????
 -- nms553PowerUpAlm              no         system             no        Informational
 -- nms553NvRamCorrupt            no         system             no        major
 -- nms553UnitFailure             no         system             no        major
 -- nms553MbiLock                 Not Supported on 553S
 -- nms553LocalPwrFail            Not Supported on 553S
 -- nms553TimingLoss              yes        system             no        major
 -- nms553StatusChange            yes        system             no        other
 -- nms553UnsolicitedTest         yes        system             no        other
 -- nms553LossofSignal            yes        net/casc           no        major
 -- nms553LossOfFrame             yes        net/casc           no        major
 -- nms553AlarmIndicationSignal   yes        net/casc           no        major
 -- nms553ReceivedYellow          yes        net/casc           no        minor
 -- nms553UnavailableSignalstate  yes        net/casc           no        major
 -- nms553ExcessiveZeros          yes        net only           no        minor
 -- nms553LowAverageDensity       yes        net only           no        minor
 -- nms553ControlledSlips         yes        net only           no        minor
 -- nms553BipolarViolations       yes        net/casc           yes       minor
 -- nms553CrcErrors               yes        net/casc           yes       minor
 

-- ----------------------------------------------------------------------------
--
--   			 Alarm Thresholds
-- ----------------------------------------------------------------------------

 
nms553AlarmConfigTable OBJECT-TYPE
     SYNTAX SEQUENCE OF Nms553AlarmConfigEntry
     ACCESS not-accessible
     STATUS mandatory
     DESCRIPTION
         "The nms553AlarmConfigTable contains entries that configure alarm
         reporting.  The structure of the table is such that alarm
         configuration is supported on a unit and interface basis, and
         then on an alarm type basis within the interface.  For
         simplicity sake alarms, be they unit or interface
         related, are represented in one table."
     ::= { nms553Alarms 2 }
 
nms553AlarmConfigEntry OBJECT-TYPE
     SYNTAX Nms553AlarmConfigEntry
     ACCESS not-accessible
     STATUS mandatory
     DESCRIPTION
         "An entry in the GDC Alarm Configuration table."
     INDEX { nms553AlarmConfigIndex, nms553AlarmConfigIdentifier }
     ::= { nms553AlarmConfigTable 1 }
 
Nms553AlarmConfigEntry ::=
     SEQUENCE {
         nms553AlarmConfigIndex
             SCinstance,
         nms553AlarmConfigIdentifier
             OBJECT IDENTIFIER,
         nms553AlarmCountWindow
             INTEGER,
         nms553AlarmCountThreshold
             INTEGER
     }
 
nms553AlarmConfigIndex OBJECT-TYPE
     SYNTAX SCinstance
     ACCESS read-only
     STATUS mandatory
     DESCRIPTION
         "The index value which uniquely identifies the interface to
         which this entry is applicable."
     ::= { nms553AlarmConfigEntry 1 }
 
nms553AlarmConfigIdentifier OBJECT-TYPE
     SYNTAX OBJECT IDENTIFIER
     ACCESS read-only
     STATUS mandatory
     DESCRIPTION
         "The unique alarm identifier assigned to this alarm type.
         The format of this identifier is an OBJECT IDENTIFIER that has
         the following format: {iso(1) org(3) dod(6) internet(1)
         private(4) enterprises(1) gdc(498) xxx(x) alarm(z) yyy(y)
         where xxx(x) is the administratively assigned family object
         identifier (z) is the object identifier for alarms in the family
         defined MIB and yyy(y) is the administratively assigned alarm
         type identifier for this alarm."
     ::= { nms553AlarmConfigEntry 2 }
 
nms553AlarmCountWindow OBJECT-TYPE
    SYNTAX INTEGER{
        disabled(1),
        last1sec(2),
        last1min(3),
        last1hr(4),
        infinite(5)
    }
    ACCESS  read-write
    STATUS  mandatory
    DESCRIPTION
    "This variable sets/reads the BPV alarm window.
 
    This window is used with the alarm threshold to determine
    how long the alarm should be active before reporting."
    ::= { nms553AlarmConfigEntry 3 }
 
nms553AlarmCountThreshold OBJECT-TYPE
    SYNTAX INTEGER {
        thresGT10(1),
        thresGT100(2),
        thresGT1000(3),
        thresGT10000(4)
    }
    ACCESS  read-write
    STATUS  mandatory
    DESCRIPTION
    "This function sets/reads the BPV alarm threshold criteria.
 
    This threshold is used along with the the alarm window to
    determine the number of instances in a given time frame for
    an alarm to occur before the alarm is considered active."
    ::= { nms553AlarmConfigEntry 4 }


--^L
-- ****************************************************************************
--                 Alarm History Tables
-- ****************************************************************************

-- ----------------------------------------------------------------------------
--
--                     Alarm History table
-- ----------------------------------------------------------------------------


nms553AlarmHistoryTable OBJECT-TYPE
    SYNTAX SEQUENCE OF Nms553AlarmHistoryEntry
    ACCESS not-accessible
    STATUS mandatory
    DESCRIPTION
        "The nms553AlarmHistoryTable contains entries that report the
        history of all supported alarms.  The history consists of the
        the number of times the alarm has occurred since last history
        reset, the time of the first alarm occurence (hours,minutes,
        seconds,day,month,year), and the time of the last alarm occurrence
        (hours,minutes,seconds,day,month,year).
 
        The structure of the table is such that alarm status is
        supported on a unit or interface basis, and then on an alarm
        type basis within the interface.  For simplicity sake and to
        support the reporting of status of all alarms, a unit is
        treated as an interface 1 in this table."
    ::= { nms553AlarmHistory 1 }
 
nms553AlarmHistoryEntry OBJECT-TYPE
    SYNTAX Nms553AlarmHistoryEntry
    ACCESS not-accessible
    STATUS mandatory
    DESCRIPTION
        "An entry in the GDC NMS553 Alarm History table."
    INDEX { nms553AlarmHistoryIndex, nms553AlarmHistoryIdentifier }
    ::= { nms553AlarmHistoryTable 1 }
 
Nms553AlarmHistoryEntry ::=
    SEQUENCE {
        nms553AlarmHistoryIndex
            SCinstance,
        nms553AlarmHistoryIdentifier
            OBJECT IDENTIFIER,
        nms553AlarmCount
            Gauge,
        nms553AlarmFirstOccurrenceHours
            INTEGER,
        nms553AlarmFirstOccurrenceMinutes
            INTEGER,
        nms553AlarmFirstOccurrenceSeconds
            INTEGER,
        nms553AlarmFirstOccurrenceMonth
            INTEGER,
        nms553AlarmFirstOccurrenceDay
            INTEGER,
        nms553AlarmFirstOccurrenceYear
            INTEGER,
        nms553AlarmLastOccurrenceHours
            INTEGER,
        nms553AlarmLastOccurrenceMinutes
            INTEGER,
        nms553AlarmLastOccurrenceSeconds
            INTEGER,
        nms553AlarmLastOccurrenceMonth
            INTEGER,
        nms553AlarmLastOccurrenceDay
            INTEGER,
        nms553AlarmLastOccurrenceYear
            INTEGER
    }
 
nms553AlarmHistoryIndex OBJECT-TYPE
    SYNTAX SCinstance
    ACCESS read-only
    STATUS mandatory
    DESCRIPTION
        "The index value which uniquely identifies the interface to
        which this entry is applicable."
    ::= { nms553AlarmHistoryEntry 1 }
 
nms553AlarmHistoryIdentifier OBJECT-TYPE
    SYNTAX OBJECT IDENTIFIER
    ACCESS read-only
    STATUS mandatory
    DESCRIPTION
        "The unique alarm identifier assigned to this alarm type.
        The format of this identifier is an OBJECT IDENTIFIER that has
        the following format: {iso(1) org(3) dod(6) internet(1)
        private(4) enterprises(1) gdc(498) xxx(x) alarm(z) yyy(y)
        where xxx(x) is the administratively assigned family object
        identifier (z) is the object identifier for alarms in the family
        defined MIB and yyy(y) is the administratively assigned alarm
        type identifier for this alarm."
  ::= { nms553AlarmHistoryEntry 2 }
 
nms553AlarmCount OBJECT-TYPE
    SYNTAX Gauge
    ACCESS read-only
    STATUS mandatory
    DESCRIPTION
        "The number of occurrences of this alarm.  This objects value
        is incremented once for each time that the alarm occurs.  This
        count is incremented regardless of whether or not the alarm
        is masked or is not reporteded because of the threshold
        configuration."
    ::= { nms553AlarmHistoryEntry 3 }
 
nms553AlarmFirstOccurrenceHours OBJECT-TYPE
    SYNTAX INTEGER
    ACCESS read-only
    STATUS mandatory
    DESCRIPTION
        "The hour (0-23) the alarm first occurred."
    ::= { nms553AlarmHistoryEntry 4 }
 
nms553AlarmFirstOccurrenceMinutes OBJECT-TYPE
    SYNTAX INTEGER
    ACCESS read-only
    STATUS mandatory
    DESCRIPTION
        "The minute (0-59) the alarm first occurred."
    ::= { nms553AlarmHistoryEntry 5 }
 
nms553AlarmFirstOccurrenceSeconds OBJECT-TYPE
    SYNTAX INTEGER
    ACCESS read-only
    STATUS mandatory
    DESCRIPTION
        "The second (0-59) the alarm first occurred."
    ::= { nms553AlarmHistoryEntry 6 }
 
nms553AlarmFirstOccurrenceMonth OBJECT-TYPE
    SYNTAX INTEGER
    ACCESS read-only
    STATUS mandatory
    DESCRIPTION
        "The month (1-12) the alarm first occurred."
    ::= { nms553AlarmHistoryEntry 7 }
 
nms553AlarmFirstOccurrenceDay OBJECT-TYPE
    SYNTAX INTEGER
    ACCESS read-only
    STATUS mandatory
    DESCRIPTION
        "The day (1-31) the alarm first occurred."
    ::= { nms553AlarmHistoryEntry 8 }
 
nms553AlarmFirstOccurrenceYear OBJECT-TYPE
    SYNTAX INTEGER
    ACCESS read-only
    STATUS mandatory
    DESCRIPTION
        "The year (0-99) the alarm first occurred."
    ::= { nms553AlarmHistoryEntry 9 }
 
nms553AlarmLastOccurrenceHours OBJECT-TYPE
    SYNTAX INTEGER
    ACCESS read-only
    STATUS mandatory
    DESCRIPTION
        "The hour (0-23) the alarm last occurred."
    ::= { nms553AlarmHistoryEntry 10 }
 
nms553AlarmLastOccurrenceMinutes OBJECT-TYPE
    SYNTAX INTEGER
    ACCESS read-only
    STATUS mandatory
    DESCRIPTION
        "The minute (0-59) the alarm last occurred."
    ::= { nms553AlarmHistoryEntry 11 }
 
nms553AlarmLastOccurrenceSeconds OBJECT-TYPE
    SYNTAX INTEGER
    ACCESS read-only
    STATUS mandatory
    DESCRIPTION
        "The second (0-59) the alarm last occurred."
    ::= { nms553AlarmHistoryEntry 12 }
 
nms553AlarmLastOccurrenceMonth OBJECT-TYPE
    SYNTAX INTEGER
    ACCESS read-only
    STATUS mandatory
    DESCRIPTION
        "The month (1-12) the alarm last occurred."
    ::= { nms553AlarmHistoryEntry 13 }
 
nms553AlarmLastOccurrenceDay OBJECT-TYPE
    SYNTAX INTEGER
    ACCESS read-only
    STATUS mandatory
    DESCRIPTION
        "The day (1-31) the alarm last occurred."
    ::= { nms553AlarmHistoryEntry 14 }
 
nms553AlarmLastOccurrenceYear OBJECT-TYPE
    SYNTAX INTEGER
    ACCESS read-only
    STATUS mandatory
    DESCRIPTION
        "The year (0-99) the alarm last occurred."
    ::= { nms553AlarmHistoryEntry 15 }
 


-- ----------------------------------------------------------------------------
--
--                  Alarm History Maintenance Table
-- ----------------------------------------------------------------------------

nms553AlarmMaintenanceTable OBJECT-TYPE
    SYNTAX SEQUENCE OF Nms553AlarmMaintenanceEntry
    ACCESS not-accessible
    STATUS mandatory
    DESCRIPTION
        "The nms553AlarmMaintenanceTable contains entries that configure
        the real time clock and that clear the alarm history table."
    ::= { nms553AlarmHistory 2 }
 
 
nms553AlarmMaintenanceEntry OBJECT-TYPE
    SYNTAX Nms553AlarmMaintenanceEntry
    ACCESS not-accessible
    STATUS mandatory
    DESCRIPTION
        "An entry in the GDC nms553 Alarm Maintenance Table."
    INDEX  { nms553AlarmMaintenanceIndex }
    ::= { nms553AlarmMaintenanceTable 1 }

Nms553AlarmMaintenanceEntry ::=
    SEQUENCE {
        nms553AlarmMaintenanceIndex
            SCinstance,
        nms553ClearAlarmHistory
            INTEGER,
        nms553RTCHours
            INTEGER,
        nms553RTCMinutes
            INTEGER,
        nms553RTCSeconds
            INTEGER,
        nms553RTCMonth
            INTEGER,
        nms553RTCDay
            INTEGER,
        nms553RTCYear
            INTEGER,
        nms553TimeOfLastAlarmClear
            OCTET STRING (SIZE(6))
    }
 
nms553AlarmMaintenanceIndex OBJECT-TYPE
    SYNTAX SCinstance
    ACCESS read-only
    STATUS mandatory
    DESCRIPTION
        "The index value which uniquely identifies the interface to
        which this entry is applicable."
    ::= { nms553AlarmMaintenanceEntry 1 }
 
nms553ClearAlarmHistory      OBJECT-TYPE
    SYNTAX INTEGER {
        clear(1),
        norm(2)
    }
    ACCESS read-write
    STATUS mandatory
    DESCRIPTION
        "Supports the action of clearing the alarm history table.
        When this object is set to clear(1), then the unit clears
        the alarm history table. The value of norm(2) will be
        returned when the clear is complete.
 
        The value of norm(2) can not be set by management."
 
    ::= { nms553AlarmMaintenanceEntry 2 }
 
nms553RTCHours OBJECT-TYPE
    SYNTAX INTEGER
    ACCESS read-write
    STATUS mandatory
    DESCRIPTION
        "The hour of day (0-23) to be set or read."
    ::= { nms553AlarmMaintenanceEntry 3 }
 
nms553RTCMinutes OBJECT-TYPE
    SYNTAX INTEGER
    ACCESS read-write
    STATUS mandatory
    DESCRIPTION
        "The minute of the hour (0-59) to be set or read."
    ::= { nms553AlarmMaintenanceEntry 4 }
 
nms553RTCSeconds OBJECT-TYPE
    SYNTAX INTEGER
    ACCESS read-write
    STATUS mandatory
    DESCRIPTION
        "The second of the minute (0-59) to be set or read."
    ::= { nms553AlarmMaintenanceEntry 5 }
 
nms553RTCMonth OBJECT-TYPE
    SYNTAX INTEGER
    ACCESS read-write
    STATUS mandatory
    DESCRIPTION
        "The month of the year (1-12) to be set or read."
    ::= { nms553AlarmMaintenanceEntry 6 }
 
nms553RTCDay OBJECT-TYPE
    SYNTAX INTEGER
    ACCESS read-write
    STATUS mandatory
    DESCRIPTION
        "The day of the month (1-31) to be set or read."
    ::= { nms553AlarmMaintenanceEntry 7 }
 
nms553RTCYear OBJECT-TYPE
    SYNTAX INTEGER
    ACCESS read-write
    STATUS mandatory
    DESCRIPTION
        "The year (0-99) to be set or read."
    ::= { nms553AlarmMaintenanceEntry 8 }
 
nms553TimeOfLastAlarmClear OBJECT-TYPE
    SYNTAX OCTET STRING (SIZE(6))
    ACCESS  read-only
    STATUS  mandatory
    DESCRIPTION
        "Returns the time (hours,minutes,seconds,month,day,year) of
        the last alarm clear command sent to the unit.
        Octet 1 - Hour of last alarm clear (0-23)
        Octet 2 - Minute of last alarm clear (0-59)
        Octet 3 - Second of last alarm clear (0-59)
        Octet 4 - Month of last alarm clear (1-12)
        Octet 5 - Day of last alarm clear (1-31)
        Octet 6 - Year of last alarm clear (0-99)."
    ::= { nms553AlarmMaintenanceEntry 9 }


 -- ********************************************************************
 --  			Performance Tables
 -- ********************************************************************

-- ----------------------------------------------------------------------------
--
--                     ATT Current Performance Table
-- ----------------------------------------------------------------------------


nms553CurrentTable 	OBJECT-TYPE
	 SYNTAX  SEQUENCE OF Nms553CurrentEntry
	 ACCESS  not-accessible
	 STATUS  mandatory
	 DESCRIPTION
		 "The nms553 Current table.  This table supplements the
		 entries in the DS1 AT&T performance table of the DS1
		 MIB defined in RFC1406."
	 ::= { nms553Performance 1 }


nms553CurrentEntry 	OBJECT-TYPE
	 SYNTAX  Nms553CurrentEntry
	 ACCESS  not-accessible
	 STATUS  mandatory
	 DESCRIPTION
		 "An entry in the nms553 Current table."
	 INDEX   { nms553CurrentIndex }
	 ::= { nms553CurrentTable 1 }

Nms553CurrentEntry ::=
    SEQUENCE {
        nms553CurrentIndex
            SCinstance,
        nms553CurrentESs
            Gauge,
        nms553CurrentSESs
            Gauge,
        nms553CurrentBESs
            Gauge,
        nms553CurrentUASs
            Gauge,
        nms553CurrentLOFCs
            Gauge,
        nms553CurrentCSSs
            Gauge
	  }

nms553CurrentIndex 	OBJECT-TYPE
    SYNTAX  SCinstance
    ACCESS  read-only
    STATUS  mandatory
    DESCRIPTION
        "The index value which uniquely identifies the interface to
        which this entry is applicable.  This has the form of a
        SCinstance which defines the slot, line, drop, and interface,
        which in this case is a network interface."
    ::= { nms553CurrentEntry 1 }

nms553CurrentESs OBJECT-TYPE
    SYNTAX  Gauge
    ACCESS  read-only
    STATUS  mandatory
    DESCRIPTION
        "The number of Errored Seconds, encountered  by
        a DS1 interface in the current 15 minute inter-
        val."
    ::= { nms553CurrentEntry 2 }
 
 
nms553CurrentSESs OBJECT-TYPE
    SYNTAX  Gauge
    ACCESS  read-only
    STATUS  mandatory
    DESCRIPTION
        "The number of Severely Errored Seconds encoun-
        tered  by  a  DS1  interface  in the current 15
        minute interval."
    ::= { nms553CurrentEntry 3 }

nms553CurrentBESs OBJECT-TYPE
    SYNTAX Gauge
    ACCESS read-only
    STATUS mandatory
    DESCRIPTION
        "The number of Bursty  Errored  Seconds  (BESs)
        encountered  by  a DS1 interface in the current
        15 minute interval."
    ::= { nms553CurrentEntry 4 }

nms553CurrentUASs OBJECT-TYPE
    SYNTAX  Gauge
    ACCESS  read-only
    STATUS  mandatory
    DESCRIPTION
        "The number of Unavailable Seconds  encountered
        by a DS1 interface in the current 15 minute in-
        terval."
    ::= { nms553CurrentEntry 5 }

nms553CurrentLOFCs OBJECT-TYPE
    SYNTAX Gauge
    ACCESS read-only
    STATUS mandatory
    DESCRIPTION
        "The number of Loss of Frame Counts (LOFCs) encountered by a DS1 
        interface in the current 15 minute interval."
    ::= { nms553CurrentEntry 6 }

nms553CurrentCSSs OBJECT-TYPE
    SYNTAX  Gauge
    ACCESS  read-only
    STATUS  mandatory
    DESCRIPTION
        "The number of Controlled Slip Seconds  encoun-
        tered  by  a  DS1  interface  in the current 15
        minute interval."
    ::= { nms553CurrentEntry 7 }
 

-- ----------------------------------------------------------------------------
--
--                     ATT Interval Performance Table
-- ----------------------------------------------------------------------------



nms553IntervalTable 	OBJECT-TYPE
    SYNTAX  SEQUENCE OF Nms553IntervalEntry
    ACCESS  not-accessible
    STATUS  mandatory
    DESCRIPTION
        "The nms553 Interval table.  This table supplements the
        entries in the DS1 AT&T performance table of the DS1
        MIB defined in RFC1406."
    ::= { nms553Performance 2 }

nms553IntervalEntry 	OBJECT-TYPE
    SYNTAX  Nms553IntervalEntry
    ACCESS  not-accessible
    STATUS  mandatory
    DESCRIPTION
        "An entry in the DS1 Interval table."
    INDEX   { nms553IntervalIndex, nms553IntervalNumber }
    ::= { nms553IntervalTable 1 }

Nms553IntervalEntry ::=
    SEQUENCE {
        nms553IntervalIndex
            SCinstance,
        nms553IntervalNumber
            INTEGER,
        nms553IntervalESs
            Gauge,
        nms553IntervalSESs
            Gauge,
        nms553IntervalBESs
            Gauge,
        nms553IntervalUASs
            Gauge,
        nms553IntervalLOFCs
            Gauge,
        nms553IntervalCSSs
            Gauge
}

nms553IntervalIndex OBJECT-TYPE
    SYNTAX  SCinstance
    ACCESS  read-only
    STATUS  mandatory
    DESCRIPTION
        "The index value which uniquely identifies the interface to
        which this entry is applicable.  This has the form of a
        SCinstance which defines the slot, line, drop, and interface,
        which in this case is a network interface."
    ::= { nms553IntervalEntry 1 }

nms553IntervalNumber 	OBJECT-TYPE
    SYNTAX  INTEGER (1..96)
    ACCESS  read-only
    STATUS  mandatory
    DESCRIPTION
        "A number between 1 and 96, where 1 is the most recently completed 
        minute interval and 96 is the least recently completed 15 minutes  
        interval   (assuming   that  all  96  intervals  are valid)."
    ::= { nms553IntervalEntry 2 }

nms553IntervalESs OBJECT-TYPE
    SYNTAX  Gauge
    ACCESS  read-only
    STATUS  mandatory
    DESCRIPTION
        "The number of Errored Seconds encountered by a
        DS1  interface in one of the previous 96, indi-
        vidual 15 minute, intervals."
    ::= { nms553IntervalEntry 3 }

nms553IntervalSESs OBJECT-TYPE
    SYNTAX  Gauge
    ACCESS  read-only
    STATUS  mandatory
    DESCRIPTION
        "The number of Severely Errored Seconds encoun-
        tered by a DS1 interface in one of the previous
        96, individual 15 minute, intervals."
    ::= { nms553IntervalEntry 4 }

nms553IntervalBESs OBJECT-TYPE
    SYNTAX Gauge
    ACCESS read-only
    STATUS mandatory
    DESCRIPTION
        "The number of Bursty  Errored  Seconds  (BESs)
        encountered  by  a  DS1 interface in one of the
        previous 96, individual 15 minute, intervals."
    ::= { nms553IntervalEntry 5 }

nms553IntervalUASs OBJECT-TYPE
    SYNTAX  Gauge
    ACCESS  read-only
    STATUS  mandatory
    DESCRIPTION
        "The number of Unavailable Seconds  encountered
        by  a  DS1 interface in one of the previous 96,
        individual 15 minute, intervals."
    ::= { nms553IntervalEntry 6 }

nms553IntervalLOFCs 	OBJECT-TYPE
    SYNTAX Gauge
    ACCESS read-only
    STATUS mandatory
    DESCRIPTION
        "The number of Loss of Frame Counts (LOFCs) encountered by a DS1 
        interface in the current 15 minute interval."
    ::= {nms553IntervalEntry 7 }

nms553IntervalCSSs OBJECT-TYPE
    SYNTAX  Gauge
    ACCESS  read-only
    STATUS  mandatory
    DESCRIPTION
        "The number of Controlled Slip Seconds  encoun-
        tered by a DS1 interface in one of the previous
        96, individual 15 minute, intervals."
    ::= { nms553IntervalEntry 8 }


-- ----------------------------------------------------------------------------
--
--                     ATT Total Performance Table
-- ----------------------------------------------------------------------------


nms553TotalTable OBJECT-TYPE
    SYNTAX  SEQUENCE OF Nms553TotalEntry
    ACCESS  not-accessible
    STATUS  mandatory
    DESCRIPTION
        "The DS1 Total table.  24 hour interval.
        This table supplements the entries in the DS1 
        AT&T performance table of the DS1
        MIB defined in RFC1406."
    ::= { nms553Performance 3}

nms553TotalEntry 		OBJECT-TYPE
    SYNTAX  Nms553TotalEntry
    ACCESS  not-accessible
    STATUS  mandatory
    DESCRIPTION
        "An entry in the DS1 Total table."
    INDEX   { nms553TotalIndex }
    ::= { nms553TotalTable 1 }

Nms553TotalEntry ::=
    SEQUENCE {
    nms553TotalIndex
        SCinstance,
    nms553TotalESs
        Gauge,
    nms553TotalSESs
        Gauge,
    nms553TotalBESs
        Gauge,
    nms553TotalUASs
        Gauge,
    nms553TotalLOFCs
        Gauge,
    nms553TotalCSSs
        Gauge
    }

nms553TotalIndex OBJECT-TYPE
    SYNTAX  SCinstance
    ACCESS  read-only
    STATUS  mandatory
    DESCRIPTION
        "The index value which uniquely identifies the interface to
        which this entry is applicable.  This has the form of a
        SCinstance which defines the slot, line, drop, and interface,
        which in this case is a network interface."
    ::= { nms553TotalEntry 1 }

nms553TotalESs OBJECT-TYPE
    SYNTAX  Gauge
    ACCESS  read-only
    STATUS  mandatory
    DESCRIPTION
        "The number of Errored Seconds encountered by a
        DS1 interface in the previous 24 hour interval"
    ::= { nms553TotalEntry 2 }
 
nms553TotalSESs OBJECT-TYPE
    SYNTAX  Gauge
    ACCESS  read-only
    STATUS  mandatory
    DESCRIPTION
        "The number of Severely Errored Seconds encoun-
        tered  by  a  DS1  interface in the previous 24
        hour interval."
    ::= { nms553TotalEntry 3 }
 
nms553TotalBESs OBJECT-TYPE
    SYNTAX  Gauge
    ACCESS  read-only
    STATUS  mandatory
    DESCRIPTION
        "The number of Bursty  Errored  Seconds  (BESs)
        encountered  by a DS1 interface in the previous
        24 hour interval."
    ::= { nms553TotalEntry 4 }
 
nms553TotalUASs OBJECT-TYPE
    SYNTAX  Gauge
    ACCESS  read-only
    STATUS  mandatory
    DESCRIPTION
        "The number of Unavailable Seconds  encountered
        by  a DS1 interface in the previous 24 hour in-
        terval."
    ::= { nms553TotalEntry 5 }
 
nms553TotalLOFCs OBJECT-TYPE
    SYNTAX Gauge
    ACCESS read-only
    STATUS mandatory
    DESCRIPTION
        "The number of Loss of Frame Counts (LOFCs) encountered by a
        DS1interface in the current 15 minute interval."
    ::= {nms553TotalEntry 6 }
 
nms553TotalCSSs OBJECT-TYPE
    SYNTAX  Gauge
    ACCESS  read-only
    STATUS  mandatory
    DESCRIPTION
        "The number of Controlled Slip Seconds  encoun-
        tered  by  a  DS1  interface in the previous 24
        hour interval."
    ::= { nms553TotalEntry 7 }
 
 
END
