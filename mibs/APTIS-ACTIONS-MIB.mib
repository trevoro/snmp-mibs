--
--	Aptis Enterprise MIB
--	Actions Module (V2 SMI)
-- 
--	Nortel Networks
--	11 Elizabeth Drive
--	Chelmsford, MA 01824
--
--	NOTE: this MIB is programmatically generated and should not
--	be modified by hand.
--
--	Copyright (c) 1997-2000 Nortel Networks
--	All Rights Reserved.

APTIS-ACTIONS-MIB DEFINITIONS ::= BEGIN

    IMPORTS
        aptis-actions, Boolean
            FROM APTIS-MIB
	aptis-modules
 	    FROM APTIS-REG-MIB
        MODULE-IDENTITY, OBJECT-TYPE, IpAddress
            FROM SNMPv2-SMI
        DisplayString, RowStatus
            FROM SNMPv2-TC;

    aptisActionsModule MODULE-IDENTITY
        LAST-UPDATED "0004140000Z"
        ORGANIZATION "Nortel Networks"
        CONTACT-INFO
            "   Technical Support/Customer Service
                Nortel Networks

                Postal: 11 Elizabeth Drive
                        Chelmsford, MA 01824

                Tel:
                In the USA: Dial 1-800-758-4827 to contact a Technical Support engineer.
                Outside the USA:  Contact your Regional Nortel Networks Support Prime.

                For information about the Nortel Networks Network Access Division,
                go to the World Wide Web (WWW) site at http://www.nortelnetworks.com."

        DESCRIPTION
            "The following variables describe the administrative actions
            that may be invoked through SNMP."

    ::= { aptis-modules 5 }

-- This file generated from  actions.cml by smog.
-- date: Thu Jun 29 01:11:51  2000

	resetTable	OBJECT-TYPE
		SYNTAX		SEQUENCE OF ResetEntry
		MAX-ACCESS	not-accessible
		STATUS		current
		DESCRIPTION
			"CVX Chassis <RESET> Options."

	::= { aptis-actions 3510 }

	resetEntry	OBJECT-TYPE
		SYNTAX		ResetEntry
		MAX-ACCESS	not-accessible
		STATUS		current
		DESCRIPTION
			"This is the structure of entries in the
			 resetTable."
		INDEX		{ resetInstance }
	::= { resetTable 1 }

	ResetEntry ::= SEQUENCE {
		resetInstance			INTEGER,
		resetStatusGeneral		INTEGER,
		resetResetType			INTEGER
	}

	resetInstance	OBJECT-TYPE
		SYNTAX		INTEGER
		MAX-ACCESS	read-create
		STATUS		current
		DESCRIPTION
			"Each invocation of this action will have a unique
			instance number, assigned by the switch."

		DEFVAL		{ 0 }
	::= { resetEntry 1 }

	resetStatusGeneral	OBJECT-TYPE
		SYNTAX		INTEGER {
				    started(0),
				    succeeded(1),
				    failed(2),
				    errParam(4)
				}
		MAX-ACCESS	read-create
		STATUS		current
		DESCRIPTION
			"This is the standard actionStatus enum used for all
			actions."

		DEFVAL		{ started }
	::= { resetEntry 2 }

	resetResetType	OBJECT-TYPE
		SYNTAX		INTEGER {
				    hard(1),
				    cold(2),
				    warm(3)
				}
		MAX-ACCESS	read-create
		STATUS		current
		DESCRIPTION
			"Select the type of reset requested."

		DEFVAL		{ hard }
	::= { resetEntry 11 }

-- This file generated from  flash.cml by smog.
-- date: Thu Jun 29 01:11:52  2000

	flashWriteTable	OBJECT-TYPE
		SYNTAX		SEQUENCE OF FlashWriteEntry
		MAX-ACCESS	not-accessible
		STATUS		current
		DESCRIPTION
			"This action causes a portion of the configuration
			subtree to be written out to a text file on one of the
			CVX system's local flash cards."

	::= { aptis-actions 3501 }

	flashWriteEntry	OBJECT-TYPE
		SYNTAX		FlashWriteEntry
		MAX-ACCESS	not-accessible
		STATUS		current
		DESCRIPTION
			"This is the structure of entries in the
			 flashWriteTable."
		INDEX		{ flashWriteInstance }
	::= { flashWriteTable 1 }

	FlashWriteEntry ::= SEQUENCE {
		flashWriteInstance		INTEGER,
		flashWriteStatusGeneral		INTEGER,
		flashWriteStatusSpecific	INTEGER,
		flashWritePathString		DisplayString,
		flashWriteFileName		DisplayString,
		flashWriteBytesWritten		INTEGER,
		flashWriteVerboseMode		Boolean
	}

	flashWriteInstance	OBJECT-TYPE
		SYNTAX		INTEGER
		MAX-ACCESS	read-create
		STATUS		current
		DESCRIPTION
			"Each invocation of this action will have a unique
			instance number, assigned by the switch."

		DEFVAL		{ 0 }
	::= { flashWriteEntry 1 }

	flashWriteStatusGeneral	OBJECT-TYPE
		SYNTAX		INTEGER {
				    started(0),
				    succeeded(1),
				    failed(2),
				    errParam(4)
				}
		MAX-ACCESS	read-create
		STATUS		current
		DESCRIPTION
			"This is the standard actionStatus enum used for all
			actions."

		DEFVAL		{ started }
	::= { flashWriteEntry 2 }

	flashWriteStatusSpecific	OBJECT-TYPE
		SYNTAX		INTEGER {
				    noError(0),
				    badArgs(1),
				    lackOfResources(2),
				    genFail(3)
				}
		MAX-ACCESS	read-create
		STATUS		current
		DESCRIPTION
			"If generalStatus is err-param or failed, this will
			hold a more specific error number."

		DEFVAL		{ noError }
	::= { flashWriteEntry 3 }

	flashWritePathString	OBJECT-TYPE
		SYNTAX		DisplayString
		MAX-ACCESS	read-create
		STATUS		current
		DESCRIPTION
			"The starting node in the configuration tree. The
			contents of all the nodes under this node will be
			written out to the text file."

	::= { flashWriteEntry 11 }

	flashWriteFileName	OBJECT-TYPE
		SYNTAX		DisplayString (SIZE (0..16))
		MAX-ACCESS	read-create
		STATUS		current
		DESCRIPTION
			"The relative file name to hold the text config. The
			CVX file system uses drive C: to refer to the bottom
			flash card, and D: to refer to the top flash card. If
			the drive letter is not specified, then C: is assumed.
			If this file exists, it will only be overwritten with
			a complete copy of the output from this action. NOTE
			that the file CONFIG.CVX is not accessible through
			this action. To save the config to flash where it will
			be used at the next reboot, use the flashSave action
			instead."

	::= { flashWriteEntry 12 }

	flashWriteBytesWritten	OBJECT-TYPE
		SYNTAX		INTEGER
		MAX-ACCESS	read-create
		STATUS		current
		DESCRIPTION
			"On success, the total number of bytes written to
			flash."

		DEFVAL		{ 0 }
	::= { flashWriteEntry 13 }

	flashWriteVerboseMode	OBJECT-TYPE
		SYNTAX		Boolean
		MAX-ACCESS	read-create
		STATUS		current
		DESCRIPTION
			"Setting this field to TRUE requests that the output
			file contain all configuration values, otherwise only
			those that differ from the default values."

		DEFVAL		{ false }
	::= { flashWriteEntry 14 }


	flashReadTable	OBJECT-TYPE
		SYNTAX		SEQUENCE OF FlashReadEntry
		MAX-ACCESS	not-accessible
		STATUS		current
		DESCRIPTION
			"This action causes the configuration subtree to be
			read to one of the CVX system's local flash cards."

	::= { aptis-actions 3502 }

	flashReadEntry	OBJECT-TYPE
		SYNTAX		FlashReadEntry
		MAX-ACCESS	not-accessible
		STATUS		current
		DESCRIPTION
			"This is the structure of entries in the
			 flashReadTable."
		INDEX		{ flashReadInstance }
	::= { flashReadTable 1 }

	FlashReadEntry ::= SEQUENCE {
		flashReadInstance		INTEGER,
		flashReadStatusGeneral		INTEGER,
		flashReadFileName		DisplayString,
		flashReadLinesRead		INTEGER
	}

	flashReadInstance	OBJECT-TYPE
		SYNTAX		INTEGER
		MAX-ACCESS	read-create
		STATUS		current
		DESCRIPTION
			"Each invocation of this action will have a unique
			instance number, assigned by the switch."

		DEFVAL		{ 0 }
	::= { flashReadEntry 1 }

	flashReadStatusGeneral	OBJECT-TYPE
		SYNTAX		INTEGER {
				    started(0),
				    succeeded(1),
				    failed(2),
				    badFile(4),
				    genFail(5)
				}
		MAX-ACCESS	read-create
		STATUS		current
		DESCRIPTION
			"This is the standard actionStatus enum used for all
			actions."

		DEFVAL		{ started }
	::= { flashReadEntry 2 }

	flashReadFileName	OBJECT-TYPE
		SYNTAX		DisplayString (SIZE (0..16))
		MAX-ACCESS	read-create
		STATUS		current
		DESCRIPTION
			"The relative file name to hold the text config. The
			CVX file system uses drive C: to refer to the bottom
			flash card, and D: to refer to the top flash card. If
			the drive letter is not specified, then C: is
			assumed."

	::= { flashReadEntry 12 }

	flashReadLinesRead	OBJECT-TYPE
		SYNTAX		INTEGER
		MAX-ACCESS	read-create
		STATUS		current
		DESCRIPTION
			"On success, the total number of lines read from
			flash."

		DEFVAL		{ 0 }
	::= { flashReadEntry 13 }


	flashSaveTable	OBJECT-TYPE
		SYNTAX		SEQUENCE OF FlashSaveEntry
		MAX-ACCESS	not-accessible
		STATUS		current
		DESCRIPTION
			"This action saves the configuration to the flash file
			CONFIG.CVX. It is equivalent to the 'write' command in
			the CLI."

	::= { aptis-actions 3503 }

	flashSaveEntry	OBJECT-TYPE
		SYNTAX		FlashSaveEntry
		MAX-ACCESS	not-accessible
		STATUS		current
		DESCRIPTION
			"This is the structure of entries in the
			 flashSaveTable."
		INDEX		{ flashSaveInstance }
	::= { flashSaveTable 1 }

	FlashSaveEntry ::= SEQUENCE {
		flashSaveInstance		INTEGER,
		flashSaveStatusGeneral		INTEGER,
		flashSaveStatusSpecific		INTEGER
	}

	flashSaveInstance	OBJECT-TYPE
		SYNTAX		INTEGER
		MAX-ACCESS	read-create
		STATUS		current
		DESCRIPTION
			"Each invocation of this action will have a unique
			instance number, assigned by the switch."

		DEFVAL		{ 0 }
	::= { flashSaveEntry 1 }

	flashSaveStatusGeneral	OBJECT-TYPE
		SYNTAX		INTEGER {
				    started(0),
				    succeeded(1),
				    failed(2),
				    errParam(4)
				}
		MAX-ACCESS	read-create
		STATUS		current
		DESCRIPTION
			"This is the standard actionStatus enum used for all
			actions."

		DEFVAL		{ started }
	::= { flashSaveEntry 2 }

	flashSaveStatusSpecific	OBJECT-TYPE
		SYNTAX		INTEGER {
				    noError(0),
				    lackOfResources(2),
				    genFail(3)
				}
		MAX-ACCESS	read-create
		STATUS		current
		DESCRIPTION
			"If generalStatus is err-param or failed, this will
			hold a more specific error number."

		DEFVAL		{ noError }
	::= { flashSaveEntry 3 }

-- This file generated from  sessions.cml by smog.
-- date: Thu Jun 29 01:11:54  2000

	sessionTerminateTable	OBJECT-TYPE
		SYNTAX		SEQUENCE OF SessionTerminateEntry
		MAX-ACCESS	not-accessible
		STATUS		current
		DESCRIPTION
			"This action allows a remote manager to terminate an
			active session."

	::= { aptis-actions 230 }

	sessionTerminateEntry	OBJECT-TYPE
		SYNTAX		SessionTerminateEntry
		MAX-ACCESS	not-accessible
		STATUS		current
		DESCRIPTION
			"This is the structure of entries in the
			 sessionTerminateTable."
		INDEX		{ sessionTerminateInstance }
	::= { sessionTerminateTable 1 }

	SessionTerminateEntry ::= SEQUENCE {
		sessionTerminateInstance	INTEGER,
		sessionTerminateStatusGeneral	INTEGER,
		sessionTerminateStatusSpecific	INTEGER,
		sessionTerminateBootEra		INTEGER,
		sessionTerminateSessionID	INTEGER,
		sessionTerminateSignature	DisplayString
	}

	sessionTerminateInstance	OBJECT-TYPE
		SYNTAX		INTEGER
		MAX-ACCESS	read-create
		STATUS		current
		DESCRIPTION
			"Each invocation of this action will have a unique
			instance number, assigned by the switch."

		DEFVAL		{ 0 }
	::= { sessionTerminateEntry 1 }

	sessionTerminateStatusGeneral	OBJECT-TYPE
		SYNTAX		INTEGER {
				    started(0),
				    succeeded(1),
				    failed(2),
				    errParam(4)
				}
		MAX-ACCESS	read-create
		STATUS		current
		DESCRIPTION
			"This is the standard actionStatus enum used for all
			actions."

		DEFVAL		{ started }
	::= { sessionTerminateEntry 2 }

	sessionTerminateStatusSpecific	OBJECT-TYPE
		SYNTAX		INTEGER {
				    noError(0),
				    badSignature(1),
				    badSession(2),
				    genFail(3)
				}
		MAX-ACCESS	read-create
		STATUS		current
		DESCRIPTION
			"If generalStatus is err-param or failed, this will
			hold a more specific error number."

		DEFVAL		{ noError }
	::= { sessionTerminateEntry 3 }

	sessionTerminateBootEra	OBJECT-TYPE
		SYNTAX		INTEGER
		MAX-ACCESS	read-create
		STATUS		current
		DESCRIPTION
			"An input parameter to the session-terminate action.
			Together with the sessionID, uniquely identifies the
			session to terminate. If a value is provided, it must
			match the current value of bootEra, so this field is
			only provided as a safeguard to ensure that sessions
			from the wrong boot era can't be terminated
			accidentally."

		DEFVAL		{ 0 }
	::= { sessionTerminateEntry 11 }

	sessionTerminateSessionID	OBJECT-TYPE
		SYNTAX		INTEGER
		MAX-ACCESS	read-create
		STATUS		current
		DESCRIPTION
			"An input parameter to the session-terminate action,
			naming the session which should be terminated."

		DEFVAL		{ 0 }
	::= { sessionTerminateEntry 12 }

	sessionTerminateSignature	OBJECT-TYPE
		SYNTAX		DisplayString
		MAX-ACCESS	read-create
		STATUS		current
		DESCRIPTION
			"An input parameter to the session-terminate action,
			providing a cryptographically secure verification that
			the manager requesting the termination has the
			appropriate credentials to do so. NOTE: the exact
			algorithm for generating the signature has not yet
			been determined."

	::= { sessionTerminateEntry 13 }

-- This file generated from  slots.cml by smog.
-- date: Thu Jun 29 01:11:54  2000

	slotControlTable	OBJECT-TYPE
		SYNTAX		SEQUENCE OF SlotControlEntry
		MAX-ACCESS	not-accessible
		STATUS		current
		DESCRIPTION
			"slot control"

	::= { aptis-actions 203 }

	slotControlEntry	OBJECT-TYPE
		SYNTAX		SlotControlEntry
		MAX-ACCESS	not-accessible
		STATUS		current
		DESCRIPTION
			"This is the structure of entries in the
			 slotControlTable."
		INDEX		{ slotControlInstance }
	::= { slotControlTable 1 }

	SlotControlEntry ::= SEQUENCE {
		slotControlInstance		INTEGER,
		slotControlStatusGeneral	INTEGER,
		slotControlStatusSpecific	INTEGER,
		slotControlSlotIndex		INTEGER,
		slotControlSlotAction		INTEGER
	}

	slotControlInstance	OBJECT-TYPE
		SYNTAX		INTEGER
		MAX-ACCESS	read-create
		STATUS		current
		DESCRIPTION
			"Each invocation of this action will have a unique
			instance number, assigned by the switch."

		DEFVAL		{ 0 }
	::= { slotControlEntry 1 }

	slotControlStatusGeneral	OBJECT-TYPE
		SYNTAX		INTEGER {
				    started(0),
				    succeeded(1),
				    failed(2),
				    errParam(4)
				}
		MAX-ACCESS	read-create
		STATUS		current
		DESCRIPTION
			"like, did it work, or what? This is the standard
			actionStatus enum used for all actions."

		DEFVAL		{ started }
	::= { slotControlEntry 2 }

	slotControlStatusSpecific	OBJECT-TYPE
		SYNTAX		INTEGER {
				    unknown(0),
				    noCard(1),
				    notAllowed(2),
				    badSlot(3),
				    inUse(4),
				    inappropriate(5)
				}
		MAX-ACCESS	read-create
		STATUS		current
		DESCRIPTION
			"like, did it work, or what? If the generalStatus is
			err-param or failed, this will hold a more specific
			error number."

		DEFVAL		{ unknown }
	::= { slotControlEntry 3 }

	slotControlSlotIndex	OBJECT-TYPE
		SYNTAX		INTEGER (1..18)
		MAX-ACCESS	read-create
		STATUS		current
		DESCRIPTION
			"The physical slot number."

		DEFVAL		{ 1 }
	::= { slotControlEntry 11 }

	slotControlSlotAction	OBJECT-TYPE
		SYNTAX		INTEGER {
				    slotNoChange(0),
				    slotDown(1),
				    slotDownPend(2),
				    slotUp(3),
				    slotReset(4),
				    slotDownTimed(5),
				    slotAbortDry(6)
				}
		MAX-ACCESS	read-create
		STATUS		current
		DESCRIPTION
			"The action requested for this slot."

		DEFVAL		{ slotNoChange }
	::= { slotControlEntry 12 }

-- This file generated from  t1.cml by smog.
-- date: Thu Jun 29 01:11:54  2000

	t1TestTable	OBJECT-TYPE
		SYNTAX		SEQUENCE OF T1TestEntry
		MAX-ACCESS	not-accessible
		STATUS		current
		DESCRIPTION
			"T1 Testing Control."

	::= { aptis-actions 2106 }

	t1TestEntry	OBJECT-TYPE
		SYNTAX		T1TestEntry
		MAX-ACCESS	not-accessible
		STATUS		current
		DESCRIPTION
			"This is the structure of entries in the
			 t1TestTable."
		INDEX		{ t1TestInstance }
	::= { t1TestTable 1 }

	T1TestEntry ::= SEQUENCE {
		t1TestInstance			INTEGER,
		t1TestTestType			INTEGER,
		t1TestSlotNumber		INTEGER,
		t1TestPortNumber		INTEGER,
		t1TestTestLength		INTEGER,
		t1TestErrorRate			INTEGER,
		t1TestState			INTEGER
	}

	t1TestInstance	OBJECT-TYPE
		SYNTAX		INTEGER
		MAX-ACCESS	read-create
		STATUS		current
		DESCRIPTION
			"T1 Test Instance."

		DEFVAL		{ 0 }
	::= { t1TestEntry 1 }

	t1TestTestType	OBJECT-TYPE
		SYNTAX		INTEGER {
				    ones(1),
				    zeros(2),
				    fives(3),
				    qrss(4)
				}
		MAX-ACCESS	read-create
		STATUS		current
		DESCRIPTION
			"type of test to run."

		DEFVAL		{ ones }
	::= { t1TestEntry 2 }

	t1TestSlotNumber	OBJECT-TYPE
		SYNTAX		INTEGER {
				    slot1(1),
				    slot2(2),
				    slot3(3),
				    slot4(4),
				    slot5(5),
				    slot6(6),
				    slot7(7),
				    slot8(8),
				    slot11(11),
				    slot12(12),
				    slot13(13),
				    slot14(14),
				    slot15(15),
				    slot16(16),
				    slot17(17),
				    slot18(18)
				}
		MAX-ACCESS	read-create
		STATUS		current
		DESCRIPTION
			"ID of the slot to run the test on."

		DEFVAL		{ slot1 }
	::= { t1TestEntry 3 }

	t1TestPortNumber	OBJECT-TYPE
		SYNTAX		INTEGER {
				    ds11(1),
				    ds12(2),
				    ds13(3),
				    ds14(4),
				    ds15(5),
				    ds16(6),
				    ds17(7),
				    ds18(8),
				    ds19(9),
				    ds110(10),
				    ds111(11),
				    ds112(12),
				    ds113(13),
				    ds114(14),
				    ds115(15),
				    ds116(16),
				    ds117(17),
				    ds118(18),
				    ds119(19),
				    ds120(20),
				    ds121(21),
				    ds122(22),
				    ds123(23),
				    ds124(24),
				    ds125(25),
				    ds126(26),
				    ds127(27),
				    ds128(28),
				    ds129(29),
				    ds130(30),
				    ds131(31),
				    ds132(32),
				    ds133(33),
				    ds134(34),
				    ds135(35),
				    ds136(36),
				    ds137(37),
				    ds138(38),
				    ds139(39),
				    ds140(40),
				    ds141(41),
				    ds142(42),
				    ds143(43),
				    ds144(44),
				    ds145(45),
				    ds146(46),
				    ds147(47),
				    ds148(48),
				    ds149(49),
				    ds150(50),
				    ds151(51),
				    ds152(52),
				    ds153(53),
				    ds154(54),
				    ds155(55),
				    ds156(56)
				}
		MAX-ACCESS	read-create
		STATUS		current
		DESCRIPTION
			"ID of the DS1 to run the test on."

		DEFVAL		{ ds11 }
	::= { t1TestEntry 4 }

	t1TestTestLength	OBJECT-TYPE
		SYNTAX		INTEGER (1..30000)
		MAX-ACCESS	read-create
		STATUS		current
		DESCRIPTION
			"number of bytes of data to send."

		DEFVAL		{ 1 }
	::= { t1TestEntry 5 }

	t1TestErrorRate	OBJECT-TYPE
		SYNTAX		INTEGER (0..100)
		MAX-ACCESS	read-create
		STATUS		current
		DESCRIPTION
			"percentage of data received with errors."

		DEFVAL		{ 0 }
	::= { t1TestEntry 6 }

	t1TestState	OBJECT-TYPE
		SYNTAX		INTEGER {
				    initializing(1),
				    loopingUp(2),
				    sendingData(3),
				    checkingResults(4),
				    loopingDown(5),
				    complete(6),
				    failed(7),
				    cancelled(8)
				}
		MAX-ACCESS	read-create
		STATUS		current
		DESCRIPTION
			"current state of test."

		DEFVAL		{ initializing }
	::= { t1TestEntry 7 }

END
