Nortel-Magellan-Passport-VoiceNetworkingMIB
DEFINITIONS ::= BEGIN



IMPORTS

      OBJECT-TYPE
   FROM RFC-1212

      components,
      passportMIBs
   FROM Nortel-Magellan-Passport-UsefulDefinitionsMIB

      Counter32,
      RowPointer,
      DisplayString,
      StorageType,
      RowStatus,
      PassportCounter64,
      InterfaceIndex,
      Gauge32,
      Integer32,
      Unsigned32
   FROM Nortel-Magellan-Passport-StandardTextualConventionsMIB

      AsciiString,
      Hex,
      NonReplicated,
      DigitString,
      EnterpriseDateAndTime,
      Link
   FROM Nortel-Magellan-Passport-TextualConventionsMIB;




-- LAST-UPDATED   "9906090000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     VoiceNetworking Enterprise MIB."

voiceNetworkingMIB OBJECT IDENTIFIER ::= { passportMIBs 109 }










-- SigChan/n		
-- The SigChan component defines the signalling characteristics of the 
-- connection to the external equipment. 

sigChan OBJECT IDENTIFIER ::= { components 115 }



sigChanRowStatusTable OBJECT-TYPE
   SYNTAX     SEQUENCE OF SigChanRowStatusEntry
   ACCESS     not-accessible
   STATUS     mandatory
   DESCRIPTION
     "This entry controls the addition and deletion of 
      sigChan components."
::= { sigChan 1 }

sigChanRowStatusEntry OBJECT-TYPE
   SYNTAX     SigChanRowStatusEntry
   ACCESS     not-accessible
   STATUS     mandatory
   DESCRIPTION
     "A single entry in the table represents a single 
      sigChan component."
   INDEX {
      sigChanIndex }
::= { sigChanRowStatusTable 1 }

SigChanRowStatusEntry ::= SEQUENCE {
   sigChanRowStatus
      RowStatus,
   sigChanComponentName
      DisplayString,
   sigChanStorageType
      StorageType,
   sigChanIndex
      Integer32 }

sigChanRowStatus OBJECT-TYPE
   SYNTAX     RowStatus 
   ACCESS     read-write
   STATUS     mandatory
   DESCRIPTION
     "This variable is used as the basis for SNMP naming of
      sigChan components.
      These components can be added and deleted."
::= { sigChanRowStatusEntry 1 }

sigChanComponentName OBJECT-TYPE
   SYNTAX     DisplayString 
   ACCESS     read-only
   STATUS     mandatory
   DESCRIPTION
     "This variable provides the component's string name for
      use with the ASCII Console Interface"
::= { sigChanRowStatusEntry 2 }

sigChanStorageType OBJECT-TYPE
   SYNTAX     StorageType 
   ACCESS     read-only
   STATUS     mandatory
   DESCRIPTION
     "This variable represents the storage type value for the
      sigChan tables."
::= { sigChanRowStatusEntry 4 }

sigChanIndex OBJECT-TYPE
   SYNTAX     Integer32 (1..16)
   ACCESS     not-accessible
   STATUS     mandatory
   DESCRIPTION
     "This variable represents the index for the sigChan tables."
::= { sigChanRowStatusEntry 10 }

sigChanCidDataTable OBJECT-TYPE
   SYNTAX     SEQUENCE OF SigChanCidDataEntry
   ACCESS     not-accessible
   STATUS     mandatory
   DESCRIPTION
     "This group contains the attribute for a component's Customer 
      Identifier (CID). Refer to the attribute description for a detailed 
      explanation of CIDs."
::= { sigChan 100 }

sigChanCidDataEntry OBJECT-TYPE
   SYNTAX     SigChanCidDataEntry
   ACCESS     not-accessible
   STATUS     mandatory
   DESCRIPTION
     "An entry in the sigChanCidDataTable."
   INDEX {
      sigChanIndex }
::= { sigChanCidDataTable 1 }

SigChanCidDataEntry ::= SEQUENCE {
   sigChanCustomerIdentifier
      Unsigned32 }

sigChanCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { sigChanCidDataEntry 1 }

sigChanIfEntryTable OBJECT-TYPE
   SYNTAX     SEQUENCE OF SigChanIfEntryEntry
   ACCESS     not-accessible
   STATUS     mandatory
   DESCRIPTION
     "This group contains the provisionable attributes for the ifEntry."
::= { sigChan 101 }

sigChanIfEntryEntry OBJECT-TYPE
   SYNTAX     SigChanIfEntryEntry
   ACCESS     not-accessible
   STATUS     mandatory
   DESCRIPTION
     "An entry in the sigChanIfEntryTable."
   INDEX {
      sigChanIndex }
::= { sigChanIfEntryTable 1 }

SigChanIfEntryEntry ::= SEQUENCE {
   sigChanIfAdminStatus
      INTEGER,
   sigChanIfIndex
      InterfaceIndex }

sigChanIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { sigChanIfEntryEntry 1 }

sigChanIfIndex OBJECT-TYPE
   SYNTAX     InterfaceIndex (1..65535)
   ACCESS     read-only
   STATUS     mandatory
   DESCRIPTION
     "This is the index for the IfEntry. Its value is automatically initialized 
      during the provisioning process."
::= { sigChanIfEntryEntry 2 }

sigChanOperStatusTable OBJECT-TYPE
   SYNTAX     SEQUENCE OF SigChanOperStatusEntry
   ACCESS     not-accessible
   STATUS     mandatory
   DESCRIPTION
     "This group includes the Operational Status attribute. This attribute 
      defines the current operational state of this component."
::= { sigChan 102 }

sigChanOperStatusEntry OBJECT-TYPE
   SYNTAX     SigChanOperStatusEntry
   ACCESS     not-accessible
   STATUS     mandatory
   DESCRIPTION
     "An entry in the sigChanOperStatusTable."
   INDEX {
      sigChanIndex }
::= { sigChanOperStatusTable 1 }

SigChanOperStatusEntry ::= SEQUENCE {
   sigChanSnmpOperStatus
      INTEGER }

sigChanSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { sigChanOperStatusEntry 1 }

sigChanStateTable OBJECT-TYPE
   SYNTAX     SEQUENCE OF SigChanStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { sigChan 103 }

sigChanStateEntry OBJECT-TYPE
   SYNTAX     SigChanStateEntry
   ACCESS     not-accessible
   STATUS     mandatory
   DESCRIPTION
     "An entry in the sigChanStateTable."
   INDEX {
      sigChanIndex }
::= { sigChanStateTable 1 }

SigChanStateEntry ::= SEQUENCE {
   sigChanAdminState
      INTEGER,
   sigChanOperationalState
      INTEGER,
   sigChanUsageState
      INTEGER }

sigChanAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { sigChanStateEntry 1 }

sigChanOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { sigChanStateEntry 2 }

sigChanUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { sigChanStateEntry 3 }

sigChanProvTable OBJECT-TYPE
   SYNTAX     SEQUENCE OF SigChanProvEntry
   ACCESS     not-accessible
   STATUS     mandatory
   DESCRIPTION
     "This group represents the provisionable attributes of a SigChan."
::= { sigChan 104 }

sigChanProvEntry OBJECT-TYPE
   SYNTAX     SigChanProvEntry
   ACCESS     not-accessible
   STATUS     mandatory
   DESCRIPTION
     "An entry in the sigChanProvTable."
   INDEX {
      sigChanIndex }
::= { sigChanProvTable 1 }

SigChanProvEntry ::= SEQUENCE {
   sigChanCommentText
      AsciiString,
   sigChanOctothorpeEod
      INTEGER,
   sigChanForceNpiTon
      INTEGER,
   sigChanDefaultNpiTon
      INTEGER }

sigChanCommentText OBJECT-TYPE
   SYNTAX     AsciiString (SIZE (0..40))
   ACCESS     read-write
   STATUS     mandatory
   DESCRIPTION
     "Use of this attribute is at the discretion of the system administrator. 
      Typically, this attribute specifies the name of the customer that is 
      using this SigChan."
::= { sigChanProvEntry 1 }

sigChanOctothorpeEod OBJECT-TYPE
   SYNTAX     INTEGER  {
                 yes(0),
                 no(1) }
   ACCESS     read-write
   STATUS     mandatory
   DESCRIPTION
     "This attribute specifies whether the octothorpe should be used as an 
      end of dialling indication. When this character is received, only the 
      digits that have been received to that point will be used for address 
      resolution. All subsequent digits will be forwarded to the far-end, 
      but they will not be used. 
      The octothorpe will not be sent to the far-end."
   DEFVAL     { no }
::= { sigChanProvEntry 2 }

sigChanForceNpiTon OBJECT-TYPE
   SYNTAX     INTEGER  {
                 yes(0),
                 no(1) }
   ACCESS     read-write
   STATUS     mandatory
   DESCRIPTION
     "This attribute, together with the defaultNpiTon attribute, controls 
      Numbering Plan Identifier (NPI) and Type Of Number (TON) 
      values to be used by the SigChan component for egress calls (if 
      applicable).
      If set to yes, NPI and TON values defined by the defaultNpiTon 
      attribute unconditionally overwrite values received in the call setup 
      message from the subnet."
   DEFVAL     { no }
::= { sigChanProvEntry 3 }

sigChanDefaultNpiTon OBJECT-TYPE
   SYNTAX     INTEGER  {
                 unknown(0),
                 international(1),
                 national(2),
                 subscriber(3),
                 p0(4),
                 p1(5),
                 p2(6),
                 p3(7),
                 p4(8),
                 p5(9),
                 p6(10),
                 p7(11),
                 casUnknown(12) }
   ACCESS     read-write
   STATUS     mandatory
   DESCRIPTION
     "This attribute, together with the forceNpiTon attribute, controls 
      Numbering Plan Identifier (NPI) and Type Of Number (TON) 
      values to be used by the SigChan component for egress calls (if 
      applicable).
      The combination of NPI and TON values defined by the 
      defaultNpiTon attribute is used for an egress call whenever:
      - the call setup message received from subnet indicates that NPI or 
      TON information is not supplied or doesn't make sense, or
      - attribute forceNpiTon is set to yes
      Mapping between values of the defaultNpiTon attribute and 
      associated combinations of NPI and TON values follows:
      casUnknown: NPI=unknown (0) TON=unknown (0)
      unknown: NPI=E.164 (1) TON=unknown (0)
      international: NPI=E.164 (1) TON=international (1)
      national: NPI=E.164 (1) TON=national (2)
      subscriber: NPI=E.164 (1) TON=subscriber (4)
      p0: NPI=private(9) TON=0
      p1: NPI=private(9) TON=1
      p2: NPI=private(9) TON=2
      p3: NPI=private(9) TON=3
      p4: NPI=private(9) TON=4
      p5: NPI=private(9) TON=5
      p6: NPI=private(9) TON=6
      p7: NPI=private(9) TON=7"
   DEFVAL     { casUnknown }
::= { sigChanProvEntry 4 }

sigChanSubroutesTable OBJECT-TYPE
   SYNTAX     SEQUENCE OF SigChanSubroutesEntry
   ACCESS     not-accessible
   STATUS     mandatory
   DESCRIPTION
     "This attribute identifies all of the VoiceSubroutes which are 
      associated with this signalling channel."
::= { sigChan 307 }

sigChanSubroutesEntry OBJECT-TYPE
   SYNTAX     SigChanSubroutesEntry
   ACCESS     not-accessible
   STATUS     mandatory
   DESCRIPTION
     "An entry in the sigChanSubroutesTable."
   INDEX {
      sigChanIndex,
      sigChanSubroutesValue }
::= { sigChanSubroutesTable 1 }

SigChanSubroutesEntry ::= SEQUENCE {
   sigChanSubroutesValue
      Link,
   sigChanSubroutesRowStatus
      RowStatus }

sigChanSubroutesValue OBJECT-TYPE
   SYNTAX     Link 
   ACCESS     read-write
   STATUS     mandatory
   DESCRIPTION
     "This variable represents both the value and the index for the
      sigChanSubroutesTable."
::= { sigChanSubroutesEntry 1 }

sigChanSubroutesRowStatus OBJECT-TYPE
   SYNTAX     RowStatus 
   ACCESS     write-only
   STATUS     mandatory
   DESCRIPTION
     "This variable is used to control the addition and deletion 
      of individual values of the sigChanSubroutesTable."
::= { sigChanSubroutesEntry 2 }

sigChanDegradedSubroutesTable OBJECT-TYPE
   SYNTAX     SEQUENCE OF SigChanDegradedSubroutesEntry
   ACCESS     not-accessible
   STATUS     mandatory
   DESCRIPTION
     "This attribute lists all of the VoiceSubroute components that do not 
      have all of their SwitchedVoiceService subcomponents available for 
      use."
::= { sigChan 308 }

sigChanDegradedSubroutesEntry OBJECT-TYPE
   SYNTAX     SigChanDegradedSubroutesEntry
   ACCESS     not-accessible
   STATUS     mandatory
   DESCRIPTION
     "An entry in the sigChanDegradedSubroutesTable."
   INDEX {
      sigChanIndex,
      sigChanDegradedSubroutesValue }
::= { sigChanDegradedSubroutesTable 1 }

SigChanDegradedSubroutesEntry ::= SEQUENCE {
   sigChanDegradedSubroutesValue
      RowPointer }

sigChanDegradedSubroutesValue OBJECT-TYPE
   SYNTAX     RowPointer 
   ACCESS     read-only
   STATUS     mandatory
   DESCRIPTION
     "This variable represents both the value and the index for the
      sigChanDegradedSubroutesTable."
::= { sigChanDegradedSubroutesEntry 1 }

-- 
-- *** THIS SUBTREE CURRENTLY NOT IMPLEMENTED ***
-- 

-- SigChan/n Bchannel/n
-- This component contains operational attributes of an individual 
-- B-channel serviced by the SigChan component. The Bchannel 
-- component instance value reflects the external (protocol specific) 
-- channel number. In nB+D configurations, channel number also 
-- reflects the related interface:
-- Bchannel/1-xx - primary interface,
-- Bchannel/101-1xx - secondary interface,
-- Bchannel/201-2xx - tertiary interface,
-- Bchannel/301-3xx - quaternary interface

sigChanBch OBJECT IDENTIFIER ::= { sigChan 7 }



sigChanBchRowStatusTable OBJECT-TYPE
   SYNTAX     SEQUENCE OF SigChanBchRowStatusEntry
   ACCESS     not-accessible
   STATUS     mandatory
   DESCRIPTION
     "*** THIS TABLE CURRENTLY NOT IMPLEMENTED ***

      This entry controls the addition and deletion of 
      sigChanBch components."
::= { sigChanBch 1 }

sigChanBchRowStatusEntry OBJECT-TYPE
   SYNTAX     SigChanBchRowStatusEntry
   ACCESS     not-accessible
   STATUS     mandatory
   DESCRIPTION
     "A single entry in the table represents a single 
      sigChanBch component."
   INDEX {
      sigChanIndex,
      sigChanBchIndex }
::= { sigChanBchRowStatusTable 1 }

SigChanBchRowStatusEntry ::= SEQUENCE {
   sigChanBchRowStatus
      RowStatus,
   sigChanBchComponentName
      DisplayString,
   sigChanBchStorageType
      StorageType,
   sigChanBchIndex
      Integer32 }

sigChanBchRowStatus OBJECT-TYPE
   SYNTAX     RowStatus 
   ACCESS     read-only
   STATUS     mandatory
   DESCRIPTION
     "This variable is used as the basis for SNMP naming of
      sigChanBch components.
      These components cannot be added nor deleted."
::= { sigChanBchRowStatusEntry 1 }

sigChanBchComponentName OBJECT-TYPE
   SYNTAX     DisplayString 
   ACCESS     read-only
   STATUS     mandatory
   DESCRIPTION
     "This variable provides the component's string name for
      use with the ASCII Console Interface"
::= { sigChanBchRowStatusEntry 2 }

sigChanBchStorageType OBJECT-TYPE
   SYNTAX     StorageType 
   ACCESS     read-only
   STATUS     mandatory
   DESCRIPTION
     "This variable represents the storage type value for the
      sigChanBch tables."
::= { sigChanBchRowStatusEntry 4 }

sigChanBchIndex OBJECT-TYPE
   SYNTAX     Integer32 (1..331)
   ACCESS     not-accessible
   STATUS     mandatory
   DESCRIPTION
     "This variable represents the index for the sigChanBch tables."
::= { sigChanBchRowStatusEntry 10 }

sigChanBchOperTable OBJECT-TYPE
   SYNTAX     SEQUENCE OF SigChanBchOperEntry
   ACCESS     not-accessible
   STATUS     mandatory
   DESCRIPTION
     "*** THIS TABLE CURRENTLY NOT IMPLEMENTED ***

      This group contains various operational attributes of a B-channel 
      serviced by a Signalling Channel."
::= { sigChanBch 4 }

sigChanBchOperEntry OBJECT-TYPE
   SYNTAX     SigChanBchOperEntry
   ACCESS     not-accessible
   STATUS     mandatory
   DESCRIPTION
     "An entry in the sigChanBchOperTable."
   INDEX {
      sigChanIndex,
      sigChanBchIndex }
::= { sigChanBchOperTable 1 }

SigChanBchOperEntry ::= SEQUENCE {
   sigChanBchStatus
      INTEGER,
   sigChanBchTimeSlot
      Unsigned32,
   sigChanBchVsrInstance
      Unsigned32,
   sigChanBchCalledDirectoryNumber
      DigitString }

sigChanBchStatus OBJECT-TYPE
   SYNTAX     INTEGER  {
                 unknown(0),
                 maintB(1),
                 idle(2),
                 busy(3),
                 ingress(4),
                 egress(5),
                 idleMaintenance(6),
                 ingressMaintenance(7),
                 egressMaintenance(8),
                 outOfService(9) }
   ACCESS     read-only
   STATUS     mandatory
   DESCRIPTION
     "This attribute indicates what is current internal B-channel state.
      The attribute may have the following values for any supported 
      access signalling protocol on Passport: 
      unknown, the B-channel has not registered yet for SigChan services
      maintB, the B-channel is undergoing a maintenance action
      idle, the B-channel is available for ingress/egress calls
      busy, the B-channel is currently being used for an ingress or egress 
      call
      ingress, the B-channel is currently being used for an ingress call 
      (from the external network to the subnet)
      egress, the B-channel is currently being used for an egress call 
      (from the subnet to the external network)
      
      In addition, CCS protocols supporting SERVICE messaging may 
      also use the following values:
      idleMaintenance, the B-channel received a SERVICE message 
      placing the channel in maintenance, and no calls are active on the 
      channel
      ingressMaintenance, the B-channel received a SERVICE message 
      placing the channel in maintenance, and an incoming call is active 
      on the channel
      egressMaintenance, the B-channel received a SERVICE message 
      placing the channel in maintenance, and an outgoing call is active 
      on the channel
      outOfService, a SERVICE message to or from the PBX has placed 
      the channel out of service"
   DEFVAL     { unknown }
::= { sigChanBchOperEntry 1 }

sigChanBchTimeSlot OBJECT-TYPE
   SYNTAX     Unsigned32 (0..100)
   ACCESS     read-only
   STATUS     mandatory
   DESCRIPTION
     "This attribute indicates which timeslot the B-channel uses."
   DEFVAL     { 0 }
::= { sigChanBchOperEntry 2 }

sigChanBchVsrInstance OBJECT-TYPE
   SYNTAX     Unsigned32 (0..255)
   ACCESS     read-only
   STATUS     mandatory
   DESCRIPTION
     "This attribute indicates the component instance of the 
      VoiceSubroute to which the B-channel belongs."
   DEFVAL     { 0 }
::= { sigChanBchOperEntry 3 }

sigChanBchCalledDirectoryNumber OBJECT-TYPE
   SYNTAX     DigitString (SIZE (1..32))
   ACCESS     read-only
   STATUS     mandatory
   DESCRIPTION
     "This attribute indicates the dialled number for the currently active 
      call on this B-channel."
::= { sigChanBchOperEntry 4 }


-- SigChan/n Gateway
-- This component contains operational attributes which describe 
-- gateway capabilities of the SigChan component as well as the basic 
-- statistics related to calls requiring signalling protocol conversion.

sigChanGw OBJECT IDENTIFIER ::= { sigChan 15 }



sigChanGwRowStatusTable OBJECT-TYPE
   SYNTAX     SEQUENCE OF SigChanGwRowStatusEntry
   ACCESS     not-accessible
   STATUS     mandatory
   DESCRIPTION
     "This entry controls the addition and deletion of 
      sigChanGw components."
::= { sigChanGw 1 }

sigChanGwRowStatusEntry OBJECT-TYPE
   SYNTAX     SigChanGwRowStatusEntry
   ACCESS     not-accessible
   STATUS     mandatory
   DESCRIPTION
     "A single entry in the table represents a single 
      sigChanGw component."
   INDEX {
      sigChanIndex,
      sigChanGwIndex }
::= { sigChanGwRowStatusTable 1 }

SigChanGwRowStatusEntry ::= SEQUENCE {
   sigChanGwRowStatus
      RowStatus,
   sigChanGwComponentName
      DisplayString,
   sigChanGwStorageType
      StorageType,
   sigChanGwIndex
      NonReplicated }

sigChanGwRowStatus OBJECT-TYPE
   SYNTAX     RowStatus 
   ACCESS     read-only
   STATUS     mandatory
   DESCRIPTION
     "This variable is used as the basis for SNMP naming of
      sigChanGw components.
      These components cannot be added nor deleted."
::= { sigChanGwRowStatusEntry 1 }

sigChanGwComponentName OBJECT-TYPE
   SYNTAX     DisplayString 
   ACCESS     read-only
   STATUS     mandatory
   DESCRIPTION
     "This variable provides the component's string name for
      use with the ASCII Console Interface"
::= { sigChanGwRowStatusEntry 2 }

sigChanGwStorageType OBJECT-TYPE
   SYNTAX     StorageType 
   ACCESS     read-only
   STATUS     mandatory
   DESCRIPTION
     "This variable represents the storage type value for the
      sigChanGw tables."
::= { sigChanGwRowStatusEntry 4 }

sigChanGwIndex OBJECT-TYPE
   SYNTAX     NonReplicated 
   ACCESS     not-accessible
   STATUS     mandatory
   DESCRIPTION
     "This variable represents the index for the sigChanGw tables."
::= { sigChanGwRowStatusEntry 10 }

sigChanGwStatsTable OBJECT-TYPE
   SYNTAX     SEQUENCE OF SigChanGwStatsEntry
   ACCESS     not-accessible
   STATUS     mandatory
   DESCRIPTION
     "This group provides signalling gateway related statistical attributes 
      for the SigChan component."
::= { sigChanGw 101 }

sigChanGwStatsEntry OBJECT-TYPE
   SYNTAX     SigChanGwStatsEntry
   ACCESS     not-accessible
   STATUS     mandatory
   DESCRIPTION
     "An entry in the sigChanGwStatsTable."
   INDEX {
      sigChanIndex,
      sigChanGwIndex }
::= { sigChanGwStatsTable 1 }

SigChanGwStatsEntry ::= SEQUENCE {
   sigChanGwRequiredConversions
      Counter32,
   sigChanGwUnsupportedConversions
      Counter32 }

sigChanGwRequiredConversions OBJECT-TYPE
   SYNTAX     Counter32 
   ACCESS     read-only
   STATUS     mandatory
   DESCRIPTION
     "This attribute counts the total number of calls that have been made 
      from the subnet to the interface (that is external equipment, for 
      example a PBX) which needed signalling protocol conversion. The 
      value wraps to zero when it exceeds its maximum. The count 
      includes both, supported and unsupported conversions."
::= { sigChanGwStatsEntry 1 }

sigChanGwUnsupportedConversions OBJECT-TYPE
   SYNTAX     Counter32 
   ACCESS     read-only
   STATUS     mandatory
   DESCRIPTION
     "This attribute counts the total number of calls that have been made 
      from the subnet to the interface (that is external equipment, for 
      example a PBX) which needed signalling protocol conversion but 
      were rejected since the requested conversion was not supported. 
      The value wraps to zero when it exceeds its maximum."
::= { sigChanGwStatsEntry 2 }

sigChanGwGwcTable OBJECT-TYPE
   SYNTAX     SEQUENCE OF SigChanGwGwcEntry
   ACCESS     not-accessible
   STATUS     obsolete
   DESCRIPTION
     "This attribute has been migrated to gatewayCapability."
::= { sigChanGw 301 }

sigChanGwGwcEntry OBJECT-TYPE
   SYNTAX     SigChanGwGwcEntry
   ACCESS     not-accessible
   STATUS     obsolete
   DESCRIPTION
     "An entry in the sigChanGwGwcTable."
   INDEX {
      sigChanIndex,
      sigChanGwIndex,
      sigChanGwGwcIndex }
::= { sigChanGwGwcTable 1 }

SigChanGwGwcEntry ::= SEQUENCE {
   sigChanGwGwcIndex
      INTEGER,
   sigChanGwGwcValue
      INTEGER }

sigChanGwGwcIndex OBJECT-TYPE
   SYNTAX     INTEGER  {
                 etsiQsigPG(0),
                 nisPG(1),
                 analogAndCasPG(2),
                 euroIsdnPG(3),
                 mcdnPG(4),
                 mcdnUniPG(5) }
   ACCESS     not-accessible
   STATUS     obsolete
   DESCRIPTION
     "This variable represents the sigChanGwGwcTable
      specific index for the sigChanGwGwcTable."
::= { sigChanGwGwcEntry 1 }

sigChanGwGwcValue OBJECT-TYPE
   SYNTAX     INTEGER  {
                 noGw(0),
                 singleEndedGw(1),
                 doubleEndedGw(2),
                 singleOrDoubleEndedGw(3),
                 nativePG(4) }
   ACCESS     read-only
   STATUS     obsolete
   DESCRIPTION
     "This variable represents an individual value for the
      sigChanGwGwcTable."
::= { sigChanGwGwcEntry 2 }

sigChanGwGatewayCapTable OBJECT-TYPE
   SYNTAX     SEQUENCE OF SigChanGwGatewayCapEntry
   ACCESS     not-accessible
   STATUS     mandatory
   DESCRIPTION
     "This attribute indicates the SigChan component's capability to 
      convert from one access signalling type to another. Access 
      signalling protocols (protocols between a Passport and external 
      switching equipment, for example a PBX) are grouped into protocol 
      groups. Protocols within the same protocol group are considered 
      completely compatible. This means that no extra processing is 
      needed when a call originates from an ingress link using protocol A 
      and terminates on an egress link using protocol B if protocols A and 
      B belong to the same protocol group. The following protocol groups 
      are defined:
      etsiQsigPG - ETSI QSIG protocol group containing ETSI QSIG 
      protocol,
      mcdnFamilyPG - MCDN Family protocol group containing NIS, 
      Meridian Customer Defined Network (MCDN) peer to peer, and 
      MCDN User to Network (UNI) protocols,
      analogAndCasPG - Analog and CAS protocol group containing 
      most of the analog and channel associated signalling protocols with 
      steady state line signalling and DTMF register signalling,
      euroIsdnPG - EURO ISDN protocol group containing most of the 
      European national ISDN protocols based on ETSI ISDN (ETSI-T) 
      standard.
      For every of the protocols group this attribute indicates what is the 
      level of protocol conversion support available on the SigChan 
      component:
      noGw - no protocol conversion available for the protocol group,
      singleEndedGw - only full protocol conversion available for the 
      protocol group (that is the SigChan component on the other side of 
      the subnet does not have to get involved in the gateway processing),
      doubleEndedGw - only partial protocol conversion available for the 
      protocol group (that is both SigChan components, ingress and 
      egress, have to get involved in signalling conversion),
      singleOrDoubleEndedGw - both, full and partial protocol 
      conversions available for the protocol group,
      nativePG - the protocol group is the native protocol group for the 
      SigChan component."
::= { sigChanGw 302 }

sigChanGwGatewayCapEntry OBJECT-TYPE
   SYNTAX     SigChanGwGatewayCapEntry
   ACCESS     not-accessible
   STATUS     mandatory
   DESCRIPTION
     "An entry in the sigChanGwGatewayCapTable."
   INDEX {
      sigChanIndex,
      sigChanGwIndex,
      sigChanGwGatewayCapIndex }
::= { sigChanGwGatewayCapTable 1 }

SigChanGwGatewayCapEntry ::= SEQUENCE {
   sigChanGwGatewayCapIndex
      INTEGER,
   sigChanGwGatewayCapValue
      INTEGER }

sigChanGwGatewayCapIndex OBJECT-TYPE
   SYNTAX     INTEGER  {
                 etsiQsigPG(0),
                 mcdnPG(1),
                 analogAndCasPG(2),
                 euroIsdnPG(3) }
   ACCESS     not-accessible
   STATUS     mandatory
   DESCRIPTION
     "This variable represents the sigChanGwGatewayCapTable
      specific index for the sigChanGwGatewayCapTable."
::= { sigChanGwGatewayCapEntry 1 }

sigChanGwGatewayCapValue OBJECT-TYPE
   SYNTAX     INTEGER  {
                 noGw(0),
                 singleEndedGw(1),
                 doubleEndedGw(2),
                 singleOrDoubleEndedGw(3),
                 nativePG(4) }
   ACCESS     read-only
   STATUS     mandatory
   DESCRIPTION
     "This variable represents an individual value for the
      sigChanGwGatewayCapTable."
::= { sigChanGwGatewayCapEntry 2 }

-- 
-- *** THIS SUBTREE CURRENTLY NOT IMPLEMENTED ***
-- 

-- SigChan/n NcaSession/n
-- This component represents a single Non Call-Associated signalling 
-- Session (NCAS) serviced by the SigChan component. Non 
-- call-associated signalling sessions are only supported on some 
-- Common Channel Signalling (CCS) protocols (for example ETSI 
-- QSIG, ETSI UNI ISDN). The instance value of a NcaSession 
-- component is an arbitrary number which does not change during an 
-- individual NCAS session.

sigChanNcas OBJECT IDENTIFIER ::= { sigChan 16 }



sigChanNcasRowStatusTable OBJECT-TYPE
   SYNTAX     SEQUENCE OF SigChanNcasRowStatusEntry
   ACCESS     not-accessible
   STATUS     mandatory
   DESCRIPTION
     "*** THIS TABLE CURRENTLY NOT IMPLEMENTED ***

      This entry controls the addition and deletion of 
      sigChanNcas components."
::= { sigChanNcas 1 }

sigChanNcasRowStatusEntry OBJECT-TYPE
   SYNTAX     SigChanNcasRowStatusEntry
   ACCESS     not-accessible
   STATUS     mandatory
   DESCRIPTION
     "A single entry in the table represents a single 
      sigChanNcas component."
   INDEX {
      sigChanIndex,
      sigChanNcasIndex }
::= { sigChanNcasRowStatusTable 1 }

SigChanNcasRowStatusEntry ::= SEQUENCE {
   sigChanNcasRowStatus
      RowStatus,
   sigChanNcasComponentName
      DisplayString,
   sigChanNcasStorageType
      StorageType,
   sigChanNcasIndex
      Integer32 }

sigChanNcasRowStatus OBJECT-TYPE
   SYNTAX     RowStatus 
   ACCESS     read-only
   STATUS     mandatory
   DESCRIPTION
     "This variable is used as the basis for SNMP naming of
      sigChanNcas components.
      These components cannot be added nor deleted."
::= { sigChanNcasRowStatusEntry 1 }

sigChanNcasComponentName OBJECT-TYPE
   SYNTAX     DisplayString 
   ACCESS     read-only
   STATUS     mandatory
   DESCRIPTION
     "This variable provides the component's string name for
      use with the ASCII Console Interface"
::= { sigChanNcasRowStatusEntry 2 }

sigChanNcasStorageType OBJECT-TYPE
   SYNTAX     StorageType 
   ACCESS     read-only
   STATUS     mandatory
   DESCRIPTION
     "This variable represents the storage type value for the
      sigChanNcas tables."
::= { sigChanNcasRowStatusEntry 4 }

sigChanNcasIndex OBJECT-TYPE
   SYNTAX     Integer32 (0..65535)
   ACCESS     not-accessible
   STATUS     mandatory
   DESCRIPTION
     "This variable represents the index for the sigChanNcas tables."
::= { sigChanNcasRowStatusEntry 10 }

sigChanNcasOperTable OBJECT-TYPE
   SYNTAX     SEQUENCE OF SigChanNcasOperEntry
   ACCESS     not-accessible
   STATUS     mandatory
   DESCRIPTION
     "*** THIS TABLE CURRENTLY NOT IMPLEMENTED ***

      This group contains various operational attributes of a non 
      call-associated signalling session serviced by a SigChan 
      component."
::= { sigChanNcas 100 }

sigChanNcasOperEntry OBJECT-TYPE
   SYNTAX     SigChanNcasOperEntry
   ACCESS     not-accessible
   STATUS     mandatory
   DESCRIPTION
     "An entry in the sigChanNcasOperTable."
   INDEX {
      sigChanIndex,
      sigChanNcasIndex }
::= { sigChanNcasOperTable 1 }

SigChanNcasOperEntry ::= SEQUENCE {
   sigChanNcasDirection
      INTEGER,
   sigChanNcasCallReference
      Hex,
   sigChanNcasCalledDirectoryNumber
      DigitString,
   sigChanNcasDuration
      Unsigned32 }

sigChanNcasDirection OBJECT-TYPE
   SYNTAX     INTEGER  {
                 ingress(1),
                 egress(2) }
   ACCESS     read-only
   STATUS     mandatory
   DESCRIPTION
     "This attribute indicates what is the direction of the non 
      call-associated signalling session. The attribute may have the 
      following values:
      ingress, the NCAS session is originated by the external equipment 
      into the subnet
      egress, the NCAS session is originated by the subnet into the 
      external equipment"
::= { sigChanNcasOperEntry 1 }

sigChanNcasCallReference OBJECT-TYPE
   SYNTAX     Hex (0..65535)
   ACCESS     read-only
   STATUS     mandatory
   DESCRIPTION
     "This attribute indicates which call reference the NCAS session uses."
::= { sigChanNcasOperEntry 2 }

sigChanNcasCalledDirectoryNumber OBJECT-TYPE
   SYNTAX     DigitString (SIZE (1..32))
   ACCESS     read-only
   STATUS     mandatory
   DESCRIPTION
     "This attribute indicates the dialled number for the NCAS session."
::= { sigChanNcasOperEntry 3 }

sigChanNcasDuration OBJECT-TYPE
   SYNTAX     Unsigned32 (0..4294967295)
   ACCESS     read-only
   STATUS     mandatory
   DESCRIPTION
     "This attribute indicates duration of the NCAS session since its 
      establishment."
   DEFVAL     { 0 }
::= { sigChanNcasOperEntry 4 }


-- SigChan/n VnetInternalCauseManipulation
-- This component represents the provisionable attributes for the 
-- internal, Passport and subnet generated cause codes of an 
-- establishing call. This component can be added for most of the 
-- ISDN (common channel signalling) protocols (EtsiQsig, NisSig, 
-- EuroIsdn) and cannot be added for a channel associated signalling 
-- protocol. This component is useful in a network where the 
-- originating PBX has restricted conditions to initiating alternate 
-- rerouting (rerouting on just one, specific, clearing cause code).

sigChanICmap OBJECT IDENTIFIER ::= { sigChan 18 }



sigChanICmapRowStatusTable OBJECT-TYPE
   SYNTAX     SEQUENCE OF SigChanICmapRowStatusEntry
   ACCESS     not-accessible
   STATUS     mandatory
   DESCRIPTION
     "This entry controls the addition and deletion of 
      sigChanICmap components."
::= { sigChanICmap 1 }

sigChanICmapRowStatusEntry OBJECT-TYPE
   SYNTAX     SigChanICmapRowStatusEntry
   ACCESS     not-accessible
   STATUS     mandatory
   DESCRIPTION
     "A single entry in the table represents a single 
      sigChanICmap component."
   INDEX {
      sigChanIndex,
      sigChanICmapIndex }
::= { sigChanICmapRowStatusTable 1 }

SigChanICmapRowStatusEntry ::= SEQUENCE {
   sigChanICmapRowStatus
      RowStatus,
   sigChanICmapComponentName
      DisplayString,
   sigChanICmapStorageType
      StorageType,
   sigChanICmapIndex
      NonReplicated }

sigChanICmapRowStatus OBJECT-TYPE
   SYNTAX     RowStatus 
   ACCESS     read-write
   STATUS     mandatory
   DESCRIPTION
     "This variable is used as the basis for SNMP naming of
      sigChanICmap components.
      These components can be added and deleted."
::= { sigChanICmapRowStatusEntry 1 }

sigChanICmapComponentName OBJECT-TYPE
   SYNTAX     DisplayString 
   ACCESS     read-only
   STATUS     mandatory
   DESCRIPTION
     "This variable provides the component's string name for
      use with the ASCII Console Interface"
::= { sigChanICmapRowStatusEntry 2 }

sigChanICmapStorageType OBJECT-TYPE
   SYNTAX     StorageType 
   ACCESS     read-only
   STATUS     mandatory
   DESCRIPTION
     "This variable represents the storage type value for the
      sigChanICmap tables."
::= { sigChanICmapRowStatusEntry 4 }

sigChanICmapIndex OBJECT-TYPE
   SYNTAX     NonReplicated 
   ACCESS     not-accessible
   STATUS     mandatory
   DESCRIPTION
     "This variable represents the index for the sigChanICmap tables."
::= { sigChanICmapRowStatusEntry 10 }

sigChanICmapIntCauseTable OBJECT-TYPE
   SYNTAX     SEQUENCE OF SigChanICmapIntCauseEntry
   ACCESS     not-accessible
   STATUS     mandatory
   DESCRIPTION
     "This group contains the provisionable, Passport generated clearing 
      reasons of an establishing call."
::= { sigChanICmap 100 }

sigChanICmapIntCauseEntry OBJECT-TYPE
   SYNTAX     SigChanICmapIntCauseEntry
   ACCESS     not-accessible
   STATUS     mandatory
   DESCRIPTION
     "An entry in the sigChanICmapIntCauseTable."
   INDEX {
      sigChanIndex,
      sigChanICmapIndex }
::= { sigChanICmapIntCauseTable 1 }

SigChanICmapIntCauseEntry ::= SEQUENCE {
   sigChanICmapEgressLinkOutOfServCause
      Unsigned32,
   sigChanICmapChanOrCircNotAvailCause
      Unsigned32,
   sigChanICmapTempFailureCause
      Unsigned32,
   sigChanICmapSwitchCongestCause
      Unsigned32,
   sigChanICmapReqChanOrCircNotAvailCause
      Unsigned32,
   sigChanICmapResourceUnavailCause
      Unsigned32,
   sigChanICmapServNotAllowedCause
      Unsigned32,
   sigChanICmapNoSuchChannelCause
      Unsigned32,
   sigChanICmapIncompatDestCause
      Unsigned32 }

sigChanICmapEgressLinkOutOfServCause OBJECT-TYPE
   SYNTAX     Unsigned32 (0..127 | 128)
   ACCESS     read-write
   STATUS     mandatory
   DESCRIPTION
     "This attribute specifies the cause code sent to the originating PBX 
      when the data link to the remote PBX is down or when remote 
      channels are in maintenance. 
      If the component is not added or if the default value autoConfigure 
      is provisioned for the attribute the cause code sent to the originating 
      PBX is not manipulated and the clearing process is not influenced. 
      For this case, a typical cause code value sent back to the originating 
      PBX is 27.

      VALUES (

      128 = autoConfigure

      )"
   DEFVAL     { 128 }
::= { sigChanICmapIntCauseEntry 1 }

sigChanICmapChanOrCircNotAvailCause OBJECT-TYPE
   SYNTAX     Unsigned32 (0..127 | 128)
   ACCESS     read-write
   STATUS     mandatory
   DESCRIPTION
     "This attribute specifies the cause code sent to the originating PBX if 
      no timeslot is available for an incoming call. 
      If the component is not added or if the default value autoConfigure 
      is provisioned for the attribute the cause code sent to the originating 
      PBX is not manipulated and the clearing process is not influenced. 
      For this case, a typical cause code value sent back to the originating 
      PBX is 34.

      VALUES (

      128 = autoConfigure

      )"
   DEFVAL     { 128 }
::= { sigChanICmapIntCauseEntry 2 }

sigChanICmapTempFailureCause OBJECT-TYPE
   SYNTAX     Unsigned32 (0..127 | 128)
   ACCESS     read-write
   STATUS     mandatory
   DESCRIPTION
     "This attribute specifies the cause code sent to the originating PBX 
      when PORS fails to establish a call due to congestion or a disabled 
      trunk. It is also generated when the calling side fails to decode 
      payload capabilities sent by the called side. 
      If the component is not added or if the default value autoConfigure 
      is provisioned for the attribute the cause code sent to the originating 
      PBX is not manipulated and the clearing process is not influenced. 
      For this case, a typical cause code value sent back to the originating 
      PBX is 41.

      VALUES (

      128 = autoConfigure

      )"
   DEFVAL     { 128 }
::= { sigChanICmapIntCauseEntry 3 }

sigChanICmapSwitchCongestCause OBJECT-TYPE
   SYNTAX     Unsigned32 (0..127 | 128)
   ACCESS     read-write
   STATUS     mandatory
   DESCRIPTION
     "This attribute specifies the cause code sent to the originating PBX 
      when the allocation of internal resources for an incoming call fails. 
      If the component is not added or if the default value autoConfigure 
      is provisioned for the attribute the cause code sent to the originating 
      PBX is not manipulated and the clearing process is not influenced. 
      For this case, typical cause code values sent back to the originating 
      PBX are 42 for NIS and 41 for ETSI.

      VALUES (

      128 = autoConfigure

      )"
   DEFVAL     { 128 }
::= { sigChanICmapIntCauseEntry 4 }

sigChanICmapReqChanOrCircNotAvailCause OBJECT-TYPE
   SYNTAX     Unsigned32 (0..127 | 128)
   ACCESS     read-write
   STATUS     mandatory
   DESCRIPTION
     "This attribute specifies the cause code sent to the originating PBX 
      when an exclusively requested channel is not in service or a channel 
      request is unsuccessful. 
      If the component is not added or if the default value autoConfigure 
      is provisioned for the attribute the cause code sent to the originating 
      PBX is not manipulated and the clearing process is not influenced. 
      For this case, a typical cause code value sent back to the originating 
      PBX is 44.

      VALUES (

      128 = autoConfigure

      )"
   DEFVAL     { 128 }
::= { sigChanICmapIntCauseEntry 5 }

sigChanICmapResourceUnavailCause OBJECT-TYPE
   SYNTAX     Unsigned32 (0..127 | 128)
   ACCESS     read-write
   STATUS     mandatory
   DESCRIPTION
     "This attribute specifies the cause code sent to the originating PBX 
      when the path establishing timer expires, when the switched voice 
      service associated to a call is locked by CAS or when an H-channel 
      is requested. 
      If the component is not added or if the default value autoConfigure 
      is provisioned for the attribute the cause code sent to the originating 
      PBX is not manipulated and the clearing process is not influenced. 
      For this case, typical cause code values sent back to the originating 
      PBX are 47 for NIS and 44 for ETSI.

      VALUES (

      128 = autoConfigure

      )"
   DEFVAL     { 128 }
::= { sigChanICmapIntCauseEntry 6 }

sigChanICmapServNotAllowedCause OBJECT-TYPE
   SYNTAX     Unsigned32 (0..127 | 128)
   ACCESS     read-write
   STATUS     mandatory
   DESCRIPTION
     "This attribute specifies the cause code sent to the originating PBX 
      when the requested call type (voice or data) is not compatible with 
      Vroute typeOfRoute at the calling side. 
      If the component is not added or if the default value autoConfigure 
      is provisioned for the attribute the cause code sent to the originating 
      PBX is not manipulated and the clearing process is not influenced. 
      For this case, a typical cause code value sent back to the originating 
      PBX is 63.

      VALUES (

      128 = autoConfigure

      )"
   DEFVAL     { 128 }
::= { sigChanICmapIntCauseEntry 7 }

sigChanICmapNoSuchChannelCause OBJECT-TYPE
   SYNTAX     Unsigned32 (0..127 | 128)
   ACCESS     read-write
   STATUS     mandatory
   DESCRIPTION
     "This attribute specifies the cause code sent to the originating PBX 
      when a requested channel does not exist. 
      If the component is not added or if the default value autoConfigure 
      is provisioned for the attribute the cause code sent to the originating 
      PBX is not manipulated and the clearing process is not influenced. 
      For this case, a typical cause code value sent back to the originating 
      PBX is 82.

      VALUES (

      128 = autoConfigure

      )"
   DEFVAL     { 128 }
::= { sigChanICmapIntCauseEntry 8 }

sigChanICmapIncompatDestCause OBJECT-TYPE
   SYNTAX     Unsigned32 (0..127 | 128)
   ACCESS     read-write
   STATUS     mandatory
   DESCRIPTION
     "This attribute specifies the cause code sent to the originating PBX 
      when the calling and called side capabilities do not match. 
      If the component is not added or if the default value autoConfigure 
      is provisioned for the attribute the cause code sent to the originating 
      PBX is not manipulated and the clearing process is not influenced. 
      For this case, a typical cause code value sent back to the originating 
      PBX is 88.

      VALUES (

      128 = autoConfigure

      )"
   DEFVAL     { 128 }
::= { sigChanICmapIntCauseEntry 9 }


-- VoiceRoute/n		
-- A VoiceRoute component defines the common characteristics of the 
-- connections to a Private Branch Exchange (PBX). There is normally 
-- one VoiceRoute per attached PBX.

vRoute OBJECT IDENTIFIER ::= { components 116 }



vRouteRowStatusTable OBJECT-TYPE
   SYNTAX     SEQUENCE OF VRouteRowStatusEntry
   ACCESS     not-accessible
   STATUS     mandatory
   DESCRIPTION
     "This entry controls the addition and deletion of 
      vRoute components."
::= { vRoute 1 }

vRouteRowStatusEntry OBJECT-TYPE
   SYNTAX     VRouteRowStatusEntry
   ACCESS     not-accessible
   STATUS     mandatory
   DESCRIPTION
     "A single entry in the table represents a single 
      vRoute component."
   INDEX {
      vRouteIndex }
::= { vRouteRowStatusTable 1 }

VRouteRowStatusEntry ::= SEQUENCE {
   vRouteRowStatus
      RowStatus,
   vRouteComponentName
      DisplayString,
   vRouteStorageType
      StorageType,
   vRouteIndex
      Integer32 }

vRouteRowStatus OBJECT-TYPE
   SYNTAX     RowStatus 
   ACCESS     read-write
   STATUS     mandatory
   DESCRIPTION
     "This variable is used as the basis for SNMP naming of
      vRoute components.
      These components can be added and deleted."
::= { vRouteRowStatusEntry 1 }

vRouteComponentName OBJECT-TYPE
   SYNTAX     DisplayString 
   ACCESS     read-only
   STATUS     mandatory
   DESCRIPTION
     "This variable provides the component's string name for
      use with the ASCII Console Interface"
::= { vRouteRowStatusEntry 2 }

vRouteStorageType OBJECT-TYPE
   SYNTAX     StorageType 
   ACCESS     read-only
   STATUS     mandatory
   DESCRIPTION
     "This variable represents the storage type value for the
      vRoute tables."
::= { vRouteRowStatusEntry 4 }

vRouteIndex OBJECT-TYPE
   SYNTAX     Integer32 (1..16)
   ACCESS     not-accessible
   STATUS     mandatory
   DESCRIPTION
     "This variable represents the index for the vRoute tables."
::= { vRouteRowStatusEntry 10 }

vRouteProvTable OBJECT-TYPE
   SYNTAX     SEQUENCE OF VRouteProvEntry
   ACCESS     not-accessible
   STATUS     mandatory
   DESCRIPTION
     "This group contains the provisionable attributes of a Voice 
      Networking VoiceRoute component."
::= { vRoute 10 }

vRouteProvEntry OBJECT-TYPE
   SYNTAX     VRouteProvEntry
   ACCESS     not-accessible
   STATUS     mandatory
   DESCRIPTION
     "An entry in the vRouteProvTable."
   INDEX {
      vRouteIndex }
::= { vRouteProvTable 1 }

VRouteProvEntry ::= SEQUENCE {
   vRouteCommentText
      AsciiString,
   vRouteTypeOfRoute
      INTEGER,
   vRouteDiallingPlan0
      OCTET STRING,
   vRouteDiallingPlan1
      OCTET STRING,
   vRouteDiallingPlan2
      OCTET STRING,
   vRouteHuntingAlgorithm
      INTEGER,
   vRouteMinimumDigitsToRoute
      Unsigned32,
   vRouteVoiceNetworkingCallServer
      Link,
   vRouteOverrideDirectoryNumber
      DigitString,
   vRoutePrivateNetworkIdentifer
      Unsigned32 }

vRouteCommentText OBJECT-TYPE
   SYNTAX     AsciiString (SIZE (0..40))
   ACCESS     read-write
   STATUS     mandatory
   DESCRIPTION
     "Use of this attribute is at the discretion of the system administrator. 
      Typically, it specifies the name of the customer that is using this 
      VoiceRoute."
::= { vRouteProvEntry 1 }

vRouteTypeOfRoute OBJECT-TYPE
   SYNTAX     INTEGER  {
                 voice(0),
                 data(1),
                 voiceData(2) }
   ACCESS     read-write
   STATUS     mandatory
   DESCRIPTION
     "This attribute specifies the type of calls (either voice, data, or both 
      voice and data) that this VoiceRoute will accept from the Passport 
      subnet and the local PBX. If typeOfRoute is set to voice, then all 
      data calls from the subnet and the local PBX will be rejected. If 
      typeOfRoute is set to data, then all voice calls from the subnet and 
      the local PBX will be rejected. If typeOfRoute is set to voiceData, 
      then all data and voice calls will be accepted from the subnet and 
      the local PBX."
   DEFVAL     { voiceData }
::= { vRouteProvEntry 2 }

vRouteDiallingPlan0 OBJECT-TYPE
   SYNTAX     OCTET STRING (SIZE (2))
   ACCESS     read-write
   STATUS     mandatory
   DESCRIPTION
     "This attribute specifies how to map the numbering plan indication 
      and the type of number into the Vncs database diallingPlan0. For 
      more information refer to NTP 241-7001-4xx Voice Networking 
      Users Guide. There are three numbering plans that are allowed, 
      unknown, E.164, and private. Within each of these, there are eight 
      possible type of numbers. Since the name for the type of numbers 
      for the private numbering plans varies from protocol to protocol, a 
      generic scheme has been adopted.
      unknown means that the sending and receiving switches have no 
      knowledge of the numbering plan.
      international means that the sending switch has identified the 
      number format as matching the E.164 international dialling.
      national means that the sending switch has identified the number as 
      conforming to the E.164 national dialling plan
      subscriber means that the number is the address of a customer 
      conforming to the local public network.
      p0, p1, p2, p3, p4, p5, p6 and p7 are private numbering plans, with a 
      type of number zero to seven.
      casUnknown means any number received from a Channel 
      Associated Signalling (CAS) trunk.

      Description of bits:
      unknown(0)
      international(1)
      national(2)
      subscriber(3)
      p0(4)
      p1(5)
      p2(6)
      p3(7)
      p4(8)
      p5(9)
      p6(10)
      p7(11)
      casUnknown(12)"
   DEFVAL     { 'fff8'H }
::= { vRouteProvEntry 6 }

vRouteDiallingPlan1 OBJECT-TYPE
   SYNTAX     OCTET STRING (SIZE (2))
   ACCESS     read-write
   STATUS     mandatory
   DESCRIPTION
     "This attribute specifies how to map the numbering plan indication 
      and the type of number into the Vncs database diallingPlan1. For 
      more information refer to NTP 241-7001-4xx Voice Networking 
      Users Guide. There are three numbering plans that are allowed, 
      unknown, E.164, and private. Within each of these, there are eight 
      possible type of numbers. Since the name for the type of numbers 
      for the private numbering plans varies from protocol to protocol, a 
      generic scheme has been adopted.
      unknown means that the sending and receiving switches have no 
      knowledge of the numbering plan.
      international means that the sending switch has identified the 
      number format as matching the E.164 international dialling plan.
      national means that the sending switch has identified the number as 
      conforming to the E.164 national dialling plan
      subscriber means that the number is the address of a customer 
      conforming to the local public network.
      p0, p1, p2, p3, p4, p5, p6 and p7 are private numbering plans, with a 
      type of number zero to seven.
      casUnknown means any number received from a Channel 
      Associated Signalling (CAS) trunk.

      Description of bits:
      unknown(0)
      international(1)
      national(2)
      subscriber(3)
      p0(4)
      p1(5)
      p2(6)
      p3(7)
      p4(8)
      p5(9)
      p6(10)
      p7(11)
      casUnknown(12)"
::= { vRouteProvEntry 7 }

vRouteDiallingPlan2 OBJECT-TYPE
   SYNTAX     OCTET STRING (SIZE (2))
   ACCESS     read-write
   STATUS     mandatory
   DESCRIPTION
     "This attribute specifies how to map the numbering plan indication 
      and the type of number into the Vncs database diallingPlan2. For 
      more information refer to NTP 241-7001-4xx Voice Networking 
      Users Guide. There are three numbering plans that are allowed, 
      unknown, E.164, and private. Within each of these, there are eight 
      possible type of numbers. Since the name for the type of numbers 
      for the private numbering plans varies from protocol to protocol, a 
      generic scheme has been adopted.
      unknown means that the sending and receiving switches have no 
      knowledge of the numbering plan.
      international means that the sending switch has identified the 
      number format as matching the E.164 international dialling plan.
      national means that the sending switch has identified the number as 
      conforming to the E.164 national dialling plan
      subscriber means that the number is the address of a customer 
      conforming to the local public network.
      p0, p1, p2, p3, p4, p5, p6 and p7 are private numbering plans, with a 
      type of number zero to seven.
      casUnknown means any number received from a Channel 
      Associated Signalling (CAS) trunk.

      Description of bits:
      unknown(0)
      international(1)
      national(2)
      subscriber(3)
      p0(4)
      p1(5)
      p2(6)
      p3(7)
      p4(8)
      p5(9)
      p6(10)
      p7(11)
      casUnknown(12)"
::= { vRouteProvEntry 8 }

vRouteHuntingAlgorithm OBJECT-TYPE
   SYNTAX     INTEGER  {
                 bottomUpLinear(0),
                 topDownLinear(1) }
   ACCESS     read-write
   STATUS     mandatory
   DESCRIPTION
     "This attribute specifies the type of hunting algorithm that should be 
      used by the VoiceRoute and VoiceSubroutes when selecting a 
      channel to make an outgoing call. 
      bottomUpLinear means that a call from the subnet will be passed to 
      the lowest instance of the VoiceSubroutes, which in turn will pass 
      the call to the lowest instance of SwitchedVoiceService. If there are 
      no available SwitchedVoiceServices in that VoiceSubroute then the 
      process will be repeated for the next lowest instance of 
      VoiceSubroute.
      topDownLinear means that a call from the subnet will be passed to 
      the highest instance of the VoiceSubroutes, which in turn will pass 
      the call to the highest instance of SwitchedVoiceService. If there are 
      no available SwitchedVoiceServices in that VoiceSubroute then the 
      process will be repeated for the next highest instance of 
      VoiceSubroute."
   DEFVAL     { bottomUpLinear }
::= { vRouteProvEntry 9 }

vRouteMinimumDigitsToRoute OBJECT-TYPE
   SYNTAX     Unsigned32 (1..16)
   ACCESS     read-write
   STATUS     mandatory
   DESCRIPTION
     "This attribute specifies the number of digits that must be received 
      before an address resolution request will be sent to the 
      VoiceNetworkingCallServer. Once this level has been exceeded an 
      address resolution request will be sent for every digit received until 
      the dialled number has been resolved in the database.
      This number should be set to a value which represents the average 
      number of digits that will allow for a unique end-point to be 
      identified. If the number is set too low, then the number of 
      simultaneous calls that can be handled by the 
      VoiceNetworkingCallServer will be reduced since the number of 
      address resolution requests sent for each call will be increased. If it 
      is set too high then address resolution request messages will not be 
      sent to the VoiceNetworkingCallServer until the end-of-dial timer 
      has expired (approximately 12 seconds after the last digit has been 
      received). This can result in very long call setup times."
   DEFVAL     { 3 }
::= { vRouteProvEntry 10 }

vRouteVoiceNetworkingCallServer OBJECT-TYPE
   SYNTAX     Link 
   ACCESS     read-write
   STATUS     mandatory
   DESCRIPTION
     "This attribute specifies which Vncs instance should be used by all 
      calls into this VoiceRoute from the PBX."
::= { vRouteProvEntry 11 }

vRouteOverrideDirectoryNumber OBJECT-TYPE
   SYNTAX     DigitString (SIZE (0..24))
   ACCESS     read-write
   STATUS     mandatory
   DESCRIPTION
     "The number specified here will be used in place of the dialled 
      number to lookup the destination in the 
      VoiceNetworkingCallServer. A null string means that the routing 
      decision should be based on the dialled number.
      The numbering plan type that will be used will be noAccessCode."
   DEFVAL     { ''H }  -- ""
::= { vRouteProvEntry 12 }

vRoutePrivateNetworkIdentifer OBJECT-TYPE
   SYNTAX     Unsigned32 (0..32700)
   ACCESS     read-write
   STATUS     mandatory
   DESCRIPTION
     "This attribute specifies the private network identifier (PNI) value. If 
      the value is zero then connectionless supplementary service 
      transport for TCAP formatted FACILITY messages is not 
      supported."
   DEFVAL     { 0 }
::= { vRouteProvEntry 13 }

vRouteCidDataTable OBJECT-TYPE
   SYNTAX     SEQUENCE OF VRouteCidDataEntry
   ACCESS     not-accessible
   STATUS     mandatory
   DESCRIPTION
     "This group contains the attribute for a component's Customer 
      Identifier (CID). Refer to the attribute description for a detailed 
      explanation of CIDs."
::= { vRoute 11 }

vRouteCidDataEntry OBJECT-TYPE
   SYNTAX     VRouteCidDataEntry
   ACCESS     not-accessible
   STATUS     mandatory
   DESCRIPTION
     "An entry in the vRouteCidDataTable."
   INDEX {
      vRouteIndex }
::= { vRouteCidDataTable 1 }

VRouteCidDataEntry ::= SEQUENCE {
   vRouteCustomerIdentifier
      Unsigned32 }

vRouteCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { vRouteCidDataEntry 1 }

vRouteIfEntryTable OBJECT-TYPE
   SYNTAX     SEQUENCE OF VRouteIfEntryEntry
   ACCESS     not-accessible
   STATUS     mandatory
   DESCRIPTION
     "This group contains the provisionable attributes for the ifEntry."
::= { vRoute 12 }

vRouteIfEntryEntry OBJECT-TYPE
   SYNTAX     VRouteIfEntryEntry
   ACCESS     not-accessible
   STATUS     mandatory
   DESCRIPTION
     "An entry in the vRouteIfEntryTable."
   INDEX {
      vRouteIndex }
::= { vRouteIfEntryTable 1 }

VRouteIfEntryEntry ::= SEQUENCE {
   vRouteIfAdminStatus
      INTEGER,
   vRouteIfIndex
      InterfaceIndex }

vRouteIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { vRouteIfEntryEntry 1 }

vRouteIfIndex OBJECT-TYPE
   SYNTAX     InterfaceIndex (1..65535)
   ACCESS     read-only
   STATUS     mandatory
   DESCRIPTION
     "This is the index for the IfEntry. Its value is automatically initialized 
      during the provisioning process."
::= { vRouteIfEntryEntry 2 }

vRouteStateTable OBJECT-TYPE
   SYNTAX     SEQUENCE OF VRouteStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { vRoute 13 }

vRouteStateEntry OBJECT-TYPE
   SYNTAX     VRouteStateEntry
   ACCESS     not-accessible
   STATUS     mandatory
   DESCRIPTION
     "An entry in the vRouteStateTable."
   INDEX {
      vRouteIndex }
::= { vRouteStateTable 1 }

VRouteStateEntry ::= SEQUENCE {
   vRouteAdminState
      INTEGER,
   vRouteOperationalState
      INTEGER,
   vRouteUsageState
      INTEGER }

vRouteAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { vRouteStateEntry 1 }

vRouteOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { vRouteStateEntry 2 }

vRouteUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { vRouteStateEntry 3 }

vRouteOperStatusTable OBJECT-TYPE
   SYNTAX     SEQUENCE OF VRouteOperStatusEntry
   ACCESS     not-accessible
   STATUS     mandatory
   DESCRIPTION
     "This group includes the Operational Status attribute. This attribute 
      defines the current operational state of this component."
::= { vRoute 14 }

vRouteOperStatusEntry OBJECT-TYPE
   SYNTAX     VRouteOperStatusEntry
   ACCESS     not-accessible
   STATUS     mandatory
   DESCRIPTION
     "An entry in the vRouteOperStatusTable."
   INDEX {
      vRouteIndex }
::= { vRouteOperStatusTable 1 }

VRouteOperStatusEntry ::= SEQUENCE {
   vRouteSnmpOperStatus
      INTEGER }

vRouteSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { vRouteOperStatusEntry 1 }

vRouteStatsTable OBJECT-TYPE
   SYNTAX     SEQUENCE OF VRouteStatsEntry
   ACCESS     not-accessible
   STATUS     mandatory
   DESCRIPTION
     "This group provides the operational attributes for the VoiceRoute 
      component. It contains information relating to calls that originate 
      from the network."
::= { vRoute 15 }

vRouteStatsEntry OBJECT-TYPE
   SYNTAX     VRouteStatsEntry
   ACCESS     not-accessible
   STATUS     mandatory
   DESCRIPTION
     "An entry in the vRouteStatsTable."
   INDEX {
      vRouteIndex }
::= { vRouteStatsTable 1 }

VRouteStatsEntry ::= SEQUENCE {
   vRouteTotalCallsFromSubnet
      Counter32,
   vRouteCallsClearedNoChannel
      Counter32,
   vRouteCallsClearedOutOfService
      Counter32,
   vRouteCallsRejected
      Counter32 }

vRouteTotalCallsFromSubnet OBJECT-TYPE
   SYNTAX     Counter32 
   ACCESS     read-only
   STATUS     mandatory
   DESCRIPTION
     "This attribute counts the total number of calls that have been 
      received from the Passport subnet, including calls that fail.
      The value wraps to zero when it reaches its maximum."
::= { vRouteStatsEntry 1 }

vRouteCallsClearedNoChannel OBJECT-TYPE
   SYNTAX     Counter32 
   ACCESS     read-only
   STATUS     mandatory
   DESCRIPTION
     "This attribute counts the total number of calls from the subnet that 
      were rejected when all of the in-service channels were busy. When a 
      call is rejected for this reason, the cause code sent to the originator 
      is 34, no circuit/channel available.
      The value wraps to zero when it reaches its maximum."
::= { vRouteStatsEntry 2 }

vRouteCallsClearedOutOfService OBJECT-TYPE
   SYNTAX     Counter32 
   ACCESS     read-only
   STATUS     mandatory
   DESCRIPTION
     "This attribute counts the total number of calls from the subnet that 
      were rejected because all of the channels were out-of-service. A 
      channel is considered out-of-service if it is unavailable for any 
      reason other than it is being engaged in handling a call. That is, an 
      operator lock of any of the components required for the channel's 
      operation, or problems which interfere with the connection to the 
      PBX, will cause the channel to be considered out-of-service. When 
      a call is rejected for this reason, the cause code sent back to the 
      originator is 27, destination out-of-service.
      The value wraps to zero when it reaches its maximum."
::= { vRouteStatsEntry 3 }

vRouteCallsRejected OBJECT-TYPE
   SYNTAX     Counter32 
   ACCESS     read-only
   STATUS     mandatory
   DESCRIPTION
     "This attribute counts the total number of calls from the subnet that 
      were rejected because they were: 
      1) voice calls to a typeOfRoute which is set to data,
      2) data calls to a typeOfRoute which is set to voice,
      3) using a signalling protocol which is incompatible with this end.
      The value wraps to zero when it reaches its maximum."
::= { vRouteStatsEntry 4 }

vRouteSubroutesTable OBJECT-TYPE
   SYNTAX     SEQUENCE OF VRouteSubroutesEntry
   ACCESS     not-accessible
   STATUS     mandatory
   DESCRIPTION
     "This attribute specifies all of the VoiceSubroutes which are 
      associated with this VoiceRoute. There are only 4 VoiceSubroutes 
      allowed per VoiceRoute."
::= { vRoute 309 }

vRouteSubroutesEntry OBJECT-TYPE
   SYNTAX     VRouteSubroutesEntry
   ACCESS     not-accessible
   STATUS     mandatory
   DESCRIPTION
     "An entry in the vRouteSubroutesTable."
   INDEX {
      vRouteIndex,
      vRouteSubroutesValue }
::= { vRouteSubroutesTable 1 }

VRouteSubroutesEntry ::= SEQUENCE {
   vRouteSubroutesValue
      Link,
   vRouteSubroutesRowStatus
      RowStatus }

vRouteSubroutesValue OBJECT-TYPE
   SYNTAX     Link 
   ACCESS     read-write
   STATUS     mandatory
   DESCRIPTION
     "This variable represents both the value and the index for the
      vRouteSubroutesTable."
::= { vRouteSubroutesEntry 1 }

vRouteSubroutesRowStatus OBJECT-TYPE
   SYNTAX     RowStatus 
   ACCESS     write-only
   STATUS     mandatory
   DESCRIPTION
     "This variable is used to control the addition and deletion 
      of individual values of the vRouteSubroutesTable."
::= { vRouteSubroutesEntry 2 }

vRouteDegradedSubroutesTable OBJECT-TYPE
   SYNTAX     SEQUENCE OF VRouteDegradedSubroutesEntry
   ACCESS     not-accessible
   STATUS     mandatory
   DESCRIPTION
     "This attribute indicates all of the VoiceSubroutes that have at least 
      one SwitchedVoiceService whose operationalState is disabled."
::= { vRoute 310 }

vRouteDegradedSubroutesEntry OBJECT-TYPE
   SYNTAX     VRouteDegradedSubroutesEntry
   ACCESS     not-accessible
   STATUS     mandatory
   DESCRIPTION
     "An entry in the vRouteDegradedSubroutesTable."
   INDEX {
      vRouteIndex,
      vRouteDegradedSubroutesValue }
::= { vRouteDegradedSubroutesTable 1 }

VRouteDegradedSubroutesEntry ::= SEQUENCE {
   vRouteDegradedSubroutesValue
      RowPointer }

vRouteDegradedSubroutesValue OBJECT-TYPE
   SYNTAX     RowPointer 
   ACCESS     read-only
   STATUS     mandatory
   DESCRIPTION
     "This variable represents both the value and the index for the
      vRouteDegradedSubroutesTable."
::= { vRouteDegradedSubroutesEntry 1 }


-- VRoute/n Debug		
-- The Debug component defines the debug operational characteristics 
-- of the VoiceRoute component.

vRouteDebug OBJECT IDENTIFIER ::= { vRoute 2 }



vRouteDebugRowStatusTable OBJECT-TYPE
   SYNTAX     SEQUENCE OF VRouteDebugRowStatusEntry
   ACCESS     not-accessible
   STATUS     mandatory
   DESCRIPTION
     "This entry controls the addition and deletion of 
      vRouteDebug components."
::= { vRouteDebug 1 }

vRouteDebugRowStatusEntry OBJECT-TYPE
   SYNTAX     VRouteDebugRowStatusEntry
   ACCESS     not-accessible
   STATUS     mandatory
   DESCRIPTION
     "A single entry in the table represents a single 
      vRouteDebug component."
   INDEX {
      vRouteIndex,
      vRouteDebugIndex }
::= { vRouteDebugRowStatusTable 1 }

VRouteDebugRowStatusEntry ::= SEQUENCE {
   vRouteDebugRowStatus
      RowStatus,
   vRouteDebugComponentName
      DisplayString,
   vRouteDebugStorageType
      StorageType,
   vRouteDebugIndex
      NonReplicated }

vRouteDebugRowStatus OBJECT-TYPE
   SYNTAX     RowStatus 
   ACCESS     read-only
   STATUS     mandatory
   DESCRIPTION
     "This variable is used as the basis for SNMP naming of
      vRouteDebug components.
      These components cannot be added nor deleted."
::= { vRouteDebugRowStatusEntry 1 }

vRouteDebugComponentName OBJECT-TYPE
   SYNTAX     DisplayString 
   ACCESS     read-only
   STATUS     mandatory
   DESCRIPTION
     "This variable provides the component's string name for
      use with the ASCII Console Interface"
::= { vRouteDebugRowStatusEntry 2 }

vRouteDebugStorageType OBJECT-TYPE
   SYNTAX     StorageType 
   ACCESS     read-only
   STATUS     mandatory
   DESCRIPTION
     "This variable represents the storage type value for the
      vRouteDebug tables."
::= { vRouteDebugRowStatusEntry 4 }

vRouteDebugIndex OBJECT-TYPE
   SYNTAX     NonReplicated 
   ACCESS     not-accessible
   STATUS     mandatory
   DESCRIPTION
     "This variable represents the index for the vRouteDebug tables."
::= { vRouteDebugRowStatusEntry 10 }


-- VoiceRoute/n Interface
-- This component defines the interface between a voice route and a 
-- PBX.

vRouteInterface OBJECT IDENTIFIER ::= { vRoute 3 }



vRouteInterfaceRowStatusTable OBJECT-TYPE
   SYNTAX     SEQUENCE OF VRouteInterfaceRowStatusEntry
   ACCESS     not-accessible
   STATUS     mandatory
   DESCRIPTION
     "This entry controls the addition and deletion of 
      vRouteInterface components."
::= { vRouteInterface 1 }

vRouteInterfaceRowStatusEntry OBJECT-TYPE
   SYNTAX     VRouteInterfaceRowStatusEntry
   ACCESS     not-accessible
   STATUS     mandatory
   DESCRIPTION
     "A single entry in the table represents a single 
      vRouteInterface component."
   INDEX {
      vRouteIndex,
      vRouteInterfaceIndex }
::= { vRouteInterfaceRowStatusTable 1 }

VRouteInterfaceRowStatusEntry ::= SEQUENCE {
   vRouteInterfaceRowStatus
      RowStatus,
   vRouteInterfaceComponentName
      DisplayString,
   vRouteInterfaceStorageType
      StorageType,
   vRouteInterfaceIndex
      NonReplicated }

vRouteInterfaceRowStatus OBJECT-TYPE
   SYNTAX     RowStatus 
   ACCESS     read-only
   STATUS     mandatory
   DESCRIPTION
     "This variable is used as the basis for SNMP naming of
      vRouteInterface components.
      These components cannot be added nor deleted."
::= { vRouteInterfaceRowStatusEntry 1 }

vRouteInterfaceComponentName OBJECT-TYPE
   SYNTAX     DisplayString 
   ACCESS     read-only
   STATUS     mandatory
   DESCRIPTION
     "This variable provides the component's string name for
      use with the ASCII Console Interface"
::= { vRouteInterfaceRowStatusEntry 2 }

vRouteInterfaceStorageType OBJECT-TYPE
   SYNTAX     StorageType 
   ACCESS     read-only
   STATUS     mandatory
   DESCRIPTION
     "This variable represents the storage type value for the
      vRouteInterface tables."
::= { vRouteInterfaceRowStatusEntry 4 }

vRouteInterfaceIndex OBJECT-TYPE
   SYNTAX     NonReplicated 
   ACCESS     not-accessible
   STATUS     mandatory
   DESCRIPTION
     "This variable represents the index for the vRouteInterface tables."
::= { vRouteInterfaceRowStatusEntry 10 }

vRouteInterfaceProvTable OBJECT-TYPE
   SYNTAX     SEQUENCE OF VRouteInterfaceProvEntry
   ACCESS     not-accessible
   STATUS     mandatory
   DESCRIPTION
     "This group contains attributes specifying the interface to a PBX."
::= { vRouteInterface 10 }

vRouteInterfaceProvEntry OBJECT-TYPE
   SYNTAX     VRouteInterfaceProvEntry
   ACCESS     not-accessible
   STATUS     mandatory
   DESCRIPTION
     "An entry in the vRouteInterfaceProvTable."
   INDEX {
      vRouteIndex,
      vRouteInterfaceIndex }
::= { vRouteInterfaceProvTable 1 }

VRouteInterfaceProvEntry ::= SEQUENCE {
   vRouteInterfaceIngressAudioGain
      INTEGER,
   vRouteInterfaceEgressAudioGain
      INTEGER,
   vRouteInterfaceTandemPassThrough
      INTEGER,
   vRouteInterfaceEchoCancellation
      INTEGER,
   vRouteInterfaceComfortNoiseCap
      INTEGER,
   vRouteInterfaceSpeechHangoverTime
      Unsigned32,
   vRouteInterfaceFaxHangoverTimeG711G726
      Unsigned32,
   vRouteInterfaceModemFaxSpeechDiscrim
      INTEGER,
   vRouteInterfaceEchoTailDelay
      Unsigned32,
   vRouteInterfaceEchoReturnLoss
      Unsigned32,
   vRouteInterfaceEcanBypassMode
      INTEGER }

vRouteInterfaceIngressAudioGain OBJECT-TYPE
   SYNTAX     INTEGER (-12..12)
   ACCESS     read-write
   STATUS     mandatory
   DESCRIPTION
     "This attribute specifies the gain in dB that is applied to data coming 
      from outside the network before it is transferred across the network. 
      It applies to voice, modem and fax traffic. For example, ingress gain 
      is applied to audio data coming from a PBX. If ingressAudioGain is 
      negative, a loss is applied.
      
      ingressAudioGain and egressAudioGain are used in loss planning, 
      which is the configuration of the devices in a network to ensure that 
      the signal level from any point in the network to any other point is 
      correct.
      
      ingressAudioGain is ignored for calls on 1pDS1V and 1pE1V cards."
   DEFVAL     { 0 }
::= { vRouteInterfaceProvEntry 1 }

vRouteInterfaceEgressAudioGain OBJECT-TYPE
   SYNTAX     INTEGER (-12..12)
   ACCESS     read-write
   STATUS     mandatory
   DESCRIPTION
     "This attribute specifies the gain in dB that is applied to data leaving 
      the network. It applies to voice, modem and fax traffic. For 
      example, egress gain is applied to audio data going to a PBX. If 
      egressAudioGain is negative, a loss is applied.
      
      ingressAudioGain and egressAudioGain are used in loss planning, 
      which is the configuration of the devices in the network to ensure 
      that the signal level from any point in the network to any other point 
      is correct."
   DEFVAL     { 0 }
::= { vRouteInterfaceProvEntry 2 }

vRouteInterfaceTandemPassThrough OBJECT-TYPE
   SYNTAX     INTEGER  {
                 disabled(0),
                 enabled(1) }
   ACCESS     read-write
   STATUS     mandatory
   DESCRIPTION
     "This attribute specifies whether tandem pass through is desired. If 
      tandemPassThrough is enabled, tandem pass through is used if 
      possible. If tandemPassThrough is disabled, tandem pass through is 
      not used under any circumstances. The actual state of tandem pass 
      through is indicated in Vsr Svs Framer tptStatus.
      
      The negotiated tandem pass through is available in Vsr Svs Framer 
      negotiatedTandemPassThrough.
      
      Tandem pass through is not supported on 1pDS1V and 1pE1V 
      cards, so tandemPassThrough is ignored on these cards."
   DEFVAL     { disabled }
::= { vRouteInterfaceProvEntry 3 }

vRouteInterfaceEchoCancellation OBJECT-TYPE
   SYNTAX     INTEGER  {
                 off(0),
                 on(1) }
   ACCESS     read-write
   STATUS     obsolete
   DESCRIPTION
     "This attribute has been migrated to echoCancellation."
   DEFVAL     { on }
::= { vRouteInterfaceProvEntry 5 }

vRouteInterfaceComfortNoiseCap OBJECT-TYPE
   SYNTAX     INTEGER (-78 | -65 | -60 | -54 | -52 | -50 | -48 | -46 | -44 | -42 | -40)
   ACCESS     read-write
   STATUS     mandatory
   DESCRIPTION
     "This attribute specifies the maximum level at which comfort noise is 
      generated. The comfort noise is limited by comfortNoiseCap before 
      egressAudioGain is applied. The default value of -40 dBm0 equates 
      to the maximum level of comfort noise available and effectively 
      disables the comfortNoiseCap."
   DEFVAL     { -40 }
::= { vRouteInterfaceProvEntry 6 }

vRouteInterfaceSpeechHangoverTime OBJECT-TYPE
   SYNTAX     Unsigned32 (10..500)
   ACCESS     read-write
   STATUS     mandatory
   DESCRIPTION
     "This attribute specifies the time after the end of speech before 
      silence suppression starts. It applies only to voice traffic. It is not 
      used unless Vsr Svs Framer negotiatedSilenceSuppression is on, 
      congested or slowAndCongested.
      
      Higher values of speechHangoverTime reduce undesirable clipping 
      but increase bandwidth usage.
      
      speechHangoverTime is not used on DS1V, E1V, 1pDS1V, 1pE1V 
      and J2MV cards."
   DEFVAL     { 150 }
::= { vRouteInterfaceProvEntry 7 }

vRouteInterfaceFaxHangoverTimeG711G726 OBJECT-TYPE
   SYNTAX     Unsigned32 (300..20000)
   ACCESS     read-write
   STATUS     mandatory
   DESCRIPTION
     "This attribute specifies the time after the end of fax traffic before 
      G.711/G.726 fax idle suppression starts. It applies only if the 
      negotiated fax encoding, available in Vsr Svs Framer 
      negotiatedEncoding, is g711, g726 or g711G726 and Vsr Svs 
      Framer negotiatedFisG711G726 is on.
      
      Higher values of faxHangoverTimeG711G726 reduce undesirable 
      clipping but increase bandwidth usage.
      
      faxHangoverTimeG711G726 is not used on DS1V, E1V, 1pDS1V, 
      1pE1V and J2MV cards."
   DEFVAL     { 1000 }
::= { vRouteInterfaceProvEntry 8 }

vRouteInterfaceModemFaxSpeechDiscrim OBJECT-TYPE
   SYNTAX     INTEGER  {
                 off(0),
                 on(1) }
   ACCESS     read-write
   STATUS     mandatory
   DESCRIPTION
     "This attribute specifies whether this VoiceRoute differentiates 
      between modemFax traffic and speech. If modemFaxSpeechDiscrim 
      is on and a false 2100 Hz tone is detected, any Svs using this route 
      reverts to speech mode when speech is detected.
      
      modemFaxSpeechDiscrim is not used on DS1V, E1V, 1pDS1V, 
      1pE1V and J2MV cards."
   DEFVAL     { on }
::= { vRouteInterfaceProvEntry 9 }

vRouteInterfaceEchoTailDelay OBJECT-TYPE
   SYNTAX     Unsigned32 (32 | 64)
   ACCESS     read-write
   STATUS     mandatory
   DESCRIPTION
     "This attribute specifies the maximum echo canceller tail delay 
      coverage. It should be selected higher than the summation of the 
      round trip delay of echo and hybrid response time. A 32 msec 
      setting is good for a radius of 2700 km, assuming that the signal is 
      going through 4 exchanges and the hybrid response time is 6 msec. 
      A 64 msec setting offers even greater coverage (more distance or 
      more switches), with comparable convergence time. The 
      recommended setting is 64 msec. This attribute is not used on 
      DS1V, E1V, 1pDS1V, 1pE1V, J2MV, 1pE1Mvp, 1pDS1Mvp, or 
      1pTTC2mMvp card."
   DEFVAL     { 64 }
::= { vRouteInterfaceProvEntry 10 }

vRouteInterfaceEchoReturnLoss OBJECT-TYPE
   SYNTAX     Unsigned32 (0 | 3 | 6)
   ACCESS     read-write
   STATUS     mandatory
   DESCRIPTION
     "This attribute specifies the echo return loss parameter of the echo 
      canceller. 0 db is the normal value for most line conditions. If the 
      line quality is poor, in terms of echo, selecting a higher value may 
      allow the echo canceller to perform better. A side effect is that the 
      voice level is attenuated by the same amount, which may not always 
      be acceptable. This attribute is not used on DS1V, E1V, 1pDS1V, 
      1pE1V, J2MV, 1pE1Mvp, 1pDS1Mvp, or 1pTTC2mMvp card."
   DEFVAL     { 0 }
::= { vRouteInterfaceProvEntry 11 }

vRouteInterfaceEcanBypassMode OBJECT-TYPE
   SYNTAX     INTEGER  {
                 g164(0),
                 g165(1),
                 never(2) }
   ACCESS     read-write
   STATUS     mandatory
   DESCRIPTION
     "This attribute specifies when version 2 internal echo cancellers are 
      placed in bypass mode on this VoiceRoute.  This attribute only 
      applies if v2 of echoCancellation is on. If ecanBypassMode is g165, 
      the internal echo canceller is placed in bypass mode as per ITU-T 
      G.165. If ecanBypassMode is g164, the internal echo canceller is 
      placed in bypass mode as per ITU-T G.164. If ecanBypassMode is 
      never, the internal echo canceller is never placed in bypass mode. 
      This mode should only be used for debugging.
      
      This attribute does not apply to 1pE1V, 1pDS1V, J2MV, 1pE1Mvp, 
      1pDS1Mvp or 1pTTC2mMvp cards."
   DEFVAL     { g165 }
::= { vRouteInterfaceProvEntry 15 }

vRouteInterfaceStructuredEchoCancellationTable OBJECT-TYPE
   SYNTAX     SEQUENCE OF VRouteInterfaceStructuredEchoCancellationEntry
   ACCESS     not-accessible
   STATUS     mandatory
   DESCRIPTION
     "This attribute specifies whether echo cancellation is performed on 
      this VoiceRoute. v1 specifies whether echo cancellation is 
      performed by version 1 internal echo cancellers. v2 specifes 
      whether echo cancellation is performed by version 2 echo 
      cancellers. If echoCancellation is on, the internal echo canceller is 
      enabled and echo cancellation is performed. If echoCancellation is 
      off, the internal echo canceller is placed in transparent bypass mode 
      and echo cancellation is never performed."
::= { vRouteInterface 472 }

vRouteInterfaceStructuredEchoCancellationEntry OBJECT-TYPE
   SYNTAX     VRouteInterfaceStructuredEchoCancellationEntry
   ACCESS     not-accessible
   STATUS     mandatory
   DESCRIPTION
     "An entry in the vRouteInterfaceStructuredEchoCancellationTable."
   INDEX {
      vRouteIndex,
      vRouteInterfaceIndex,
      vRouteInterfaceStructuredEchoCancellationIndex }
::= { vRouteInterfaceStructuredEchoCancellationTable 1 }

VRouteInterfaceStructuredEchoCancellationEntry ::= SEQUENCE {
   vRouteInterfaceStructuredEchoCancellationIndex
      INTEGER,
   vRouteInterfaceStructuredEchoCancellationValue
      INTEGER }

vRouteInterfaceStructuredEchoCancellationIndex OBJECT-TYPE
   SYNTAX     INTEGER  {
                 v1(0),
                 v2(1) }
   ACCESS     not-accessible
   STATUS     mandatory
   DESCRIPTION
     "This variable represents the vRouteInterfaceStructuredEchoCancellationTable
      specific index for the vRouteInterfaceStructuredEchoCancellationTable."
::= { vRouteInterfaceStructuredEchoCancellationEntry 1 }

vRouteInterfaceStructuredEchoCancellationValue OBJECT-TYPE
   SYNTAX     INTEGER  {
                 off(0),
                 on(1) }
   ACCESS     read-write
   STATUS     mandatory
   DESCRIPTION
     "This variable represents an individual value for the
      vRouteInterfaceStructuredEchoCancellationTable."
::= { vRouteInterfaceStructuredEchoCancellationEntry 2 }


-- vroute/n Dna
-- This is the description of the VRoute Dna component. It offers a 
-- subset of the generic Dna component attributes.

vRouteDna OBJECT IDENTIFIER ::= { vRoute 4 }



vRouteDnaRowStatusTable OBJECT-TYPE
   SYNTAX     SEQUENCE OF VRouteDnaRowStatusEntry
   ACCESS     not-accessible
   STATUS     mandatory
   DESCRIPTION
     "This entry controls the addition and deletion of 
      vRouteDna components."
::= { vRouteDna 1 }

vRouteDnaRowStatusEntry OBJECT-TYPE
   SYNTAX     VRouteDnaRowStatusEntry
   ACCESS     not-accessible
   STATUS     mandatory
   DESCRIPTION
     "A single entry in the table represents a single 
      vRouteDna component."
   INDEX {
      vRouteIndex,
      vRouteDnaIndex }
::= { vRouteDnaRowStatusTable 1 }

VRouteDnaRowStatusEntry ::= SEQUENCE {
   vRouteDnaRowStatus
      RowStatus,
   vRouteDnaComponentName
      DisplayString,
   vRouteDnaStorageType
      StorageType,
   vRouteDnaIndex
      NonReplicated }

vRouteDnaRowStatus OBJECT-TYPE
   SYNTAX     RowStatus 
   ACCESS     read-only
   STATUS     mandatory
   DESCRIPTION
     "This variable is used as the basis for SNMP naming of
      vRouteDna components.
      These components cannot be added nor deleted."
::= { vRouteDnaRowStatusEntry 1 }

vRouteDnaComponentName OBJECT-TYPE
   SYNTAX     DisplayString 
   ACCESS     read-only
   STATUS     mandatory
   DESCRIPTION
     "This variable provides the component's string name for
      use with the ASCII Console Interface"
::= { vRouteDnaRowStatusEntry 2 }

vRouteDnaStorageType OBJECT-TYPE
   SYNTAX     StorageType 
   ACCESS     read-only
   STATUS     mandatory
   DESCRIPTION
     "This variable represents the storage type value for the
      vRouteDna tables."
::= { vRouteDnaRowStatusEntry 4 }

vRouteDnaIndex OBJECT-TYPE
   SYNTAX     NonReplicated 
   ACCESS     not-accessible
   STATUS     mandatory
   DESCRIPTION
     "This variable represents the index for the vRouteDna tables."
::= { vRouteDnaRowStatusEntry 10 }

vRouteDnaAddressTable OBJECT-TYPE
   SYNTAX     SEQUENCE OF VRouteDnaAddressEntry
   ACCESS     not-accessible
   STATUS     mandatory
   DESCRIPTION
     "Address group contains attributes common to all Dna's. Every Dna 
      used in the network is defined with this group of 2 attributes. String 
      of address digits is complemented by type of address and Npi. 
      These attributes are used to interpret format of the address digits."
::= { vRouteDna 10 }

vRouteDnaAddressEntry OBJECT-TYPE
   SYNTAX     VRouteDnaAddressEntry
   ACCESS     not-accessible
   STATUS     mandatory
   DESCRIPTION
     "An entry in the vRouteDnaAddressTable."
   INDEX {
      vRouteIndex,
      vRouteDnaIndex }
::= { vRouteDnaAddressTable 1 }

VRouteDnaAddressEntry ::= SEQUENCE {
   vRouteDnaNumberingPlanIndicator
      INTEGER,
   vRouteDnaDataNetworkAddress
      DigitString }

vRouteDnaNumberingPlanIndicator OBJECT-TYPE
   SYNTAX     INTEGER  {
                 x121(0),
                 e164(1) }
   ACCESS     read-write
   STATUS     mandatory
   DESCRIPTION
     "This attribute indicates the Numbering Plan Indicator (NPI) of the 
      Dna that is entered. Address may belong to X.121 or E.164 plans. 
      X.121 is used in packet svitched data networks."
   DEFVAL     { e164 }
::= { vRouteDnaAddressEntry 1 }

vRouteDnaDataNetworkAddress OBJECT-TYPE
   SYNTAX     DigitString (SIZE (0..15))
   ACCESS     read-write
   STATUS     mandatory
   DESCRIPTION
     "Dna attribute contains digits which form unique identifier of the 
      customer interface. It can be compared (approximation only) to 
      telephone number where phone number identifies unique telephone 
      set. Dna digits are selected and assigned by network operators."
::= { vRouteDnaAddressEntry 2 }


-- Vroute/n Dna/n hgm
-- VnetHuntGroupMember is an optional component. It specifies the 
-- vroute/n as a member of a hunt group. Each hunt group member 
-- subscribes to at least one hunt group. The hunt group server's dna 
-- address should be added to the VnetHuntGroupAddress which is the 
-- sub-component of VnetHuntGroupMember. 

vRouteDnaHgm OBJECT IDENTIFIER ::= { vRouteDna 3 }



vRouteDnaHgmRowStatusTable OBJECT-TYPE
   SYNTAX     SEQUENCE OF VRouteDnaHgmRowStatusEntry
   ACCESS     not-accessible
   STATUS     mandatory
   DESCRIPTION
     "This entry controls the addition and deletion of 
      vRouteDnaHgm components."
::= { vRouteDnaHgm 1 }

vRouteDnaHgmRowStatusEntry OBJECT-TYPE
   SYNTAX     VRouteDnaHgmRowStatusEntry
   ACCESS     not-accessible
   STATUS     mandatory
   DESCRIPTION
     "A single entry in the table represents a single 
      vRouteDnaHgm component."
   INDEX {
      vRouteIndex,
      vRouteDnaIndex,
      vRouteDnaHgmIndex }
::= { vRouteDnaHgmRowStatusTable 1 }

VRouteDnaHgmRowStatusEntry ::= SEQUENCE {
   vRouteDnaHgmRowStatus
      RowStatus,
   vRouteDnaHgmComponentName
      DisplayString,
   vRouteDnaHgmStorageType
      StorageType,
   vRouteDnaHgmIndex
      NonReplicated }

vRouteDnaHgmRowStatus OBJECT-TYPE
   SYNTAX     RowStatus 
   ACCESS     read-write
   STATUS     mandatory
   DESCRIPTION
     "This variable is used as the basis for SNMP naming of
      vRouteDnaHgm components.
      These components can be added and deleted."
::= { vRouteDnaHgmRowStatusEntry 1 }

vRouteDnaHgmComponentName OBJECT-TYPE
   SYNTAX     DisplayString 
   ACCESS     read-only
   STATUS     mandatory
   DESCRIPTION
     "This variable provides the component's string name for
      use with the ASCII Console Interface"
::= { vRouteDnaHgmRowStatusEntry 2 }

vRouteDnaHgmStorageType OBJECT-TYPE
   SYNTAX     StorageType 
   ACCESS     read-only
   STATUS     mandatory
   DESCRIPTION
     "This variable represents the storage type value for the
      vRouteDnaHgm tables."
::= { vRouteDnaHgmRowStatusEntry 4 }

vRouteDnaHgmIndex OBJECT-TYPE
   SYNTAX     NonReplicated 
   ACCESS     not-accessible
   STATUS     mandatory
   DESCRIPTION
     "This variable represents the index for the vRouteDnaHgm tables."
::= { vRouteDnaHgmRowStatusEntry 10 }

vRouteDnaHgmIfTable OBJECT-TYPE
   SYNTAX     SEQUENCE OF VRouteDnaHgmIfEntry
   ACCESS     not-accessible
   STATUS     mandatory
   DESCRIPTION
     "This group contains the interface parameters between the 
      HuntGroupMember and the Hunt Group server."
::= { vRouteDnaHgm 10 }

vRouteDnaHgmIfEntry OBJECT-TYPE
   SYNTAX     VRouteDnaHgmIfEntry
   ACCESS     not-accessible
   STATUS     mandatory
   DESCRIPTION
     "An entry in the vRouteDnaHgmIfTable."
   INDEX {
      vRouteIndex,
      vRouteDnaIndex,
      vRouteDnaHgmIndex }
::= { vRouteDnaHgmIfTable 1 }

VRouteDnaHgmIfEntry ::= SEQUENCE {
   vRouteDnaHgmUsageDeltaUpdateThreshold
      Unsigned32 }

vRouteDnaHgmUsageDeltaUpdateThreshold OBJECT-TYPE
   SYNTAX     Unsigned32 (0..4096)
   ACCESS     read-write
   STATUS     mandatory
   DESCRIPTION
     "This attribute specifies by how much the availability of a hunt group 
      member must change before the member's availability is updated to 
      the hunt group server."
   DEFVAL     { 1 }
::= { vRouteDnaHgmIfEntry 1 }

vRouteDnaHgmOpTable OBJECT-TYPE
   SYNTAX     SEQUENCE OF VRouteDnaHgmOpEntry
   ACCESS     not-accessible
   STATUS     mandatory
   DESCRIPTION
     "This group contains the operational attributes of the 
      HuntGroupMember component."
::= { vRouteDnaHgm 11 }

vRouteDnaHgmOpEntry OBJECT-TYPE
   SYNTAX     VRouteDnaHgmOpEntry
   ACCESS     not-accessible
   STATUS     mandatory
   DESCRIPTION
     "An entry in the vRouteDnaHgmOpTable."
   INDEX {
      vRouteIndex,
      vRouteDnaIndex,
      vRouteDnaHgmIndex }
::= { vRouteDnaHgmOpTable 1 }

VRouteDnaHgmOpEntry ::= SEQUENCE {
   vRouteDnaHgmMaxAvailableChannels
      Unsigned32,
   vRouteDnaHgmAvailableChannels
      Unsigned32,
   vRouteDnaHgmAvailabilityDelta
      INTEGER }

vRouteDnaHgmMaxAvailableChannels OBJECT-TYPE
   SYNTAX     Unsigned32 (0..4096)
   ACCESS     read-only
   STATUS     mandatory
   DESCRIPTION
     "This attribute indicates the maximum number of available channels 
      for this HuntGroupMember."
::= { vRouteDnaHgmOpEntry 1 }

vRouteDnaHgmAvailableChannels OBJECT-TYPE
   SYNTAX     Unsigned32 (0..4096)
   ACCESS     read-only
   STATUS     mandatory
   DESCRIPTION
     "This attribute indicates the number of available channels reported to 
      the hunt group in the Availability Message Packet (AMP). It is 
      incremented by the application when a channel is freed and 
      decremented when a channel is active."
::= { vRouteDnaHgmOpEntry 2 }

vRouteDnaHgmAvailabilityDelta OBJECT-TYPE
   SYNTAX     INTEGER (-4096..4096)
   ACCESS     read-only
   STATUS     mandatory
   DESCRIPTION
     "This attribute specifies the delta between the actual availability of a 
      hunt group member and the hunt group member's 
      currentAvailability. Once the absolute value of this attribute reaches 
      the usageDeltaUpdateThreshold, the currentAvailability of the hunt 
      group member is then updated with the actual availability and the 
      availabilityDelta is reset to 0.
      If this attribute is positive the number of available channels has 
      increased since the last AMP was sent. If it is negative the number 
      of available channels has decreased since the last AMP was sent."
::= { vRouteDnaHgmOpEntry 3 }


-- Vroute/n Dna/n HgM HuntGroupAddress/n
-- This component specifies the Hunt Group address to which this 
-- member belongs. A hunt group member belongs to at least one hunt 
-- group.

vRouteDnaHgmHgAddr OBJECT IDENTIFIER ::= { vRouteDnaHgm 2 }



vRouteDnaHgmHgAddrRowStatusTable OBJECT-TYPE
   SYNTAX     SEQUENCE OF VRouteDnaHgmHgAddrRowStatusEntry
   ACCESS     not-accessible
   STATUS     mandatory
   DESCRIPTION
     "This entry controls the addition and deletion of 
      vRouteDnaHgmHgAddr components."
::= { vRouteDnaHgmHgAddr 1 }

vRouteDnaHgmHgAddrRowStatusEntry OBJECT-TYPE
   SYNTAX     VRouteDnaHgmHgAddrRowStatusEntry
   ACCESS     not-accessible
   STATUS     mandatory
   DESCRIPTION
     "A single entry in the table represents a single 
      vRouteDnaHgmHgAddr component."
   INDEX {
      vRouteIndex,
      vRouteDnaIndex,
      vRouteDnaHgmIndex,
      vRouteDnaHgmHgAddrIndex }
::= { vRouteDnaHgmHgAddrRowStatusTable 1 }

VRouteDnaHgmHgAddrRowStatusEntry ::= SEQUENCE {
   vRouteDnaHgmHgAddrRowStatus
      RowStatus,
   vRouteDnaHgmHgAddrComponentName
      DisplayString,
   vRouteDnaHgmHgAddrStorageType
      StorageType,
   vRouteDnaHgmHgAddrIndex
      Integer32 }

vRouteDnaHgmHgAddrRowStatus OBJECT-TYPE
   SYNTAX     RowStatus 
   ACCESS     read-write
   STATUS     mandatory
   DESCRIPTION
     "This variable is used as the basis for SNMP naming of
      vRouteDnaHgmHgAddr components.
      These components can be added and deleted."
::= { vRouteDnaHgmHgAddrRowStatusEntry 1 }

vRouteDnaHgmHgAddrComponentName OBJECT-TYPE
   SYNTAX     DisplayString 
   ACCESS     read-only
   STATUS     mandatory
   DESCRIPTION
     "This variable provides the component's string name for
      use with the ASCII Console Interface"
::= { vRouteDnaHgmHgAddrRowStatusEntry 2 }

vRouteDnaHgmHgAddrStorageType OBJECT-TYPE
   SYNTAX     StorageType 
   ACCESS     read-only
   STATUS     mandatory
   DESCRIPTION
     "This variable represents the storage type value for the
      vRouteDnaHgmHgAddr tables."
::= { vRouteDnaHgmHgAddrRowStatusEntry 4 }

vRouteDnaHgmHgAddrIndex OBJECT-TYPE
   SYNTAX     Integer32 (0..1)
   ACCESS     not-accessible
   STATUS     mandatory
   DESCRIPTION
     "This variable represents the index for the vRouteDnaHgmHgAddr tables."
::= { vRouteDnaHgmHgAddrRowStatusEntry 10 }

vRouteDnaHgmHgAddrAddrTable OBJECT-TYPE
   SYNTAX     SEQUENCE OF VRouteDnaHgmHgAddrAddrEntry
   ACCESS     not-accessible
   STATUS     mandatory
   DESCRIPTION
     "This group contains DNA attributes common to all DNAs."
::= { vRouteDnaHgmHgAddr 10 }

vRouteDnaHgmHgAddrAddrEntry OBJECT-TYPE
   SYNTAX     VRouteDnaHgmHgAddrAddrEntry
   ACCESS     not-accessible
   STATUS     mandatory
   DESCRIPTION
     "An entry in the vRouteDnaHgmHgAddrAddrTable."
   INDEX {
      vRouteIndex,
      vRouteDnaIndex,
      vRouteDnaHgmIndex,
      vRouteDnaHgmHgAddrIndex }
::= { vRouteDnaHgmHgAddrAddrTable 1 }

VRouteDnaHgmHgAddrAddrEntry ::= SEQUENCE {
   vRouteDnaHgmHgAddrNumberingPlanIndicator
      INTEGER,
   vRouteDnaHgmHgAddrDataNetworkAddress
      DigitString }

vRouteDnaHgmHgAddrNumberingPlanIndicator OBJECT-TYPE
   SYNTAX     INTEGER  {
                 x121(0),
                 e164(1) }
   ACCESS     read-write
   STATUS     mandatory
   DESCRIPTION
     "This attribute specifies the Numbering Plan Indicator (NPI) of the 
      Dna that is entered. The address may belong to the X.121 or E.164 
      numbering plans."
   DEFVAL     { x121 }
::= { vRouteDnaHgmHgAddrAddrEntry 1 }

vRouteDnaHgmHgAddrDataNetworkAddress OBJECT-TYPE
   SYNTAX     DigitString (SIZE (1..15))
   ACCESS     read-write
   STATUS     mandatory
   DESCRIPTION
     "This attribute specifies the digits that form the unique identifier of 
      the customer interface. It can be compared to a telephone number 
      where phone number identifies unique telephone set. Dna digits are 
      selected and assigned by network operators."
::= { vRouteDnaHgmHgAddrAddrEntry 2 }


-- Vroute/n VoiceAccounting
-- The VoiceAccounting component defines the operational 
-- characteristics of the accounting system of the Vroute component. 
-- Accounting record generation for calls on the Vroute is managed by 
-- this component.

vRouteAcct OBJECT IDENTIFIER ::= { vRoute 5 }



vRouteAcctRowStatusTable OBJECT-TYPE
   SYNTAX     SEQUENCE OF VRouteAcctRowStatusEntry
   ACCESS     not-accessible
   STATUS     mandatory
   DESCRIPTION
     "This entry controls the addition and deletion of 
      vRouteAcct components."
::= { vRouteAcct 1 }

vRouteAcctRowStatusEntry OBJECT-TYPE
   SYNTAX     VRouteAcctRowStatusEntry
   ACCESS     not-accessible
   STATUS     mandatory
   DESCRIPTION
     "A single entry in the table represents a single 
      vRouteAcct component."
   INDEX {
      vRouteIndex,
      vRouteAcctIndex }
::= { vRouteAcctRowStatusTable 1 }

VRouteAcctRowStatusEntry ::= SEQUENCE {
   vRouteAcctRowStatus
      RowStatus,
   vRouteAcctComponentName
      DisplayString,
   vRouteAcctStorageType
      StorageType,
   vRouteAcctIndex
      NonReplicated }

vRouteAcctRowStatus OBJECT-TYPE
   SYNTAX     RowStatus 
   ACCESS     read-only
   STATUS     mandatory
   DESCRIPTION
     "This variable is used as the basis for SNMP naming of
      vRouteAcct components.
      These components cannot be added nor deleted."
::= { vRouteAcctRowStatusEntry 1 }

vRouteAcctComponentName OBJECT-TYPE
   SYNTAX     DisplayString 
   ACCESS     read-only
   STATUS     mandatory
   DESCRIPTION
     "This variable provides the component's string name for
      use with the ASCII Console Interface"
::= { vRouteAcctRowStatusEntry 2 }

vRouteAcctStorageType OBJECT-TYPE
   SYNTAX     StorageType 
   ACCESS     read-only
   STATUS     mandatory
   DESCRIPTION
     "This variable represents the storage type value for the
      vRouteAcct tables."
::= { vRouteAcctRowStatusEntry 4 }

vRouteAcctIndex OBJECT-TYPE
   SYNTAX     NonReplicated 
   ACCESS     not-accessible
   STATUS     mandatory
   DESCRIPTION
     "This variable represents the index for the vRouteAcct tables."
::= { vRouteAcctRowStatusEntry 10 }

vRouteAcctProvTable OBJECT-TYPE
   SYNTAX     SEQUENCE OF VRouteAcctProvEntry
   ACCESS     not-accessible
   STATUS     mandatory
   DESCRIPTION
     "This group contains the provisionable attributes of a 
      VoiceAccounting component."
::= { vRouteAcct 2 }

vRouteAcctProvEntry OBJECT-TYPE
   SYNTAX     VRouteAcctProvEntry
   ACCESS     not-accessible
   STATUS     mandatory
   DESCRIPTION
     "An entry in the vRouteAcctProvTable."
   INDEX {
      vRouteIndex,
      vRouteAcctIndex }
::= { vRouteAcctProvTable 1 }

VRouteAcctProvEntry ::= SEQUENCE {
   vRouteAcctAccountCollection
      OCTET STRING,
   vRouteAcctAccountClass
      Unsigned32,
   vRouteAcctServiceExchange
      Unsigned32,
   vRouteAcctDigitsSuppressed
      Unsigned32,
   vRouteAcctAccountingOptions
      OCTET STRING }

vRouteAcctAccountCollection OBJECT-TYPE
   SYNTAX     OCTET STRING (SIZE (1))
   ACCESS     read-write
   STATUS     mandatory
   DESCRIPTION
     "This attribute specifies that accounting records are to be collected 
      for the various reasons: bill, test, study, audit.  The last of the 
      parameters, force, specifies that accounting records are to be 
      collected irrespective of other collection reasons.  If none of these 
      reasons is set, then accounting will be suppressed.

      Description of bits:
      bill(0)
      test(1)
      study(2)
      audit(3)
      force(4)"
::= { vRouteAcctProvEntry 2 }

vRouteAcctAccountClass OBJECT-TYPE
   SYNTAX     Unsigned32 (0..255)
   ACCESS     read-write
   STATUS     mandatory
   DESCRIPTION
     "This attribute specifies the accounting class which is reserved for 
      network operations usage. Its value is returned in the accounting 
      record in the local and remote service type attributes. The use of 
      this attribute is decided by the network operator."
   DEFVAL     { 0 }
::= { vRouteAcctProvEntry 3 }

vRouteAcctServiceExchange OBJECT-TYPE
   SYNTAX     Unsigned32 (0..255)
   ACCESS     read-write
   STATUS     mandatory
   DESCRIPTION
     "This attribute specifies  a user defined value, Data Service 
      Exchange, as entered by the network operator and reported in the 
      accounting record."
   DEFVAL     { 0 }
::= { vRouteAcctProvEntry 4 }

vRouteAcctDigitsSuppressed OBJECT-TYPE
   SYNTAX     Unsigned32 (0..8)
   ACCESS     read-write
   STATUS     mandatory
   DESCRIPTION
     "This attribute specifies the number of trailing digits which will be 
      suppressed in the calledNumber in the accounting records. Each of 
      the specified number of trailing digits are replaced with an 'X'. 
      This option exists to satisfy privacy requirements in a number of 
      countries."
   DEFVAL     { 0 }
::= { vRouteAcctProvEntry 5 }

vRouteAcctAccountingOptions OBJECT-TYPE
   SYNTAX     OCTET STRING (SIZE (1))
   ACCESS     read-write
   STATUS     mandatory
   DESCRIPTION
     "This attribute specifies optional settings for the voice networking 
      accounting system. The options are:
      suppressTerminatingEndRecords - setting this option suppresses 
      the generation of accounting records at the destination node. This 
      reduces the volume of accounting data. This option has local 
      significance only. It only suppresses the generation of accounting 
      records for calls received by this node.

      Description of bits:
      notused0(0)
      suppressTerminatingEndRecords(1)"
::= { vRouteAcctProvEntry 6 }


-- VoiceSubroute/n		
-- A VoiceSubroute component defines the characteristics of the 
-- connection to a Private Branch Exchange (PBX). A VoiceSubroute 
-- is a collection of 64 kbit/s channels on the same physical DS1 or E1 
-- interface. Typically there is one VoiceSubroute per physical link. 

vsr OBJECT IDENTIFIER ::= { components 117 }



vsrRowStatusTable OBJECT-TYPE
   SYNTAX     SEQUENCE OF VsrRowStatusEntry
   ACCESS     not-accessible
   STATUS     mandatory
   DESCRIPTION
     "This entry controls the addition and deletion of 
      vsr components."
::= { vsr 1 }

vsrRowStatusEntry OBJECT-TYPE
   SYNTAX     VsrRowStatusEntry
   ACCESS     not-accessible
   STATUS     mandatory
   DESCRIPTION
     "A single entry in the table represents a single 
      vsr component."
   INDEX {
      vsrIndex }
::= { vsrRowStatusTable 1 }

VsrRowStatusEntry ::= SEQUENCE {
   vsrRowStatus
      RowStatus,
   vsrComponentName
      DisplayString,
   vsrStorageType
      StorageType,
   vsrIndex
      Integer32 }

vsrRowStatus OBJECT-TYPE
   SYNTAX     RowStatus 
   ACCESS     read-write
   STATUS     mandatory
   DESCRIPTION
     "This variable is used as the basis for SNMP naming of
      vsr components.
      These components can be added and deleted."
::= { vsrRowStatusEntry 1 }

vsrComponentName OBJECT-TYPE
   SYNTAX     DisplayString 
   ACCESS     read-only
   STATUS     mandatory
   DESCRIPTION
     "This variable provides the component's string name for
      use with the ASCII Console Interface"
::= { vsrRowStatusEntry 2 }

vsrStorageType OBJECT-TYPE
   SYNTAX     StorageType 
   ACCESS     read-only
   STATUS     mandatory
   DESCRIPTION
     "This variable represents the storage type value for the
      vsr tables."
::= { vsrRowStatusEntry 4 }

vsrIndex OBJECT-TYPE
   SYNTAX     Integer32 (1..255)
   ACCESS     not-accessible
   STATUS     mandatory
   DESCRIPTION
     "This variable represents the index for the vsr tables."
::= { vsrRowStatusEntry 10 }

vsrCidDataTable OBJECT-TYPE
   SYNTAX     SEQUENCE OF VsrCidDataEntry
   ACCESS     not-accessible
   STATUS     mandatory
   DESCRIPTION
     "This group contains the attribute for a component's Customer 
      Identifier (CID). Refer to the attribute description for a detailed 
      explanation of CIDs."
::= { vsr 10 }

vsrCidDataEntry OBJECT-TYPE
   SYNTAX     VsrCidDataEntry
   ACCESS     not-accessible
   STATUS     mandatory
   DESCRIPTION
     "An entry in the vsrCidDataTable."
   INDEX {
      vsrIndex }
::= { vsrCidDataTable 1 }

VsrCidDataEntry ::= SEQUENCE {
   vsrCustomerIdentifier
      Unsigned32 }

vsrCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { vsrCidDataEntry 1 }

vsrIfEntryTable OBJECT-TYPE
   SYNTAX     SEQUENCE OF VsrIfEntryEntry
   ACCESS     not-accessible
   STATUS     mandatory
   DESCRIPTION
     "This group contains the provisionable attributes for the ifEntry."
::= { vsr 11 }

vsrIfEntryEntry OBJECT-TYPE
   SYNTAX     VsrIfEntryEntry
   ACCESS     not-accessible
   STATUS     mandatory
   DESCRIPTION
     "An entry in the vsrIfEntryTable."
   INDEX {
      vsrIndex }
::= { vsrIfEntryTable 1 }

VsrIfEntryEntry ::= SEQUENCE {
   vsrIfAdminStatus
      INTEGER,
   vsrIfIndex
      InterfaceIndex }

vsrIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { vsrIfEntryEntry 1 }

vsrIfIndex OBJECT-TYPE
   SYNTAX     InterfaceIndex (1..65535)
   ACCESS     read-only
   STATUS     mandatory
   DESCRIPTION
     "This is the index for the IfEntry. Its value is automatically initialized 
      during the provisioning process."
::= { vsrIfEntryEntry 2 }

vsrProvTable OBJECT-TYPE
   SYNTAX     SEQUENCE OF VsrProvEntry
   ACCESS     not-accessible
   STATUS     mandatory
   DESCRIPTION
     "This group represents the provisionable attributes of a 
      VoiceSubroute."
::= { vsr 12 }

vsrProvEntry OBJECT-TYPE
   SYNTAX     VsrProvEntry
   ACCESS     not-accessible
   STATUS     mandatory
   DESCRIPTION
     "An entry in the vsrProvTable."
   INDEX {
      vsrIndex }
::= { vsrProvTable 1 }

VsrProvEntry ::= SEQUENCE {
   vsrCommentText
      AsciiString,
   vsrVoiceRoute
      Link,
   vsrSignallingChannel
      Link }

vsrCommentText OBJECT-TYPE
   SYNTAX     AsciiString (SIZE (0..40))
   ACCESS     read-write
   STATUS     mandatory
   DESCRIPTION
     "Use of this attribute is at the discretion of the system administrator. 
      Typically, it specifies the name of the customer that is using this 
      VoiceSubroute. Typical use of this attribute is to store customer 
      name."
::= { vsrProvEntry 1 }

vsrVoiceRoute OBJECT-TYPE
   SYNTAX     Link 
   ACCESS     read-write
   STATUS     mandatory
   DESCRIPTION
     "This attribute specifies the VoiceRoute component that this 
      VoiceSubroute belongs to."
::= { vsrProvEntry 3 }

vsrSignallingChannel OBJECT-TYPE
   SYNTAX     Link 
   ACCESS     read-write
   STATUS     mandatory
   DESCRIPTION
     "This attribute specifies the signalling channel to be used by the 
      VoiceSubroute."
::= { vsrProvEntry 311 }

vsrStateTable OBJECT-TYPE
   SYNTAX     SEQUENCE OF VsrStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { vsr 13 }

vsrStateEntry OBJECT-TYPE
   SYNTAX     VsrStateEntry
   ACCESS     not-accessible
   STATUS     mandatory
   DESCRIPTION
     "An entry in the vsrStateTable."
   INDEX {
      vsrIndex }
::= { vsrStateTable 1 }

VsrStateEntry ::= SEQUENCE {
   vsrAdminState
      INTEGER,
   vsrOperationalState
      INTEGER,
   vsrUsageState
      INTEGER }

vsrAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { vsrStateEntry 1 }

vsrOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { vsrStateEntry 2 }

vsrUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { vsrStateEntry 3 }

vsrOperStatusTable OBJECT-TYPE
   SYNTAX     SEQUENCE OF VsrOperStatusEntry
   ACCESS     not-accessible
   STATUS     mandatory
   DESCRIPTION
     "This group includes the Operational Status attribute. This attribute 
      defines the current operational state of this component."
::= { vsr 14 }

vsrOperStatusEntry OBJECT-TYPE
   SYNTAX     VsrOperStatusEntry
   ACCESS     not-accessible
   STATUS     mandatory
   DESCRIPTION
     "An entry in the vsrOperStatusTable."
   INDEX {
      vsrIndex }
::= { vsrOperStatusTable 1 }

VsrOperStatusEntry ::= SEQUENCE {
   vsrSnmpOperStatus
      INTEGER }

vsrSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { vsrOperStatusEntry 1 }

vsrStatsTable OBJECT-TYPE
   SYNTAX     SEQUENCE OF VsrStatsEntry
   ACCESS     not-accessible
   STATUS     mandatory
   DESCRIPTION
     "This group provides the operational statistics for the VoiceSubroute 
      component."
::= { vsr 15 }

vsrStatsEntry OBJECT-TYPE
   SYNTAX     VsrStatsEntry
   ACCESS     not-accessible
   STATUS     mandatory
   DESCRIPTION
     "An entry in the vsrStatsTable."
   INDEX {
      vsrIndex }
::= { vsrStatsTable 1 }

VsrStatsEntry ::= SEQUENCE {
   vsrTotalCallsFromIf
      Counter32,
   vsrTotalFailedCallsFromIf
      Counter32,
   vsrInvalidNumberingPlanCalls
      Counter32,
   vsrAddressResolutionFailedCalls
      Counter32,
   vsrAddressIncompleteCalls
      Counter32,
   vsrPathAttributesNotMetCalls
      Counter32,
   vsrPathSetupTimeOutCalls
      Counter32,
   vsrCallsRejectedLocally
      Counter32,
   vsrCallsRejectedByFarEnd
      Counter32 }

vsrTotalCallsFromIf OBJECT-TYPE
   SYNTAX     Counter32 
   ACCESS     read-only
   STATUS     mandatory
   DESCRIPTION
     "This attribute indicates the total number of calls that have been 
      received by this VoiceSubroute from the PBX.
      The value wraps to zero when it reaches its maximum."
::= { vsrStatsEntry 1 }

vsrTotalFailedCallsFromIf OBJECT-TYPE
   SYNTAX     Counter32 
   ACCESS     read-only
   STATUS     mandatory
   DESCRIPTION
     "This attribute counts indicates the total number of calls that have 
      been received by this VoiceSubroute from the PBX which failed to 
      be successfully routed through the subnet for various reasons.
      The value wraps to zero when it reaches its maximum."
::= { vsrStatsEntry 2 }

vsrInvalidNumberingPlanCalls OBJECT-TYPE
   SYNTAX     Counter32 
   ACCESS     read-only
   STATUS     mandatory
   DESCRIPTION
     "This attribute counts the calls from the interface for which the type 
      of number and the numbering plan identification was not associated 
      to an access code. The numbering plan types noAccessCode, 
      accessCode1 and accessCode2 are provisioned in the VoiceRoute. 
      Refer to NTP-241-7001-xxx for more information.
      The value wraps to zero when it reaches its maximum."
::= { vsrStatsEntry 3 }

vsrAddressResolutionFailedCalls OBJECT-TYPE
   SYNTAX     Counter32 
   ACCESS     read-only
   STATUS     mandatory
   DESCRIPTION
     "This attribute counts the calls from the interface which had dialled 
      numbers that had no entry in the VoiceNetworkingCallServer data 
      base.
      The value wraps to zero when it reaches its maximum."
::= { vsrStatsEntry 4 }

vsrAddressIncompleteCalls OBJECT-TYPE
   SYNTAX     Counter32 
   ACCESS     read-only
   STATUS     mandatory
   DESCRIPTION
     "This attribute counts the calls from the interface which had dialled 
      numbers with insufficient digits to resolve to a unique entry in the 
      VoiceNetworkingCallServer data base.
      The value wraps to zero when it reaches its maximum."
::= { vsrStatsEntry 5 }

vsrPathAttributesNotMetCalls OBJECT-TYPE
   SYNTAX     Counter32 
   ACCESS     read-only
   STATUS     mandatory
   DESCRIPTION
     "This attribute counts the calls from the interface for which a path to 
      the end point could not be established based on the attributes 
      specified in the VoiceProfile.
      The value wraps to zero when it reaches its maximum."
::= { vsrStatsEntry 6 }

vsrPathSetupTimeOutCalls OBJECT-TYPE
   SYNTAX     Counter32 
   ACCESS     read-only
   STATUS     mandatory
   DESCRIPTION
     "This attribute counts the calls from the interface for which a path to 
      the end point could not be established due to a subnet path setup 
      time-out.
      The value wraps to zero when it reaches its maximum."
::= { vsrStatsEntry 7 }

vsrCallsRejectedLocally OBJECT-TYPE
   SYNTAX     Counter32 
   ACCESS     read-only
   STATUS     mandatory
   DESCRIPTION
     "This attribute counts the calls from the interface which were 
      rejected by the originating end because it was:
      1) a data call on a voice only VoiceRoute, or
      2) a voice call on a data only VoiceRoute, or 
      3) a data call to an end-point whose VoiceProfile prevents data calls 
      from being made.
      The value wraps to zero when it reaches its maximum."
::= { vsrStatsEntry 8 }

vsrCallsRejectedByFarEnd OBJECT-TYPE
   SYNTAX     Counter32 
   ACCESS     read-only
   STATUS     mandatory
   DESCRIPTION
     "This attribute counts the calls from the interface which were 
      rejected by the far-end. This rejection could be due to:
      1) no free channels at the end-point, or 
      2) a voice call going to a data only VoiceRoute, or 
      3) a data call going to a voice only VoiceRoute, or 
      4) a signalling protocol incompatibility between end-points.
      The value wraps to zero when it reaches its maximum."
::= { vsrStatsEntry 9 }

vsrOperTable OBJECT-TYPE
   SYNTAX     SEQUENCE OF VsrOperEntry
   ACCESS     not-accessible
   STATUS     mandatory
   DESCRIPTION
     "This group provides the operational attributes for the VoiceSubroute 
      component."
::= { vsr 16 }

vsrOperEntry OBJECT-TYPE
   SYNTAX     VsrOperEntry
   ACCESS     not-accessible
   STATUS     mandatory
   DESCRIPTION
     "An entry in the vsrOperTable."
   INDEX {
      vsrIndex }
::= { vsrOperTable 1 }

VsrOperEntry ::= SEQUENCE {
   vsrActiveChannels
      Counter32,
   vsrPeakActiveChannels
      Counter32,
   vsrActiveVoiceChannels
      Counter32,
   vsrActiveModemChannels
      Counter32,
   vsrActiveDataChannels
      Counter32,
   vsrPeakActiveVoiceChannels
      Counter32,
   vsrPeakActiveModemChannels
      Counter32,
   vsrPeakActiveDataChannels
      Counter32,
   vsrActiveFaxRelayChannels
      Gauge32,
   vsrActiveTptChannels
      Gauge32,
   vsrPeakActiveFaxRelayChannels
      Gauge32,
   vsrPeakActiveTptChannels
      Gauge32 }

vsrActiveChannels OBJECT-TYPE
   SYNTAX     Counter32 
   ACCESS     read-only
   STATUS     mandatory
   DESCRIPTION
     "This attribute indicates the total number of B-channels that 
      currently have active calls."
::= { vsrOperEntry 2 }

vsrPeakActiveChannels OBJECT-TYPE
   SYNTAX     Counter32 
   ACCESS     read-only
   STATUS     mandatory
   DESCRIPTION
     "This attribute indicates the peak number of B-channels that were 
      active during the previous polling period."
::= { vsrOperEntry 3 }

vsrActiveVoiceChannels OBJECT-TYPE
   SYNTAX     Counter32 
   ACCESS     read-only
   STATUS     mandatory
   DESCRIPTION
     "This attribute indicates the number of B-channels that are currently 
      carrying voice."
::= { vsrOperEntry 4 }

vsrActiveModemChannels OBJECT-TYPE
   SYNTAX     Counter32 
   ACCESS     read-only
   STATUS     mandatory
   DESCRIPTION
     "This attribute indicates the number of B-channels that are currently 
      active, where a 2100Hz tone was detected."
::= { vsrOperEntry 5 }

vsrActiveDataChannels OBJECT-TYPE
   SYNTAX     Counter32 
   ACCESS     read-only
   STATUS     mandatory
   DESCRIPTION
     "This attribute indicates the number of B-channels that are currently 
      active carrying data."
::= { vsrOperEntry 6 }

vsrPeakActiveVoiceChannels OBJECT-TYPE
   SYNTAX     Counter32 
   ACCESS     read-only
   STATUS     mandatory
   DESCRIPTION
     "This attribute indicates the peak number of B-channels that were 
      active carrying voice during the previous polling period."
::= { vsrOperEntry 7 }

vsrPeakActiveModemChannels OBJECT-TYPE
   SYNTAX     Counter32 
   ACCESS     read-only
   STATUS     mandatory
   DESCRIPTION
     "This attribute indicates the peak number of active B-channels that a 
      2100Hz tone was detected during the previous polling period."
::= { vsrOperEntry 8 }

vsrPeakActiveDataChannels OBJECT-TYPE
   SYNTAX     Counter32 
   ACCESS     read-only
   STATUS     mandatory
   DESCRIPTION
     "This attribute indicates the maximum number of B-channels that 
      were active carrying data during the previous polling period."
::= { vsrOperEntry 9 }

vsrActiveFaxRelayChannels OBJECT-TYPE
   SYNTAX     Gauge32 (0..30)
   ACCESS     read-only
   STATUS     mandatory
   DESCRIPTION
     "This attribute indicates the number of B-channels that are currently 
      performing fax relay."
::= { vsrOperEntry 10 }

vsrActiveTptChannels OBJECT-TYPE
   SYNTAX     Gauge32 (0..32)
   ACCESS     read-only
   STATUS     mandatory
   DESCRIPTION
     "This attribute indicates the number of B-channels that are currently 
      performing tandem pass through."
::= { vsrOperEntry 11 }

vsrPeakActiveFaxRelayChannels OBJECT-TYPE
   SYNTAX     Gauge32 (0..30)
   ACCESS     read-only
   STATUS     mandatory
   DESCRIPTION
     "This attribute indicates the peak number of B-channels that 
      performed fax relay during the previous polling period."
::= { vsrOperEntry 12 }

vsrPeakActiveTptChannels OBJECT-TYPE
   SYNTAX     Gauge32 (0..30)
   ACCESS     read-only
   STATUS     mandatory
   DESCRIPTION
     "This attribute indicates the peak number of B-channels that 
      performed tandem pass through during the previous polling period."
::= { vsrOperEntry 13 }


-- Vsr/n SwitchedVoiceService/n		
-- The SwitchedVoiceService component defines the operational 
-- characteristics of the connection to a Private Branch Exchange 
-- (PBX). One instance of this component must be required for each 
-- channel (that is, timeslot) which is part of the VoiceSubroute.

vsrSvs OBJECT IDENTIFIER ::= { vsr 2 }



vsrSvsRowStatusTable OBJECT-TYPE
   SYNTAX     SEQUENCE OF VsrSvsRowStatusEntry
   ACCESS     not-accessible
   STATUS     mandatory
   DESCRIPTION
     "This entry controls the addition and deletion of 
      vsrSvs components."
::= { vsrSvs 1 }

vsrSvsRowStatusEntry OBJECT-TYPE
   SYNTAX     VsrSvsRowStatusEntry
   ACCESS     not-accessible
   STATUS     mandatory
   DESCRIPTION
     "A single entry in the table represents a single 
      vsrSvs component."
   INDEX {
      vsrIndex,
      vsrSvsIndex }
::= { vsrSvsRowStatusTable 1 }

VsrSvsRowStatusEntry ::= SEQUENCE {
   vsrSvsRowStatus
      RowStatus,
   vsrSvsComponentName
      DisplayString,
   vsrSvsStorageType
      StorageType,
   vsrSvsIndex
      Integer32 }

vsrSvsRowStatus OBJECT-TYPE
   SYNTAX     RowStatus 
   ACCESS     read-write
   STATUS     mandatory
   DESCRIPTION
     "This variable is used as the basis for SNMP naming of
      vsrSvs components.
      These components can be added and deleted."
::= { vsrSvsRowStatusEntry 1 }

vsrSvsComponentName OBJECT-TYPE
   SYNTAX     DisplayString 
   ACCESS     read-only
   STATUS     mandatory
   DESCRIPTION
     "This variable provides the component's string name for
      use with the ASCII Console Interface"
::= { vsrSvsRowStatusEntry 2 }

vsrSvsStorageType OBJECT-TYPE
   SYNTAX     StorageType 
   ACCESS     read-only
   STATUS     mandatory
   DESCRIPTION
     "This variable represents the storage type value for the
      vsrSvs tables."
::= { vsrSvsRowStatusEntry 4 }

vsrSvsIndex OBJECT-TYPE
   SYNTAX     Integer32 (1..32)
   ACCESS     not-accessible
   STATUS     mandatory
   DESCRIPTION
     "This variable represents the index for the vsrSvs tables."
::= { vsrSvsRowStatusEntry 10 }

vsrSvsIfEntryTable OBJECT-TYPE
   SYNTAX     SEQUENCE OF VsrSvsIfEntryEntry
   ACCESS     not-accessible
   STATUS     mandatory
   DESCRIPTION
     "This group contains the provisionable attributes for the ifEntry."
::= { vsrSvs 11 }

vsrSvsIfEntryEntry OBJECT-TYPE
   SYNTAX     VsrSvsIfEntryEntry
   ACCESS     not-accessible
   STATUS     mandatory
   DESCRIPTION
     "An entry in the vsrSvsIfEntryTable."
   INDEX {
      vsrIndex,
      vsrSvsIndex }
::= { vsrSvsIfEntryTable 1 }

VsrSvsIfEntryEntry ::= SEQUENCE {
   vsrSvsIfAdminStatus
      INTEGER,
   vsrSvsIfIndex
      InterfaceIndex }

vsrSvsIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { vsrSvsIfEntryEntry 1 }

vsrSvsIfIndex OBJECT-TYPE
   SYNTAX     InterfaceIndex (1..65535)
   ACCESS     read-only
   STATUS     mandatory
   DESCRIPTION
     "This is the index for the IfEntry. Its value is automatically initialized 
      during the provisioning process."
::= { vsrSvsIfEntryEntry 2 }

vsrSvsOperTable OBJECT-TYPE
   SYNTAX     SEQUENCE OF VsrSvsOperEntry
   ACCESS     not-accessible
   STATUS     mandatory
   DESCRIPTION
     "This group provides the operational attributes for the 
      SwitchedVoiceService component."
::= { vsrSvs 12 }

vsrSvsOperEntry OBJECT-TYPE
   SYNTAX     VsrSvsOperEntry
   ACCESS     not-accessible
   STATUS     mandatory
   DESCRIPTION
     "An entry in the vsrSvsOperTable."
   INDEX {
      vsrIndex,
      vsrSvsIndex }
::= { vsrSvsOperTable 1 }

VsrSvsOperEntry ::= SEQUENCE {
   vsrSvsStatus
      INTEGER,
   vsrSvsProfileNumber
      Counter32,
   vsrSvsCallType
      INTEGER,
   vsrSvsCalledNumber
      DigitString,
   vsrSvsCallingNumber
      DigitString,
   vsrSvsClearCauseCode
      Hex }

vsrSvsStatus OBJECT-TYPE
   SYNTAX     INTEGER  {
                 idle(0),
                 seized(1),
                 answered(2),
                 clearing(3),
                 lockout(4),
                 idleMaintenance(5) }
   ACCESS     read-only
   STATUS     mandatory
   DESCRIPTION
     "This attribute indicates the current state of the channel. 
      idle means that there is no call currently active on this channel.
      seized means that the channel is currently setting up a call, but a 
      connect message has not been received.
      answered means that a connect message has been received.
      clearing means that the call is being taken down.
      lockout means that due to glare or channel rejection, the channel is 
      available for ingress calls only. That is, either the PBX and the 
      Passport tried to seize the channel for a call at the same time (glare), 
      or the PBX rejected the Passport seizure.
      idleMaintenance means that due to explicit channel maintenance 
      messages, the channel is not available for egress calls. This can only 
      happen when the protocol control places the channel into a 
      maintenance state, and only happens if the Passport receives a 
      message causing the channel state change such as the SERVICE 
      maintenance message."
::= { vsrSvsOperEntry 1 }

vsrSvsProfileNumber OBJECT-TYPE
   SYNTAX     Counter32 
   ACCESS     read-only
   STATUS     mandatory
   DESCRIPTION
     "This attribute indicates the VoiceProfile number that is being used 
      for this call. If no call is active, then it displays the value of the last 
      profile used."
::= { vsrSvsOperEntry 2 }

vsrSvsCallType OBJECT-TYPE
   SYNTAX     INTEGER  {
                 voice(0),
                 data(1),
                 modem(2) }
   ACCESS     read-only
   STATUS     mandatory
   DESCRIPTION
     "This attribute indicates the type of call that this channel is currently 
      carrying. If no call is active, then it displays the value for the last 
      call."
::= { vsrSvsOperEntry 3 }

vsrSvsCalledNumber OBJECT-TYPE
   SYNTAX     DigitString (SIZE (1..32))
   ACCESS     read-only
   STATUS     mandatory
   DESCRIPTION
     "This attribute indicates the dialled number that is active on this 
      channel. If no call is active, then it displays the dialled number from 
      the last call."
::= { vsrSvsOperEntry 4 }

vsrSvsCallingNumber OBJECT-TYPE
   SYNTAX     DigitString (SIZE (1..16))
   ACCESS     read-only
   STATUS     mandatory
   DESCRIPTION
     "This attribute indicates the originator's number for the currently 
      active call. If no call is active, then it displays the originator's 
      number from the last call."
::= { vsrSvsOperEntry 5 }

vsrSvsClearCauseCode OBJECT-TYPE
   SYNTAX     Hex (0..127)
   ACCESS     read-only
   STATUS     mandatory
   DESCRIPTION
     "This attribute indicates the clear cause code of the call. This code is 
      always the Q.931 code, regardless of the access protocol."
::= { vsrSvsOperEntry 6 }

vsrSvsStatsTable OBJECT-TYPE
   SYNTAX     SEQUENCE OF VsrSvsStatsEntry
   ACCESS     not-accessible
   STATUS     mandatory
   DESCRIPTION
     "This group provides the operational attributes for the 
      SwitchedVoiceService component."
::= { vsrSvs 13 }

vsrSvsStatsEntry OBJECT-TYPE
   SYNTAX     VsrSvsStatsEntry
   ACCESS     not-accessible
   STATUS     mandatory
   DESCRIPTION
     "An entry in the vsrSvsStatsTable."
   INDEX {
      vsrIndex,
      vsrSvsIndex }
::= { vsrSvsStatsTable 1 }

VsrSvsStatsEntry ::= SEQUENCE {
   vsrSvsTotalCalls
      Counter32,
   vsrSvsTotalCallSeconds
      Counter32 }

vsrSvsTotalCalls OBJECT-TYPE
   SYNTAX     Counter32 
   ACCESS     read-only
   STATUS     mandatory
   DESCRIPTION
     "This attribute counts the call attempts processed on this channel (in 
      both directions). This counter includes the number of unsuccessful 
      as well as successful call attempts.
      The value wraps when it reaches its maximum."
::= { vsrSvsStatsEntry 1 }

vsrSvsTotalCallSeconds OBJECT-TYPE
   SYNTAX     Counter32 
   ACCESS     read-only
   STATUS     mandatory
   DESCRIPTION
     "This attribute indicates the total number of seconds that this channel 
      is handling a call. This is regardless of whether the call is successful 
      or not. In other words, this is the amount of time that the channel is 
      not in the idle state.
      The value wraps when it reaches its maximum."
::= { vsrSvsStatsEntry 2 }

vsrSvsStateTable OBJECT-TYPE
   SYNTAX     SEQUENCE OF VsrSvsStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { vsrSvs 14 }

vsrSvsStateEntry OBJECT-TYPE
   SYNTAX     VsrSvsStateEntry
   ACCESS     not-accessible
   STATUS     mandatory
   DESCRIPTION
     "An entry in the vsrSvsStateTable."
   INDEX {
      vsrIndex,
      vsrSvsIndex }
::= { vsrSvsStateTable 1 }

VsrSvsStateEntry ::= SEQUENCE {
   vsrSvsAdminState
      INTEGER,
   vsrSvsOperationalState
      INTEGER,
   vsrSvsUsageState
      INTEGER }

vsrSvsAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { vsrSvsStateEntry 1 }

vsrSvsOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { vsrSvsStateEntry 2 }

vsrSvsUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { vsrSvsStateEntry 3 }

vsrSvsOperStatusTable OBJECT-TYPE
   SYNTAX     SEQUENCE OF VsrSvsOperStatusEntry
   ACCESS     not-accessible
   STATUS     mandatory
   DESCRIPTION
     "This group includes the Operational Status attribute. This attribute 
      defines the current operational state of this component."
::= { vsrSvs 15 }

vsrSvsOperStatusEntry OBJECT-TYPE
   SYNTAX     VsrSvsOperStatusEntry
   ACCESS     not-accessible
   STATUS     mandatory
   DESCRIPTION
     "An entry in the vsrSvsOperStatusTable."
   INDEX {
      vsrIndex,
      vsrSvsIndex }
::= { vsrSvsOperStatusTable 1 }

VsrSvsOperStatusEntry ::= SEQUENCE {
   vsrSvsSnmpOperStatus
      INTEGER }

vsrSvsSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { vsrSvsOperStatusEntry 1 }


-- Vsr/n Svs/n Framer
-- The Framer component controls link layer framing for application 
-- components sending and receiving data on a link interface. It is also 
-- through Framer, that an application component is associated with a 
-- specific hardware link interface.
-- The Framer component provides provisionable attributes related to 
-- datapath aspects of the hardware interface rather than interface 
-- specific attributes (such as modem leads and clocking) which are 
-- associated with specific hardware components (such as E1 or DS1).
-- The Framer component also provides a provisionable attribute 
-- which binds the application component to a specific hardware 
-- component.
-- The Framer component contains operational attributes for link 
-- interface datapath statistics (such as frame counts).

vsrSvsFramer OBJECT IDENTIFIER ::= { vsrSvs 2 }



vsrSvsFramerRowStatusTable OBJECT-TYPE
   SYNTAX     SEQUENCE OF VsrSvsFramerRowStatusEntry
   ACCESS     not-accessible
   STATUS     mandatory
   DESCRIPTION
     "This entry controls the addition and deletion of 
      vsrSvsFramer components."
::= { vsrSvsFramer 1 }

vsrSvsFramerRowStatusEntry OBJECT-TYPE
   SYNTAX     VsrSvsFramerRowStatusEntry
   ACCESS     not-accessible
   STATUS     mandatory
   DESCRIPTION
     "A single entry in the table represents a single 
      vsrSvsFramer component."
   INDEX {
      vsrIndex,
      vsrSvsIndex,
      vsrSvsFramerIndex }
::= { vsrSvsFramerRowStatusTable 1 }

VsrSvsFramerRowStatusEntry ::= SEQUENCE {
   vsrSvsFramerRowStatus
      RowStatus,
   vsrSvsFramerComponentName
      DisplayString,
   vsrSvsFramerStorageType
      StorageType,
   vsrSvsFramerIndex
      NonReplicated }

vsrSvsFramerRowStatus OBJECT-TYPE
   SYNTAX     RowStatus 
   ACCESS     read-only
   STATUS     mandatory
   DESCRIPTION
     "This variable is used as the basis for SNMP naming of
      vsrSvsFramer components.
      These components cannot be added nor deleted."
::= { vsrSvsFramerRowStatusEntry 1 }

vsrSvsFramerComponentName OBJECT-TYPE
   SYNTAX     DisplayString 
   ACCESS     read-only
   STATUS     mandatory
   DESCRIPTION
     "This variable provides the component's string name for
      use with the ASCII Console Interface"
::= { vsrSvsFramerRowStatusEntry 2 }

vsrSvsFramerStorageType OBJECT-TYPE
   SYNTAX     StorageType 
   ACCESS     read-only
   STATUS     mandatory
   DESCRIPTION
     "This variable represents the storage type value for the
      vsrSvsFramer tables."
::= { vsrSvsFramerRowStatusEntry 4 }

vsrSvsFramerIndex OBJECT-TYPE
   SYNTAX     NonReplicated 
   ACCESS     not-accessible
   STATUS     mandatory
   DESCRIPTION
     "This variable represents the index for the vsrSvsFramer tables."
::= { vsrSvsFramerRowStatusEntry 10 }

vsrSvsFramerProvTable OBJECT-TYPE
   SYNTAX     SEQUENCE OF VsrSvsFramerProvEntry
   ACCESS     not-accessible
   STATUS     mandatory
   DESCRIPTION
     "This group contains the base provisioning data for the Framer 
      component. Application or hardware interface specific provisioning 
      data is contained in other provisionable Framer groups."
::= { vsrSvsFramer 10 }

vsrSvsFramerProvEntry OBJECT-TYPE
   SYNTAX     VsrSvsFramerProvEntry
   ACCESS     not-accessible
   STATUS     mandatory
   DESCRIPTION
     "An entry in the vsrSvsFramerProvTable."
   INDEX {
      vsrIndex,
      vsrSvsIndex,
      vsrSvsFramerIndex }
::= { vsrSvsFramerProvTable 1 }

VsrSvsFramerProvEntry ::= SEQUENCE {
   vsrSvsFramerInterfaceName
      Link }

vsrSvsFramerInterfaceName OBJECT-TYPE
   SYNTAX     Link 
   ACCESS     read-write
   STATUS     mandatory
   DESCRIPTION
     "This attribute contains a hardware component name.
      
      The attribute associates the application with a specific link. This 
      defines the module processor on which Framer's parent component 
      (as well as Framer itself) will run."
::= { vsrSvsFramerProvEntry 1 }

vsrSvsFramerStateTable OBJECT-TYPE
   SYNTAX     SEQUENCE OF VsrSvsFramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { vsrSvsFramer 14 }

vsrSvsFramerStateEntry OBJECT-TYPE
   SYNTAX     VsrSvsFramerStateEntry
   ACCESS     not-accessible
   STATUS     mandatory
   DESCRIPTION
     "An entry in the vsrSvsFramerStateTable."
   INDEX {
      vsrIndex,
      vsrSvsIndex,
      vsrSvsFramerIndex }
::= { vsrSvsFramerStateTable 1 }

VsrSvsFramerStateEntry ::= SEQUENCE {
   vsrSvsFramerAdminState
      INTEGER,
   vsrSvsFramerOperationalState
      INTEGER,
   vsrSvsFramerUsageState
      INTEGER }

vsrSvsFramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { vsrSvsFramerStateEntry 1 }

vsrSvsFramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { vsrSvsFramerStateEntry 2 }

vsrSvsFramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { vsrSvsFramerStateEntry 3 }

vsrSvsFramerStatsTable OBJECT-TYPE
   SYNTAX     SEQUENCE OF VsrSvsFramerStatsEntry
   ACCESS     not-accessible
   STATUS     mandatory
   DESCRIPTION
     "This group contains the operational statistics data for a Framer 
      component."
::= { vsrSvsFramer 15 }

vsrSvsFramerStatsEntry OBJECT-TYPE
   SYNTAX     VsrSvsFramerStatsEntry
   ACCESS     not-accessible
   STATUS     mandatory
   DESCRIPTION
     "An entry in the vsrSvsFramerStatsTable."
   INDEX {
      vsrIndex,
      vsrSvsIndex,
      vsrSvsFramerIndex }
::= { vsrSvsFramerStatsTable 1 }

VsrSvsFramerStatsEntry ::= SEQUENCE {
   vsrSvsFramerTotalCells
      Unsigned32,
   vsrSvsFramerAudioCells
      Unsigned32,
   vsrSvsFramerSilenceCells
      Unsigned32,
   vsrSvsFramerModemCells
      Unsigned32,
   vsrSvsFramerCurrentEncodingRate
      INTEGER,
   vsrSvsFramerLrcErrors
      Unsigned32,
   vsrSvsFramerFrmLostInNetwork
      Unsigned32,
   vsrSvsFramerFrmUnderRuns
      Unsigned32,
   vsrSvsFramerFrmDumped
      Unsigned32,
   vsrSvsFramerModemSilenceCells
      Counter32,
   vsrSvsFramerCurrentEncoding
      INTEGER,
   vsrSvsFramerTptStatus
      INTEGER,
   vsrSvsFramerFaxRelayCells
      Counter32,
   vsrSvsFramerModemFaxCells
      Unsigned32,
   vsrSvsFramerFaxIdleCells
      Counter32 }

vsrSvsFramerTotalCells OBJECT-TYPE
   SYNTAX     Unsigned32 (0..4294967295)
   ACCESS     read-only
   STATUS     mandatory
   DESCRIPTION
     "This attribute counts the total number of cells received from the 
      interface.
      Each cell contains 44 bytes of data from the DS0 channel. Since a 
      DS0 provides data at 64 kbit/s, each cell contains 5.5 ms of audio 
      data.
      This data flow is measured before compression is performed on the 
      channel.
      This counter wraps to zero after reaching its maximum value."
::= { vsrSvsFramerStatsEntry 1 }

vsrSvsFramerAudioCells OBJECT-TYPE
   SYNTAX     Unsigned32 (0..4294967295)
   ACCESS     read-only
   STATUS     mandatory
   DESCRIPTION
     "This attribute counts the total number of cells containing audio data 
      received from the interface while the channel was seized. A CCS 
      channel is always considered to be seized. Audio data includes cells 
      containing voice as well modem audio, but not silence. 
      A cell contains 44 bytes of data from the DS0 channel(5.5 ms).
      This flow is measured before compression is performed on the 
      channel.
      This counter wraps to zero after reaching its maximum value."
::= { vsrSvsFramerStatsEntry 2 }

vsrSvsFramerSilenceCells OBJECT-TYPE
   SYNTAX     Unsigned32 (0..4294967295)
   ACCESS     read-only
   STATUS     mandatory
   DESCRIPTION
     "This attribute counts the total number of cells containing silence 
      data received from the interface which was not forwarded into the 
      network, thus saving bandwidth. A channel may go into silence due 
      to the operation of the silence suppression feature or for CAS 
      channels when the ABCD signalling bits go idle.
      A cell contains 44 bytes of data from the DS0 channel(5.5 ms).
      This flow is measured before compression is performed on the 
      channel.
      This counter wraps to zero after reaching its maximum value."
::= { vsrSvsFramerStatsEntry 4 }

vsrSvsFramerModemCells OBJECT-TYPE
   SYNTAX     Unsigned32 (0..4294967295)
   ACCESS     read-only
   STATUS     obsolete
   DESCRIPTION
     "This attribute is migrated into modemFaxCells."
::= { vsrSvsFramerStatsEntry 5 }

vsrSvsFramerCurrentEncodingRate OBJECT-TYPE
   SYNTAX     INTEGER  {
                 n640(1),
                 n320(2),
                 n240(3),
                 n160(4),
                 n80(5),
                 n144(6),
                 n120(7),
                 n96(8),
                 n72(9),
                 n63(10),
                 n53(11),
                 n48(12),
                 n24(13),
                 n12(14),
                 n03(15) }
   ACCESS     read-only
   STATUS     obsolete
   DESCRIPTION
     "This attribute has been migrated to currentRate in Operational 
      group."
::= { vsrSvsFramerStatsEntry 6 }

vsrSvsFramerLrcErrors OBJECT-TYPE
   SYNTAX     Unsigned32 (0..4294967295)
   ACCESS     read-only
   STATUS     mandatory
   DESCRIPTION
     "This attribute counts the number of frames received from the 
      network with LRC errors."
::= { vsrSvsFramerStatsEntry 7 }

vsrSvsFramerFrmLostInNetwork OBJECT-TYPE
   SYNTAX     Unsigned32 (0..4294967295)
   ACCESS     read-only
   STATUS     mandatory
   DESCRIPTION
     "This attribute counts the number of frames which the service knows 
      it did not receive from the network although they were sent in to the 
      network from the far end."
::= { vsrSvsFramerStatsEntry 8 }

vsrSvsFramerFrmUnderRuns OBJECT-TYPE
   SYNTAX     Unsigned32 (0..4294967295)
   ACCESS     read-only
   STATUS     mandatory
   DESCRIPTION
     "This attribute counts the number of times that a frame was needed 
      but was not available because it had been delayed too long in the 
      network.
      This error may occur repeatedly if the interface clocks at the two 
      access points to the network are operating at different rates."
::= { vsrSvsFramerStatsEntry 9 }

vsrSvsFramerFrmDumped OBJECT-TYPE
   SYNTAX     Unsigned32 (0..4294967295)
   ACCESS     read-only
   STATUS     mandatory
   DESCRIPTION
     "This attribute counts the number of frames which have been 
      dumped because the output queue grew too large. This can occur if 
      the clock rate on the incoming interface is faster than the clock rate 
      on the outgoing interface and there are no silence periods to absorb 
      the difference, or when a compression rate change occurs.
      This count wraps to zero after reaching its maximum value."
::= { vsrSvsFramerStatsEntry 10 }

vsrSvsFramerModemSilenceCells OBJECT-TYPE
   SYNTAX     Counter32 
   ACCESS     read-only
   STATUS     obsolete
   DESCRIPTION
     "This attribute is migrated into faxIdleCells."
::= { vsrSvsFramerStatsEntry 26 }

vsrSvsFramerCurrentEncoding OBJECT-TYPE
   SYNTAX     INTEGER  {
                 g729(1),
                 g728(2),
                 g723(3),
                 g726(4),
                 g711(5),
                 v22(32),
                 v22bis(33),
                 faxRelay(64),
                 v27(65),
                 v29(66),
                 v17(67),
                 none(255) }
   ACCESS     read-only
   STATUS     obsolete
   DESCRIPTION
     "This attribute has been migrated to currentEncoding in Operational 
      group."
::= { vsrSvsFramerStatsEntry 27 }

vsrSvsFramerTptStatus OBJECT-TYPE
   SYNTAX     INTEGER  {
                 operating(0),
                 rejected(1),
                 monitoring(2),
                 disabled(3) }
   ACCESS     read-only
   STATUS     obsolete
   DESCRIPTION
     "This attribute has been migrated to tptStatus in Operational group."
::= { vsrSvsFramerStatsEntry 28 }

vsrSvsFramerFaxRelayCells OBJECT-TYPE
   SYNTAX     Counter32 
   ACCESS     read-only
   STATUS     mandatory
   DESCRIPTION
     "This attribute counts the total number of fax relay cells sent to the 
      network.
      
      This counter wraps to zero after reaching its maximum value."
::= { vsrSvsFramerStatsEntry 35 }

vsrSvsFramerModemFaxCells OBJECT-TYPE
   SYNTAX     Unsigned32 (0..4294967295)
   ACCESS     read-only
   STATUS     mandatory
   DESCRIPTION
     "This attribute counts the total number of cells containing modem 
      data received from the interface while the channel was seized. A 
      CCS channel is always considered to be seized. Cells are considered 
      to be modem data if a constant energy level above          -25 dBmO 
      is detected for more than 900 ms. An energy level below -36 dBmO 
      for more than 650 ms is required to detect that the modem is no 
      longer present. 
      A cell contains 44 bytes of data from the DS0 channel (5.5 ms).
      This flow is measured before compression is performed on the 
      channel.
      This counter wraps to zero after reaching its maximum value."
::= { vsrSvsFramerStatsEntry 36 }

vsrSvsFramerFaxIdleCells OBJECT-TYPE
   SYNTAX     Counter32 
   ACCESS     read-only
   STATUS     mandatory
   DESCRIPTION
     "This attribute counts the total number of cells containing silent fax 
      data received from the interface which were not forwarded into the 
      network, thus saving bandwidth. A channel may go into silence due 
      to the silence Suppression feature or for CAS channels when the 
      ABCD signalling bits go idle.
      
      A cell contains 44 bytes of data from the DS0 channel (5.5 ms). 
      This flow is measured before compression is performed on the 
      channel.
      
      This counter wraps to zero after reaching its maximum value."
::= { vsrSvsFramerStatsEntry 37 }

vsrSvsFramerOperTable OBJECT-TYPE
   SYNTAX     SEQUENCE OF VsrSvsFramerOperEntry
   ACCESS     not-accessible
   STATUS     mandatory
   DESCRIPTION
     "This group contains the operational data for a Svs Framer."
::= { vsrSvsFramer 16 }

vsrSvsFramerOperEntry OBJECT-TYPE
   SYNTAX     VsrSvsFramerOperEntry
   ACCESS     not-accessible
   STATUS     mandatory
   DESCRIPTION
     "An entry in the vsrSvsFramerOperTable."
   INDEX {
      vsrIndex,
      vsrSvsIndex,
      vsrSvsFramerIndex }
::= { vsrSvsFramerOperTable 1 }

VsrSvsFramerOperEntry ::= SEQUENCE {
   vsrSvsFramerOpCurrentEncoding
      INTEGER,
   vsrSvsFramerCurrentRate
      INTEGER,
   vsrSvsFramerOpTptStatus
      INTEGER }

vsrSvsFramerOpCurrentEncoding OBJECT-TYPE
   SYNTAX     INTEGER  {
                 g729(1),
                 g728(2),
                 g723(3),
                 g726(4),
                 g711(5),
                 v22(32),
                 v22bis(33),
                 faxRelay(64),
                 v27(65),
                 v29(66),
                 v17(67),
                 none(255) }
   ACCESS     read-only
   STATUS     mandatory
   DESCRIPTION
     "This attribute indicates the encoding currently being performed on 
      this channel. g711 indicates that pulse code modulation (PCM) 
      defined by ITU-T G.711 is being performed. g726 indicates that 
      adaptive differential pulse code modulation (ADPCM) defined by 
      ITU-T G.726 is being performed. g728 indicates that the Low Delay 
      Coded Excited Linear Predictive Coder (LD-CELP) algorithm 
      defined by ITU-T G.728 is being performed. g729 indicates that the 
      Conjunctive Structure Algebraic Code Excited Linear Predictive 
      Coder (CS-ACELP) algorithm defined by ITU-T G.729 is being 
      performed. v27 indicates that the algorithm defined by ITU-T V.27 
      is being performed. v29 indicates that the algorithm defined by 
      ITU-T V.29 is being performed."
::= { vsrSvsFramerOperEntry 1 }

vsrSvsFramerCurrentRate OBJECT-TYPE
   SYNTAX     INTEGER  {
                 n0(0),
                 n640(1),
                 n320(2),
                 n240(3),
                 n160(4),
                 n80(5),
                 n144(6),
                 n120(7),
                 n96(8),
                 n72(9),
                 n63(10),
                 n53(11),
                 n48(12),
                 n24(13),
                 n12(14),
                 n03(15) }
   ACCESS     read-only
   STATUS     mandatory
   DESCRIPTION
     "This attribute indicates the current encoding rate for frames being 
      sent to the network."
::= { vsrSvsFramerOperEntry 2 }

vsrSvsFramerOpTptStatus OBJECT-TYPE
   SYNTAX     INTEGER  {
                 operating(0),
                 monitoring(2),
                 disabled(3) }
   ACCESS     read-only
   STATUS     mandatory
   DESCRIPTION
     "This attribute indicates the current status of the tandem pass through 
      algorithm. If tptStatus is operating, the tandem pass through 
      algorithm is cutting through a voice switch. If tptStatus is 
      monitoring, negotiatedTandemPassThrough is enabled, but the 
      tandem pass through algorithm is not cutting through a voice 
      switch. If tptStatus is disabled, negotiatedTandemPassThrough is 
      disabled."
::= { vsrSvsFramerOperEntry 3 }

vsrSvsFramerNegTable OBJECT-TYPE
   SYNTAX     SEQUENCE OF VsrSvsFramerNegEntry
   ACCESS     not-accessible
   STATUS     mandatory
   DESCRIPTION
     "This group contains the attributes indicating the results of voice 
      networking end to end negotiation."
::= { vsrSvsFramer 17 }

vsrSvsFramerNegEntry OBJECT-TYPE
   SYNTAX     VsrSvsFramerNegEntry
   ACCESS     not-accessible
   STATUS     mandatory
   DESCRIPTION
     "An entry in the vsrSvsFramerNegTable."
   INDEX {
      vsrIndex,
      vsrSvsIndex,
      vsrSvsFramerIndex }
::= { vsrSvsFramerNegTable 1 }

VsrSvsFramerNegEntry ::= SEQUENCE {
   vsrSvsFramerNegotiatedSilenceSuppression
      INTEGER,
   vsrSvsFramerNegotiatedFisG711G726
      INTEGER,
   vsrSvsFramerNegotiatedDtmfRegeneration
      INTEGER,
   vsrSvsFramerNegotiatedV17AsG711G726
      INTEGER,
   vsrSvsFramerNegotiatedTandemPassThrough
      INTEGER }

vsrSvsFramerNegotiatedSilenceSuppression OBJECT-TYPE
   SYNTAX     INTEGER  {
                 off(0),
                 on(1),
                 congested(2),
                 slow(3),
                 slowAndCongested(4) }
   ACCESS     read-write
   STATUS     mandatory
   DESCRIPTION
     "This attribute indicates the result of negotiating silence suppression 
      with the remote end across the subnet. The parameter used for 
      negotiating with the remote end is provisioned in Vncs Vp 
      silenceSuppression.
      
      If negotiatedSilenceSuppression is off, silence suppression is never 
      performed.
      If negotiatedSilenceSuppression is on, silence suppression is always 
      performed.
      If negotiatedSilenceSuppression is congested, silence suppression is 
      performed only when the network is congested.
      If negotiatedSilenceSuppression is slow, silence suppression begins 
      after 10 to 20 seconds without any speech or audio being detected.
      If negotiatedSilenceSuppression is slowAndCongested, both the 
      slow and congested options are applied."
::= { vsrSvsFramerNegEntry 1 }

vsrSvsFramerNegotiatedFisG711G726 OBJECT-TYPE
   SYNTAX     INTEGER  {
                 off(0),
                 on(1) }
   ACCESS     read-write
   STATUS     mandatory
   DESCRIPTION
     "This attribute indicates the result of negotiating G.711/G.726 fax 
      idle suppression with the remote end across the subnet. The 
      parameter used for negotiating with the remote end is provisioned in 
      Vncs Vp faxIdleSuppressionG711G726."
::= { vsrSvsFramerNegEntry 2 }

vsrSvsFramerNegotiatedDtmfRegeneration OBJECT-TYPE
   SYNTAX     INTEGER  {
                 off(0),
                 on(1) }
   ACCESS     read-write
   STATUS     mandatory
   DESCRIPTION
     "This attribute indicates the result of negotiating DTMF regeneration 
      with the remote end across the subnet. The parameter used for 
      negotiating with the remote end is provisioned in Vncs Vp 
      dtmfRegeneration.
      
      If negotiatedDtmfRegeneration is on, DTMF tones received from 
      the link are first converted to digits before being sent to the subnet. 
      When a digit is received from the subnet, its respective DTMF tone 
      is generated before being sent to the link. 
      
      If negotiatedDtmfRegeneration is off, DTMF tones are transported 
      transparently."
::= { vsrSvsFramerNegEntry 3 }

vsrSvsFramerNegotiatedV17AsG711G726 OBJECT-TYPE
   SYNTAX     INTEGER  {
                 no(0),
                 yes(1) }
   ACCESS     read-only
   STATUS     mandatory
   DESCRIPTION
     "This attribute indicates how this SwitchedVoiceService negotiates 
      with V.17 fax machines, as determined by negotiation with the 
      remote end across the subnet. The parameter used for negotiating 
      with the remote end is provisioned in Vncs Vp 
      v17EncodedAsG711G726.
      
      If negotiatedV17AsG711G726 is no, V.17 fax machines are 
      instructed to use V.29, and V.29 fax traffic sent by fax machines is 
      demodulated and encoded using fax relay.
      
      If negotiatedV17AsG711G726 is yes, V.17 fax machines are 
      permitted to use V.17 and V.17 fax traffic sent by fax machines is 
      encoded using G.711 or G.726, at the rates given in 
      negotiatedRates."
::= { vsrSvsFramerNegEntry 4 }

vsrSvsFramerNegotiatedTandemPassThrough OBJECT-TYPE
   SYNTAX     INTEGER  {
                 disabled(0),
                 enabled(1) }
   ACCESS     read-only
   STATUS     mandatory
   DESCRIPTION
     "This attribute indicates the result of negotiating tandem pass 
      through with the remote end across the subnet. The parameter used 
      for negotiating with the remote end is provisioned in Vncs Vp 
      tandemPassThrough."
::= { vsrSvsFramerNegEntry 5 }

vsrSvsFramerFrmToNetworkTable OBJECT-TYPE
   SYNTAX     SEQUENCE OF VsrSvsFramerFrmToNetworkEntry
   ACCESS     not-accessible
   STATUS     mandatory
   DESCRIPTION
     "This attribute counts the number of frames sent to the network at 
      each encoding rate. Fax relay cells are not included."
::= { vsrSvsFramer 315 }

vsrSvsFramerFrmToNetworkEntry OBJECT-TYPE
   SYNTAX     VsrSvsFramerFrmToNetworkEntry
   ACCESS     not-accessible
   STATUS     mandatory
   DESCRIPTION
     "An entry in the vsrSvsFramerFrmToNetworkTable."
   INDEX {
      vsrIndex,
      vsrSvsIndex,
      vsrSvsFramerIndex,
      vsrSvsFramerFrmToNetworkIndex }
::= { vsrSvsFramerFrmToNetworkTable 1 }

VsrSvsFramerFrmToNetworkEntry ::= SEQUENCE {
   vsrSvsFramerFrmToNetworkIndex
      INTEGER,
   vsrSvsFramerFrmToNetworkValue
      Unsigned32 }

vsrSvsFramerFrmToNetworkIndex OBJECT-TYPE
   SYNTAX     INTEGER  {
                 n64KbitS(0),
                 n32KbitS(1),
                 n24KbitS(2),
                 n16KbitS(3),
                 n8KbitS(4) }
   ACCESS     not-accessible
   STATUS     mandatory
   DESCRIPTION
     "This variable represents the vsrSvsFramerFrmToNetworkTable
      specific index for the vsrSvsFramerFrmToNetworkTable."
::= { vsrSvsFramerFrmToNetworkEntry 1 }

vsrSvsFramerFrmToNetworkValue OBJECT-TYPE
   SYNTAX     Unsigned32 (0..4294967295)
   ACCESS     read-only
   STATUS     mandatory
   DESCRIPTION
     "This variable represents an individual value for the
      vsrSvsFramerFrmToNetworkTable."
::= { vsrSvsFramerFrmToNetworkEntry 2 }

vsrSvsFramerFrmFromNetworkTable OBJECT-TYPE
   SYNTAX     SEQUENCE OF VsrSvsFramerFrmFromNetworkEntry
   ACCESS     not-accessible
   STATUS     mandatory
   DESCRIPTION
     "This attribute counts the number of frames received from the 
      network at each encoding rate."
::= { vsrSvsFramer 316 }

vsrSvsFramerFrmFromNetworkEntry OBJECT-TYPE
   SYNTAX     VsrSvsFramerFrmFromNetworkEntry
   ACCESS     not-accessible
   STATUS     mandatory
   DESCRIPTION
     "An entry in the vsrSvsFramerFrmFromNetworkTable."
   INDEX {
      vsrIndex,
      vsrSvsIndex,
      vsrSvsFramerIndex,
      vsrSvsFramerFrmFromNetworkIndex }
::= { vsrSvsFramerFrmFromNetworkTable 1 }

VsrSvsFramerFrmFromNetworkEntry ::= SEQUENCE {
   vsrSvsFramerFrmFromNetworkIndex
      INTEGER,
   vsrSvsFramerFrmFromNetworkValue
      Unsigned32 }

vsrSvsFramerFrmFromNetworkIndex OBJECT-TYPE
   SYNTAX     INTEGER  {
                 n64KbitS(0),
                 n32KbitS(1),
                 n24KbitS(2),
                 n16KbitS(3),
                 n8KbitS(4) }
   ACCESS     not-accessible
   STATUS     mandatory
   DESCRIPTION
     "This variable represents the vsrSvsFramerFrmFromNetworkTable
      specific index for the vsrSvsFramerFrmFromNetworkTable."
::= { vsrSvsFramerFrmFromNetworkEntry 1 }

vsrSvsFramerFrmFromNetworkValue OBJECT-TYPE
   SYNTAX     Unsigned32 (0..4294967295)
   ACCESS     read-only
   STATUS     mandatory
   DESCRIPTION
     "This variable represents an individual value for the
      vsrSvsFramerFrmFromNetworkTable."
::= { vsrSvsFramerFrmFromNetworkEntry 2 }

vsrSvsFramerNEncodingTable OBJECT-TYPE
   SYNTAX     SEQUENCE OF VsrSvsFramerNEncodingEntry
   ACCESS     not-accessible
   STATUS     mandatory
   DESCRIPTION
     "This attribute indicates the results of negotiating audio call 
      encodings for voice, modemFax and fax traffic with the remote end 
      across the subnet. The parameters used for negotiating with the 
      remote end are provisioned in Vncs Vp voiceEncodingChoice and 
      Vncs Vp modemFaxEncodingChoice.
      
      voice traffic is all traffic from the start of a call or speech until a 
      2100 Hz tone or call release. modemFax traffic is all traffic after a 
      2100 Hz tone but before a fax preamble, speech or call release. fax 
      traffic is all traffic after a fax preamble but before speech or call 
      release.
      
      g711 indicates that pulse code modulation (PCM) defined by ITU-T 
      G.711 is the negotiated encoding.
      g726 indicates that Adaptive Differential Pulse Code Modulation 
      (ADPCM) defined by ITU-T G.726 is the negotiated encoding. 
      g711G726 indicates that pulse code modulation (PCM) defined by 
      ITU-T G.711 and Adaptive Differential Pulse Code Modulation 
      (ADPCM) defined by ITU-T G.726 are both negotiated encodings. 
      If negotiatedEncoding is g711G726, the actual encoding performed 
      can be either G.711 or G.726, depending on network congestion.
      g728 indicates that Low Delay Coded Excited Linear Predictive 
      Coder (CS-ACELP) defined by ITU-T G.728 is the negotiated 
      encoding.
      g729 indicates that Conjunctive Structure Algebraic Code Excited 
      Linear Predictive Coder (CS-ACELP) defined by ITU-T G.729 is 
      the negotiated encoding.
      v29V27Relay indicates that fax relay using ITU-T V.27 or ITU-T 
      V.29 is the negotiated encoding.
      v17V29V27Relay indicates that fax relay using ITU-T V.17, ITU-T 
      V.27, or ITU-T V.29 is the negotiated encoding.
      
      If all negotiated encodings are none, the negotiation of audio call 
      encodings is not complete."
::= { vsrSvsFramer 467 }

vsrSvsFramerNEncodingEntry OBJECT-TYPE
   SYNTAX     VsrSvsFramerNEncodingEntry
   ACCESS     not-accessible
   STATUS     mandatory
   DESCRIPTION
     "An entry in the vsrSvsFramerNEncodingTable."
   INDEX {
      vsrIndex,
      vsrSvsIndex,
      vsrSvsFramerIndex,
      vsrSvsFramerNEncodingIndex }
::= { vsrSvsFramerNEncodingTable 1 }

VsrSvsFramerNEncodingEntry ::= SEQUENCE {
   vsrSvsFramerNEncodingIndex
      INTEGER,
   vsrSvsFramerNEncodingValue
      INTEGER }

vsrSvsFramerNEncodingIndex OBJECT-TYPE
   SYNTAX     INTEGER  {
                 voice(0),
                 modemFax(1),
                 fax(2) }
   ACCESS     not-accessible
   STATUS     mandatory
   DESCRIPTION
     "This variable represents the vsrSvsFramerNEncodingTable
      specific index for the vsrSvsFramerNEncodingTable."
::= { vsrSvsFramerNEncodingEntry 1 }

vsrSvsFramerNEncodingValue OBJECT-TYPE
   SYNTAX     INTEGER  {
                 g729(1),
                 g728(2),
                 g726(4),
                 g711(5),
                 g711G726(31),
                 v29V27Relay(64),
                 v17V29V27Relay(68),
                 none(255) }
   ACCESS     read-write
   STATUS     mandatory
   DESCRIPTION
     "This variable represents an individual value for the
      vsrSvsFramerNEncodingTable."
::= { vsrSvsFramerNEncodingEntry 2 }

vsrSvsFramerNRatesTable OBJECT-TYPE
   SYNTAX     SEQUENCE OF VsrSvsFramerNRatesEntry
   ACCESS     not-accessible
   STATUS     mandatory
   DESCRIPTION
     "This attribute indicates the results of negotiating minimum and 
      maximum rates for voice, modemFax and fax traffic with the 
      remote end across the subnet. The parameters used for negotiating 
      with the remote end are provisioned in Vncs Vp voiceRates and 
      Vncs Vp modemFaxRates."
::= { vsrSvsFramer 479 }

vsrSvsFramerNRatesEntry OBJECT-TYPE
   SYNTAX     VsrSvsFramerNRatesEntry
   ACCESS     not-accessible
   STATUS     mandatory
   DESCRIPTION
     "An entry in the vsrSvsFramerNRatesTable."
   INDEX {
      vsrIndex,
      vsrSvsIndex,
      vsrSvsFramerIndex,
      vsrSvsFramerNRatesTrafficIndex,
      vsrSvsFramerNRatesRateIndex }
::= { vsrSvsFramerNRatesTable 1 }

VsrSvsFramerNRatesEntry ::= SEQUENCE {
   vsrSvsFramerNRatesTrafficIndex
      INTEGER,
   vsrSvsFramerNRatesRateIndex
      INTEGER,
   vsrSvsFramerNRatesValue
      INTEGER }

vsrSvsFramerNRatesTrafficIndex OBJECT-TYPE
   SYNTAX     INTEGER  {
                 voice(0),
                 modemFax(1),
                 fax(2) }
   ACCESS     not-accessible
   STATUS     mandatory
   DESCRIPTION
     "This variable represents the next to last index for the 
      vsrSvsFramerNRatesTable."
::= { vsrSvsFramerNRatesEntry 1 }

vsrSvsFramerNRatesRateIndex OBJECT-TYPE
   SYNTAX     INTEGER  {
                 min(0),
                 max(1) }
   ACCESS     not-accessible
   STATUS     mandatory
   DESCRIPTION
     "This variable represents the final index for the 
      vsrSvsFramerNRatesTable."
::= { vsrSvsFramerNRatesEntry 2 }

vsrSvsFramerNRatesValue OBJECT-TYPE
   SYNTAX     INTEGER  {
                 n00(0),
                 n03(1),
                 n12(2),
                 n24(3),
                 n48(4),
                 n72(5),
                 n96(6),
                 n120(7),
                 n144(8),
                 n80(66),
                 n160(67),
                 n240(68),
                 n320(69),
                 n640(70) }
   ACCESS     read-write
   STATUS     mandatory
   DESCRIPTION
     "This variable represents an individual value for the
      vsrSvsFramerNRatesTable."
::= { vsrSvsFramerNRatesEntry 3 }


-- Vsr/m Svs/n Framer VfpDebug
-- This component contains debugging attributes for a voice service 
-- running on a DS1V, E1V, 1pDS1V, 1pE1V or J2MV functional 
-- processor.

vsrSvsFramerVfpDebug OBJECT IDENTIFIER ::= { vsrSvsFramer 5 }



vsrSvsFramerVfpDebugRowStatusTable OBJECT-TYPE
   SYNTAX     SEQUENCE OF VsrSvsFramerVfpDebugRowStatusEntry
   ACCESS     not-accessible
   STATUS     mandatory
   DESCRIPTION
     "This entry controls the addition and deletion of 
      vsrSvsFramerVfpDebug components."
::= { vsrSvsFramerVfpDebug 1 }

vsrSvsFramerVfpDebugRowStatusEntry OBJECT-TYPE
   SYNTAX     VsrSvsFramerVfpDebugRowStatusEntry
   ACCESS     not-accessible
   STATUS     mandatory
   DESCRIPTION
     "A single entry in the table represents a single 
      vsrSvsFramerVfpDebug component."
   INDEX {
      vsrIndex,
      vsrSvsIndex,
      vsrSvsFramerIndex,
      vsrSvsFramerVfpDebugIndex }
::= { vsrSvsFramerVfpDebugRowStatusTable 1 }

VsrSvsFramerVfpDebugRowStatusEntry ::= SEQUENCE {
   vsrSvsFramerVfpDebugRowStatus
      RowStatus,
   vsrSvsFramerVfpDebugComponentName
      DisplayString,
   vsrSvsFramerVfpDebugStorageType
      StorageType,
   vsrSvsFramerVfpDebugIndex
      NonReplicated }

vsrSvsFramerVfpDebugRowStatus OBJECT-TYPE
   SYNTAX     RowStatus 
   ACCESS     read-only
   STATUS     mandatory
   DESCRIPTION
     "This variable is used as the basis for SNMP naming of
      vsrSvsFramerVfpDebug components.
      These components cannot be added nor deleted."
::= { vsrSvsFramerVfpDebugRowStatusEntry 1 }

vsrSvsFramerVfpDebugComponentName OBJECT-TYPE
   SYNTAX     DisplayString 
   ACCESS     read-only
   STATUS     mandatory
   DESCRIPTION
     "This variable provides the component's string name for
      use with the ASCII Console Interface"
::= { vsrSvsFramerVfpDebugRowStatusEntry 2 }

vsrSvsFramerVfpDebugStorageType OBJECT-TYPE
   SYNTAX     StorageType 
   ACCESS     read-only
   STATUS     mandatory
   DESCRIPTION
     "This variable represents the storage type value for the
      vsrSvsFramerVfpDebug tables."
::= { vsrSvsFramerVfpDebugRowStatusEntry 4 }

vsrSvsFramerVfpDebugIndex OBJECT-TYPE
   SYNTAX     NonReplicated 
   ACCESS     not-accessible
   STATUS     mandatory
   DESCRIPTION
     "This variable represents the index for the vsrSvsFramerVfpDebug tables."
::= { vsrSvsFramerVfpDebugRowStatusEntry 10 }


-- Vsr/m Svs/n Framer MvpDebug
-- This component contains debugging attributes on a voice service's 
-- framer running on a 1pE1Mvp, 1pDS1Mvp or 1pTTC2mMvp 
-- functional processor.

vsrSvsFramerMvpDebug OBJECT IDENTIFIER ::= { vsrSvsFramer 6 }



vsrSvsFramerMvpDebugRowStatusTable OBJECT-TYPE
   SYNTAX     SEQUENCE OF VsrSvsFramerMvpDebugRowStatusEntry
   ACCESS     not-accessible
   STATUS     mandatory
   DESCRIPTION
     "This entry controls the addition and deletion of 
      vsrSvsFramerMvpDebug components."
::= { vsrSvsFramerMvpDebug 1 }

vsrSvsFramerMvpDebugRowStatusEntry OBJECT-TYPE
   SYNTAX     VsrSvsFramerMvpDebugRowStatusEntry
   ACCESS     not-accessible
   STATUS     mandatory
   DESCRIPTION
     "A single entry in the table represents a single 
      vsrSvsFramerMvpDebug component."
   INDEX {
      vsrIndex,
      vsrSvsIndex,
      vsrSvsFramerIndex,
      vsrSvsFramerMvpDebugIndex }
::= { vsrSvsFramerMvpDebugRowStatusTable 1 }

VsrSvsFramerMvpDebugRowStatusEntry ::= SEQUENCE {
   vsrSvsFramerMvpDebugRowStatus
      RowStatus,
   vsrSvsFramerMvpDebugComponentName
      DisplayString,
   vsrSvsFramerMvpDebugStorageType
      StorageType,
   vsrSvsFramerMvpDebugIndex
      NonReplicated }

vsrSvsFramerMvpDebugRowStatus OBJECT-TYPE
   SYNTAX     RowStatus 
   ACCESS     read-only
   STATUS     mandatory
   DESCRIPTION
     "This variable is used as the basis for SNMP naming of
      vsrSvsFramerMvpDebug components.
      These components cannot be added nor deleted."
::= { vsrSvsFramerMvpDebugRowStatusEntry 1 }

vsrSvsFramerMvpDebugComponentName OBJECT-TYPE
   SYNTAX     DisplayString 
   ACCESS     read-only
   STATUS     mandatory
   DESCRIPTION
     "This variable provides the component's string name for
      use with the ASCII Console Interface"
::= { vsrSvsFramerMvpDebugRowStatusEntry 2 }

vsrSvsFramerMvpDebugStorageType OBJECT-TYPE
   SYNTAX     StorageType 
   ACCESS     read-only
   STATUS     mandatory
   DESCRIPTION
     "This variable represents the storage type value for the
      vsrSvsFramerMvpDebug tables."
::= { vsrSvsFramerMvpDebugRowStatusEntry 4 }

vsrSvsFramerMvpDebugIndex OBJECT-TYPE
   SYNTAX     NonReplicated 
   ACCESS     not-accessible
   STATUS     mandatory
   DESCRIPTION
     "This variable represents the index for the vsrSvsFramerMvpDebug tables."
::= { vsrSvsFramerMvpDebugRowStatusEntry 10 }


-- Vsr/n Svs/m Framer PcmCapture
-- This component contains attributes for PCM data capture.

vsrSvsFramerPcmCapture OBJECT IDENTIFIER ::= { vsrSvsFramer 7 }



vsrSvsFramerPcmCaptureRowStatusTable OBJECT-TYPE
   SYNTAX     SEQUENCE OF VsrSvsFramerPcmCaptureRowStatusEntry
   ACCESS     not-accessible
   STATUS     mandatory
   DESCRIPTION
     "This entry controls the addition and deletion of 
      vsrSvsFramerPcmCapture components."
::= { vsrSvsFramerPcmCapture 1 }

vsrSvsFramerPcmCaptureRowStatusEntry OBJECT-TYPE
   SYNTAX     VsrSvsFramerPcmCaptureRowStatusEntry
   ACCESS     not-accessible
   STATUS     mandatory
   DESCRIPTION
     "A single entry in the table represents a single 
      vsrSvsFramerPcmCapture component."
   INDEX {
      vsrIndex,
      vsrSvsIndex,
      vsrSvsFramerIndex,
      vsrSvsFramerPcmCaptureIndex }
::= { vsrSvsFramerPcmCaptureRowStatusTable 1 }

VsrSvsFramerPcmCaptureRowStatusEntry ::= SEQUENCE {
   vsrSvsFramerPcmCaptureRowStatus
      RowStatus,
   vsrSvsFramerPcmCaptureComponentName
      DisplayString,
   vsrSvsFramerPcmCaptureStorageType
      StorageType,
   vsrSvsFramerPcmCaptureIndex
      NonReplicated }

vsrSvsFramerPcmCaptureRowStatus OBJECT-TYPE
   SYNTAX     RowStatus 
   ACCESS     read-only
   STATUS     mandatory
   DESCRIPTION
     "This variable is used as the basis for SNMP naming of
      vsrSvsFramerPcmCapture components.
      These components cannot be added nor deleted."
::= { vsrSvsFramerPcmCaptureRowStatusEntry 1 }

vsrSvsFramerPcmCaptureComponentName OBJECT-TYPE
   SYNTAX     DisplayString 
   ACCESS     read-only
   STATUS     mandatory
   DESCRIPTION
     "This variable provides the component's string name for
      use with the ASCII Console Interface"
::= { vsrSvsFramerPcmCaptureRowStatusEntry 2 }

vsrSvsFramerPcmCaptureStorageType OBJECT-TYPE
   SYNTAX     StorageType 
   ACCESS     read-only
   STATUS     mandatory
   DESCRIPTION
     "This variable represents the storage type value for the
      vsrSvsFramerPcmCapture tables."
::= { vsrSvsFramerPcmCaptureRowStatusEntry 4 }

vsrSvsFramerPcmCaptureIndex OBJECT-TYPE
   SYNTAX     NonReplicated 
   ACCESS     not-accessible
   STATUS     mandatory
   DESCRIPTION
     "This variable represents the index for the vsrSvsFramerPcmCapture tables."
::= { vsrSvsFramerPcmCaptureRowStatusEntry 10 }


-- ...Lc
-- This component contains all of the operation attributes for a Path 
-- Oriented Logical Connection.

vsrSvsLCo OBJECT IDENTIFIER ::= { vsrSvs 3 }



vsrSvsLCoRowStatusTable OBJECT-TYPE
   SYNTAX     SEQUENCE OF VsrSvsLCoRowStatusEntry
   ACCESS     not-accessible
   STATUS     mandatory
   DESCRIPTION
     "This entry controls the addition and deletion of 
      vsrSvsLCo components."
::= { vsrSvsLCo 1 }

vsrSvsLCoRowStatusEntry OBJECT-TYPE
   SYNTAX     VsrSvsLCoRowStatusEntry
   ACCESS     not-accessible
   STATUS     mandatory
   DESCRIPTION
     "A single entry in the table represents a single 
      vsrSvsLCo component."
   INDEX {
      vsrIndex,
      vsrSvsIndex,
      vsrSvsLCoIndex }
::= { vsrSvsLCoRowStatusTable 1 }

VsrSvsLCoRowStatusEntry ::= SEQUENCE {
   vsrSvsLCoRowStatus
      RowStatus,
   vsrSvsLCoComponentName
      DisplayString,
   vsrSvsLCoStorageType
      StorageType,
   vsrSvsLCoIndex
      NonReplicated }

vsrSvsLCoRowStatus OBJECT-TYPE
   SYNTAX     RowStatus 
   ACCESS     read-only
   STATUS     mandatory
   DESCRIPTION
     "This variable is used as the basis for SNMP naming of
      vsrSvsLCo components.
      These components cannot be added nor deleted."
::= { vsrSvsLCoRowStatusEntry 1 }

vsrSvsLCoComponentName OBJECT-TYPE
   SYNTAX     DisplayString 
   ACCESS     read-only
   STATUS     mandatory
   DESCRIPTION
     "This variable provides the component's string name for
      use with the ASCII Console Interface"
::= { vsrSvsLCoRowStatusEntry 2 }

vsrSvsLCoStorageType OBJECT-TYPE
   SYNTAX     StorageType 
   ACCESS     read-only
   STATUS     mandatory
   DESCRIPTION
     "This variable represents the storage type value for the
      vsrSvsLCo tables."
::= { vsrSvsLCoRowStatusEntry 4 }

vsrSvsLCoIndex OBJECT-TYPE
   SYNTAX     NonReplicated 
   ACCESS     not-accessible
   STATUS     mandatory
   DESCRIPTION
     "This variable represents the index for the vsrSvsLCo tables."
::= { vsrSvsLCoRowStatusEntry 10 }

vsrSvsLCoPathDataTable OBJECT-TYPE
   SYNTAX     SEQUENCE OF VsrSvsLCoPathDataEntry
   ACCESS     not-accessible
   STATUS     mandatory
   DESCRIPTION
     "This group contains all operational attributes for the path oriented 
      LCo."
::= { vsrSvsLCo 10 }

vsrSvsLCoPathDataEntry OBJECT-TYPE
   SYNTAX     VsrSvsLCoPathDataEntry
   ACCESS     not-accessible
   STATUS     mandatory
   DESCRIPTION
     "An entry in the vsrSvsLCoPathDataTable."
   INDEX {
      vsrIndex,
      vsrSvsIndex,
      vsrSvsLCoIndex }
::= { vsrSvsLCoPathDataTable 1 }

VsrSvsLCoPathDataEntry ::= SEQUENCE {
   vsrSvsLCoState
      INTEGER,
   vsrSvsLCoOverrideRemoteName
      AsciiString,
   vsrSvsLCoEnd
      INTEGER,
   vsrSvsLCoCostMetric
      Unsigned32,
   vsrSvsLCoDelayMetric
      Unsigned32,
   vsrSvsLCoRoundTripDelay
      Unsigned32,
   vsrSvsLCoSetupPriority
      Unsigned32,
   vsrSvsLCoHoldingPriority
      Unsigned32,
   vsrSvsLCoRequiredTxBandwidth
      Gauge32,
   vsrSvsLCoRequiredRxBandwidth
      Gauge32,
   vsrSvsLCoRequiredTrafficType
      INTEGER,
   vsrSvsLCoPermittedTrunkTypes
      OCTET STRING,
   vsrSvsLCoRequiredSecurity
      Unsigned32,
   vsrSvsLCoRequiredCustomerParameter
      Unsigned32,
   vsrSvsLCoEmissionPriority
      Unsigned32,
   vsrSvsLCoDiscardPriority
      Unsigned32,
   vsrSvsLCoPathType
      INTEGER,
   vsrSvsLCoRetryCount
      Unsigned32,
   vsrSvsLCoPathFailureCount
      Unsigned32,
   vsrSvsLCoReasonForNoRoute
      INTEGER,
   vsrSvsLCoLastTearDownReason
      INTEGER,
   vsrSvsLCoPathFailureAction
      INTEGER,
   vsrSvsLCoBumpPreference
      INTEGER,
   vsrSvsLCoOptimization
      INTEGER,
   vsrSvsLCoPathUpDateTime
      EnterpriseDateAndTime }

vsrSvsLCoState OBJECT-TYPE
   SYNTAX     INTEGER  {
                 pathDown(0),
                 selectingRoute(1),
                 connecting(2),
                 pathUp(3),
                 pathDownRetrying(4) }
   ACCESS     read-only
   STATUS     mandatory
   DESCRIPTION
     "This attribute reflects the current state of the connection. The 
      pathDown state indicates a connection that has no remote end 
      provisioned or the application has not yet signalled for a path. The 
      selectingRoute state occurs when a request has been sent to route 
      selector and it has not yet responded. The connectingState occurs 
      while a path is being established. The pathUp state is the normal 
      operational state of a path. The pathDownRetrying state indicates a 
      path that attempted route selection but received no route and is now 
      waiting to retry route selection again."
::= { vsrSvsLCoPathDataEntry 1 }

vsrSvsLCoOverrideRemoteName OBJECT-TYPE
   SYNTAX     AsciiString (SIZE (0..40))
   ACCESS     read-write
   STATUS     mandatory
   DESCRIPTION
     "If set and the current PLC remoteName is blank this remoteName 
      will override the blank PLC remoteName. Usually you would set 
      this attribute and then lock/unlock the service component which 
      will result in this new overrideRemoteName being used as if it had 
      been provisioned into the PLC remoteName. The advantage of this 
      attribute is that the connection's remoteName can be changed 
      immediately without having to 'activate prov' but the disadvantage 
      is that the overrideRemoteName is not permanent and if the card or 
      switch is reset the override will be lost."
::= { vsrSvsLCoPathDataEntry 2 }

vsrSvsLCoEnd OBJECT-TYPE
   SYNTAX     INTEGER  {
                 calling(0),
                 called(1) }
   ACCESS     read-only
   STATUS     mandatory
   DESCRIPTION
     "This attribute identifies whether this is the calling or called end of 
      the path."
::= { vsrSvsLCoPathDataEntry 3 }

vsrSvsLCoCostMetric OBJECT-TYPE
   SYNTAX     Unsigned32 (0..65535)
   ACCESS     read-only
   STATUS     mandatory
   DESCRIPTION
     "This attribute gives the route's total cost metric. It is calculated as 
      the sum of the cost metric of all trunks in the path at the time the 
      connection was established. The cost metric of a trunk is defined by 
      the trunkCost attribute of the Trunk component. The costMetric for 
      an LCo that is originated and terminated on the same module is 0."
::= { vsrSvsLCoPathDataEntry 4 }

vsrSvsLCoDelayMetric OBJECT-TYPE
   SYNTAX     Unsigned32 (0..100000)
   ACCESS     read-only
   STATUS     mandatory
   DESCRIPTION
     "This attribute gives the total delay of the route as the one way delay 
      for a 512 byte packet. It is calculated as the sum of the delays of all 
      trunks in the path stored in topology at the time the connection was 
      established. The delay for an LCo that is originated and terminated 
      on the same module is 0."
::= { vsrSvsLCoPathDataEntry 5 }

vsrSvsLCoRoundTripDelay OBJECT-TYPE
   SYNTAX     Unsigned32 (0..200000)
   ACCESS     read-only
   STATUS     mandatory
   DESCRIPTION
     "This attribute contains the time taken for a packet (cell) of 44 bytes 
      to be transmitted to the remote LCo and return to this LCo. The 
      number reported is given in milliseconds to the nearest millisecond. 
      A value of one millisecond is reported if the time is less than 1 
      millisecond even though the delay may be less than 1 Millisecond 
      when the LCo is originated and terminated on the same module."
::= { vsrSvsLCoPathDataEntry 6 }

vsrSvsLCoSetupPriority OBJECT-TYPE
   SYNTAX     Unsigned32 (0..4)
   ACCESS     read-only
   STATUS     mandatory
   DESCRIPTION
     "This attribute gives the priority at which the current path is 
      established. Zero is the highest priority and four is the lowest. The 
      holdingPriority, a complementary attribute of this component, 
      indicates the priority a path maintains once it is established."
::= { vsrSvsLCoPathDataEntry 7 }

vsrSvsLCoHoldingPriority OBJECT-TYPE
   SYNTAX     Unsigned32 (0..4)
   ACCESS     read-only
   STATUS     mandatory
   DESCRIPTION
     "This attribute gives the priority at which a path holds its current 
      path once the path is established. Zero is the highest priority and 
      four is the lowest. The setupPriority, a complementary attribute, 
      indicates the priority of a path at establishment time."
::= { vsrSvsLCoPathDataEntry 8 }

vsrSvsLCoRequiredTxBandwidth OBJECT-TYPE
   SYNTAX     Gauge32 (0..4294967295)
   ACCESS     read-only
   STATUS     mandatory
   DESCRIPTION
     "This attribute gives the actual bandwidth (in bits per second) 
      reserved by this path on each of the trunks of its route. This attribute 
      represents the bandwidth for traffic outgoing to the remote end 
      point. The originating end of the connection determines this value."
::= { vsrSvsLCoPathDataEntry 9 }

vsrSvsLCoRequiredRxBandwidth OBJECT-TYPE
   SYNTAX     Gauge32 (0..4294967295)
   ACCESS     read-only
   STATUS     mandatory
   DESCRIPTION
     "This attribute gives the actual bandwidth (in bits per second) 
      reserved by this path on each of trunks of its route. This attribute 
      represents the bandwidth for traffic incoming from the remote end 
      point. The originating end of the connection determines this value"
::= { vsrSvsLCoPathDataEntry 10 }

vsrSvsLCoRequiredTrafficType OBJECT-TYPE
   SYNTAX     INTEGER  {
                 voice(0),
                 data(1),
                 video(2),
                 trafficType1(3),
                 trafficType2(4),
                 trafficType3(5),
                 trafficType4(6),
                 trafficType5(7) }
   ACCESS     read-only
   STATUS     mandatory
   DESCRIPTION
     "This operational attribute indicates the type of traffic transmitted 
      over the path. There are eight possible traffic types, and the path can 
      transmit only one of them. The originating end of the connection 
      determines the type. These are arbitrary designations for traffic 
      type. The voice, data and video traffic types are defined, and five 
      other arbitrary traffic types can be defined by the network 
      administration. This attribute is used in the route selection process 
      to restrict the route to trunks that support this traffic type. The 
      supportedTrafficType trunk attribute lists all the types of traffic 
      allowed on the trunk. For example, if requiredTrafficType is 
      specified as trafficType1 then only trunks that include trafficType1 
      in supportedTrafficType, will be candidates for this connection."
::= { vsrSvsLCoPathDataEntry 11 }

vsrSvsLCoPermittedTrunkTypes OBJECT-TYPE
   SYNTAX     OCTET STRING (SIZE (1))
   ACCESS     read-only
   STATUS     mandatory
   DESCRIPTION
     "This operational attribute lists up to eight types of trunk that can be 
      used on the route. The originating end of the connection determines 
      the types. The terrestrial and satellite trunk types have been 
      defined, leaving six remaining arbitrary types that can be defined by 
      the network administration. The trunk's type is indicated in the 
      trunkType attribute of the Trunk component. When selecting a 
      route, PORS only chooses trunks whose trunkType are in the 
      permittedTrunkTypes for the path.

      Description of bits:
      terrestrial(0)
      satellite(1)
      trunkType1(2)
      trunkType2(3)
      trunkType3(4)
      trunkType4(5)
      trunkType5(6)
      trunkType6(7)"
::= { vsrSvsLCoPathDataEntry 12 }

vsrSvsLCoRequiredSecurity OBJECT-TYPE
   SYNTAX     Unsigned32 (0..7)
   ACCESS     read-only
   STATUS     mandatory
   DESCRIPTION
     "This attribute indicates the required minimum level of security of 
      the trunks on the route. Zero represents the most secure and seven 
      represents the least secure. The trunk's security is indicated by the 
      trunkSecurity attribute of the Trunk component, and has values 
      identical in range and meaning to the requiredSecurity attribute. 
      PORS ensures that any route selected does not contain a trunk 
      whose trunkSecurity attribute is numerically greater than the 
      requiredSecurity."
::= { vsrSvsLCoPathDataEntry 13 }

vsrSvsLCoRequiredCustomerParameter OBJECT-TYPE
   SYNTAX     Unsigned32 (0..7)
   ACCESS     read-only
   STATUS     mandatory
   DESCRIPTION
     "This attribute indicates the allowed customer defined parameter of 
      the trunks on the route.The originating end of the connection 
      determines the customer defined parameter. Its value, a number 
      from zero to seven, is chosen by a network administration to have a 
      meaning specific to their network, thus allowing them to customize 
      the use of their trunks. A complementary trunk attribute, 
      customerParameter, also has a value from zero to seven. The route 
      selection process does not consider trunks whose 
      customerParameter is greater than the requiredCustomerParameter 
      of the path."
::= { vsrSvsLCoPathDataEntry 14 }

vsrSvsLCoEmissionPriority OBJECT-TYPE
   SYNTAX     Unsigned32 (0..2)
   ACCESS     read-only
   STATUS     mandatory
   DESCRIPTION
     "This attribute indicates the urgency with which packets on the path 
      are emitted by the trunks on the route. The originating end of the 
      connection selects the emissionPriority. EmissionPriority of zero 
      indicates the highest emission priority, while two indicates the 
      lowest emission priority. Packets with a higher emissionPriority (or 
      numerically less) are serviced and sent out before the packets of 
      lower emissionPriority (or numerically higher)."
::= { vsrSvsLCoPathDataEntry 15 }

vsrSvsLCoDiscardPriority OBJECT-TYPE
   SYNTAX     Unsigned32 (1..3)
   ACCESS     read-only
   STATUS     mandatory
   DESCRIPTION
     "This attribute indicates the importance of the packets on the 
      path.The originating end of the connection sets discardPriority. One 
      is used for paths carrying the most important traffic, and three is 
      used for paths carrying the least important traffic. Packets with 
      lower discardPriority(numerically lower) are discarded after 
      packets with a higher discardPriority(numerically higher)."
::= { vsrSvsLCoPathDataEntry 16 }

vsrSvsLCoPathType OBJECT-TYPE
   SYNTAX     INTEGER  {
                 normal(0),
                 manual(1),
                 forced(2) }
   ACCESS     read-only
   STATUS     mandatory
   DESCRIPTION
     "This attribute indicates whether the path for this PLC was 
      determined automatically or by static provisioning. Normal 
      pathTypes are selected automatically by Route Selector.The other 
      pathTypes are both manual pathTypes where the operator must 
      specify, through provisioning, a static route termed the manualPath. 
      A manual pathType connection is nearly identical to a normal path 
      type connection with the exception that the route is pre-provisioned. 
      For a manual pathType, bandwidth reservations are respected along 
      the path exactly as in a normal path. The last type, the forced 
      pathType, is also a manual path but regardless of the bandwidth 
      available the route is granted provided the trunks are operational 
      and there are sufficient Logical Channels (LChs).
      
      The forced pathType could result in over committing the reserved 
      bandwidth allowed on a trunk. A better way to achieve the effects of 
      a forced pathType is to use a manual pathType with setupPriority = 
      0 and holdingPriority = 0. In this manner the path will reserve 
      correct bandwidth and it will bump other paths if required while not 
      being bumped itself."
::= { vsrSvsLCoPathDataEntry 17 }

vsrSvsLCoRetryCount OBJECT-TYPE
   SYNTAX     Unsigned32 (0..255)
   ACCESS     read-only
   STATUS     mandatory
   DESCRIPTION
     "This attribute is the count of the number of times the path chosen 
      during route selection could not be instantiated. This count should 
      be three or below if the network is performing adequately. A high 
      value indicates that the route selection is often performed using an 
      out-of-date view of available network bandwidth and/or topology.
      This attribute will only increase at the calling end of the connection.
      This attribute is reset each time a path reconnects and stops 
      counting when it reaches its maximum value."
::= { vsrSvsLCoPathDataEntry 18 }

vsrSvsLCoPathFailureCount OBJECT-TYPE
   SYNTAX     Unsigned32 (0..65535)
   ACCESS     read-only
   STATUS     mandatory
   DESCRIPTION
     "This attribute is the count of the number of times the path has 
      successfully connected. It is set to zero the first time the path is up. 
      If a path fails anytime after connecting this count will be 
      incremented when the path is up again. Failed route requests do not 
      count in this statistic. See retryCount above. This attribute stops 
      counting at its maximum value."
::= { vsrSvsLCoPathDataEntry 19 }

vsrSvsLCoReasonForNoRoute OBJECT-TYPE
   SYNTAX     INTEGER  {
                 none(0),
                 destinationNameTooLong(1),
                 destinationNotSpecified(2),
                 unknownDestinationName(3),
                 incorrectDestination(4),
                 incorrectDestinationEndPoint(5),
                 unknownSource(6),
                 unknownDestination(7),
                 sameNode(8),
                 routeCostTooMuch(9),
                 routesDelayTooLong(10),
                 attributesNotMet(11),
                 anError(12),
                 attributeProfileProblem(13),
                 manualPathIndexProblem(14) }
   ACCESS     read-only
   STATUS     mandatory
   DESCRIPTION
     "This attribute is the route selection's reasonForNoRoute and 
      provides a brief reason for which a route was not selected. The 
      reasons are essentially self-explanatory. Perhaps two reasons for no 
      route require some explanation. The reason 
      unknownRemoteNodeName is issued when the remote node name 
      is not in the topological database. The reason plcAttributesNotMet 
      is issued when there is no network connectivity at a level specified 
      by the PLC attributes. This reason is also issued when there is no 
      physical connectivity between two end nodes."
   DEFVAL     { none }
::= { vsrSvsLCoPathDataEntry 20 }

vsrSvsLCoLastTearDownReason OBJECT-TYPE
   SYNTAX     INTEGER  {
                 none(0),
                 normalShutDown(1),
                 insufficientTxLcOrBandwidth(2),
                 insufficientRxLcOrBandwidth(3),
                 trunkFailure(4),
                 trunkCardFailure(5),
                 operatorForced(6),
                 lostLcnClash(7),
                 networkCongestion(8),
                 trunkNotFound(9),
                 farEndNotFound(10),
                 wrongModuleReached(11),
                 farEndBusy(12),
                 callLoopedBack(13),
                 unknownReason(14),
                 farEndNotReady(15),
                 remoteNameMismatch(16),
                 serviceTypeMismatch(17),
                 reconnectFromFarEnd(18),
                 bumped(19),
                 accessCardFailure(20),
                 optimized(21),
                 overrideRemoteName(22),
                 trunkOrFarEndDidNotSupportMode(23) }
   ACCESS     read-only
   STATUS     mandatory
   DESCRIPTION
     "This attribute reflects the last tear down reason for a connection 
      (LCo). In many cases this displays the reason for a momentary 
      service interruption. This attribute applies to the last path failure 
      only. If a path is no longer up, this may give an indication to the 
      reason that the path has failed. In many cases an alarm will also be 
      generated with more specific information. The following is a brief 
      description of the reasons:
      none - This path has no information for the teardown this is typical 
      of a path provisioned with no remoteName that has not been up.
      normalShutDown - This path has gone down due to normal call 
      termination.
      insufficientTxLcOrBandwidth - At present there is either no 
      available bandwidth or logical channel numbers available on one or 
      more of the trunks for this path in the transmit direction.
      insufficientRxLcOrBandwidth - At present there is either no 
      available bandwidth or logical channel numbers available on one or 
      more of the trunks for this path in the receive direction.
      trunkFailure- A trunk on the path has failed or has gone down due 
      to a provisioning change of a critical attribute.
      trunkCardFailure- A trunk FP card has failed along the path.
      accessCardFailure- The FP on which the peer access service was 
      running has failed.
      operatorForced- The path has terminated due to the operator 
      locking a trunk along the path.
      lostLcnClash- The path has terminated because the PA's at both 
      ends of an intermediate trunk have allocated the same LC to 
      different calls. When this happens both calls must go down and then 
      try to come up again a fraction of a second later (effectively 
      ensuring that they will now be assigned different LC's). It is normal 
      to get the odd clash especially when the PA's usedLC is 
      approaching the PA's maxLC.
      networkCongestion - The path has failed due to control information 
      being lost and not recoverable.
      trunkNotFound - Occurs on a manual path usually. Check for 
      trunks not up or names provisioned incorrectly.
      farEndNotFound - The far end is not provisioned or is not up. 
      Check remote Name.
      wrongModuleReached - This may occur on a manual path. Check 
      provisioning for correct trunk and service names. For a normal 
      path, the network Topology may be changing check remoteName.
      farEndBusy - The far end has been reached but it is busy. Check 
      remoteName and remote end provisioning.
      callLoopedBack - This LCo is provisioned to call itself. Re-
      provision since this is invalid.
      unknownReason - The failure was not resolved.
      farEndNotReady - The remote end was reached but the connection 
      was refused due to the remote end not being enabled.
      remoteNameMismatch - The remote end has alarmed and rejected 
      this setup due to remoteName provisioning.
      serviceTypeMismatch - The remote Service Type does not match 
      this service type. Check provisioning.
      reconnectFromFarEnd - The remote end re-established this 
      connection. Check the remote end lastTearDownReason to 
      determine the real reason.
      bumped - Another call bumped this path from a trunk to get 
      bandwidth (or an LC) which it required to come up. This other path 
      had a higher setupPriority than this path's holdingPriority hence it 
      was allowed to steal the bandwidth (or LC) from this path.
      optimized - This call has been rerouted due to the optimization 
      feature. The call is still active this just indicates why the path 
      changed.
      trunkOrFarEndDidNotSupportMode - This call was unable to 
      complete because a mode required by the service was not supported 
      by one of the trunks the route went through or by the far end service 
      it connected to. Currently the only mode that this applies to is the 
      map/mux mode on TRUNK PA ATM component. Map mode was 
      required by the application (CES/FrAtm etc.) but was not available 
      on the TRUNK PA ATM component through which the call was 
      routed or the far end CES/FrAtm component did not specify the 
      same mode."
   DEFVAL     { none }
::= { vsrSvsLCoPathDataEntry 21 }

vsrSvsLCoPathFailureAction OBJECT-TYPE
   SYNTAX     INTEGER  {
                 disconnectConnection(0),
                 reRoutePath(1) }
   ACCESS     read-only
   STATUS     mandatory
   DESCRIPTION
     "This attribute displays whether the application is set to tolerate 
      momentary interruption of a path while a new path is selected. If 
      disconnectConnection is displayed, the application is informed as 
      soon as possible about a failure by disconnection. If the attribute 
      displays reRoutePath, the path may attempt an immediate reroute, 
      provided the failure is a recoverable failure. If rerouting fails the 
      application is informed of the failure. 
      With this option set to reRoutePath the LCo may wait up to 30 
      seconds before informing the service of complete disconnection in 
      order to allow both ends to attempt to reconnect. Note that if PLC 
      components are different at both ends only the calling end is 
      allowed to reconnect.
      
      All pathTypes respect this attribute. Also on a manualPath with 
      both ends provisioned with independent paths (at least with respect 
      to the failure) this option will have the desired effect that the path is 
      rerouted without complete disconnection at both ends"
::= { vsrSvsLCoPathDataEntry 22 }

vsrSvsLCoBumpPreference OBJECT-TYPE
   SYNTAX     INTEGER  {
                 bumpWhenNecessary(0),
                 bumpToObtainBestRoute(1) }
   ACCESS     read-only
   STATUS     mandatory
   DESCRIPTION
     "This attribute specifies when bumping will occur during route 
      selection process. Bumping may occur when necessary or always. It 
      will be necessary for a connection to bump if there is not enough 
      resources for the connection to be established and these resources 
      are occupied by a connection whose setupPriority is lower 
      (numerically higher) than the connection's setupPriority. A 
      connection may also always bump in order to obtain the best route."
::= { vsrSvsLCoPathDataEntry 23 }

vsrSvsLCoOptimization OBJECT-TYPE
   SYNTAX     INTEGER  {
                 disabled(0),
                 enabled(1) }
   ACCESS     read-only
   STATUS     mandatory
   DESCRIPTION
     "This attribute is used to specify whether this connection should 
      attempt to optimize its path when requested by the routing PORS 
      component. Every path is as optimal as it can be when it is 
      established, but as network traffic patterns and configurations 
      change this path may no longer be as optimal as it could be. The 
      PORS connection manager on a module requests circuits to 
      optimize at the optimization interval."
::= { vsrSvsLCoPathDataEntry 24 }

vsrSvsLCoPathUpDateTime OBJECT-TYPE
   SYNTAX     EnterpriseDateAndTime (SIZE (0 | 19))
   ACCESS     read-only
   STATUS     mandatory
   DESCRIPTION
     "This is the time stamp when the current path was established or 
      reestablished."
::= { vsrSvsLCoPathDataEntry 25 }

vsrSvsLCoStatsTable OBJECT-TYPE
   SYNTAX     SEQUENCE OF VsrSvsLCoStatsEntry
   ACCESS     not-accessible
   STATUS     mandatory
   DESCRIPTION
     "This group contains the operational statistics attributes for the path 
      oriented LCo."
::= { vsrSvsLCo 11 }

vsrSvsLCoStatsEntry OBJECT-TYPE
   SYNTAX     VsrSvsLCoStatsEntry
   ACCESS     not-accessible
   STATUS     mandatory
   DESCRIPTION
     "An entry in the vsrSvsLCoStatsTable."
   INDEX {
      vsrIndex,
      vsrSvsIndex,
      vsrSvsLCoIndex }
::= { vsrSvsLCoStatsTable 1 }

VsrSvsLCoStatsEntry ::= SEQUENCE {
   vsrSvsLCoPktsToNetwork
      PassportCounter64,
   vsrSvsLCoBytesToNetwork
      PassportCounter64,
   vsrSvsLCoPktsFromNetwork
      PassportCounter64,
   vsrSvsLCoBytesFromNetwork
      PassportCounter64 }

vsrSvsLCoPktsToNetwork OBJECT-TYPE
   SYNTAX     PassportCounter64 
   ACCESS     read-only
   STATUS     mandatory
   DESCRIPTION
     "This attribute counts the number of packets transmitted to the 
      network over this Logical Connection."
::= { vsrSvsLCoStatsEntry 1 }

vsrSvsLCoBytesToNetwork OBJECT-TYPE
   SYNTAX     PassportCounter64 
   ACCESS     read-only
   STATUS     mandatory
   DESCRIPTION
     "This attribute counts the number of bytes sent to the network over 
      this Logical Connection."
::= { vsrSvsLCoStatsEntry 2 }

vsrSvsLCoPktsFromNetwork OBJECT-TYPE
   SYNTAX     PassportCounter64 
   ACCESS     read-only
   STATUS     mandatory
   DESCRIPTION
     "This attribute counts the number of packets received from the 
      remote LCo via the network."
::= { vsrSvsLCoStatsEntry 3 }

vsrSvsLCoBytesFromNetwork OBJECT-TYPE
   SYNTAX     PassportCounter64 
   ACCESS     read-only
   STATUS     mandatory
   DESCRIPTION
     "This attribute counts the number of bytes received from the remote 
      LCo via the network."
::= { vsrSvsLCoStatsEntry 4 }

vsrSvsLCoPathTable OBJECT-TYPE
   SYNTAX     SEQUENCE OF VsrSvsLCoPathEntry
   ACCESS     not-accessible
   STATUS     mandatory
   DESCRIPTION
     "This attribute contains the trunk component names over which the 
      path has been instantiated and the remote end point name 
      terminating the path."
::= { vsrSvsLCo 264 }

vsrSvsLCoPathEntry OBJECT-TYPE
   SYNTAX     VsrSvsLCoPathEntry
   ACCESS     not-accessible
   STATUS     mandatory
   DESCRIPTION
     "An entry in the vsrSvsLCoPathTable."
   INDEX {
      vsrIndex,
      vsrSvsIndex,
      vsrSvsLCoIndex,
      vsrSvsLCoPathValue }
::= { vsrSvsLCoPathTable 1 }

VsrSvsLCoPathEntry ::= SEQUENCE {
   vsrSvsLCoPathValue
      AsciiString }

vsrSvsLCoPathValue OBJECT-TYPE
   SYNTAX     AsciiString (SIZE (0..40))
   ACCESS     read-only
   STATUS     mandatory
   DESCRIPTION
     "This variable represents both the value and the index for the
      vsrSvsLCoPathTable."
::= { vsrSvsLCoPathEntry 1 }


-- Vsr/n Svs/n Debug		
-- The Debug component defines the debug operational characteristics 
-- of the svs component.

vsrSvsDebug OBJECT IDENTIFIER ::= { vsrSvs 4 }



vsrSvsDebugRowStatusTable OBJECT-TYPE
   SYNTAX     SEQUENCE OF VsrSvsDebugRowStatusEntry
   ACCESS     not-accessible
   STATUS     mandatory
   DESCRIPTION
     "This entry controls the addition and deletion of 
      vsrSvsDebug components."
::= { vsrSvsDebug 1 }

vsrSvsDebugRowStatusEntry OBJECT-TYPE
   SYNTAX     VsrSvsDebugRowStatusEntry
   ACCESS     not-accessible
   STATUS     mandatory
   DESCRIPTION
     "A single entry in the table represents a single 
      vsrSvsDebug component."
   INDEX {
      vsrIndex,
      vsrSvsIndex,
      vsrSvsDebugIndex }
::= { vsrSvsDebugRowStatusTable 1 }

VsrSvsDebugRowStatusEntry ::= SEQUENCE {
   vsrSvsDebugRowStatus
      RowStatus,
   vsrSvsDebugComponentName
      DisplayString,
   vsrSvsDebugStorageType
      StorageType,
   vsrSvsDebugIndex
      NonReplicated }

vsrSvsDebugRowStatus OBJECT-TYPE
   SYNTAX     RowStatus 
   ACCESS     read-only
   STATUS     mandatory
   DESCRIPTION
     "This variable is used as the basis for SNMP naming of
      vsrSvsDebug components.
      These components cannot be added nor deleted."
::= { vsrSvsDebugRowStatusEntry 1 }

vsrSvsDebugComponentName OBJECT-TYPE
   SYNTAX     DisplayString 
   ACCESS     read-only
   STATUS     mandatory
   DESCRIPTION
     "This variable provides the component's string name for
      use with the ASCII Console Interface"
::= { vsrSvsDebugRowStatusEntry 2 }

vsrSvsDebugStorageType OBJECT-TYPE
   SYNTAX     StorageType 
   ACCESS     read-only
   STATUS     mandatory
   DESCRIPTION
     "This variable represents the storage type value for the
      vsrSvsDebug tables."
::= { vsrSvsDebugRowStatusEntry 4 }

vsrSvsDebugIndex OBJECT-TYPE
   SYNTAX     NonReplicated 
   ACCESS     not-accessible
   STATUS     mandatory
   DESCRIPTION
     "This variable represents the index for the vsrSvsDebug tables."
::= { vsrSvsDebugRowStatusEntry 10 }


-- Vsr/n Debug		
-- The Debug component defines the debug operational characteristics 
-- of the VoiceSubroute component. There are three main areas of 
-- interest, the VoiceSubroute itself, the call state machines (CSM), 
-- and the call channel manager (CCM).
-- These debug groups can be reached by typing:
-- d Vsr/n debug
-- d Vsr/n debug sr
-- d Vsr/n debug csm
-- d Vsr/n debug ccm

vsrDebug OBJECT IDENTIFIER ::= { vsr 3 }



vsrDebugRowStatusTable OBJECT-TYPE
   SYNTAX     SEQUENCE OF VsrDebugRowStatusEntry
   ACCESS     not-accessible
   STATUS     mandatory
   DESCRIPTION
     "This entry controls the addition and deletion of 
      vsrDebug components."
::= { vsrDebug 1 }

vsrDebugRowStatusEntry OBJECT-TYPE
   SYNTAX     VsrDebugRowStatusEntry
   ACCESS     not-accessible
   STATUS     mandatory
   DESCRIPTION
     "A single entry in the table represents a single 
      vsrDebug component."
   INDEX {
      vsrIndex,
      vsrDebugIndex }
::= { vsrDebugRowStatusTable 1 }

VsrDebugRowStatusEntry ::= SEQUENCE {
   vsrDebugRowStatus
      RowStatus,
   vsrDebugComponentName
      DisplayString,
   vsrDebugStorageType
      StorageType,
   vsrDebugIndex
      NonReplicated }

vsrDebugRowStatus OBJECT-TYPE
   SYNTAX     RowStatus 
   ACCESS     read-only
   STATUS     mandatory
   DESCRIPTION
     "This variable is used as the basis for SNMP naming of
      vsrDebug components.
      These components cannot be added nor deleted."
::= { vsrDebugRowStatusEntry 1 }

vsrDebugComponentName OBJECT-TYPE
   SYNTAX     DisplayString 
   ACCESS     read-only
   STATUS     mandatory
   DESCRIPTION
     "This variable provides the component's string name for
      use with the ASCII Console Interface"
::= { vsrDebugRowStatusEntry 2 }

vsrDebugStorageType OBJECT-TYPE
   SYNTAX     StorageType 
   ACCESS     read-only
   STATUS     mandatory
   DESCRIPTION
     "This variable represents the storage type value for the
      vsrDebug tables."
::= { vsrDebugRowStatusEntry 4 }

vsrDebugIndex OBJECT-TYPE
   SYNTAX     NonReplicated 
   ACCESS     not-accessible
   STATUS     mandatory
   DESCRIPTION
     "This variable represents the index for the vsrDebug tables."
::= { vsrDebugRowStatusEntry 10 }




-- 
-- Version and Compliance statements
-- 



-- Object-Group Statement:
-- A list of all current accessible leaf objects.

-- OBJECTS { vsrVoiceRoute,
--           vsrAdminState,
--           vRouteInterfaceStructuredEchoCancellationValue,
--           vsrSvsFramerVfpDebugStorageType,
--           vsrSvsLCoOptimization,
--           vsrIfAdminStatus,
--           sigChanOperationalState,
--           sigChanICmapNoSuchChannelCause,
--           vsrCustomerIdentifier,
--           vsrSvsLCoLastTearDownReason,
--           sigChanBchVsrInstance,
--           vsrSvsFramerPcmCaptureStorageType,
--           vRouteInterfaceFaxHangoverTimeG711G726,
--           vsrSvsLCoRequiredSecurity,
--           vsrSvsLCoPathFailureCount,
--           vsrSvsFramerModemFaxCells,
--           sigChanGwUnsupportedConversions,
--           vRouteDnaNumberingPlanIndicator,
--           vRouteDiallingPlan2,
--           vsrSvsSnmpOperStatus,
--           sigChanICmapComponentName,
--           vsrInvalidNumberingPlanCalls,
--           sigChanNcasRowStatus,
--           vsrSvsLCoPathFailureAction,
--           vRouteDnaHgmHgAddrNumberingPlanIndicator,
--           sigChanGwRowStatus,
--           vsrSvsLCoHoldingPriority,
--           vsrSvsFramerStorageType,
--           vRouteInterfaceEcanBypassMode,
--           vsrSvsFramerMvpDebugComponentName,
--           vsrSvsLCoEnd,
--           vRouteAcctComponentName,
--           vsrSvsFramerAdminState,
--           vRouteAcctAccountClass,
--           vsrSvsFramerCurrentRate,
--           vRouteAcctAccountingOptions,
--           vsrSvsFramerNEncodingValue,
--           vRouteVoiceNetworkingCallServer,
--           vsrSvsFramerFrmToNetworkValue,
--           vsrSvsFramerFaxIdleCells,
--           vsrSvsRowStatus,
--           vsrSvsLCoPathType,
--           vsrSvsFramerVfpDebugComponentName,
--           sigChanICmapTempFailureCause,
--           vsrActiveTptChannels,
--           vsrPathAttributesNotMetCalls,
--           vsrSvsFramerFrmFromNetworkValue,
--           vsrPeakActiveDataChannels,
--           sigChanBchCalledDirectoryNumber,
--           vsrSvsFramerFrmLostInNetwork,
--           vsrSvsLCoStorageType,
--           vsrSvsCalledNumber,
--           vsrSvsFramerNegotiatedTandemPassThrough,
--           vRouteCommentText,
--           vRouteInterfaceIngressAudioGain,
--           vsrSvsLCoPktsFromNetwork,
--           vRouteInterfaceEchoReturnLoss,
--           vsrSvsFramerNegotiatedFisG711G726,
--           vRouteInterfaceComponentName,
--           vsrSvsLCoRequiredRxBandwidth,
--           vRouteAcctAccountCollection,
--           sigChanNcasDirection,
--           vRouteSubroutesRowStatus,
--           vRouteStorageType,
--           vsrSvsLCoBytesFromNetwork,
--           vRouteDnaHgmStorageType,
--           vRouteInterfaceEgressAudioGain,
--           vsrSvsDebugStorageType,
--           vsrSvsLCoRequiredCustomerParameter,
--           vRouteSubroutesValue,
--           vRouteTotalCallsFromSubnet,
--           vsrSvsFramerMvpDebugStorageType,
--           vRouteCallsClearedNoChannel,
--           vsrTotalFailedCallsFromIf,
--           sigChanBchTimeSlot,
--           vRouteDebugComponentName,
--           vsrSvsFramerMvpDebugRowStatus,
--           vsrComponentName,
--           vsrSvsFramerAudioCells,
--           sigChanICmapIncompatDestCause,
--           sigChanICmapChanOrCircNotAvailCause,
--           vRouteMinimumDigitsToRoute,
--           vsrSignallingChannel,
--           vRouteIfAdminStatus,
--           sigChanBchRowStatus,
--           vRouteInterfaceRowStatus,
--           sigChanCommentText,
--           vRouteCustomerIdentifier,
--           vsrSvsFramerVfpDebugRowStatus,
--           vsrSvsStatus,
--           sigChanGwRequiredConversions,
--           sigChanSubroutesRowStatus,
--           vRouteAcctServiceExchange,
--           vsrActiveChannels,
--           vsrSvsLCoSetupPriority,
--           sigChanNcasCallReference,
--           vsrSvsIfIndex,
--           vsrSvsFramerPcmCaptureComponentName,
--           vRouteDnaHgmAvailableChannels,
--           sigChanSubroutesValue,
--           vsrPeakActiveFaxRelayChannels,
--           sigChanDefaultNpiTon,
--           vsrSnmpOperStatus,
--           vsrIfIndex,
--           sigChanAdminState,
--           vRouteDnaStorageType,
--           vsrSvsLCoRetryCount,
--           sigChanIfAdminStatus,
--           vsrSvsLCoEmissionPriority,
--           vsrSvsFramerComponentName,
--           vsrSvsCallingNumber,
--           sigChanCustomerIdentifier,
--           vsrPeakActiveTptChannels,
--           vsrSvsFramerNegotiatedV17AsG711G726,
--           vRouteDnaHgmHgAddrStorageType,
--           vRouteInterfaceTandemPassThrough,
--           vRouteCallsRejected,
--           vsrSvsLCoDiscardPriority,
--           vsrActiveFaxRelayChannels,
--           vsrActiveVoiceChannels,
--           sigChanNcasStorageType,
--           vRouteDegradedSubroutesValue,
--           sigChanICmapRowStatus,
--           vRouteDebugRowStatus,
--           vsrSvsLCoBumpPreference,
--           sigChanGwStorageType,
--           vsrRowStatus,
--           sigChanICmapSwitchCongestCause,
--           vRouteInterfaceComfortNoiseCap,
--           sigChanICmapResourceUnavailCause,
--           vsrSvsLCoPktsToNetwork,
--           sigChanBchStatus,
--           vsrDebugRowStatus,
--           sigChanOctothorpeEod,
--           vsrUsageState,
--           vsrSvsLCoCostMetric,
--           vsrPathSetupTimeOutCalls,
--           vsrSvsFramerNRatesValue,
--           vRouteDnaHgmUsageDeltaUpdateThreshold,
--           vsrSvsLCoRequiredTxBandwidth,
--           vRouteAdminState,
--           vsrOperationalState,
--           vsrDebugStorageType,
--           vsrSvsFramerPcmCaptureRowStatus,
--           vsrSvsStorageType,
--           vRouteDnaHgmAvailabilityDelta,
--           vRouteDnaRowStatus,
--           vRouteCallsClearedOutOfService,
--           vsrSvsLCoPermittedTrunkTypes,
--           vsrSvsOperationalState,
--           sigChanDegradedSubroutesValue,
--           vRouteComponentName,
--           vsrSvsFramerFaxRelayCells,
--           vRouteDnaHgmComponentName,
--           vsrSvsDebugComponentName,
--           vsrSvsAdminState,
--           vsrSvsFramerTotalCells,
--           vsrSvsFramerRowStatus,
--           vsrActiveModemChannels,
--           sigChanNcasDuration,
--           vsrPeakActiveChannels,
--           vsrSvsIfAdminStatus,
--           vsrSvsUsageState,
--           sigChanComponentName,
--           vsrCallsRejectedByFarEnd,
--           vsrSvsFramerUsageState,
--           vRouteInterfaceEchoTailDelay,
--           sigChanUsageState,
--           vsrSvsLCoDelayMetric,
--           vRouteAcctDigitsSuppressed,
--           vRouteInterfaceSpeechHangoverTime,
--           vsrSvsDebugRowStatus,
--           vsrSvsFramerInterfaceName,
--           vRouteTypeOfRoute,
--           sigChanICmapReqChanOrCircNotAvailCause,
--           vsrSvsLCoComponentName,
--           vRoutePrivateNetworkIdentifer,
--           vRouteHuntingAlgorithm,
--           vsrSvsFramerOperationalState,
--           vsrSvsFramerFrmDumped,
--           vRouteSnmpOperStatus,
--           vsrSvsLCoOverrideRemoteName,
--           vRouteIfIndex,
--           vsrSvsProfileNumber,
--           vRouteDiallingPlan1,
--           vsrSvsFramerOpTptStatus,
--           vRouteOverrideDirectoryNumber,
--           vsrSvsFramerLrcErrors,
--           vRouteAcctStorageType,
--           sigChanBchStorageType,
--           vsrSvsFramerNegotiatedSilenceSuppression,
--           vsrPeakActiveVoiceChannels,
--           vsrSvsLCoPathValue,
--           vRouteDiallingPlan0,
--           vRouteDnaComponentName,
--           vsrSvsLCoState,
--           vsrSvsClearCauseCode,
--           vRouteDnaHgmHgAddrComponentName,
--           sigChanSnmpOperStatus,
--           vRouteRowStatus,
--           vsrSvsTotalCallSeconds,
--           vsrSvsTotalCalls,
--           vRouteDnaHgmRowStatus,
--           vsrSvsCallType,
--           vsrSvsLCoRoundTripDelay,
--           sigChanIfIndex,
--           vRouteDnaHgmMaxAvailableChannels,
--           vsrSvsLCoRequiredTrafficType,
--           sigChanICmapServNotAllowedCause,
--           sigChanNcasComponentName,
--           vRouteUsageState,
--           vsrCallsRejectedLocally,
--           vRouteInterfaceModemFaxSpeechDiscrim,
--           sigChanGwComponentName,
--           sigChanBchComponentName,
--           vRouteInterfaceStorageType,
--           vsrSvsLCoRowStatus,
--           vsrSvsFramerNegotiatedDtmfRegeneration,
--           sigChanICmapEgressLinkOutOfServCause,
--           vRouteOperationalState,
--           vsrCommentText,
--           vsrActiveDataChannels,
--           vRouteDnaDataNetworkAddress,
--           vsrTotalCallsFromIf,
--           vsrPeakActiveModemChannels,
--           vRouteDnaHgmHgAddrRowStatus,
--           vsrAddressIncompleteCalls,
--           sigChanNcasCalledDirectoryNumber,
--           vsrSvsFramerSilenceCells,
--           vRouteAcctRowStatus,
--           vsrSvsLCoPathUpDateTime,
--           sigChanRowStatus,
--           sigChanICmapStorageType,
--           vRouteDebugStorageType,
--           vRouteDnaHgmHgAddrDataNetworkAddress,
--           sigChanGwGatewayCapValue,
--           vsrStorageType,
--           vsrSvsComponentName,
--           vsrSvsLCoReasonForNoRoute,
--           vsrSvsFramerFrmUnderRuns,
--           sigChanForceNpiTon,
--           vsrAddressResolutionFailedCalls,
--           sigChanStorageType,
--           vsrSvsFramerOpCurrentEncoding,
--           vsrSvsLCoBytesToNetwork,
--           vsrDebugComponentName }
-- STATUS  mandatory
-- DESCRIPTION
--   "A list of all current accessible leaf objects."

voiceNetworkingGroup OBJECT IDENTIFIER ::= { voiceNetworkingMIB 1 }
voiceNetworkingGroupBE OBJECT IDENTIFIER ::= { voiceNetworkingGroup 5 }
voiceNetworkingGroupBE01 OBJECT IDENTIFIER ::= { voiceNetworkingGroupBE 2 }
voiceNetworkingGroupBE01A OBJECT IDENTIFIER ::= { voiceNetworkingGroupBE01 2 }



-- Agent-Capabilities Statement:

-- PRODUCT-RELEASE "Passport Release 7.0 VoiceNetworking."
-- STATUS          mandatory
-- DESCRIPTION     "VoiceNetworking MIB: MIB Version BE01A,
--                  Software Version BG00S4C."
-- SUPPORTS        Nortel-Magellan-Passport-VoiceNetworkingMIB
--    INCLUDES     { voiceNetworkingGroupBE01A }

voiceNetworkingCapabilities OBJECT IDENTIFIER ::= { voiceNetworkingMIB 3 }
voiceNetworkingCapabilitiesBE OBJECT IDENTIFIER ::= { voiceNetworkingCapabilities 5 }
voiceNetworkingCapabilitiesBE01 OBJECT IDENTIFIER ::= { voiceNetworkingCapabilitiesBE 2 }
voiceNetworkingCapabilitiesBE01A OBJECT IDENTIFIER ::= { voiceNetworkingCapabilitiesBE01 2 }





END
