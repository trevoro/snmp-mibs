-- automatically generated by mosy 7.1 #1 (elc), do not edit!
-- crmFileBupFileType add (99.3.30 kameishi)
-- crmChangeBand change(99.3.30 kameishi)

CRMMISC-MIB DEFINITIONS ::= BEGIN


IMPORTS
	DisplayString
		FROM RFC1213-MIB
	OBJECT-TYPE
		FROM RFC-1212
	Counter, IpAddress
		FROM RFC1155-SMI
	InterfaceIndex
		FROM IF-MIB
	mib-2, ifIndex
		FROM RFC1213-MIB
	RowStatus, TimeStamp
		FROM SNMPv2-TC;

org OBJECT IDENTIFIER ::= { iso  3 }

dod OBJECT IDENTIFIER ::= { org  6 }

internet OBJECT IDENTIFIER ::= { dod  1 }

private OBJECT IDENTIFIER ::= { internet  4 }

enterprises OBJECT IDENTIFIER ::= { private  1 }

ntt OBJECT IDENTIFIER ::= { enterprises  210 }

mibDoc OBJECT IDENTIFIER ::= { ntt  2 }

ba3000 OBJECT IDENTIFIER ::= { mibDoc  8 }

crmCommon OBJECT IDENTIFIER ::= { ba3000  1 }

-- created from crmMisc (9605221200Z)

crmMisc OBJECT IDENTIFIER ::= { crmCommon  8 }

crmFileBup OBJECT IDENTIFIER ::= { crmMisc  1 }

crmMemCont OBJECT IDENTIFIER ::= { crmMisc  2 }

crmFileRead OBJECT IDENTIFIER ::= { crmMisc  3 }

crmAlmSup OBJECT IDENTIFIER ::= { crmMisc  4 }

crmAddInfo OBJECT IDENTIFIER ::= { crmMisc  5 }

crmPkgMemBranch OBJECT IDENTIFIER ::= { crmMemCont  1 }

crmFileDataBranch OBJECT IDENTIFIER ::= { crmMemCont  2 }

-- Add object
crmChangeBand OBJECT IDENTIFIER ::= { crmMisc  6 }
-- end

crmFileBupTable OBJECT-TYPE
    SYNTAX  SEQUENCE OF CrmFileBupEntry
    ACCESS  not-accessible
    STATUS  mandatory
    DESCRIPTION
           "DUMMY"
    ::= { crmFileBup  1 }

crmFileBupEntry OBJECT-TYPE
    SYNTAX  CrmFileBupEntry
    ACCESS  not-accessible
    STATUS  mandatory
    DESCRIPTION
           "DUMMY"
    INDEX   { crmFileBupFileType,  crmFileBupWriteHd,  crmFileBupWriteMod }
    ::= { crmFileBupTable  1 }

CrmFileBupEntry ::=
    SEQUENCE {
        crmFileBupFileType
            INTEGER,

        crmFileBupWriteHd
            INTEGER,

        crmFileBupWriteMod
            INTEGER,

        crmFileBupStatus
            INTEGER,

        crmFileBupName
            DisplayString
    }

crmFileBupFileType OBJECT-TYPE
    SYNTAX  INTEGER {
    systemFile(1),
    dataFile(2),
    p-mpPathInfo(3),
    dynamicInfo(4),
    fr-lineDlciInfo(5),
    routeInfo(6),
    managePathInfo(7),
    clkInfo(8),
    priContInfo(9),
    callFilterInfo(10),
    atmAdrInfo(11),
    sapInfo(12),
    atmAdrChgInfo(13),
    spvcInfo(14)
}
-- spvcInfo(14)

    ACCESS  not-accessible
    STATUS  mandatory
    DESCRIPTION
           "DUMMY"
    ::= { crmFileBupEntry  1 }

crmFileBupWriteHd OBJECT-TYPE
    SYNTAX  INTEGER {
    system0(1),
    system1(2)
}
    ACCESS  not-accessible
    STATUS  mandatory
    DESCRIPTION
           "DUMMY"
    ::= { crmFileBupEntry  2 }

crmFileBupWriteMod OBJECT-TYPE
    SYNTAX  INTEGER {
    asNewFile(1),
    asOldFile(2)
}
    ACCESS  not-accessible
    STATUS  mandatory
    DESCRIPTION
           "DUMMY"
    ::= { crmFileBupEntry  3 }

crmFileBupStatus OBJECT-TYPE
    SYNTAX  INTEGER {
    writeFile(1),
    normalEnd(2),
    errorEnd(3),
    others(4)
}
    ACCESS  read-write
    STATUS  mandatory
    DESCRIPTION
           "DUMMY"
    DEFVAL {  2  }

    ::= { crmFileBupEntry  4 }

crmFileBupName OBJECT-TYPE
    SYNTAX  DisplayString
    ACCESS  read-only
    STATUS  mandatory
    DESCRIPTION
           "DUMMY"
    ::= { crmFileBupEntry  5 }

crmPkgMemType OBJECT-TYPE
    SYNTAX  INTEGER {
    cpm(1),
    asw(2),
    acm(3),
    ifp(4),
    asws(5)
}
    ACCESS  read-write
    STATUS  mandatory
    DESCRIPTION
           "DUMMY"
    ::= { crmPkgMemBranch  1 }

crmPkgMemShelfIndex OBJECT-TYPE
    SYNTAX  INTEGER
    ACCESS  read-write
    STATUS  mandatory
    DESCRIPTION
           "DUMMY"
    ::= { crmPkgMemBranch  2 }

crmPkgMemPkgIndex OBJECT-TYPE
    SYNTAX  INTEGER
    ACCESS  read-write
    STATUS  mandatory
    DESCRIPTION
           "DUMMY"
    ::= { crmPkgMemBranch  3 }

crmPkgMemProcessorIndex OBJECT-TYPE
    SYNTAX  INTEGER (-2147483648..2147483647)
    ACCESS  read-write
    STATUS  mandatory
    DESCRIPTION
           "DUMMY"
    ::= { crmPkgMemBranch  4 }

crmPkgMemAddress OBJECT-TYPE
    SYNTAX  DisplayString
    ACCESS  read-write
    STATUS  mandatory
    DESCRIPTION
           "DUMMY"
    ::= { crmPkgMemBranch  5 }

crmPkgMemSize OBJECT-TYPE
    SYNTAX  INTEGER
    ACCESS  read-write
    STATUS  mandatory
    DESCRIPTION
           "DUMMY"
    DEFVAL {  0  }

    ::= { crmPkgMemBranch  6 }

crmPkgMemData OBJECT-TYPE
    SYNTAX  DisplayString
    ACCESS  read-write
    STATUS  mandatory
    DESCRIPTION
           "DUMMY"
    ::= { crmPkgMemBranch  7 }

crmFilePathName OBJECT-TYPE
    SYNTAX  DisplayString
    ACCESS  read-write
    STATUS  mandatory
    DESCRIPTION
           "DUMMY"
    ::= { crmFileDataBranch  1 }

crmFileDataAddress OBJECT-TYPE
    SYNTAX  DisplayString
    ACCESS  read-write
    STATUS  mandatory
    DESCRIPTION
           "DUMMY"
    ::= { crmFileDataBranch  2 }

crmFileDataSize OBJECT-TYPE
    SYNTAX  INTEGER
    ACCESS  read-write
    STATUS  mandatory
    DESCRIPTION
           "DUMMY"
    ::= { crmFileDataBranch  3 }

crmFileHdSysNo OBJECT-TYPE
    SYNTAX  INTEGER {
    system0(1),
    system1(2)
}
    ACCESS  read-write
    STATUS  mandatory
    DESCRIPTION
           "DUMMY"
    ::= { crmFileDataBranch  4 }

crmFileData OBJECT-TYPE
    SYNTAX  DisplayString
    ACCESS  read-write
    STATUS  mandatory
    DESCRIPTION
           "DUMMY"
    ::= { crmFileDataBranch  5 }

crmFileReadPathName OBJECT-TYPE
    SYNTAX  DisplayString
    ACCESS  read-write
    STATUS  mandatory
    DESCRIPTION
           "DUMMY"
    ::= { crmFileRead  1 }

crmFileReadStatus OBJECT-TYPE
    SYNTAX  INTEGER {
    readFile(1),
    normalEnd(2),
    errorEnd(3),
    others(4)
}
    ACCESS  read-write
    STATUS  mandatory
    DESCRIPTION
           "DUMMY"
    ::= { crmFileRead  2 }

crmAlmSupIfTable OBJECT-TYPE
    SYNTAX  SEQUENCE OF CrmAlmSupIfEntry
    ACCESS  not-accessible
    STATUS  mandatory
    DESCRIPTION
           "DUMMY"
    ::= { crmAlmSup  1 }

crmAlmSupIfEntry OBJECT-TYPE
    SYNTAX  CrmAlmSupIfEntry
    ACCESS  not-accessible
    STATUS  mandatory
    DESCRIPTION
           "DUMMY"
    INDEX   { crmAlmSupIfIndex }
    ::= { crmAlmSupIfTable  1 }

CrmAlmSupIfEntry ::=
    SEQUENCE {
        crmAlmSupIfIndex
            InterfaceIndex,

        crmAlmSupIfAdminStatus
            INTEGER,

        crmAlmSupIfOperStatus
            INTEGER
    }

crmAlmSupIfIndex OBJECT-TYPE
    SYNTAX  InterfaceIndex
    ACCESS  not-accessible
    STATUS  mandatory
    DESCRIPTION
           "DUMMY"
    ::= { crmAlmSupIfEntry  1 }

crmAlmSupIfAdminStatus OBJECT-TYPE
    SYNTAX  INTEGER {
    up(1),
    down(2)
}
    ACCESS  read-write
    STATUS  mandatory
    DESCRIPTION
           "DUMMY"
    ::= { crmAlmSupIfEntry  2 }

crmAlmSupIfOperStatus OBJECT-TYPE
    SYNTAX  INTEGER {
    up(1),
    down(2),
    other(3)
}
    ACCESS  read-only
    STATUS  mandatory
    DESCRIPTION
           "DUMMY"
    ::= { crmAlmSupIfEntry  3 }

crmAlmSupIfPkgTable OBJECT-TYPE
    SYNTAX  SEQUENCE OF CrmAlmSupIfPkgEntry
    ACCESS  not-accessible
    STATUS  mandatory
    DESCRIPTION
           "DUMMY"
    ::= { crmAlmSup  2 }

crmAlmSupIfPkgEntry OBJECT-TYPE
    SYNTAX  CrmAlmSupIfPkgEntry
    ACCESS  not-accessible
    STATUS  mandatory
    DESCRIPTION
           "DUMMY"
    INDEX   { crmAlmSupIfPkgShelfNumber,  crmAlmSupIfPkgIndex }
    ::= { crmAlmSupIfPkgTable  1 }

CrmAlmSupIfPkgEntry ::=
    SEQUENCE {
        crmAlmSupIfPkgShelfNumber
            INTEGER,

        crmAlmSupIfPkgIndex
            INTEGER,

        crmAlmSupIfPkgAdminStatus
            INTEGER,

        crmAlmSupIfPkgOperStatus
            INTEGER
    }

crmAlmSupIfPkgShelfNumber OBJECT-TYPE
    SYNTAX  INTEGER
    ACCESS  not-accessible
    STATUS  mandatory
    DESCRIPTION
           "DUMMY"
    ::= { crmAlmSupIfPkgEntry  1 }

crmAlmSupIfPkgIndex OBJECT-TYPE
    SYNTAX  INTEGER
    ACCESS  not-accessible
    STATUS  mandatory
    DESCRIPTION
           "DUMMY"
    ::= { crmAlmSupIfPkgEntry  2 }

crmAlmSupIfPkgAdminStatus OBJECT-TYPE
    SYNTAX  INTEGER {
    up(1),
    down(2)
}
    ACCESS  read-write
    STATUS  mandatory
    DESCRIPTION
           "DUMMY"
    ::= { crmAlmSupIfPkgEntry  3 }

crmAlmSupIfPkgOperStatus OBJECT-TYPE
    SYNTAX  INTEGER {
    up(1),
    down(2),
    other(3)
}
    ACCESS  read-only
    STATUS  mandatory
    DESCRIPTION
           "DUMMY"
    ::= { crmAlmSupIfPkgEntry  4 }

crmAlmSupSwPkgAdminStatus OBJECT-TYPE
    SYNTAX  INTEGER {
    up(1),
    down(2)
}
    ACCESS  read-write
    STATUS  mandatory
    DESCRIPTION
           "DUMMY"
    ::= { crmAlmSup  3 }

crmAlmSupSwPkgOperStatus OBJECT-TYPE
    SYNTAX  INTEGER {
    up(1),
    down(2),
    other(3)
}
    ACCESS  read-only
    STATUS  mandatory
    DESCRIPTION
           "DUMMY"
    ::= { crmAlmSup  4 }

crmAddInfoData1 OBJECT-TYPE
    SYNTAX  INTEGER (-2147483648..2147483647)
    ACCESS  read-only
    STATUS  mandatory
    DESCRIPTION
           "DUMMY"
    ::= { crmAddInfo  1 }

crmAddInfoDebugData1 OBJECT-TYPE
    SYNTAX  INTEGER (-2147483648..2147483647)
    ACCESS  read-write
    STATUS  mandatory
    DESCRIPTION
           "DUMMY"
    ::= { crmAddInfo  2 }

crmAddInfoDebugData2 OBJECT-TYPE
    SYNTAX  INTEGER (-2147483648..2147483647)
    ACCESS  read-write
    STATUS  mandatory
    DESCRIPTION
           "DUMMY"
    ::= { crmAddInfo  3 }

crmAddInfoDebugData3 OBJECT-TYPE
    SYNTAX  INTEGER (-2147483648..2147483647)
    ACCESS  read-write
    STATUS  mandatory
    DESCRIPTION
           "DUMMY"
    ::= { crmAddInfo  4 }

crmAddInfoDebugData4 OBJECT-TYPE
    SYNTAX  INTEGER (-2147483648..2147483647)
    ACCESS  read-write
    STATUS  mandatory
    DESCRIPTION
           "DUMMY"
    ::= { crmAddInfo  5 }

crmAddInfoDebugData5 OBJECT-TYPE
    SYNTAX  INTEGER (-2147483648..2147483647)
    ACCESS  read-write
    STATUS  mandatory
    DESCRIPTION
           "DUMMY"
    ::= { crmAddInfo  6 }

crmAddInfoDebugData6 OBJECT-TYPE
    SYNTAX  INTEGER (-2147483648..2147483647)
    ACCESS  read-write
    STATUS  mandatory
    DESCRIPTION
           "DUMMY"
    ::= { crmAddInfo  7 }

crmAddInfoDebugData7 OBJECT-TYPE
    SYNTAX  INTEGER (-2147483648..2147483647)
    ACCESS  read-write
    STATUS  mandatory
    DESCRIPTION
           "DUMMY"
    ::= { crmAddInfo  8 }

crmAddInfoDebugData8 OBJECT-TYPE
    SYNTAX  INTEGER (-2147483648..2147483647)
    ACCESS  read-write
    STATUS  mandatory
    DESCRIPTION
           "DUMMY"
    ::= { crmAddInfo  9 }

crmAddInfoDebugData9 OBJECT-TYPE
    SYNTAX  INTEGER (-2147483648..2147483647)
    ACCESS  read-write
    STATUS  mandatory
    DESCRIPTION
           "DUMMY"
    ::= { crmAddInfo  10 }

crmAddInfoDebugData10 OBJECT-TYPE
    SYNTAX  INTEGER (-2147483648..2147483647)
    ACCESS  read-write
    STATUS  mandatory
    DESCRIPTION
           "DUMMY"
    ::= { crmAddInfo  11 }

-- Add object

crmChangeBandIfIndex OBJECT-TYPE
    SYNTAX  INTEGER (-2147483648..2147483647)
    ACCESS  read-write
    STATUS  mandatory
    DESCRIPTION
           "DUMMY"
    ::= { crmChangeBand  1 }

crmChangeBandMaxSpeed OBJECT-TYPE
    SYNTAX  INTEGER (-2147483648..2147483647)
    ACCESS  read-write
    STATUS  mandatory
    DESCRIPTION
           "DUMMY"
    ::= { crmChangeBand  2 }

crmChangeBandStatus OBJECT-TYPE
    SYNTAX  INTEGER (-2147483648..2147483647)
    ACCESS  read-write
    STATUS  mandatory
    DESCRIPTION
           "DUMMY"
    ::= { crmChangeBand  3 }

-- end

END
