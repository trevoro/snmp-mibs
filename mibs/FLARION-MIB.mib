-- $Id: FLARION-MIB.txt,v 1.12 2004/08/11 21:10:48 phsu Exp $



FLARION-MIB DEFINITIONS ::= BEGIN

IMPORTS
        MODULE-IDENTITY, OBJECT-TYPE, NOTIFICATION-TYPE,
        IpAddress, TimeTicks, Unsigned32, Counter32
                FROM SNMPv2-SMI

        enterprises
                FROM RFC1155-SMI

        DisplayString, RowStatus, DateAndTime, TruthValue
                FROM SNMPv2-TC;

-- Flarion BaseStation 
flarion         MODULE-IDENTITY
        LAST-UPDATED    "200310291037Z"
        ORGANIZATION    "Flarion Technologies"
        CONTACT-INFO    "Flarion Technologies, Inc.
                        135 Route 202/206 South
                        Bedminster, NJ 07921"
        DESCRIPTION     "The MIB module for managing Flarion products."
        ::= { enterprises 8603 } 

mibs                    OBJECT IDENTIFIER ::= { flarion 1 }
oem                     OBJECT IDENTIFIER ::= { flarion 3 }
rrCommonMib             OBJECT IDENTIFIER ::= { mibs 1 }
rrMib                   OBJECT IDENTIFIER ::= { mibs 2 }


-- administrative state
AdminState ::= INTEGER {
    up(1),
    down(2),
    reset(3)
}
        
-- maintenance state enumeration
MaintState ::= INTEGER {
    unknown(0),
    active(1),
    activeCampOn(2),
    activeAlarm(3),
    outOfService(4),
    maintenance(5),
    standby(6),
    dspInit(7),
    pendingDisable(8)
}


-- BBU state
BbuState ::= INTEGER {
    null(0),
    active(1),
    disabled(2),
    standby(3),
    unknown(4),
    pendActiveStandby(5),
    disabledStandby(6),
    outOfService(7),
    nonOperational(8),
    notAvailable(9)
}


-- event type
EventType ::= INTEGER {
    communication(1),
    qualityOfService(2),
    processingError(3),
    equipment(4),
    environment(5)
}

-- alarm severity
AlarmSeverity ::= INTEGER {
    indeterminate(0),
    cleared(1),
    warning(2),
    minor(3),
    major(4),
    critical(5)
}

-- probable cause
ProbableCause ::= INTEGER {
    adapterError(1),
    applicationSubsystemFailure(2),
    bandwidthReduced(3),
    callEstablishmentError(4),
    communicationsProtocolError(5),
    communicationsSubsystemFailure(6),
    configurationOrCustomizationError(7),
    congestion(8),
    corruptData(9),
    cpuCyclesLimitExceeded(10),
    datasetOrModemError(11),
    degradedSignal(12),
    enclosureDoorOpen(13),
    equipmentMalfunction(14),
    fileError(15),
    framingError(16),
    heatingOrVentilationOrCoolingSystemProblem(17),
    inputOutputDeviceError(18),
    inputDeviceError(19),
    lanError(20),
    localNodeTransmissionError(21),
    lossOfFrame(22),
    lossOfSignal(23),
    outOfMemory(24),
    outputDeviceError(25),
    performanceDegraded(26),
    powerProblem(27),
    processorProblem(28),
    queueSizeExceeded(29),
    receiveFailure(30),
    receiverFailure(31),
    remoteNodeTransmissionError(32),
    resourceAtOrNearingCapacity(33),
    responseTimeExcessive(34),
    retransmissionRateExcessive(35),
    softwareError(36),
    softwareProgramAbnormallyTerminated(37),
    softwareProgramError(38),
    storageCapacityProblem(39),
    temperatureUnacceptable(40),
    thresholdCrossed(41),
    timingProblem(42),
    transmitFailure(43),
    transmitterFailure(44),
    underlyingResourceUnavailable(45),
    userDefinedAlarm(46),
    versionMismatch(47)
}


-- arbitrary data may be encoded in an AddtlInfo octet string
-- The size of AddtlInfo must be subjected to the maximum size
-- of the UDP packet data size.
AddtlInfo ::= OCTET STRING (SIZE(0..1024))

-- Physical Hardware Address (EUI-64)
HwAddress ::= OCTET STRING (SIZE(8))
MobileEui ::= OCTET STRING (SIZE(8))

-- Command Identifiers
CommandID ::= INTEGER {
    enable(1),
    disable(2),
    reset(8)
}

-- Managed Object Types
-- (values 9,10,11 intentionally left out)
MoType ::= INTEGER {
    mainController(1),
    baseBandUnit(2),
    rfUnit(3),
    dsp(4),
    mobile(5),
    software(6),
    powerAmp(7),
    backhaul(8),
    rxUnit(12),
    txUnit(13),
    alarmInterfaceUnit(14),
    powerControlUnit(15),
    alarmInput(16),
    relay(17),
    lowNoiseAmplifier(18),
    cabinet(19),
    powerAmpShelf(20),
    radioRouterShelf(21),
    rectifier(22),
    mlppp(23)
}


-- Log Levels
LogLevel ::= INTEGER {
    logEmerg(0),
    logAlert(1),
    logCrit(2),
    logErr(3),
    logWarning(4),
    logNotice(5),
    logInfo(6),
    logDebug(7)
}


-- download state
DownloadState ::= INTEGER {
    unknown(0),
    idle(1),
    inProgress(2),
    success(3),
    failed(4)
}


-- System action
SysAction ::= INTEGER {
    restart(1),
    reboot(2)
}


-- OS upgrade type
OsUpgradeType ::= INTEGER {
    binary(1),
    standard(2)
}


-- Media type
MediaType ::= INTEGER {
    mediaUnknown(0),
    mediaHdd(1),
    mediaFlashDrive(2)
}


-- Route Protocol
RouteProtocol ::= INTEGER {
    rtProtocolNone(0),
    rtProtocolRIPv2(1)
}


-- Route Handling
RouteHandling ::= INTEGER {
    rtHandlingNoSuperNetSupport(0),
    rtHandlingReject(1),
    rtHandlingBlackhole(2)
}


-- Floating point value expressed as a string
FloatAsString ::= DisplayString

-- Floating point value expressed as an integer. This value is computed
-- by taking the floating point value and multiplying by 100, then converting
-- the value to an integer.
FloatAsInt ::= INTEGER


-- Pass/Fail
PassFail ::= INTEGER {
    pass(1),
    fail(2)
}


-- On/Off State
OnOffState ::= INTEGER {
    on(1),
    off(2)
}

--
-- The trapDefinition & traps groups should be supported
-- in all Flarion agents.
--
rrTrapVars          OBJECT IDENTIFIER ::= { rrCommonMib 1 }
rrTraps             OBJECT IDENTIFIER ::= { rrCommonMib 2 }
rrTrapConfig        OBJECT IDENTIFIER ::= { rrCommonMib 4 }
rrTrapHistory       OBJECT IDENTIFIER ::= { rrCommonMib 5 }

--
-- rrTrapVars
--
rrTimeStamp         OBJECT-TYPE
    SYNTAX          TimeTicks
    MAX-ACCESS      read-only
    STATUS          current
    DESCRIPTION     "The time at which the event was generated.
                     This value is expressed in seconds since
                     00:00:00 UTC, January 1, 1970 (see time(2))."
    ::= { rrTrapVars 1 }

rrSeqNum            OBJECT-TYPE
    SYNTAX          INTEGER
    MAX-ACCESS      read-only
    STATUS          current
    DESCRIPTION     "The event sequence number."
    ::= { rrTrapVars 2 }

rrSeverity          OBJECT-TYPE
    SYNTAX          AlarmSeverity
    MAX-ACCESS      read-only
    STATUS          current
    DESCRIPTION     "The event severity."
    ::= { rrTrapVars 3 }

rrMoType            OBJECT-TYPE
    SYNTAX          MoType
    MAX-ACCESS      read-only
    STATUS          current
    DESCRIPTION     "Type managed object associated with this trap."
    ::= { rrTrapVars 4 }

rrMoId              OBJECT-TYPE
    SYNTAX          INTEGER (0..65535)
    MAX-ACCESS      read-only
    STATUS          current
    DESCRIPTION     "The instance of the managed object logical identifier."
    ::= { rrTrapVars 5 }

rrAddtlInfo         OBJECT-TYPE
    SYNTAX          AddtlInfo
    MAX-ACCESS      read-only
    STATUS          current
    DESCRIPTION     "Event description."
    ::= { rrTrapVars 6 }



--
-- Flarion Basestation MIB Groups
--
rrManagedObjs           OBJECT IDENTIFIER ::= { rrMib 1 }
rrAlarms                OBJECT IDENTIFIER ::= { rrMib 10 }

--
-- Management Objects
--
rrBaseStation           OBJECT IDENTIFIER ::= { rrManagedObjs 1 }
rrBaseBandUnit          OBJECT IDENTIFIER ::= { rrManagedObjs 2 }
rrMobile                OBJECT IDENTIFIER ::= { rrManagedObjs 4 }
rrBackHaulUnit          OBJECT IDENTIFIER ::= { rrManagedObjs 5 }
rrSector                OBJECT IDENTIFIER ::= { rrManagedObjs 10 }


--
-- Base Station
--
rrBsInfo                OBJECT IDENTIFIER ::= { rrBaseStation 1 }
rrForeignAgent          OBJECT IDENTIFIER ::= { rrBaseStation 2 }
rrPaging                OBJECT IDENTIFIER ::= { rrBaseStation 4 }
rrNtp                   OBJECT IDENTIFIER ::= { rrBaseStation 5 }
rrDhcp                  OBJECT IDENTIFIER ::= { rrBaseStation 8 }
rrAuthServer            OBJECT IDENTIFIER ::= { rrBaseStation 9 }
rrAccountingServer      OBJECT IDENTIFIER ::= { rrBaseStation 10 }
rrRelease               OBJECT IDENTIFIER ::= { rrBaseStation 12 }
rrDns                   OBJECT IDENTIFIER ::= { rrBaseStation 13 }
rrRoutes                OBJECT IDENTIFIER ::= { rrBaseStation 14 }
rrUserGroups            OBJECT IDENTIFIER ::= { rrBaseStation 15 }
rrCtCore                OBJECT IDENTIFIER ::= { rrBaseStation 16 }
rrL2AdmissionCtrl       OBJECT IDENTIFIER ::= { rrBaseStation 17 }
rrUpgrade               OBJECT IDENTIFIER ::= { rrBaseStation 18 }
rrIgmp                  OBJECT IDENTIFIER ::= { rrBaseStation 19 }
rrBhQos                 OBJECT IDENTIFIER ::= { rrBaseStation 20 }


rrBsAlarmState          OBJECT-TYPE
        SYNTAX          AlarmSeverity
        MAX-ACCESS      read-only
        STATUS          deprecated
        DESCRIPTION     "Base station current highest alarm severity."
        ::= { rrBsInfo 1 }

rrBsMaintState          OBJECT-TYPE  
        SYNTAX          MaintState
        MAX-ACCESS      read-only
        STATUS          deprecated
        DESCRIPTION     "Base station maintance State."   
        ::= { rrBsInfo 2 }

rrBsVersion             OBJECT-TYPE
        SYNTAX          DisplayString
        MAX-ACCESS      read-only
        STATUS          current
        DESCRIPTION     "Base station software image version."
        ::= { rrBsInfo 3 }

rrBsMibVersion          OBJECT-TYPE
        SYNTAX          DisplayString
        MAX-ACCESS      read-only
        STATUS          current
        DESCRIPTION     "The current Flarion MIB version."
        ::= { rrBsInfo 7 }

rrBsDbAuditResult       OBJECT-TYPE
        SYNTAX          PassFail
        MAX-ACCESS      read-only
        STATUS          current
        DESCRIPTION     "The result of the basestation database audit."
        ::= { rrBsInfo 8 }

-- SNMP Access Control List
aclTable                OBJECT-TYPE
        SYNTAX          SEQUENCE OF AclEntry
        MAX-ACCESS      not-accessible
        STATUS          current
        DESCRIPTION     "This table is used to configure the SNMP access
                        control list."
        ::= { rrBsInfo 9 }

aclEntry                OBJECT-TYPE
        SYNTAX          AclEntry
        MAX-ACCESS      not-accessible
        STATUS          current
        DESCRIPTION     ""
        INDEX           { aclIndex }
        ::= { aclTable 1 }

AclEntry ::= SEQUENCE {
        aclIndex    INTEGER,
        aclAddress  DisplayString,
        aclStatus   RowStatus
}

aclIndex                OBJECT-TYPE
        SYNTAX          INTEGER
        MAX-ACCESS      read-only
        STATUS          current
        DESCRIPTION     "The table index value."
        ::= { aclEntry 1 }

aclAddress              OBJECT-TYPE
        SYNTAX          DisplayString
        MAX-ACCESS      read-write
        STATUS          current
        DESCRIPTION     "A get on this object returns the ACL address. A new
                        ACL address can be added by first creating a conceptual
                        row by setting aclStatus to createAndWait(5). Then set
                        this object with the ACL address value. Finally,
                        commit the value by setting aclStatus to active(1)."
        ::= { aclEntry 2 }

aclStatus               OBJECT-TYPE
        SYNTAX          RowStatus
        MAX-ACCESS      read-create
        STATUS          current
        DESCRIPTION     "This object is used to change the state of a
                        conceptual row. Only active(1), createAndWait(5), and
                        destroy(6) are supported."
        ::= { aclEntry 3 }

-- Scratchpad for miscellaneous notes
scratchPadTable         OBJECT-TYPE
        SYNTAX          SEQUENCE OF ScratchPadEntry
        MAX-ACCESS      not-accessible
        STATUS          current
        DESCRIPTION     "This table is used to enter miscellaneous notes ."
        ::= { rrBsInfo 10 }

scratchPadEntry         OBJECT-TYPE
        SYNTAX          ScratchPadEntry
        MAX-ACCESS      not-accessible
        STATUS          current
        DESCRIPTION     ""
        INDEX           { scratchPadIndex }
        ::= { scratchPadTable 1 }

ScratchPadEntry ::= SEQUENCE {
        scratchPadIndex     INTEGER,
        scratchPadNote      DisplayString,
        scratchPadStatus    RowStatus
}

scratchPadIndex         OBJECT-TYPE
        SYNTAX          INTEGER
        MAX-ACCESS      read-only
        STATUS          current
        DESCRIPTION     "The table index value."
        ::= { scratchPadEntry 1 }

scratchPadNote          OBJECT-TYPE
        SYNTAX          DisplayString
        MAX-ACCESS      read-write
        STATUS          current
        DESCRIPTION     "A get on this object returns the scratch pad note.
                        A new note can be added by first setting
                        scratchPadStatus to createAndWait(5) to create the
                        conceptual row. Then set this object with the new value.
                        Finally, commit the value by setting scratchPadStatus
                        to active(1)."
        ::= { scratchPadEntry 2 }

scratchPadStatus        OBJECT-TYPE
        SYNTAX          RowStatus
        MAX-ACCESS      read-create
        STATUS          current
        DESCRIPTION     "This object is used to change the state of a
                        conceptual row. Only active(1), createAndWait(5), and
                        destroy(6) are supported."
        ::= { scratchPadEntry 3 }


--
-- Foreign Agent
--
faProv                  OBJECT IDENTIFIER ::= { rrForeignAgent 1 }
faStats                 OBJECT IDENTIFIER ::= { rrForeignAgent 2 }

faTosVal                OBJECT-TYPE
        SYNTAX          INTEGER (0..255)
        MAX-ACCESS      read-write
        STATUS          deprecated
        DESCRIPTION     "Mobile IP Type of Service value (refer to RFC 791)."
        DEFVAL          { 188 }
        ::= { faProv 2 }

faMipLifetime           OBJECT-TYPE
        SYNTAX          INTEGER
        MAX-ACCESS      read-write
        STATUS          current
        DESCRIPTION     "Maximum lifetime advertised for this FA. The lifetime
                        is defined in seconds, default value is 400. The
                        request timer will be limited with this value.
                        Special case: 65535 (or more) seconds mean unlimited
                        time (the binding will not expire)."
        DEFVAL          { 3600 }
        ::= { faProv 3 }

faTunnelLifetime        OBJECT-TYPE
        SYNTAX          INTEGER
        MAX-ACCESS      read-write
        STATUS          current
        DESCRIPTION     "Lifetime of the temporary home entry (tunnel), in
                        seconds."
        DEFVAL          { 5 }
        ::= { faProv 4 }

faRrepRt                OBJECT-TYPE
        SYNTAX          INTEGER
        MAX-ACCESS      read-write
        STATUS          current
        DESCRIPTION     "Time to wait for RREP after sending a RREQ, in msec."
        DEFVAL          { 1500 }
        ::= { faProv 5 }

faOutgoingTimer         OBJECT-TYPE
        SYNTAX          INTEGER
        MAX-ACCESS      read-write
        STATUS          current
        DESCRIPTION     "Outgoing handoff time, in msec."
        DEFVAL          { 10000 }
        ::= { faProv 6 }

faRegistrationTimer     OBJECT-TYPE
        SYNTAX          INTEGER
        MAX-ACCESS      read-write
        STATUS          current
        DESCRIPTION     "Amount of time a mobile has to register, in msec."
        DEFVAL          { 2000 }
        ::= { faProv 8 }

faMbbSupport            OBJECT-TYPE
        SYNTAX          TruthValue
        MAX-ACCESS      read-write
        STATUS          current
        DESCRIPTION     "Make-Before-Break handoff support. When enabled,
                        during a handoff, the old Foreign Agent waits until the
                        airlink to the mobile drops before it uses the temporary                        tunnel between FA's."
        DEFVAL          { false }
        ::= { faProv 11 }

faTrashLogLevel         OBJECT-TYPE
        SYNTAX          LogLevel
        MAX-ACCESS      read-write
        STATUS          current
        DESCRIPTION     "Trash logs above specified level. The higher the level,
                        the more logs generated by the Foreign Agent."
        DEFVAL          { logDebug }
        ::= { faProv 12 }

faMipDscp               OBJECT-TYPE
        SYNTAX          INTEGER (0..63)
        MAX-ACCESS      read-write
        STATUS          current
        DESCRIPTION     "Mobile IP Diffserv codepoint."
        DEFVAL          { 47 }
        ::= { faProv 13 }


--
-- Foreign Agent Statistics
--
faIcmp                  OBJECT IDENTIFIER ::= { faStats 2 }
faMipReg                OBJECT IDENTIFIER ::= { faStats 3 }
faExtensions            OBJECT IDENTIFIER ::= { faStats 4 }
faRouteOptimization     OBJECT IDENTIFIER ::= { faStats 5 }

faNumMobilesServed              OBJECT-TYPE
        SYNTAX                  INTEGER
        MAX-ACCESS              read-only
        STATUS                  current
        DESCRIPTION             ""
        ::= { faStats 1 }

faFaaSent                       OBJECT-TYPE
        SYNTAX                  INTEGER
        MAX-ACCESS              read-only
        STATUS                  current
        DESCRIPTION             ""
        ::= { faIcmp 1 }

faFaaResponseAs                 OBJECT-TYPE
        SYNTAX                  INTEGER
        MAX-ACCESS              read-only
        STATUS                  current
        DESCRIPTION             ""
        ::= { faIcmp 2 }

faAsRecvd                       OBJECT-TYPE
        SYNTAX                  INTEGER
        MAX-ACCESS              read-only
        STATUS                  current
        DESCRIPTION             ""
        ::= { faIcmp 3 }

faRreqRecvd                     OBJECT-TYPE
        SYNTAX                  INTEGER
        MAX-ACCESS              read-only
        STATUS                  current
        DESCRIPTION             ""
        ::= { faMipReg 1 }

faRreqRelayed                   OBJECT-TYPE
        SYNTAX                  INTEGER
        MAX-ACCESS              read-only
        STATUS                  current
        DESCRIPTION             ""
        ::= { faMipReg 2 }

faRreqDeniedUnspec              OBJECT-TYPE
        SYNTAX                  INTEGER
        MAX-ACCESS              read-only
        STATUS                  current
        DESCRIPTION             ""
        ::= { faMipReg 3 }

faRreqDeniedAdminProhib         OBJECT-TYPE
        SYNTAX                  INTEGER
        MAX-ACCESS              read-only
        STATUS                  current
        DESCRIPTION             ""
        ::= { faMipReg 4 }

faRreqDeniedNoResource          OBJECT-TYPE
        SYNTAX                  INTEGER
        MAX-ACCESS              read-only
        STATUS                  current
        DESCRIPTION             ""
        ::= { faMipReg 5 }

faRreqDeniedFailAuth            OBJECT-TYPE
        SYNTAX                  INTEGER
        MAX-ACCESS              read-only
        STATUS                  current
        DESCRIPTION             ""
        ::= { faMipReg 6 }

faRreqDeniedLifeTooLong         OBJECT-TYPE
        SYNTAX                  INTEGER
        MAX-ACCESS              read-only
        STATUS                  current
        DESCRIPTION             ""
        ::= { faMipReg 7 }

faRreqDeniedPoorlyFormed        OBJECT-TYPE
        SYNTAX                  INTEGER
        MAX-ACCESS              read-only
        STATUS                  current
        DESCRIPTION             ""
        ::= { faMipReg 8 }

faRreqDeniedEncapUnavail        OBJECT-TYPE
        SYNTAX                  INTEGER
        MAX-ACCESS              read-only
        STATUS                  current
        DESCRIPTION             ""
        ::= { faMipReg 9 }

faRreqDeniedHaUnreach           OBJECT-TYPE
        SYNTAX                  INTEGER
        MAX-ACCESS              read-only
        STATUS                  current
        DESCRIPTION             ""
        ::= { faMipReg 10 }

faRreqDeniedMissingNai          OBJECT-TYPE
        SYNTAX                  INTEGER
        MAX-ACCESS              read-only
        STATUS                  current
        DESCRIPTION             ""
        ::= { faMipReg 11 }

faRreqDeniedMissingChal         OBJECT-TYPE
        SYNTAX                  INTEGER
        MAX-ACCESS              read-only
        STATUS                  current
        DESCRIPTION             ""
        ::= { faMipReg 12 }

faRreqDeniedUnknownChal         OBJECT-TYPE
        SYNTAX                  INTEGER
        MAX-ACCESS              read-only
        STATUS                  current
        DESCRIPTION             ""
        ::= { faMipReg 13 }

faRreqDeniedInvalidCoa          OBJECT-TYPE
        SYNTAX                  INTEGER
        MAX-ACCESS              read-only
        STATUS                  current
        DESCRIPTION             ""
        ::= { faMipReg 14 }

faRreqDeniedUnknownHa           OBJECT-TYPE
        SYNTAX                  INTEGER
        MAX-ACCESS              read-only
        STATUS                  current
        DESCRIPTION             ""
        ::= { faMipReg 15 }

faRreqDeniedRevTunlUnavail      OBJECT-TYPE
        SYNTAX                  INTEGER
        MAX-ACCESS              read-only
        STATUS                  current
        DESCRIPTION             ""
        ::= { faMipReg 16 }

faRreqDeniedRegTimeout          OBJECT-TYPE
        SYNTAX                  INTEGER
        MAX-ACCESS              read-only
        STATUS                  current
        DESCRIPTION             ""
        ::= { faMipReg 17 }

faRreqDeniedFailedVendor        OBJECT-TYPE
        SYNTAX                  INTEGER
        MAX-ACCESS              read-only
        STATUS                  current
        DESCRIPTION             ""
        ::= { faMipReg 18 }

faRrepRecvd                     OBJECT-TYPE
        SYNTAX                  INTEGER
        MAX-ACCESS              read-only
        STATUS                  current
        DESCRIPTION             ""
        ::= { faMipReg 19 }

faRrepRelayed   OBJECT-TYPE
        SYNTAX                  INTEGER
        MAX-ACCESS              read-only
        STATUS                  current
        DESCRIPTION             ""
        ::= { faMipReg 20 }

faRrepSent                      OBJECT-TYPE
        SYNTAX                  INTEGER
        MAX-ACCESS              read-only
        STATUS                  current
        DESCRIPTION             ""
        ::= { faMipReg 21 }

faPfaneExtRecvd                 OBJECT-TYPE
        SYNTAX                  INTEGER
        MAX-ACCESS              read-only
        STATUS                  current
        DESCRIPTION             ""
        ::= { faExtensions 1 }

faMnChalExtRecvd                OBJECT-TYPE
        SYNTAX                  INTEGER
        MAX-ACCESS              read-only
        STATUS                  current
        DESCRIPTION             ""
        ::= { faExtensions 2 }

faMnFaAuthRecvd                 OBJECT-TYPE
        SYNTAX                  INTEGER
        MAX-ACCESS              read-only
        STATUS                  current
        DESCRIPTION             ""
        ::= { faExtensions 3 }

faMnNaiExtRecvd                 OBJECT-TYPE
        SYNTAX                  INTEGER
        MAX-ACCESS              read-only
        STATUS                  current
        DESCRIPTION             ""
        ::= { faExtensions 4 }

faBuSent                        OBJECT-TYPE
        SYNTAX                  INTEGER
        MAX-ACCESS              read-only
        STATUS                  current
        DESCRIPTION             ""
        ::= { faRouteOptimization 1 }

faBuRecvd                       OBJECT-TYPE
        SYNTAX                  INTEGER
        MAX-ACCESS              read-only
        STATUS                  current
        DESCRIPTION             ""
        ::= { faRouteOptimization 2 }

--
-- Paging
--
pagingProv              OBJECT IDENTIFIER ::= { rrPaging 1 }
pagingStats             OBJECT IDENTIFIER ::= { rrPaging 2 }

pgUdpPort               OBJECT-TYPE
        SYNTAX          INTEGER (0..65535)
        MAX-ACCESS      read-write
        STATUS          current
        DESCRIPTION     "UDP port for Page Requests/Repsonse packets."
        DEFVAL          { 15100 }
        ::= { pagingProv 1 }

pgLuUdpPort             OBJECT-TYPE
        SYNTAX          INTEGER (0..65535)
        MAX-ACCESS      read-write
        STATUS          current
        DESCRIPTION     "UDP port for Location Update/Acks and Naks."
        DEFVAL          { 15101 }
        ::= { pagingProv 2 }


pgApaProv               OBJECT IDENTIFIER ::= { pagingProv 6 }

pgApaRateBiasTime       OBJECT-TYPE
        SYNTAX          INTEGER
        MAX-ACCESS      read-write
        STATUS          current
        DESCRIPTION     "Page request round trip (bias) time, in msec. Time
                        added to compute page backoff timeout (for
                        retransmission of page requests)."
        DEFVAL          { 0 }
        ::= { pgApaProv 1 }

pgApaMonIntvlFctrs      OBJECT-TYPE
        SYNTAX          INTEGER (0..65535)
        MAX-ACCESS      read-write
        STATUS          current
        DESCRIPTION     "Factor multiplied by monitoring interval. This is
                        added to pageApaRateBiasTime to make up the page
                        backoff timeout. The monitoring interval itself,
                        is sent to the APA in a L3 Sleep message."
        DEFVAL          { 1 }
        ::= { pgApaProv 2 }

pgApaBackoffFctrsTable  OBJECT-TYPE
        SYNTAX          SEQUENCE OF PgBackoffFctrsEntry
        MAX-ACCESS      not-accessible
        STATUS          current
        DESCRIPTION     "Table of Area Paging backoff timeout factors. For each 
                         retransmission of a page request, the page backoff
                         timeout (2000 msec) is multiplied by the page backoff
                         timeout factor for that retransmission."
        ::= { pgApaProv 4 }

pgBackoffFctrsEntry     OBJECT-TYPE
        SYNTAX          PgBackoffFctrsEntry
        MAX-ACCESS      not-accessible
        STATUS          current
        DESCRIPTION     "Area Paging backoff timeout factors table entries."
        INDEX           { pgBackoffFctrIndex }
        ::= { pgApaBackoffFctrsTable 1 }

PgBackoffFctrsEntry ::= SEQUENCE {
        pgBackoffFctrIndex        INTEGER,
        pgBackoffTimeoutFactor    INTEGER
}

pgBackoffFctrIndex      OBJECT-TYPE
        SYNTAX          INTEGER
        MAX-ACCESS      read-only
        STATUS          current
        DESCRIPTION     "The backoff timeout factor table index."
        ::= { pgBackoffFctrsEntry 1 }

pgBackoffTimeoutFactor  OBJECT-TYPE
        SYNTAX          INTEGER (0..65535)
        MAX-ACCESS      read-write
        STATUS          current
        DESCRIPTION     "The backoff timeout factor."
        ::= { pgBackoffFctrsEntry 2 }


pgApaIntvlTimeout       OBJECT-TYPE
        SYNTAX          INTEGER (0..65535)
        MAX-ACCESS      read-write
        STATUS          current
        DESCRIPTION     "When the page process starts, paging retransmissions
                        will continue until either the target wakes-up or this
                        timer expires. Recommended value is 20."
        DEFVAL          { 120 }
        ::= { pgApaProv 5 }

pgApaIntvlTimeoutAction OBJECT-TYPE
        SYNTAX          INTEGER {
                            none(0),
                            reset(1)
                        }
        MAX-ACCESS      read-write
        STATUS          current
        DESCRIPTION     "This indicates the state clearing policy following an
                        interval timeout:
                            none    Remain in paging (just clear LPA 
                                    Page List).
                            reset   Clean up and return to mobile to SLEEPING 
                                    state."
        DEFVAL          { none }
        ::= { pgApaProv 6 }

pgApaSuppressTimeout    OBJECT-TYPE
        SYNTAX          INTEGER (0..65535)
        MAX-ACCESS      read-write
        STATUS          current
        DESCRIPTION     "Page Suppress Timeout in seconds. This timeout is
                         the amount of time that we suppress pages for after
                         receiving a page response with Access indicator."
        DEFVAL          { 2 }
        ::= { pgApaProv 7 }

pgApaLuSpoofSupport     OBJECT-TYPE
        SYNTAX          INTEGER {
                            disabled(0),
                            enabled(1)
                        } 
        MAX-ACCESS      read-write
        STATUS          current
        DESCRIPTION     "Indicates whether spoof support is enabled or not.
                        This determines how the list of LPAs is managed
                        (slide / no slide)." 
        DEFVAL          { enabled }
        ::= { pgApaProv 8 }

pgApaListLimit          OBJECT-TYPE
        SYNTAX          INTEGER (0..65535)
        MAX-ACCESS      read-write
        STATUS          current
        DESCRIPTION     "Maximum number of Location Updates from basestation
                        that will be saved in the basestation list as a result
                        of receiving location updates. If this value is reached,
                        a NAK packet is sent to the LPA at the basestation that
                        sent the update causing the limit to be reached."
        DEFVAL          { 10 }
        ::= { pgApaProv 9 }

pgApaFwRuleNum          OBJECT-TYPE
        SYNTAX          INTEGER (0..65535)
        MAX-ACCESS      read-write
        STATUS          current
        DESCRIPTION     "Firewall rule number used in setting up rule for
                        diverting location updates to the divert socket for
                        location updates."
        DEFVAL          { 10000 }
        ::= { pgApaProv 10 }

pgApaMobilesLuThreshPct  OBJECT-TYPE
        SYNTAX           INTEGER (0..65535)
        MAX-ACCESS       read-write
        STATUS           current
        DESCRIPTION      "Percentage applied to the maximum number of sleeping
                         mobiles allowed. Used in computing the number
                         of sleeping mobiles LU threshold. This is used to
                         avoid service disruptions in over-loaded cells."
        DEFVAL           { 80 }
        ::= { pgApaProv 11 }

pgApaTrashLogLevel      OBJECT-TYPE
        SYNTAX          LogLevel
        MAX-ACCESS      read-write
        STATUS          current
        DESCRIPTION     "Log messages with levels above the specified value
                        will not be logged."
        DEFVAL          { logDebug }
        ::= { pgApaProv 12 }


pgLpaProv               OBJECT IDENTIFIER ::= { pagingProv 7 }

pgLpaL2PageTimeout      OBJECT-TYPE
        SYNTAX          INTEGER (0..65535)
        MAX-ACCESS      read-write
        STATUS          current
        DESCRIPTION     "L2 Page Timeout.  Timeout in seconds for which we will
                         continue to wait for the mobile to go through access
                         or to receive an L2 Page Response for presence test."
        DEFVAL          { 20 }
        ::= { pgLpaProv 1 }

pgLpaSpoofThreshold     OBJECT-TYPE
        SYNTAX          INTEGER (0..65535)
        MAX-ACCESS      read-write
        STATUS          current
        DESCRIPTION     "The rate of failure of Location Update Requests
                         below which anti-spoof mechanism kicks in."
        DEFVAL          { 50 }
        ::= { pgLpaProv 2 }

pgLpaBiasFactor         OBJECT-TYPE
        SYNTAX          INTEGER (0..65535)
        MAX-ACCESS      read-write
        STATUS          current
        DESCRIPTION     "The factor which regulates the effect past failures
                        have on the exponential weighted average."
        DEFVAL          { 2 }
        ::= { pgLpaProv 3 }

pgLpaSpoofInterval      OBJECT-TYPE
        SYNTAX          INTEGER
        MAX-ACCESS      read-write
        STATUS          current
        DESCRIPTION     "LPA spoof interval."
        DEFVAL          { 5000 }
        ::= { pgLpaProv 4 }

pgLpaTrashLogLevel      OBJECT-TYPE
        SYNTAX          LogLevel
        MAX-ACCESS      read-write
        STATUS          current
        DESCRIPTION     "Log messages with levels above the specified value
                        will not be logged."
        DEFVAL          { logDebug }
        ::= { pgLpaProv 5 }


--
-- Paging Statistics
--
pgApaStats          OBJECT IDENTIFIER ::= { pagingStats 1 }
pgLpaStats			OBJECT IDENTIFIER ::= { pagingStats 2 }

pgApaMobilesSleeping            OBJECT-TYPE
        SYNTAX                  Unsigned32
        MAX-ACCESS              read-only
        STATUS                  current
        DESCRIPTION             "Number of mobiles currently sleeping."
        ::= { pgApaStats 1 }

pgApaMobilesBeingPaged          OBJECT-TYPE
        SYNTAX                  Unsigned32
        MAX-ACCESS              read-only
        STATUS                  current
        DESCRIPTION             "Number of mobiles currently being paged."
        ::= { pgApaStats 2 }

pgApaL3PgReqPktsSent            OBJECT-TYPE
        SYNTAX                  Unsigned32
        MAX-ACCESS              read-only
        STATUS                  current
        DESCRIPTION             "Number of L3 Page Request Packets sent."
        ::= { pgApaStats 9 }

pgApaL3PgRspPktsRcvd            OBJECT-TYPE
        SYNTAX                  Unsigned32
        MAX-ACCESS              read-only
        STATUS                  current
        DESCRIPTION             "Number L3 Page Response Packets received."
        ::= { pgApaStats 10 }

pgApaL3AccessRspsRcvd           OBJECT-TYPE
        SYNTAX                  Unsigned32
        MAX-ACCESS              read-only
        STATUS                  current
        DESCRIPTION             "Number L3 Page Responses with Access received."
        ::= { pgApaStats 11 }

pgApaL3AliveRspsRcvd            OBJECT-TYPE
        SYNTAX                  Unsigned32
        MAX-ACCESS              read-only
        STATUS                  current
        DESCRIPTION             "Number of L3 Page Responses with Alive received."
        ::= { pgApaStats 12 }

pgApaL3LusRcvd                  OBJECT-TYPE
        SYNTAX                  Unsigned32
        MAX-ACCESS              read-only
        STATUS                  current
        DESCRIPTION             "Number of L3 Location Updates received."
        ::= { pgApaStats 13 }

pgApaL3LuAcksSent               OBJECT-TYPE
        SYNTAX                  Unsigned32
        MAX-ACCESS              read-only
        STATUS                  current
        DESCRIPTION             "Number of L3 Location Acks sent."
        ::= { pgApaStats 14 }

pgApaPageIntvlTimeouts          OBJECT-TYPE
        SYNTAX                  Unsigned32
        MAX-ACCESS              read-only
        STATUS                  current
        DESCRIPTION             "Number of times a page interval timeout occurred."
        ::= { pgApaStats 15 }

pgApaPageSuppressTimeouts       OBJECT-TYPE
        SYNTAX                  Unsigned32
        MAX-ACCESS              read-only
        STATUS                  current
        DESCRIPTION             "Number of Page Suppress Timeouts."
        ::= { pgApaStats 16 }

pgApaPageBackoffTimeouts        OBJECT-TYPE
        SYNTAX                  Unsigned32
        MAX-ACCESS              read-only
        STATUS                  current
        DESCRIPTION             "Number of times backoff timers went off."
        ::= { pgApaStats 17 }

pgLpaMobilesBeingPaged          OBJECT-TYPE
        SYNTAX                  Unsigned32
        MAX-ACCESS              read-only
        STATUS                  current
        DESCRIPTION             "Number of mobiles currently being paged."
        ::= { pgLpaStats 2 }

pgLpaL3PgReqPktRcvd             OBJECT-TYPE
        SYNTAX                  Unsigned32
        MAX-ACCESS              read-only
        STATUS                  current
        DESCRIPTION             "Number of L3 Page Request Packet received."
        ::= { pgLpaStats 9 }

pgLpaL3PgRspPktSent             OBJECT-TYPE
        SYNTAX                  Unsigned32
        MAX-ACCESS              read-only
        STATUS                  current
        DESCRIPTION             "Number of L3 Page Responses sent."
        ::= { pgLpaStats 11 }

pgLpaL2PgIntvlTimeouts          OBJECT-TYPE
        SYNTAX                  Unsigned32
        MAX-ACCESS              read-only
        STATUS                  current
        DESCRIPTION             "Number of times L2 Page Requests timed out
                                (no L3 Up)."
        ::= { pgLpaStats 12 }

pgLpaLocUpdPktSent              OBJECT-TYPE
        SYNTAX                  Unsigned32
        MAX-ACCESS              read-only
        STATUS                  current
        DESCRIPTION             "Number of Location Update Packet messages sent."
        ::= { pgLpaStats 16 }

pgLpaLocUpdRspPktRcvd           OBJECT-TYPE
        SYNTAX                  Unsigned32
        MAX-ACCESS              read-only
        STATUS                  current
        DESCRIPTION             "Number of Location Update Response Packet messages received."
        ::= { pgLpaStats 17 }




--
-- Network Time Protocol
--
ntpServerTable          OBJECT-TYPE
        SYNTAX          SEQUENCE OF NtpServerEntry
        MAX-ACCESS      not-accessible
        STATUS          current
        DESCRIPTION     "Table of NTP servers."
        ::= { rrNtp 2 }

ntpServerEntry          OBJECT-TYPE
        SYNTAX          NtpServerEntry
        MAX-ACCESS      not-accessible
        STATUS          current
        DESCRIPTION     "NTP server table entry."
        INDEX           { ntpServerIndex }
        ::= { ntpServerTable 1 }

NtpServerEntry ::= SEQUENCE {
        ntpServerIndex        INTEGER,
        ntpServerEnabled      TruthValue,
        ntpServerId           DisplayString
}

ntpServerIndex          OBJECT-TYPE
        SYNTAX          INTEGER
        MAX-ACCESS      read-only
        STATUS          current
        DESCRIPTION     "NTP server index."
        ::= { ntpServerEntry 1 }

ntpServerEnabled        OBJECT-TYPE
        SYNTAX          TruthValue
        MAX-ACCESS      read-write
        STATUS          current
        DESCRIPTION     "Indicates if this NTP server entry is enabled."
        DEFVAL          { false }
        ::= { ntpServerEntry 2 }

ntpServerId             OBJECT-TYPE
        SYNTAX          DisplayString
        MAX-ACCESS      read-write
        STATUS          current
        DESCRIPTION     "NTP DNS name or IP address."
        ::= { ntpServerEntry 3 }



--
-- DHCP
--
dhcpProv            OBJECT IDENTIFIER ::= { rrDhcp 1 }

dhcpUseSysDns       OBJECT-TYPE
        SYNTAX      TruthValue
        MAX-ACCESS  read-write
        STATUS      current
        DESCRIPTION "Indicates if DHCP uses the MCU DNS settings."
        DEFVAL      { true }
        ::= { dhcpProv 1 }

dhcpDnsServerTable      OBJECT-TYPE
        SYNTAX          SEQUENCE OF DhcpDnsServerEntry
        MAX-ACCESS      not-accessible
        STATUS          current
        DESCRIPTION     "Table of DHCP DNS servers."
        ::= { dhcpProv 2 }

dhcpDnsServerEntry      OBJECT-TYPE
        SYNTAX          DhcpDnsServerEntry
        MAX-ACCESS      not-accessible
        STATUS          current
        DESCRIPTION     "DHCP DNS server table entry."
        INDEX           { dhcpDnsIndex }
        ::= { dhcpDnsServerTable 1 }

DhcpDnsServerEntry ::= SEQUENCE {
        dhcpDnsIndex        INTEGER,
        dhcpDnsIpAddr       IpAddress
}

dhcpDnsIndex            OBJECT-TYPE
        SYNTAX          INTEGER
        MAX-ACCESS      read-only
        STATUS          current
        DESCRIPTION     "DHCP DNS server index."
        ::= { dhcpDnsServerEntry 1 }

dhcpDnsIpAddr           OBJECT-TYPE
        SYNTAX          IpAddress
        MAX-ACCESS      read-write
        STATUS          current
        DESCRIPTION     "DHCP DNS IP address."
        ::= { dhcpDnsServerEntry 2 }

dhcpServerIpAddr       OBJECT-TYPE
        SYNTAX          IpAddress
        MAX-ACCESS  read-write
        STATUS      current
        DESCRIPTION "This represents the DHCP Server IP Address which is
                     returned in any DHCP protocol packet in the siaddr field"
        ::= { dhcpProv 3 }

--
-- Authentication/Authorization Server
--
aaProv                  OBJECT IDENTIFIER ::= { rrAuthServer 1 }

aaServerTimeout         OBJECT-TYPE
        SYNTAX          INTEGER (100..2000)
        MAX-ACCESS      read-write
        STATUS          current
        DESCRIPTION     ""
        DEFVAL          { 300 }
        ::= { aaProv 2 }

aaServerRetry           OBJECT-TYPE
        SYNTAX          INTEGER
        MAX-ACCESS      read-write
        STATUS          current
        DESCRIPTION     ""
        ::= { aaProv 3 }

aaServerTrashLogLevel   OBJECT-TYPE
        SYNTAX          LogLevel
        MAX-ACCESS      read-write
        STATUS          current
        DESCRIPTION     "Log messages with levels above the specified value will not be logged."
        DEFVAL          { logInfo }
        ::= { aaProv 8 }

aaRadServTable          OBJECT-TYPE
        SYNTAX          SEQUENCE OF AaRadServEntry
        MAX-ACCESS      not-accessible
        STATUS          current
        DESCRIPTION     "Table of RADIUS servers."
        ::= { aaProv 11 }

aaRadServEntry          OBJECT-TYPE
        SYNTAX          AaRadServEntry
        MAX-ACCESS      not-accessible
        STATUS          current
        DESCRIPTION     "RADIUS server table entry."
        INDEX           { aaRadServIndex }
        ::= { aaRadServTable 1 }

AaRadServEntry ::= SEQUENCE {
        aaRadServIndex        INTEGER,
        aaRadServValid        TruthValue,
        aaRadServName         DisplayString,
        aaRadServIpAddr       IpAddress,
        aaRadServUdpPort      INTEGER,
        aaRadServSecret       DisplayString
}

aaRadServIndex          OBJECT-TYPE
        SYNTAX          INTEGER
        MAX-ACCESS      read-only
        STATUS          current
        DESCRIPTION     "RADIUS server index."
        ::= { aaRadServEntry 1 }

aaRadServValid          OBJECT-TYPE
        SYNTAX          TruthValue
        MAX-ACCESS      read-write
        STATUS          current
        DESCRIPTION     "Indicates if this RADIUS server entry is valid."
        DEFVAL          { false }
        ::= { aaRadServEntry 2 }

aaRadServName           OBJECT-TYPE
        SYNTAX          DisplayString
        MAX-ACCESS      read-write
        STATUS          current
        DESCRIPTION     "RADIUS server name."
        ::= { aaRadServEntry 3 }

aaRadServIpAddr         OBJECT-TYPE
        SYNTAX          IpAddress
        MAX-ACCESS      read-write
        STATUS          current
        DESCRIPTION     "RADIUS server IP address."
        ::= { aaRadServEntry 4 }

aaRadServUdpPort        OBJECT-TYPE
        SYNTAX          INTEGER (0..32767)
        MAX-ACCESS      read-write
        STATUS          current
        DESCRIPTION     "RADIUS server UDP port."
        DEFVAL          { 1812 }
        ::= { aaRadServEntry 5 }

aaRadServSecret         OBJECT-TYPE
        SYNTAX          DisplayString
        MAX-ACCESS      read-write
        STATUS          current
        DESCRIPTION     "RADIUS server secret key."
        ::= { aaRadServEntry 6 }



--
-- Accounting Server Provisions
--
acntRadiusStatus        OBJECT-TYPE
        SYNTAX          AdminState
        MAX-ACCESS      read-only
        STATUS          current
        DESCRIPTION     "RADIUS server status"
        ::= { rrAccountingServer 1 }

acntProv                OBJECT IDENTIFIER ::= { rrAccountingServer 2 }

acntRadServTable        OBJECT-TYPE
        SYNTAX          SEQUENCE OF AcntRadServEntry
        MAX-ACCESS      not-accessible
        STATUS          current
        DESCRIPTION     "Table of RADIUS servers."
        ::= { acntProv 1 }

acntRadServEntry        OBJECT-TYPE
        SYNTAX          AcntRadServEntry
        MAX-ACCESS      not-accessible
        STATUS          current
        DESCRIPTION     "RADIUS server table entry."
        INDEX           { acntRadServIndex }
        ::= { acntRadServTable 1 }

AcntRadServEntry ::= SEQUENCE {
        acntRadServIndex        INTEGER,
        acntRadServValid        TruthValue,
        acntRadServName         DisplayString,
        acntRadServAddr         IpAddress,
        acntRadServPort         INTEGER,
        acntRadServSecret       DisplayString
}

acntRadServIndex        OBJECT-TYPE
        SYNTAX          INTEGER
        MAX-ACCESS      read-only
        STATUS          current
        DESCRIPTION     "RADIUS server index."
        ::= { acntRadServEntry 1 }

acntRadServValid        OBJECT-TYPE
        SYNTAX          TruthValue
        MAX-ACCESS      read-write
        STATUS          current
        DESCRIPTION     "Indicates if this RADIUS server entry is valid."
        DEFVAL          { false }
        ::= { acntRadServEntry 2 }

acntRadServName         OBJECT-TYPE
        SYNTAX          DisplayString
        MAX-ACCESS      read-write
        STATUS          current
        DESCRIPTION     "RADIUS server name."
        ::= { acntRadServEntry 3 }

acntRadServAddr         OBJECT-TYPE
        SYNTAX          IpAddress
        MAX-ACCESS      read-write
        STATUS          current
        DESCRIPTION     "RADIUS server IP address."
        ::= { acntRadServEntry 4 }

acntRadServPort         OBJECT-TYPE
        SYNTAX          INTEGER (0..65535)
        MAX-ACCESS      read-write
        STATUS          current
        DESCRIPTION     "RADIUS server port."
        DEFVAL          { 1813 }
        ::= { acntRadServEntry 5 }

acntRadServSecret       OBJECT-TYPE
        SYNTAX          DisplayString
        MAX-ACCESS      read-write
        STATUS          current
        DESCRIPTION     "RADIUS server secret key."
        ::= { acntRadServEntry 6 }

acntRadServTimeout      OBJECT-TYPE
        SYNTAX          INTEGER (0..255)
        MAX-ACCESS      read-write
        STATUS          current
        DESCRIPTION     "RADIUS server timeout."
        DEFVAL          { 3 }
        ::= { acntProv 2 }

acntRadServRetry        OBJECT-TYPE
        SYNTAX          INTEGER (0..255)
        MAX-ACCESS      read-write
        STATUS          current
        DESCRIPTION     "RADIUS server maximum retry."
        DEFVAL          { 3 }
        ::= { acntProv 3 }

acntDelaySend           OBJECT-TYPE
        SYNTAX          TruthValue
        MAX-ACCESS      read-write
        STATUS          current
        DESCRIPTION     "Include delay attribute."
        DEFVAL          { true }
        ::= { acntProv 4 }

acntServDownHd          OBJECT-TYPE
        SYNTAX          TruthValue
        MAX-ACCESS      read-write
        STATUS          current
        DESCRIPTION     "Server down handling."
        DEFVAL          { true }
        ::= { acntProv 5 }

acntL2UpDebounce        OBJECT-TYPE
        SYNTAX          INTEGER (0..255)
        MAX-ACCESS      read-write
        STATUS          current
        DESCRIPTION     "L2Up debounce time."
        DEFVAL          { 0 }
        ::= { acntProv 6 }

acntDoPerRAR            OBJECT-TYPE
        SYNTAX          TruthValue
        MAX-ACCESS      read-write
        STATUS          current
        DESCRIPTION     "Do accounting per RAR(true) / BBU(false)."
        DEFVAL          { false }
        ::= { acntProv 7 }

acntL2DownDebounce      OBJECT-TYPE
        SYNTAX          INTEGER (0..255)
        MAX-ACCESS      read-write
        STATUS          current
        DESCRIPTION     "L2Down debounce time."
        DEFVAL          { 5 }
        ::= { acntProv 8 }

acntUpdateBand          OBJECT-TYPE
        SYNTAX          INTEGER (0..65535)
        MAX-ACCESS      read-write
        STATUS          current
        DESCRIPTION     "Accounting update max bandwidth (bytes/sec)."
        DEFVAL          { 2000 }
        ::= { acntProv 9 }



--
-- BBU (Base Band Unit)
--
--
-- BBU Table
--
bbuTable            OBJECT-TYPE
    SYNTAX          SEQUENCE OF BbuEntry
    MAX-ACCESS      not-accessible
    STATUS          current
    DESCRIPTION     "Table of Base Band Units."
    ::= { rrBaseBandUnit 4 }

bbuEntry            OBJECT-TYPE
    SYNTAX          BbuEntry
    MAX-ACCESS      not-accessible
    STATUS          current
    DESCRIPTION     "Base Band Unit table entry."
    INDEX           { bbuId }
    ::= { bbuTable 1 }

BbuEntry ::= SEQUENCE {
    bbuId               INTEGER,
    bbuIpAddress        IpAddress,
    bbuAdminState       AdminState,
    bbuOperState        BbuState,
    bbuReset            TruthValue,
    bbuHwVer            DisplayString,
    bbuBootromVer       DisplayString
}

bbuId               OBJECT-TYPE
    SYNTAX          INTEGER
    MAX-ACCESS      read-only
    STATUS          current
    DESCRIPTION     "Base Band Unit ID."
    ::= { bbuEntry 1 }

bbuIpAddress        OBJECT-TYPE
    SYNTAX          IpAddress
    MAX-ACCESS      read-write
    STATUS          current
    DESCRIPTION     "BBU IP address."
    ::= { bbuEntry 2 }

bbuAdminState       OBJECT-TYPE
    SYNTAX          AdminState
    MAX-ACCESS      read-write
    STATUS          current
    DESCRIPTION     "BBU administrative state."
    ::= { bbuEntry 3 }

bbuOperState        OBJECT-TYPE
    SYNTAX          BbuState
    MAX-ACCESS      read-write
    STATUS          current
    DESCRIPTION     "A GET on this object will return the BBU's operational
                    state.

                    Valid values for a SET are:
                        active(1)           set BBU to active state
                        disabledStandby(6)  set BBU to disabled/standby state"
    ::= { bbuEntry 4 }

bbuReset            OBJECT-TYPE
    SYNTAX          TruthValue
    MAX-ACCESS      read-write
    STATUS          current
    DESCRIPTION     "Set to true(1) to reset the BBU."
    ::= { bbuEntry 5 }

bbuHwVer            OBJECT-TYPE
    SYNTAX          DisplayString
    MAX-ACCESS      read-only
    STATUS          current
    DESCRIPTION     "BBU hardware version."
    ::= { bbuEntry 6 }

bbuBootromVer       OBJECT-TYPE
    SYNTAX          DisplayString
    MAX-ACCESS      read-only
    STATUS          current
    DESCRIPTION     "BBU bootrom version."
    ::= { bbuEntry 7 }

--
-- Mobile Tables
--
rrMobileNum             OBJECT-TYPE
        SYNTAX          INTEGER
        MAX-ACCESS      read-only
        STATUS          current
        DESCRIPTION     "Total number of active mobile users on the base
                        station. An active user is a mobile which has been
                        authenticated and has acquired an IP address
                        (L3 registered)."
        ::= { rrMobile 1 }

mobileTable             OBJECT-TYPE
    SYNTAX          SEQUENCE OF MobileEntry
    MAX-ACCESS      not-accessible
    STATUS          current
    DESCRIPTION     "Table of mobile users."
    ::= { rrMobile 3 }

mobileEntry             OBJECT-TYPE
    SYNTAX          MobileEntry
    MAX-ACCESS      not-accessible
    STATUS          current
    DESCRIPTION     "Mobile user table entry."
    INDEX           { mobileEui }
    ::= { mobileTable 1 }

MobileEntry ::= SEQUENCE {
    mobileEui       MobileEui,
    mobileScrub     TruthValue
}

mobileEui           OBJECT-TYPE
    SYNTAX          MobileEui
    MAX-ACCESS      read-only
    STATUS          current
    DESCRIPTION     "Mobile EUI64."
    ::= { mobileEntry 1 }

mobileScrub         OBJECT-TYPE
    SYNTAX          TruthValue
    MAX-ACCESS      read-write
    STATUS          current
    DESCRIPTION     "Set this value to true(1) to scrub the mobile from
                    the system."
    ::= { mobileEntry 2 }

--
-- Mobile Sector Table
--
mobileSectorTable   OBJECT-TYPE
    SYNTAX          SEQUENCE OF MobileSectorEntry
    MAX-ACCESS      not-accessible
    STATUS          current
    DESCRIPTION     "Table of mobile users as seen by a particular sector."
    ::= { rrMobile 4 }

mobileSectorEntry   OBJECT-TYPE
    SYNTAX          MobileSectorEntry
    MAX-ACCESS      not-accessible
    STATUS          current
    DESCRIPTION     "Mobile user as seen by a particular sector table entry."
    INDEX           { mobileSectorEui, mobileSectorId }
    ::= { mobileSectorTable 1 }

MobileSectorEntry ::= SEQUENCE {
    mobileSectorEui             MobileEui,
    mobileSectorId              INTEGER,
    mobileSectorMipLifetime     Unsigned32,
    mobileSectorNai             DisplayString,
    mobileSectorL2State         DisplayString,
    mobileSectorQosProfile      DisplayString,
    mobileSectorAaaIp           DisplayString,
    mobileSectorAaaHa           DisplayString,
    mobileSectorActiveIp        DisplayString,
    mobileSectorActiveHa        DisplayString,
    mobileSectorFramedMtuSize   Unsigned32,
    mobileSectorMipAuthAlg      DisplayString,
    mobileSectorNaiReg          Unsigned32,
    mobileSectorIdleTimeout     Unsigned32,
    mobileSectorAcntInterval    Unsigned32,
    mobileSectorVendorId        Unsigned32,
    mobileSectorVersion         OCTET STRING
}

mobileSectorEui     OBJECT-TYPE
    SYNTAX          MobileEui
    MAX-ACCESS      read-only
    STATUS          current
    DESCRIPTION     "Mobile EUI64."
    ::= { mobileSectorEntry 1 }

mobileSectorId      OBJECT-TYPE
    SYNTAX          INTEGER
    MAX-ACCESS      read-only
    STATUS          current
    DESCRIPTION     "The sector Id."
    ::= { mobileSectorEntry 2 }

mobileSectorMipLifetime OBJECT-TYPE
    SYNTAX      Unsigned32
    MAX-ACCESS  read-only
    STATUS      current
    DESCRIPTION "The Mobile IP lifetime."
    ::= { mobileSectorEntry 3 }

mobileSectorNai OBJECT-TYPE
    SYNTAX      DisplayString
    MAX-ACCESS  read-only
    STATUS      current
    DESCRIPTION "The Network Access Identifier used to uniquely identify the
                mobile node. Typically the NAI is of the form user@realm.com."
    ::= { mobileSectorEntry 4 }

mobileSectorL2State OBJECT-TYPE
    SYNTAX      DisplayString
    MAX-ACCESS  read-only
    STATUS      current
    DESCRIPTION "The L2 access control state."
    ::= { mobileSectorEntry 5 }

mobileSectorQosProfile  OBJECT-TYPE
    SYNTAX      DisplayString
    MAX-ACCESS  read-only
    STATUS      current
    DESCRIPTION "The L2 access control QoS profile."
    ::= { mobileSectorEntry 6 }

mobileSectorAaaIp   OBJECT-TYPE
    SYNTAX      DisplayString
    MAX-ACCESS  read-only
    STATUS      current
    DESCRIPTION "The AAA assigned Home IP address."
    ::= { mobileSectorEntry 7 }

mobileSectorAaaHa   OBJECT-TYPE
    SYNTAX      DisplayString
    MAX-ACCESS  read-only
    STATUS      current
    DESCRIPTION "The AAA assigned Home Agent IP address."
    ::= { mobileSectorEntry 8 }

mobileSectorActiveIp    OBJECT-TYPE
    SYNTAX      DisplayString
    MAX-ACCESS  read-only
    STATUS      current
    DESCRIPTION "The Home Agent assigned Home IP address."
    ::= { mobileSectorEntry 9 }

mobileSectorActiveHa    OBJECT-TYPE
    SYNTAX      DisplayString
    MAX-ACCESS  read-only
    STATUS      current
    DESCRIPTION "The MCU assigned Home Agent IP address."
    ::= { mobileSectorEntry 10 }

mobileSectorFramedMtuSize   OBJECT-TYPE
    SYNTAX      Unsigned32
    MAX-ACCESS  read-only
    STATUS      current
    DESCRIPTION "The MTU frame size."
    ::= { mobileSectorEntry 11 }

mobileSectorMipAuthAlg  OBJECT-TYPE
    SYNTAX      DisplayString
    MAX-ACCESS  read-only
    STATUS      current
    DESCRIPTION "The authentication algorithm"
    ::= { mobileSectorEntry 12 }

mobileSectorNaiReg  OBJECT-TYPE
    SYNTAX      Unsigned32
    MAX-ACCESS  read-only
    STATUS      current
    DESCRIPTION "Does the mobile MIP register with NAI?"
    ::= { mobileSectorEntry 13 }

mobileSectorIdleTimeout OBJECT-TYPE
    SYNTAX      Unsigned32
    MAX-ACCESS  read-only
    STATUS      current
    DESCRIPTION "Layer 2/3 cipher key timeout."
    ::= { mobileSectorEntry 14 }

mobileSectorAcntInterval    OBJECT-TYPE
    SYNTAX      Unsigned32
    MAX-ACCESS  read-only
    STATUS      current
    DESCRIPTION "RADIUS accounting update interval (seconds)."
    ::= { mobileSectorEntry 15 }

mobileSectorVendorId    OBJECT-TYPE
    SYNTAX      Unsigned32
    MAX-ACCESS  read-only
    STATUS      current
    DESCRIPTION "Mobile vendor ID."
    ::= { mobileSectorEntry 16 }

mobileSectorVersion OBJECT-TYPE
    SYNTAX      OCTET STRING
    MAX-ACCESS  read-only
    STATUS      current
    DESCRIPTION "The mobile version information."
    ::= { mobileSectorEntry 17 }

--
-- Mobile Active Table
--
mobileActiveTable   OBJECT-TYPE
    SYNTAX          SEQUENCE OF MobileActiveEntry
    MAX-ACCESS      not-accessible
    STATUS          current
    DESCRIPTION     "This table displays the active mobiles connected on each
                    sector."
    ::= { rrMobile 5 }

mobileActiveEntry   OBJECT-TYPE
    SYNTAX          MobileActiveEntry
    MAX-ACCESS      not-accessible
    STATUS          current
    DESCRIPTION     ""
    INDEX           { mobileActiveSectorId, mobileActiveIndex }
    ::= { mobileActiveTable 1 }

MobileActiveEntry ::= SEQUENCE {
    mobileActiveSectorId    INTEGER,
    mobileActiveIndex       INTEGER,
    mobileActiveEui         MobileEui,
    mobileActiveIpAddr      IpAddress,
    mobileActiveVersion     DisplayString
}

mobileActiveSectorId	OBJECT-TYPE
    SYNTAX          INTEGER
    MAX-ACCESS      read-only
    STATUS          current
    DESCRIPTION     "Sector ID."
    ::= { mobileActiveEntry 1 }

mobileActiveIndex   OBJECT-TYPE
    SYNTAX          INTEGER
    MAX-ACCESS      read-only
    STATUS          current
    DESCRIPTION     "Active mobile index."
    ::= { mobileActiveEntry 2 }

-- mobileActiveEntry 3 intentionally left out

mobileActiveEui     OBJECT-TYPE
    SYNTAX          MobileEui
    MAX-ACCESS      read-only
    STATUS          current
    DESCRIPTION     "The mobile's EUI-64."
    ::= { mobileActiveEntry 4 }

mobileActiveIpAddr  OBJECT-TYPE        
    SYNTAX          IpAddress
    MAX-ACCESS      read-only
    STATUS          current
    DESCRIPTION     "Mobile IP address."
    ::= { mobileActiveEntry 8 }

mobileActiveVersion OBJECT-TYPE        
    SYNTAX          DisplayString
    MAX-ACCESS      read-only
    STATUS          current
    DESCRIPTION     "Mobile version number."
    ::= { mobileActiveEntry 9 }


--
-- Sector
--
sectorNum               OBJECT-TYPE
        SYNTAX          INTEGER
        MAX-ACCESS      read-only
        STATUS          current
        DESCRIPTION     "Number of sectors. A value of 1 implies that the system is
                         not-sectorized (omnidirectional)."
        ::= { rrSector 1 }

sectorTable             OBJECT-TYPE
        SYNTAX          SEQUENCE OF SectorEntry
        MAX-ACCESS      not-accessible
        STATUS          current
        DESCRIPTION     "Table of sectors."
        ::= { rrSector 2 }

sectorEntry             OBJECT-TYPE
        SYNTAX          SectorEntry
        MAX-ACCESS      not-accessible
        STATUS          current
        DESCRIPTION     "Sector table entry."
        INDEX           { sectorId }
        ::= { sectorTable 1 }

SectorEntry ::= SEQUENCE {
        sectorId                INTEGER,
        sectorBbu               INTEGER
}

sectorId                OBJECT-TYPE
        SYNTAX          INTEGER
        MAX-ACCESS      read-only
        STATUS          current
        DESCRIPTION     "The sector identifier."
        ::= { sectorEntry 1 }

sectorBbu               OBJECT-TYPE
        SYNTAX          INTEGER
        MAX-ACCESS      read-only
        STATUS          current
        DESCRIPTION     "The Base Band Unit handling this sector."
        ::= { sectorEntry 2 }


--
-- Backhaul Unit MIB
--

-- WAN Blade Table
wanBladeTable           OBJECT-TYPE
        SYNTAX          SEQUENCE OF WanBladeEntry
        MAX-ACCESS      not-accessible
        STATUS          current
        DESCRIPTION     "WAN blade table."
        ::= { rrBackHaulUnit 1 }

wanBladeEntry           OBJECT-TYPE
        SYNTAX          WanBladeEntry
        MAX-ACCESS      not-accessible
        STATUS          current
        DESCRIPTION     "WAN blade table entry."
        INDEX           { wanBladeId }
        ::= { wanBladeTable 1 }

WanBladeEntry ::= SEQUENCE {
        wanBladeId      INTEGER,
        wanBladeValid   TruthValue
}

wanBladeId              OBJECT-TYPE
        SYNTAX          INTEGER
        MAX-ACCESS      read-only
        STATUS          current
        DESCRIPTION     "The WAN blade identifier."
        ::= { wanBladeEntry 1 }

wanBladeValid           OBJECT-TYPE
        SYNTAX          TruthValue
        MAX-ACCESS      read-write
        STATUS          deprecated
        DESCRIPTION     "Indicates if this WAN blade is valid."
        ::= { wanBladeEntry 2 }

-- WAN clock
WanClock ::= INTEGER {
        external(0),
        internal(1)
}
 
-- WAN bit rate
WanBitRate ::= INTEGER {
        bitRate64k(0),
        bitRate56k(1)
}

-- WAN line coding
WanLineCoding ::= INTEGER {
        lineCodingAMI(0),
        lineCodingB8ZS(1),
        lineCodingHDB3(2)
}

-- WAN line mode
WanLineMode ::= INTEGER {
        lineModeESF(0),
        lineModeD4(1),
        lineModeG704(2),
        lineModeG704CRC(3),
        lineModeUf(4)
}

-- WAN line gain
WanLineGain ::= INTEGER {
        lineGain36db(0),
        lineGain30db(1)
}

-- WAN line build out
WanLineBuildOut ::= INTEGER {
        lbo1Mile(0),
        lbo2Mile(1),
        lbo3Mile(2),
        lbo4Mile(3)
}

-- WAN data polarity
WanPolarity ::= INTEGER {
        normalData(0),
        invertedData(1)
}

-- WAN feature state
WanFeatureState ::= INTEGER {
        featureDisabled(0),
        featureEnabled(1)
}

-- WAN jitter attenuation
WanJitterAttenuation ::= INTEGER {
        jitterAttenTx(0),
        jitterAttenRx(1)
}

-- WAN loopback mode
WanLoopbackMode ::= INTEGER {
        wanLoopbackNone(0),
        wanLoopbackInternal(1),
        wanLoopbackExternal(2)
}

-- WAN CRC
WanCrcMode ::= INTEGER {
        wanCrcNone(0),
        wanCrc16(1),
        wanCrc32(2)
}



-- WAN Port Table
wanPortTable            OBJECT-TYPE
        SYNTAX          SEQUENCE OF WanPortEntry
        MAX-ACCESS      not-accessible
        STATUS          current
        DESCRIPTION     "WAN port table."
        ::= { rrBackHaulUnit 2 }

wanPortEntry            OBJECT-TYPE
        SYNTAX          WanPortEntry
        MAX-ACCESS      not-accessible
        STATUS          current
        DESCRIPTION     "WAN port table entry."
        INDEX           { wanPortBladeId, wanPortId }
        ::= { wanPortTable 1 }

WanPortEntry ::= SEQUENCE {
        wanPortBladeId      INTEGER,
        wanPortId           INTEGER,
        wanTxBufferSize     INTEGER,
        wanTxBuffers        INTEGER,
        wanTxMaxPending     INTEGER,
        wanRxBufferSize     INTEGER,
        wanRxBuffers        INTEGER,
        wanMaxRxFrameSize   INTEGER,
        wanLoopback         WanLoopbackMode,
        wanCrcMode          WanCrcMode,
        wanClocking         WanClock,
        wanDataRate         WanBitRate,
        wanCoding           WanLineCoding,
        wanFraming          WanLineMode,
        wanRxGain           WanLineGain,
        wanLbo              WanLineBuildOut,
        wanPolarity         WanPolarity,
        wanPulse            WanFeatureState,
        wanJitter           WanFeatureState,
        wanJitterSide       WanJitterAttenuation,
        wanChan1to8         WanFeatureState,
        wanChan9to16        WanFeatureState,
        wanChan17to24       WanFeatureState,
        wanChan25to32       WanFeatureState,
        wanPortValid        TruthValue
}

wanPortBladeId          OBJECT-TYPE
        SYNTAX          INTEGER
        MAX-ACCESS      read-only
        STATUS          current
        DESCRIPTION     "The WAN blade identifier."
        ::= { wanPortEntry 1 }

wanPortId               OBJECT-TYPE
        SYNTAX          INTEGER
        MAX-ACCESS      read-only
        STATUS          current
        DESCRIPTION     "The WAN port identifier."
        ::= { wanPortEntry 2 }

wanTxBufferSize         OBJECT-TYPE
        SYNTAX          INTEGER
        MAX-ACCESS      read-write
        STATUS          current
        DESCRIPTION     "Size of each Tx buffer (bytes)."
        DEFVAL          { 1600 }
        ::= { wanPortEntry 3 }

wanTxBuffers            OBJECT-TYPE
        SYNTAX          INTEGER
        MAX-ACCESS      read-write
        STATUS          current
        DESCRIPTION     "Number of trasmit buffers."
        DEFVAL          { 128 }
        ::= { wanPortEntry 4 }

wanTxMaxPending         OBJECT-TYPE
        SYNTAX          INTEGER
        MAX-ACCESS      read-write
        STATUS          current
        DESCRIPTION     "Maximum pending Tx packets."
        DEFVAL          { 0 }
        ::= { wanPortEntry 5 }

wanRxBufferSize         OBJECT-TYPE
        SYNTAX          INTEGER
        MAX-ACCESS      read-write
        STATUS          current
        DESCRIPTION     "Size of each Rx buffer (bytes)."
        DEFVAL          { 1600 }
        ::= { wanPortEntry 6 }

wanRxBuffers            OBJECT-TYPE
        SYNTAX          INTEGER
        MAX-ACCESS      read-write
        STATUS          current
        DESCRIPTION     "Number of receive buffers."
        DEFVAL          { 128 }
        ::= { wanPortEntry 7 }

wanMaxRxFrameSize       OBJECT-TYPE
        SYNTAX          INTEGER
        MAX-ACCESS      read-write
        STATUS          current
        DESCRIPTION     "Maximum size of Rx frame."
        DEFVAL          { 1700 }
        ::= { wanPortEntry 8 }

wanLoopback             OBJECT-TYPE
        SYNTAX          WanLoopbackMode
        MAX-ACCESS      read-write
        STATUS          current
        DESCRIPTION     "Loopback mode."
        DEFVAL          { wanLoopbackNone }
        ::= { wanPortEntry 9 }

wanCrcMode              OBJECT-TYPE
        SYNTAX          WanCrcMode
        MAX-ACCESS      read-write
        STATUS          current
        DESCRIPTION     "CRC mode."
        DEFVAL          { wanCrc16 }
        ::= { wanPortEntry 10 }

wanClocking             OBJECT-TYPE
        SYNTAX          WanClock
        MAX-ACCESS      read-write
        STATUS          current
        DESCRIPTION     "DS-1 clocking."
        DEFVAL          { external }
        ::= { wanPortEntry 11 }

wanDataRate             OBJECT-TYPE
        SYNTAX          WanBitRate
        MAX-ACCESS      read-write
        STATUS          current
        DESCRIPTION     "DS-0 rate."
        DEFVAL          { bitRate64k }
        ::= { wanPortEntry 12 }

wanCoding               OBJECT-TYPE
        SYNTAX          WanLineCoding
        MAX-ACCESS      read-write
        STATUS          current
        DESCRIPTION     "DS-1 line coding."
        DEFVAL          { lineCodingB8ZS }
        ::= { wanPortEntry 13 }

wanFraming              OBJECT-TYPE
        SYNTAX          WanLineMode
        MAX-ACCESS      read-write
        STATUS          current
        DESCRIPTION     "DS-1 line mode."
        DEFVAL          { lineModeESF }
        ::= { wanPortEntry 14 }

wanRxGain               OBJECT-TYPE
        SYNTAX          WanLineGain
        MAX-ACCESS      read-write
        STATUS          current
        DESCRIPTION     "DS-1 Rx equalizer gain."
        DEFVAL          { lineGain36db }
        ::= { wanPortEntry 15 }

wanLbo                  OBJECT-TYPE
        SYNTAX          WanLineBuildOut
        MAX-ACCESS      read-write
        STATUS          current
        DESCRIPTION     "DS-1 line build out."
        DEFVAL          { lbo1Mile }
        ::= { wanPortEntry 16 }

wanPolarity             OBJECT-TYPE
        SYNTAX          WanPolarity
        MAX-ACCESS      read-write
        STATUS          current
        DESCRIPTION     "DS-1 data polarity mode."
        DEFVAL          { normalData }
        ::= { wanPortEntry 17 }

wanPulse                OBJECT-TYPE
        SYNTAX          WanFeatureState
        MAX-ACCESS      read-write
        STATUS          current
        DESCRIPTION     "DS-1 pulse density enforcer."
        DEFVAL          { featureDisabled }
        ::= { wanPortEntry 18 }

wanJitter               OBJECT-TYPE
        SYNTAX          WanFeatureState
        MAX-ACCESS      read-write
        STATUS          current
        DESCRIPTION     "DS-1 jitter attenuator."
        DEFVAL          { featureDisabled }
        ::= { wanPortEntry 19 }

wanJitterSide           OBJECT-TYPE
        SYNTAX          WanJitterAttenuation
        MAX-ACCESS      read-write
        STATUS          current
        DESCRIPTION     "DS-1 jitter attenuator."
        DEFVAL          { jitterAttenTx }
        ::= { wanPortEntry 20 }

wanChan1to8             OBJECT-TYPE
        SYNTAX          WanFeatureState
        MAX-ACCESS      read-write
        STATUS          current
        DESCRIPTION     "DS-0's 1-8 enabled."
        DEFVAL          { featureEnabled }
        ::= { wanPortEntry 21 }

wanChan9to16            OBJECT-TYPE
        SYNTAX          WanFeatureState
        MAX-ACCESS      read-write
        STATUS          current
        DESCRIPTION     "DS-0's 9-16 enabled."
        DEFVAL          { featureEnabled }
        ::= { wanPortEntry 22 }

wanChan17to24           OBJECT-TYPE
        SYNTAX          WanFeatureState
        MAX-ACCESS      read-write
        STATUS          current
        DESCRIPTION     "DS-0's 17-24 enabled."
        DEFVAL          { featureEnabled }
        ::= { wanPortEntry 23 }

wanChan25to32           OBJECT-TYPE
        SYNTAX          WanFeatureState
        MAX-ACCESS      read-write
        STATUS          current
        DESCRIPTION     "DS-0's 25-32 enabled."
        DEFVAL          { featureEnabled }
        ::= { wanPortEntry 24 }

wanPortValid            OBJECT-TYPE
        SYNTAX          TruthValue
        MAX-ACCESS      read-write
        STATUS          current
        DESCRIPTION     "Indicates if this port is valid."
	DEFVAL         	{ false }
        ::= { wanPortEntry 25 }



-- Multi-link PPP
mlppp       OBJECT IDENTIFIER ::= { rrBackHaulUnit 3 }

mlpppReconfigure        OBJECT-TYPE
        SYNTAX          TruthValue
        MAX-ACCESS      read-write
        STATUS          current
        DESCRIPTION     "Set to true to reconfigure MLPPP."
        ::= { mlppp 1 }

bundleTable             OBJECT-TYPE
        SYNTAX          SEQUENCE OF BundleEntry
        MAX-ACCESS      not-accessible
        STATUS          current
        DESCRIPTION     "MLPPP bundle table."
        ::= { mlppp 2 }

bundleEntry             OBJECT-TYPE
        SYNTAX          BundleEntry
        MAX-ACCESS      not-accessible
        STATUS          current
        DESCRIPTION     "MLPPP bundle table entry."
        INDEX           { bundleId }
        ::= { bundleTable 1 }

BundleEntry ::= SEQUENCE {
        bundleId                    INTEGER,
        bundleValid                 TruthValue,
        bundleMultilink             WanFeatureState,
        bundleCompression           WanFeatureState,
        bundleInterface             DisplayString,
        bundleLinkChap              WanFeatureState,
        bundleLinkPap               WanFeatureState,
        bundleLinkMru               INTEGER,
        bundleLinkMtu               INTEGER,
        bundleLinkKeepAliveIntvl    INTEGER,
        bundleLinkKeepAliveDur      INTEGER,
        bundleLinkAcfComp           WanFeatureState,
        bundleLinkProtoComp         WanFeatureState,
        bundleIfaceOnDemand         WanFeatureState,
        bundleIfaceIdleTimeout      INTEGER,
        bundleIpcpVjComp            WanFeatureState,
        bundleIpcpDns               IpAddress,
        bundleIpcpNbns              IpAddress,
        bundleIpcpLocalIpAddr       DisplayString,
        bundleIpcpPeerIpAddr        DisplayString,
        bundleRouteHandling         RouteHandling
}

bundleId                OBJECT-TYPE
        SYNTAX          INTEGER
        MAX-ACCESS      read-only
        STATUS          current
        DESCRIPTION     "The MLPPP bundle identifier."
        ::= { bundleEntry 1 }

bundleValid             OBJECT-TYPE
        SYNTAX          TruthValue
        MAX-ACCESS      read-write
        STATUS          current
        DESCRIPTION     "Indicates if this MLPPP bundle is valid."
        ::= { bundleEntry 2 }

bundleMultilink         OBJECT-TYPE
        SYNTAX          WanFeatureState
        MAX-ACCESS      read-write
        STATUS          current
        DESCRIPTION     "Indicates if multilink is enabled."
        ::= { bundleEntry 3 }

bundleCompression       OBJECT-TYPE
        SYNTAX          WanFeatureState
        MAX-ACCESS      read-write
        STATUS          current
        DESCRIPTION     "Indicates if multilink is enabled."
        ::= { bundleEntry 4 }

bundleInterface         OBJECT-TYPE
        SYNTAX          DisplayString
        MAX-ACCESS      read-write
        STATUS          current
        DESCRIPTION     "Netgraph interface name. Valid values are 
                        'ppp0' or 'ppp1'."
        ::= { bundleEntry 5 }

bundleLinkChap          OBJECT-TYPE
        SYNTAX          WanFeatureState
        MAX-ACCESS      read-write
        STATUS          current
        DESCRIPTION     "Indicates if CHAP Authentication is enabled."
        DEFVAL          { featureDisabled }
        ::= { bundleEntry 6 }

bundleLinkPap           OBJECT-TYPE
        SYNTAX          WanFeatureState
        MAX-ACCESS      read-write
        STATUS          current
        DESCRIPTION     "Indicates if PAP Authentication is enabled."
        DEFVAL          { featureDisabled }
        ::= { bundleEntry 7 }

bundleLinkMru           OBJECT-TYPE
        SYNTAX          INTEGER
        MAX-ACCESS      read-write
        STATUS          current
        DESCRIPTION     "PPP maximum receive unit (int bytes)."
        DEFVAL          { 1580 }
        ::= { bundleEntry 8 }

bundleLinkMtu           OBJECT-TYPE
        SYNTAX          INTEGER
        MAX-ACCESS      read-write
        STATUS          current
        DESCRIPTION     "PPP maximum trasmit unit (int bytes)."
        DEFVAL          { 1580 }
        ::= { bundleEntry 9 }

bundleLinkKeepAliveIntvl   OBJECT-TYPE
        SYNTAX          INTEGER
        MAX-ACCESS      read-write
        STATUS          current
        DESCRIPTION     "PPP LCP keep-alive interval."
        DEFVAL          { 5 }
        ::= { bundleEntry 10 }

bundleLinkKeepAliveDur  OBJECT-TYPE
        SYNTAX          INTEGER
        MAX-ACCESS      read-write
        STATUS          current
        DESCRIPTION     "PPP LCP keep-alive duration."
        DEFVAL          { 30 }
        ::= { bundleEntry 11 }

bundleLinkAcfComp       OBJECT-TYPE
        SYNTAX          WanFeatureState
        MAX-ACCESS      read-write
        STATUS          current
        DESCRIPTION     "PPP Address/Control Field compression."
        DEFVAL          { featureDisabled }
        ::= { bundleEntry 12 }

bundleLinkProtoComp     OBJECT-TYPE
        SYNTAX          WanFeatureState
        MAX-ACCESS      read-write
        STATUS          current
        DESCRIPTION     "PPP Protocol Field compression."
        DEFVAL          { featureDisabled }
        ::= { bundleEntry 13 }

bundleIfaceOnDemand     OBJECT-TYPE
        SYNTAX          WanFeatureState
        MAX-ACCESS      read-write
        STATUS          current
        DESCRIPTION     "On demand dialing."
        DEFVAL          { featureDisabled }
        ::= { bundleEntry 14 }

bundleIfaceIdleTimeout  OBJECT-TYPE
        SYNTAX          INTEGER
        MAX-ACCESS      read-write
        STATUS          current
        DESCRIPTION     "PPP idle timeout (0 means disabled)."
        DEFVAL          { 0 }
        ::= { bundleEntry 15 }

bundleIpcpVjComp        OBJECT-TYPE
        SYNTAX          WanFeatureState
        MAX-ACCESS      read-write
        STATUS          current
        DESCRIPTION     "TCP VJ compression."
        DEFVAL          { featureDisabled }
        ::= { bundleEntry 16 }

bundleIpcpDns           OBJECT-TYPE
        SYNTAX          IpAddress
        MAX-ACCESS      read-write
        STATUS          current
        DESCRIPTION     "Domain Name Server."
        ::= { bundleEntry 17 }

bundleIpcpNbns          OBJECT-TYPE
        SYNTAX          IpAddress
        MAX-ACCESS      read-write
        STATUS          current
        DESCRIPTION     "Netbios Name Server."
        ::= { bundleEntry 18 }

bundleIpcpLocalIpAddr   OBJECT-TYPE
        SYNTAX          DisplayString
        MAX-ACCESS      read-write
        STATUS          current
        DESCRIPTION     "Local MLPPP IP address. The format of this object is
                        '<ip address>/<mask>'."
        ::= { bundleEntry 19 }

bundleIpcpPeerIpAddr    OBJECT-TYPE
        SYNTAX          DisplayString
        MAX-ACCESS      read-write
        STATUS          current
        DESCRIPTION     "Peer MLPPP IP address. The format of this object is
                        '<ip address>/<mask>'."
        ::= { bundleEntry 20 }

bundleRouteHandling     OBJECT-TYPE
        SYNTAX          RouteHandling
        MAX-ACCESS      read-write
        STATUS          deprecated
        DESCRIPTION     "MLPPP handling of supernetting of MLPPP interfaces."
        DEFVAL          { rtHandlingReject }
        ::= { bundleEntry 21 }

wanlinksTable           OBJECT-TYPE
        SYNTAX          SEQUENCE OF WanlinksEntry
        MAX-ACCESS      not-accessible
        STATUS          current
        DESCRIPTION     "WAN links table."
        ::= { mlppp 3 }

wanlinksEntry           OBJECT-TYPE
        SYNTAX          WanlinksEntry
        MAX-ACCESS      not-accessible
        STATUS          current
        DESCRIPTION     "WAN links table entry."
        INDEX           { wanlinksBundleId, wanlinksId }
        ::= { wanlinksTable 1 }

WanlinksEntry ::= SEQUENCE {
        wanlinksBundleId    INTEGER,
        wanlinksId          INTEGER,
        wanlinksInBundle    TruthValue
}

wanlinksBundleId        OBJECT-TYPE
        SYNTAX          INTEGER
        MAX-ACCESS      read-only
        STATUS          current
        DESCRIPTION     "The WAN links bundle identifier."
        ::= { wanlinksEntry 1 }

wanlinksId              OBJECT-TYPE
        SYNTAX          INTEGER
        MAX-ACCESS      read-only
        STATUS          current
        DESCRIPTION     "The WAN link identifier."
        ::= { wanlinksEntry 2 }

wanlinksInBundle        OBJECT-TYPE
        SYNTAX          TruthValue
        MAX-ACCESS      read-write
        STATUS          current
        DESCRIPTION     "Indicates if wanlinks are in the bundle."
        ::= { wanlinksEntry 3 }


ifaceRouteTable         OBJECT-TYPE
        SYNTAX          SEQUENCE OF IfaceRouteEntry
        MAX-ACCESS      not-accessible
        STATUS          deprecated
        DESCRIPTION     "Bundle interface routing table."
        ::= { mlppp 4 }

ifaceRouteEntry         OBJECT-TYPE
        SYNTAX          IfaceRouteEntry
        MAX-ACCESS      not-accessible
        STATUS          deprecated
        DESCRIPTION     "Bundle interface route entry."
        INDEX           { ifaceRtBundleId, ifaceRouteId }
        ::= { ifaceRouteTable 1 }

IfaceRouteEntry ::= SEQUENCE {
        ifaceRtBundleId     INTEGER,
        ifaceRouteId        INTEGER,
        ifaceRoute          DisplayString
}

ifaceRtBundleId         OBJECT-TYPE
        SYNTAX          INTEGER
        MAX-ACCESS      read-only
        STATUS          deprecated
        DESCRIPTION     "The bundle identifier."
        ::= { ifaceRouteEntry 1 }

ifaceRouteId            OBJECT-TYPE
        SYNTAX          INTEGER
        MAX-ACCESS      read-only
        STATUS          deprecated
        DESCRIPTION     "The bundle interface route identifier."
        ::= { ifaceRouteEntry 2 }

ifaceRoute              OBJECT-TYPE
        SYNTAX          DisplayString
        MAX-ACCESS      read-write
        STATUS          deprecated
        DESCRIPTION     "The interface route. The format of this object is
                        '<ip address>/<mask>'."
        ::= { ifaceRouteEntry 3 }

-- Backhaul QoS
bhQosReconfigure    OBJECT-TYPE
    SYNTAX          TruthValue
    MAX-ACCESS      read-write
    STATUS          current
    DESCRIPTION     "Set to true(1) to reconfigure."
    ::= { rrBhQos 1 }

bhQosAqmParams      OBJECT-TYPE
    SYNTAX          DisplayString
    MAX-ACCESS      read-write
    STATUS          current
    DESCRIPTION     "Active Queue Management parameters."
    DEFVAL          { "40 50 10 40 50 10 20 30 10 5 15 10" }
    ::= { rrBhQos 2 }

-- Backhaul QoS Group Table

bhQosGroupTable     OBJECT-TYPE
    SYNTAX          SEQUENCE OF BhQosGroupEntry
    MAX-ACCESS      not-accessible
    STATUS          current
    DESCRIPTION     "This table is used to configure QoS groups."
    ::= { rrBhQos 3 }

bhQosGroupEntry     OBJECT-TYPE
    SYNTAX          BhQosGroupEntry
    MAX-ACCESS      not-accessible
    STATUS          current
    DESCRIPTION     ""
    INDEX           { bhQosGroupIndex }
    ::= { bhQosGroupTable 1 }

BhQosGroupEntry ::= SEQUENCE {
    bhQosGroupIndex     INTEGER,
    bhQosGroupName      DisplayString,
    bhQosGroupStatus    RowStatus
}

bhQosGroupIndex     OBJECT-TYPE
    SYNTAX          INTEGER
    MAX-ACCESS      read-write
    STATUS          current
    DESCRIPTION     "The table index value."
    ::= { bhQosGroupEntry 1 }

bhQosGroupName      OBJECT-TYPE
    SYNTAX          DisplayString
    MAX-ACCESS      read-write
    STATUS          current
    DESCRIPTION     "A get on this object returns the group name. A new
                    group can be added by first setting bhQosGroupStatus
                    to createAndWait(5) to create the conceptual row.
                    Then set this object with the group's name. Finally,
                    commit the value by setting bhQosGroupStatus to
                    active(1)."
    ::= { bhQosGroupEntry 2 }

bhQosGroupStatus    OBJECT-TYPE
    SYNTAX          RowStatus
    MAX-ACCESS      read-create
    STATUS          current
    DESCRIPTION     "This object is used to change the state of a
                    conceptual row. Only active(1), createAndWait(5), and
                    destroy(6) are supported."
    ::= { bhQosGroupEntry 3 }


-- Backhaul QoS Group Class Table

bhQosGroupClassTable    OBJECT-TYPE
    SYNTAX          SEQUENCE OF BhQosGroupClassEntry
    MAX-ACCESS      not-accessible
    STATUS          current
    DESCRIPTION     "This table is used to configure QoS group classes."
    ::= { rrBhQos 4 }

bhQosGroupClassEntry     OBJECT-TYPE
    SYNTAX          BhQosGroupClassEntry
    MAX-ACCESS      not-accessible
    STATUS          current
    DESCRIPTION     ""
    INDEX           { bhQosGroupIndex1, bhQosGroupClassIndex }
    ::= { bhQosGroupClassTable 1 }

BhQosGroupClassEntry ::= SEQUENCE {
    bhQosGroupIndex1         INTEGER,
    bhQosGroupClassIndex     INTEGER,
    bhQosGroupClassName      DisplayString,
    bhQosGroupClassStatus    RowStatus
}

bhQosGroupIndex1    OBJECT-TYPE
    SYNTAX          INTEGER
    MAX-ACCESS      read-write
    STATUS          current
    DESCRIPTION     "The group index associated with this class entry.
                    This index can be used to look up the group name in the
                    bhQosGroupTable."
    ::= { bhQosGroupClassEntry 1 }

bhQosGroupClassIndex    OBJECT-TYPE
    SYNTAX          INTEGER
    MAX-ACCESS      read-write
    STATUS          current
    DESCRIPTION     "An index value for this class entry."
    ::= { bhQosGroupClassEntry 2 }

bhQosGroupClassName OBJECT-TYPE
    SYNTAX          DisplayString
    MAX-ACCESS      read-write
    STATUS          current
    DESCRIPTION     "A get on this object returns the group name. A new
                    group can be added by first setting bhQosGroupClassStatus
                    to createAndWait(5) to create the conceptual row.
                    Then set this object with the group's name. Finally,
                    commit the value by setting bhQosGroupClassStatus to
                    active(1)."
    ::= { bhQosGroupClassEntry 3 }

bhQosGroupClassStatus   OBJECT-TYPE
    SYNTAX          RowStatus
    MAX-ACCESS      read-create
    STATUS          current
    DESCRIPTION     "This object is used to change the state of a
                    conceptual row. Only active(1), createAndWait(5), and
                    destroy(6) are supported."
    ::= { bhQosGroupClassEntry 4 }

-- Backhaul QoS Group Filter Table

bhQosGroupFilterTable   OBJECT-TYPE
    SYNTAX          SEQUENCE OF BhQosGroupFilterEntry
    MAX-ACCESS      not-accessible
    STATUS          current
    DESCRIPTION     "This table is used to configure QoS group filters."
    ::= { rrBhQos 5 }

bhQosGroupFilterEntry   OBJECT-TYPE
    SYNTAX          BhQosGroupFilterEntry
    MAX-ACCESS      not-accessible
    STATUS          current
    DESCRIPTION     ""
    INDEX           { bhQosGroupIndex2, bhQosGroupFilterIndex }
    ::= { bhQosGroupFilterTable 1 }

BhQosGroupFilterEntry ::= SEQUENCE {
    bhQosGroupIndex2        INTEGER,
    bhQosGroupFilterIndex   INTEGER,
    bhQosGroupFilterName    DisplayString,
    bhQosGroupFilterStatus  RowStatus
}

bhQosGroupIndex2    OBJECT-TYPE
    SYNTAX          INTEGER
    MAX-ACCESS      read-write
    STATUS          current
    DESCRIPTION     "The group index associated with this filter entry.
                    This index can be used to look up the group name in the
                    bhQosGroupTable."
    ::= { bhQosGroupFilterEntry 1 }

bhQosGroupFilterIndex   OBJECT-TYPE
    SYNTAX          INTEGER
    MAX-ACCESS      read-write
    STATUS          current
    DESCRIPTION     "An index value for this filter entry."
    ::= { bhQosGroupFilterEntry 2 }

bhQosGroupFilterName    OBJECT-TYPE
    SYNTAX          DisplayString
    MAX-ACCESS      read-write
    STATUS          current
    DESCRIPTION     "A get on this object returns the group name. A new
                    group can be added by first setting bhQosGroupFilterStatus
                    to createAndWait(5) to create the conceptual row.
                    Then set this object with the group's name. Finally,
                    commit the value by setting bhQosGroupFilterStatus to
                    active(1)."
    ::= { bhQosGroupFilterEntry 3 }

bhQosGroupFilterStatus   OBJECT-TYPE
    SYNTAX          RowStatus
    MAX-ACCESS      read-create
    STATUS          current
    DESCRIPTION     "This object is used to change the state of a
                    conceptual row. Only active(1), createAndWait(5), and
                    destroy(6) are supported."
    ::= { bhQosGroupFilterEntry 4 }

-- Backhaul QoS Group Marker Table

bhQosGroupMarkerTable   OBJECT-TYPE
    SYNTAX          SEQUENCE OF BhQosGroupMarkerEntry
    MAX-ACCESS      not-accessible
    STATUS          current
    DESCRIPTION     "This table is used to configure QoS group markers."
    ::= { rrBhQos 6 }

bhQosGroupMarkerEntry   OBJECT-TYPE
    SYNTAX          BhQosGroupMarkerEntry
    MAX-ACCESS      not-accessible
    STATUS          current
    DESCRIPTION     ""
    INDEX           { bhQosGroupIndex3, bhQosGroupMarkerIndex }
    ::= { bhQosGroupMarkerTable 1 }

BhQosGroupMarkerEntry ::= SEQUENCE {
    bhQosGroupIndex3        INTEGER,
    bhQosGroupMarkerIndex   INTEGER,
    bhQosGroupMarkerName    DisplayString,
    bhQosGroupMarkerStatus  RowStatus
}

bhQosGroupIndex3    OBJECT-TYPE
    SYNTAX          INTEGER
    MAX-ACCESS      read-write
    STATUS          current
    DESCRIPTION     "The group index associated with this marker entry.
                    This index can be used to look up the group name in the
                    bhQosGroupTable."
    ::= { bhQosGroupMarkerEntry 1 }

bhQosGroupMarkerIndex   OBJECT-TYPE
    SYNTAX          INTEGER
    MAX-ACCESS      read-write
    STATUS          current
    DESCRIPTION     "An index value for this marker entry."
    ::= { bhQosGroupMarkerEntry 2 }

bhQosGroupMarkerName    OBJECT-TYPE
    SYNTAX          DisplayString
    MAX-ACCESS      read-write
    STATUS          current
    DESCRIPTION     "A get on this object returns the group name. A new
                    group can be added by first setting bhQosGroupMarkerStatus
                    to createAndWait(5) to create the conceptual row.
                    Then set this object with the group's name. Finally,
                    commit the value by setting bhQosGroupMarkerStatus to
                    active(1)."
    ::= { bhQosGroupMarkerEntry 3 }

bhQosGroupMarkerStatus   OBJECT-TYPE
    SYNTAX          RowStatus
    MAX-ACCESS      read-create
    STATUS          current
    DESCRIPTION     "This object is used to change the state of a
                    conceptual row. Only active(1), createAndWait(5), and
                    destroy(6) are supported."
    ::= { bhQosGroupMarkerEntry 4 }



--
--
-- Software Release Management
--
relConfig           OBJECT IDENTIFIER ::= { rrRelease 1 }
relStatus           OBJECT IDENTIFIER ::= { rrRelease 2 }
relAction           OBJECT IDENTIFIER ::= { rrRelease 3 }


relServerIpAddr         OBJECT-TYPE
        SYNTAX          IpAddress
        MAX-ACCESS      read-write
        STATUS          deprecated
        DESCRIPTION     "The IP address of the FTP server containing the
                        release."
        ::= { relConfig 1 }

relPkgPath              OBJECT-TYPE
        SYNTAX          DisplayString
        MAX-ACCESS      read-write
        STATUS          deprecated
        DESCRIPTION     "The absolute path to the package file on the FTP
                        server specified by relServerIpAddr."
        ::= { relConfig 2 }

relOsPath               OBJECT-TYPE
        SYNTAX          DisplayString
        MAX-ACCESS      read-write
        STATUS          deprecated
        DESCRIPTION     "The absolute path to the OS distribution directory on
                        the FTP server specified by relServerIpAddr."
        ::= { relConfig 3 }

relApplyToStandby       OBJECT-TYPE
        SYNTAX          TruthValue
        MAX-ACCESS      read-write
        STATUS          deprecated
        DESCRIPTION     "Set this object to 'true' to upgrade the standby
                        partition. This object is only relevant when upgrading
                        packages."
        ::= { relConfig 4 }

relBootPartition        OBJECT-TYPE
        SYNTAX          INTEGER (1..2)
        MAX-ACCESS      read-write
        STATUS          deprecated
        DESCRIPTION     "The partition to boot after next system reboot."
        ::= { relConfig 5 }

relPkgRunVer            OBJECT-TYPE
        SYNTAX          DisplayString
        MAX-ACCESS      read-write
        STATUS          deprecated
        DESCRIPTION     "This object sets the package version to run.
                        Setting this object causes the system to automatically
                        restart or reboot and run the specified package. A
                        reboot will be performed if the relBootPartition object 
                        is different than the current active partition,
                        specified by activePartition."
        ::= { relConfig 6 }

relOsUpgradeType        OBJECT-TYPE
        SYNTAX          OsUpgradeType
        MAX-ACCESS      read-write
        STATUS          deprecated
        DESCRIPTION     "OS upgrade type."
        DEFVAL          { binary }     
        ::= { relConfig 7 }

relUpgradeStatus        OBJECT-TYPE
        SYNTAX          DownloadState
        MAX-ACCESS      read-only
        STATUS          deprecated
        DESCRIPTION     "The current download status."
        ::= { relStatus 1 }

relPctComplete          OBJECT-TYPE
        SYNTAX          INTEGER
        MAX-ACCESS      read-only
        STATUS          deprecated
        DESCRIPTION     "Download progress expressed as percentage complete."
        ::= { relStatus 2 }

relErrorReason          OBJECT-TYPE
        SYNTAX          DisplayString
        MAX-ACCESS      read-only
        STATUS          deprecated
        DESCRIPTION     "If relUpgradeStatus reports failure, this object will
                        contain the reason for the failure."
        ::= { relStatus 3 }

activePartition         OBJECT-TYPE
        SYNTAX          INTEGER
        MAX-ACCESS      read-only
        STATUS          deprecated
        DESCRIPTION     "The disk slice number of the active partition."
        ::= { relStatus 4 }

activeOsVer             OBJECT-TYPE
        SYNTAX          DisplayString
        MAX-ACCESS      read-only
        STATUS          deprecated
        DESCRIPTION     "The active partition OS version."
        ::= { relStatus 5 }

standbyOsVer            OBJECT-TYPE
        SYNTAX          DisplayString
        MAX-ACCESS      read-only
        STATUS          deprecated
        DESCRIPTION     "The standby partition OS version."
        ::= { relStatus 6 }

activePkgTable          OBJECT-TYPE
        SYNTAX          SEQUENCE OF ActivePkgTableEntry
        MAX-ACCESS      not-accessible
        STATUS          deprecated
        DESCRIPTION     "Active partition package table."
        ::= { relStatus 7 }

activePkgTableEntry     OBJECT-TYPE
        SYNTAX          ActivePkgTableEntry
        MAX-ACCESS      not-accessible
        STATUS          deprecated
        DESCRIPTION     ""
        INDEX           { activePkgIndex }
        ::= { activePkgTable 1 }

ActivePkgTableEntry ::= SEQUENCE {
        activePkgIndex      INTEGER,
        activePkgName       DisplayString
}

activePkgIndex          OBJECT-TYPE
        SYNTAX          INTEGER
        MAX-ACCESS      read-only
        STATUS          deprecated
        DESCRIPTION     "The table index value."
        ::= { activePkgTableEntry 1 }

activePkgName           OBJECT-TYPE
        SYNTAX          DisplayString
        MAX-ACCESS      read-only
        STATUS          deprecated
        DESCRIPTION     "The package name."
        ::= { activePkgTableEntry 2 }


standbyPkgTable         OBJECT-TYPE
        SYNTAX          SEQUENCE OF StandbyPkgTableEntry
        MAX-ACCESS      not-accessible
        STATUS          deprecated
        DESCRIPTION     "Standby partition package table."
        ::= { relStatus 8 }

standbyPkgTableEntry    OBJECT-TYPE
        SYNTAX          StandbyPkgTableEntry
        MAX-ACCESS      not-accessible
        STATUS          deprecated
        DESCRIPTION     ""
        INDEX           { standbyPkgIndex }
        ::= { standbyPkgTable 1 }

StandbyPkgTableEntry ::= SEQUENCE {
        standbyPkgIndex     INTEGER,
        standbyPkgName      DisplayString
}

standbyPkgIndex         OBJECT-TYPE
        SYNTAX          INTEGER
        MAX-ACCESS      read-only
        STATUS          deprecated
        DESCRIPTION     "The table index value."
        ::= { standbyPkgTableEntry 1 }

standbyPkgName          OBJECT-TYPE
        SYNTAX          DisplayString
        MAX-ACCESS      read-only
        STATUS          deprecated
        DESCRIPTION     "The package name."
        ::= { standbyPkgTableEntry 2 }

currentRunVer           OBJECT-TYPE
        SYNTAX          DisplayString
        MAX-ACCESS      read-only
        STATUS          deprecated
        DESCRIPTION     "Current running version."
        ::= { relStatus 9 }

relMediaType            OBJECT-TYPE
        SYNTAX          MediaType
        MAX-ACCESS      read-only
        STATUS          deprecated
        DESCRIPTION     "Media type."
        ::= { relStatus 10 }

relDoPkgUpgrade         OBJECT-TYPE
        SYNTAX          TruthValue
        MAX-ACCESS      read-write
        STATUS          deprecated
        DESCRIPTION     "Set to 'true' to begin package upgrade. If 
                         relConfig.relApplyToStandby object is set to 'true', 
                         the standby partition will be upgraded."
        ::= { relAction 1 }

relDoOsUpgrade          OBJECT-TYPE
        SYNTAX          TruthValue
        MAX-ACCESS      read-write
        STATUS          deprecated
        DESCRIPTION     "Set to 'true' to begin OS upgrade."
        ::= { relAction 2 }

relDeletePkg            OBJECT-TYPE
        SYNTAX          DisplayString
        MAX-ACCESS      read-write
        STATUS          deprecated
        DESCRIPTION     "This object takes a package name as its value. Setting                         this object will delete the package. If the
                        relConfig.relApplyToStandby object is set to 'true',
                        the package will be deleted from the standby partition."
        ::= { relAction 3 }

relSysAction            OBJECT-TYPE
        SYNTAX          SysAction
        MAX-ACCESS      read-write
        STATUS          deprecated
        DESCRIPTION     "When this object is set to restart(1), the basestation 
                        software software is restarted. If reboot(2) is
                        specified, the MCU is rebooted."
        ::= { relAction 4 }


-- DNS
dnsReconfigure          OBJECT-TYPE
        SYNTAX          TruthValue
        MAX-ACCESS      read-write
        STATUS          current
        DESCRIPTION     "Set to true to reconfigure DNS."
        ::= { rrDns 1 }

dnsNameServerTable      OBJECT-TYPE
        SYNTAX          SEQUENCE OF DnsNameServerEntry
        MAX-ACCESS      not-accessible
        STATUS          current
        DESCRIPTION     "DNS name server table."
        ::= { rrDns 2 }

dnsNameServerEntry      OBJECT-TYPE
        SYNTAX          DnsNameServerEntry
        MAX-ACCESS      not-accessible
        STATUS          current
        DESCRIPTION     ""
        INDEX           { dnsNameServerIndex }
        ::= { dnsNameServerTable 1 }

DnsNameServerEntry ::= SEQUENCE {
        dnsNameServerIndex       INTEGER,
        dnsNameServerAddr        IpAddress
}

dnsNameServerIndex      OBJECT-TYPE
        SYNTAX          INTEGER
        MAX-ACCESS      read-only
        STATUS          current
        DESCRIPTION     "The table index value."
        ::= { dnsNameServerEntry 1 }

dnsNameServerAddr       OBJECT-TYPE
        SYNTAX          IpAddress
        MAX-ACCESS      read-write
        STATUS          current
        DESCRIPTION     "The IP address of DNS name server."
        ::= { dnsNameServerEntry 2 }

dnsSearchTable          OBJECT-TYPE
        SYNTAX          SEQUENCE OF DnsSearchEntry
        MAX-ACCESS      not-accessible
        STATUS          current
        DESCRIPTION     "DNS domain search table."
        ::= { rrDns 3 }

dnsSearchEntry          OBJECT-TYPE
        SYNTAX          DnsSearchEntry
        MAX-ACCESS      not-accessible
        STATUS          current
        DESCRIPTION     ""
        INDEX           { dnsSearchIndex }
        ::= { dnsSearchTable 1 }

DnsSearchEntry ::= SEQUENCE {
        dnsSearchIndex      INTEGER,
        dnsSearchDomain     DisplayString
}

dnsSearchIndex          OBJECT-TYPE
        SYNTAX          INTEGER
        MAX-ACCESS      read-only
        STATUS          current
        DESCRIPTION     "The table index value."
        ::= { dnsSearchEntry 1 }

dnsSearchDomain         OBJECT-TYPE
        SYNTAX          DisplayString
        MAX-ACCESS      read-write
        STATUS          current
        DESCRIPTION     "The domain name suffix."
        ::= { dnsSearchEntry 2 }

-- Route Provisioning Table
routeProvTable          OBJECT-TYPE
        SYNTAX          SEQUENCE OF RouteProvEntry
        MAX-ACCESS      not-accessible
        STATUS          current
        DESCRIPTION     "This table is used to configure the routing table."
        ::= { rrRoutes 1 }

routeProvEntry          OBJECT-TYPE
        SYNTAX          RouteProvEntry
        MAX-ACCESS      not-accessible
        STATUS          current
        DESCRIPTION     ""
        INDEX           { routeProvIndex }
        ::= { routeProvTable 1 }

RouteProvEntry ::= SEQUENCE {
        routeProvIndex      INTEGER,
        routeProvName       DisplayString,
        routeProvStatus     RowStatus
}

routeProvIndex          OBJECT-TYPE
        SYNTAX          INTEGER
        MAX-ACCESS      read-only
        STATUS          current
        DESCRIPTION     "The table index value."
        ::= { routeProvEntry 1 }

routeProvName           OBJECT-TYPE
        SYNTAX          DisplayString
        MAX-ACCESS      read-write
        STATUS          current
        DESCRIPTION     "A get on this object returns the route name. A new
                        route can be added by first setting routeProvStatus
                        to createAndWait(5) to create the conceptual row.
                        Then set this object with the route value. Finally,
                        commit the value by setting routeProvStatus to
                        active(1)."
        ::= { routeProvEntry 2 }

routeProvStatus         OBJECT-TYPE
        SYNTAX          RowStatus
        MAX-ACCESS      read-create
        STATUS          current
        DESCRIPTION     "This object is used to change the state of a
                        conceptual row. Only active(1), createAndWait(5), and
                        destroy(6) are supported."
        ::= { routeProvEntry 3 }


-- Route Runtime Table
routeRuntimeTable       OBJECT-TYPE
        SYNTAX          SEQUENCE OF RouteRuntimeEntry
        MAX-ACCESS      not-accessible
        STATUS          current
        DESCRIPTION     "This table displays the routes available in the
                        system."
        ::= { rrRoutes 2 }

routeRuntimeEntry       OBJECT-TYPE
        SYNTAX          RouteRuntimeEntry
        MAX-ACCESS      not-accessible
        STATUS          current
        DESCRIPTION     ""
        INDEX           { routeRuntimeIndex }
        ::= { routeRuntimeTable 1 }

RouteRuntimeEntry ::= SEQUENCE {
        routeRuntimeIndex      INTEGER,
        routeRuntimeName       DisplayString
}

routeRuntimeIndex       OBJECT-TYPE
        SYNTAX          INTEGER
        MAX-ACCESS      read-only
        STATUS          current
        DESCRIPTION     "The table index value."
        ::= { routeRuntimeEntry 1 }

routeRuntimeName        OBJECT-TYPE
        SYNTAX          DisplayString
        MAX-ACCESS      read-only
        STATUS          current
        DESCRIPTION     "The route information."
        ::= { routeRuntimeEntry 2 }

-- Route Protocol
routeProtocol   OBJECT-TYPE
    SYNTAX      RouteProtocol
    MAX-ACCESS  read-write
    STATUS      current
    DESCRIPTION "The route protocol."
    DEFVAL      { rtProtocolRIPv2 }
    ::= { rrRoutes 3 }

routeTosVal     OBJECT-TYPE
    SYNTAX      INTEGER (0..255)
    MAX-ACCESS  read-write
    STATUS      deprecated
    DESCRIPTION "The route Type Of Service."
    DEFVAL      { 220 }
    ::= { rrRoutes 4 }

routeDscp       OBJECT-TYPE
    SYNTAX      INTEGER (0..63)
    MAX-ACCESS  read-write
    STATUS      current
    DESCRIPTION "The route Diffserv codepoint."
    DEFVAL      { 55 }
    ::= { rrRoutes 5 }


--
-- User Groups
--
userGroupTable  OBJECT-TYPE
    SYNTAX      SEQUENCE OF UserGroupEntry
    MAX-ACCESS  not-accessible
    STATUS      current
    DESCRIPTION "This table contains a set of user groups used for
                QoS (Quality of Service)."
    ::= { rrUserGroups 1 }

userGroupEntry  OBJECT-TYPE
    SYNTAX      UserGroupEntry
    MAX-ACCESS  not-accessible
    STATUS      current
    DESCRIPTION ""
    INDEX       { userGroupIndex }
    ::= { userGroupTable 1 }

UserGroupEntry ::= SEQUENCE {
    userGroupIndex      INTEGER,
    userGroupName       DisplayString,
    userGroupStatus     RowStatus,
    userGroupUlRateCap  INTEGER,
    userGroupDlRateCap  INTEGER
}

userGroupIndex  OBJECT-TYPE
    SYNTAX      INTEGER
    MAX-ACCESS  read-only
    STATUS      current
    DESCRIPTION "User group index."
    ::= { userGroupEntry 1 }

userGroupName   OBJECT-TYPE
    SYNTAX      DisplayString
    MAX-ACCESS  read-write
    STATUS      current
    DESCRIPTION "A get on this object returns the user group name. A new
                group can be added by first setting userGroupStatus to
                createAndWait(5) to create the conceptual row. Then set this
                object with the group's name. Finally, commit the value by
                setting userGroupStatus to active(1)." 
    ::= { userGroupEntry 2 }

userGroupStatus OBJECT-TYPE
    SYNTAX      RowStatus
    MAX-ACCESS  read-create
    STATUS      current
    DESCRIPTION "This object is used to change the state of a
                conceptual row. Only active(1), createAndWait(5), and
                destroy(6) are supported."
    ::= { userGroupEntry 3 }

userGroupUlRateCap  OBJECT-TYPE
    SYNTAX      INTEGER
    MAX-ACCESS  read-write
    STATUS      current
    DESCRIPTION "User group uplink rate cap."
    ::= { userGroupEntry 4 }

userGroupDlRateCap  OBJECT-TYPE
    SYNTAX      INTEGER
    MAX-ACCESS  read-write
    STATUS      current
    DESCRIPTION "User group downlink rate cap."
    ::= { userGroupEntry 5 }


-- Group Rules
groupRulesTable OBJECT-TYPE
    SYNTAX      SEQUENCE OF GroupRulesEntry
    MAX-ACCESS  not-accessible
    STATUS      current
    DESCRIPTION "This table contains a set of QoS rules for each user group."
    ::= { rrUserGroups 2 }

groupRulesEntry OBJECT-TYPE
    SYNTAX      GroupRulesEntry
    MAX-ACCESS  not-accessible
    STATUS      current
    DESCRIPTION ""
    INDEX       { groupIndex, groupRuleIndex }
    ::= { groupRulesTable 1 }

GroupRulesEntry ::= SEQUENCE {
    groupIndex          INTEGER,
    groupRuleIndex      INTEGER,
    groupRuleName       DisplayString,
    groupRuleStatus     RowStatus
}

groupIndex      OBJECT-TYPE
    SYNTAX      INTEGER
    MAX-ACCESS  read-only
    STATUS      current
    DESCRIPTION "This object specifies the user group being queried. It is equal
                to the userGroupIndex in the userGroupTable."
    ::= { groupRulesEntry 1 }

groupRuleIndex  OBJECT-TYPE
    SYNTAX      INTEGER
    MAX-ACCESS  read-only
    STATUS      current
    DESCRIPTION "This object is an index to a rule for a particular user group,
                specified by groupIndex."
    ::= { groupRulesEntry 2 }

groupRuleName   OBJECT-TYPE
    SYNTAX      DisplayString
    MAX-ACCESS  read-write
    STATUS      current
    DESCRIPTION "A get on this object returns the user group rule. A new
                rule can be added by first setting groupRuleStatus to
                createAndWait(5) to create the conceptual row. Then set this
                object with the group's name. Finally, commit the value by
                setting groupRuleStatus to active(1)." 
    ::= { groupRulesEntry 3 }

groupRuleStatus OBJECT-TYPE
    SYNTAX      RowStatus
    MAX-ACCESS  read-create
    STATUS      current
    DESCRIPTION "This object is used to change the state of a
                conceptual row. Only active(1), createAndWait(5), and
                destroy(6) are supported."
    ::= { groupRulesEntry 4 }

-- Group Streams
groupStreamsTable   OBJECT-TYPE
    SYNTAX      SEQUENCE OF GroupStreamsEntry
    MAX-ACCESS  not-accessible
    STATUS      current
    DESCRIPTION "This table contains stream configuration for each user groups."
    ::= { rrUserGroups 3 }

groupStreamsEntry   OBJECT-TYPE
    SYNTAX      GroupStreamsEntry
    MAX-ACCESS  not-accessible
    STATUS      current
    DESCRIPTION ""
    INDEX       { groupIndex, groupStreamIndex }
    ::= { groupStreamsTable 1 }

GroupStreamsEntry ::= SEQUENCE {
    groupIndex1             INTEGER,
    groupStreamIndex        INTEGER,
    groupStreamUlRateCap    INTEGER,
    groupStreamDlRateCap    INTEGER,
    groupStreamUlTokenGain  INTEGER,
    groupStreamDlTokenGain  INTEGER
}

groupIndex1     OBJECT-TYPE
    SYNTAX      INTEGER
    MAX-ACCESS  read-only
    STATUS      current
    DESCRIPTION ""
    ::= { groupStreamsEntry 1 }

groupStreamIndex    OBJECT-TYPE
    SYNTAX      INTEGER
    MAX-ACCESS  read-only
    STATUS      current
    DESCRIPTION ""
    ::= { groupStreamsEntry 2 }

groupStreamUlRateCap    OBJECT-TYPE
    SYNTAX      INTEGER
    MAX-ACCESS  read-write
    STATUS      current
    DESCRIPTION "Uplink rate cap."
    ::= { groupStreamsEntry 3 }

groupStreamDlRateCap    OBJECT-TYPE
    SYNTAX      INTEGER
    MAX-ACCESS  read-write
    STATUS      current
    DESCRIPTION "Downlink rate cap."
    ::= { groupStreamsEntry 4 }

groupStreamUlTokenGain  OBJECT-TYPE
    SYNTAX      INTEGER
    MAX-ACCESS  read-write
    STATUS      current
    DESCRIPTION "Uplink token gain."
    ::= { groupStreamsEntry 5 }

groupStreamDlTokenGain  OBJECT-TYPE
    SYNTAX      INTEGER
    MAX-ACCESS  read-write
    STATUS      current
    DESCRIPTION "Downlink token gain."
    ::= { groupStreamsEntry 6 }


-- Trap Config
trapTable               OBJECT-TYPE
        SYNTAX          SEQUENCE OF TrapTableEntry
        MAX-ACCESS      not-accessible
        STATUS          current
        DESCRIPTION     "Trap destinations table."
        ::= { rrTrapConfig 1 }

trapTableEntry          OBJECT-TYPE
        SYNTAX          TrapTableEntry
        MAX-ACCESS      not-accessible
        STATUS          current
        DESCRIPTION     ""
        INDEX           { trapIndex }
        ::= { trapTable 1 }

TrapTableEntry ::= SEQUENCE {
        trapIndex           INTEGER,
        trapEnable          TruthValue,
        trapCommunity       DisplayString,
        trapAddr            IpAddress,
        trapPort            INTEGER,
        trapSendCritical    TruthValue,
        trapSendMajor       TruthValue,
        trapSendMinor       TruthValue,
        trapSendWarning     TruthValue,
        trapSendCleared     TruthValue
}

trapIndex               OBJECT-TYPE
        SYNTAX          INTEGER
        MAX-ACCESS      read-only
        STATUS          current
        DESCRIPTION     "The table index value."
        ::= { trapTableEntry 1 }

trapEnable              OBJECT-TYPE
        SYNTAX          TruthValue
        MAX-ACCESS      read-write
        STATUS          current
        DESCRIPTION     "Set to true(1) to send traps to this destination."
        DEFVAL          { false }
        ::= { trapTableEntry 2 }

trapCommunity           OBJECT-TYPE
        SYNTAX          DisplayString
        MAX-ACCESS      read-write
        STATUS          current
        DESCRIPTION     "The trap community string for this destination."
        DEFVAL          { public }
        ::= { trapTableEntry 3 }

trapAddr                OBJECT-TYPE
        SYNTAX          IpAddress
        MAX-ACCESS      read-write
        STATUS          current
        DESCRIPTION     "The IP address of this trap destination."
        ::= { trapTableEntry 4 }

trapPort                OBJECT-TYPE
        SYNTAX          INTEGER (0..65535)
        MAX-ACCESS      read-write
        STATUS          current
        DESCRIPTION     "The trap destination port."
        DEFVAL          { 162 }
        ::= { trapTableEntry 5 }

trapSendCritical        OBJECT-TYPE
        SYNTAX          TruthValue
        MAX-ACCESS      read-write
        STATUS          current
        DESCRIPTION     "Send critical severity traps to this destination."
        ::= { trapTableEntry 6 }

trapSendMajor           OBJECT-TYPE
        SYNTAX          TruthValue
        MAX-ACCESS      read-write
        STATUS          current
        DESCRIPTION     "Send major severity traps to this destination."
        ::= { trapTableEntry 7 }

trapSendMinor           OBJECT-TYPE
        SYNTAX          TruthValue
        MAX-ACCESS      read-write
        STATUS          current
        DESCRIPTION     "Send minor severity traps to this destination."
        ::= { trapTableEntry 8 }

trapSendWarning         OBJECT-TYPE
        SYNTAX          TruthValue
        MAX-ACCESS      read-write
        STATUS          current
        DESCRIPTION     "Send warning severity traps to this destination."
        ::= { trapTableEntry 9 }

trapSendCleared         OBJECT-TYPE
        SYNTAX          TruthValue
        MAX-ACCESS      read-write
        STATUS          current
        DESCRIPTION     "Send cleared severity traps to this destination."
        ::= { trapTableEntry 10 }


-- SNMP Trap History Table

trapHistSize        OBJECT-TYPE
    SYNTAX          INTEGER
    MAX-ACCESS      read-write
    STATUS          current
    DESCRIPTION     "Maximum number of entries to store in SNMP trap
                    history table."
    DEFVAL          { 200 }
    ::= { rrTrapHistory 1 }

trapHistTable       OBJECT-TYPE
    SYNTAX          SEQUENCE OF TrapHistEntry
    MAX-ACCESS      not-accessible
    STATUS          current
    DESCRIPTION     "This is the SNMP trap history table."
    ::= { rrTrapHistory 2 }
 
trapHistEntry       OBJECT-TYPE
    SYNTAX          TrapHistEntry
    MAX-ACCESS      not-accessible
    STATUS          current
    DESCRIPTION     ""
    INDEX           { trapHistIndex }
    ::= { trapHistTable 1 }
 
TrapHistEntry ::= SEQUENCE {
    trapHistIndex      INTEGER,
    trapHistOid        OBJECT IDENTIFIER,
    trapHistMoType     MoType,
    trapHistMoId       INTEGER,
    trapHistTime       TimeTicks,
    trapHistInfo       DisplayString,
    trapHistTimestamp  INTEGER,
    trapHistSeqNum     INTEGER
}

trapHistIndex       OBJECT-TYPE
    SYNTAX          INTEGER
    MAX-ACCESS      read-only
    STATUS          current
    DESCRIPTION     "The trap history index."
    ::= { trapHistEntry 1 }
 
trapHistOid         OBJECT-TYPE
    SYNTAX          OBJECT IDENTIFIER
    MAX-ACCESS      read-only
    STATUS          current
    DESCRIPTION     "The SNMP trap OID."
    ::= { trapHistEntry 2 }

trapHistMoType      OBJECT-TYPE
    SYNTAX          MoType
    MAX-ACCESS      read-only
    STATUS          current
    DESCRIPTION     "The managed object which generated this trap."
    ::= { trapHistEntry 3 }

trapHistMoId        OBJECT-TYPE
    SYNTAX          INTEGER
    MAX-ACCESS      read-only
    STATUS          current
    DESCRIPTION     "The managed object instance identifier."
    ::= { trapHistEntry 4 }

trapHistTime        OBJECT-TYPE
    SYNTAX          TimeTicks
    MAX-ACCESS      read-only
    STATUS          current
    DESCRIPTION     "The value of MIB II's sysUpTime object when the trap
                    was generated."
    ::= { trapHistEntry 5 }

trapHistInfo        OBJECT-TYPE
    SYNTAX          DisplayString
    MAX-ACCESS      read-only
    STATUS          current
    DESCRIPTION     "Additional information related to this trap."
    ::= { trapHistEntry 6 }

trapHistTimestamp   OBJECT-TYPE
    SYNTAX          INTEGER
    MAX-ACCESS      read-only
    STATUS          current
    DESCRIPTION     "The time at which the trap was generated.
                    This value is expressed in seconds since
                    00:00:00 UTC, January 1, 1970 (see time(2))."
    ::= { trapHistEntry 7 }

trapHistSeqNum      OBJECT-TYPE
    SYNTAX          INTEGER
    MAX-ACCESS      read-only
    STATUS          current
    DESCRIPTION     "The trap's sequence number."
    ::= { trapHistEntry 8 }


-- SNMP Trap Provisioning Table
rrTrapProv         OBJECT IDENTIFIER ::= { rrCommonMib 6 }

trapProvTable       OBJECT-TYPE
    SYNTAX          SEQUENCE OF TrapProvEntry
    MAX-ACCESS      not-accessible
    STATUS          current
    DESCRIPTION     "This is the SNMP trap provisioning table."
    ::= { rrTrapProv 1 }
 
trapProvEntry       OBJECT-TYPE
    SYNTAX          TrapProvEntry
    MAX-ACCESS      not-accessible
    STATUS          current
    DESCRIPTION     ""
    INDEX           { trapProvIndex }
    ::= { trapProvTable 1 }
 
TrapProvEntry ::= SEQUENCE {
    trapProvIndex      INTEGER,
    trapProvName       DisplayString,
    trapProvEnable     TruthValue
}

trapProvIndex       OBJECT-TYPE
    SYNTAX          INTEGER
    MAX-ACCESS      read-only
    STATUS          current
    DESCRIPTION     "A unique identifier for each row in the table."
    ::= { trapProvEntry 1 }
 
trapProvName        OBJECT-TYPE
    SYNTAX          DisplayString
    MAX-ACCESS      read-only
    STATUS          current
    DESCRIPTION     "The name of the SNMP trap."
    ::= { trapProvEntry 2 }

trapProvEnable      OBJECT-TYPE
    SYNTAX          TruthValue
    MAX-ACCESS      read-write
    STATUS          current
    DESCRIPTION     "Indicates whether the SNMP trap is enabled or disabled.
                    Set to true(1) to enable the trap, false(2) to disable the
                    trap."
    ::= { trapProvEntry 3 }


-- Context Transfer Core
ctCoreProv              OBJECT IDENTIFIER ::= { rrCtCore 1 }

ctServerTable           OBJECT-TYPE
        SYNTAX          SEQUENCE OF CtServerEntry
        MAX-ACCESS      not-accessible
        STATUS          current
        DESCRIPTION     "Table of Context Transfer Core servers."
        ::= { ctCoreProv 1 }

ctServerEntry           OBJECT-TYPE
        SYNTAX          CtServerEntry
        MAX-ACCESS      not-accessible
        STATUS          current
        DESCRIPTION     "CT Core server table entry."
        INDEX           { ctServerIndex }
        ::= { ctServerTable 1 }

CtServerEntry ::= SEQUENCE {
        ctServerIndex       INTEGER,
        ctServerValid       TruthValue,
        ctServerName        DisplayString,
        ctServerAddr        IpAddress,
        ctServerPort        INTEGER,
        ctServerSecret      DisplayString
}

ctServerIndex           OBJECT-TYPE
        SYNTAX          INTEGER
        MAX-ACCESS      read-only
        STATUS          current
        DESCRIPTION     "Context Transfer server index."
        ::= { ctServerEntry 1 }

ctServerValid           OBJECT-TYPE
        SYNTAX          TruthValue
        MAX-ACCESS      read-write
        STATUS          current
        DESCRIPTION     "Indicates if this CT server entry is valid."
        DEFVAL          { false }
        ::= { ctServerEntry 2 }

ctServerName            OBJECT-TYPE
        SYNTAX          DisplayString
        MAX-ACCESS      read-write
        STATUS          current
        DESCRIPTION     "CT server name."
        ::= { ctServerEntry 3 }

ctServerAddr            OBJECT-TYPE
        SYNTAX          IpAddress
        MAX-ACCESS      read-write
        STATUS          current
        DESCRIPTION     "CT server IP address."
        ::= { ctServerEntry 4 }

ctServerPort            OBJECT-TYPE
        SYNTAX          INTEGER (0..65535)
        MAX-ACCESS      read-write
        STATUS          current
        DESCRIPTION     "CT server port."
        DEFVAL          { 51010 }
        ::= { ctServerEntry 5 }

ctServerSecret          OBJECT-TYPE
        SYNTAX          DisplayString
        MAX-ACCESS      read-write
        STATUS          current
        DESCRIPTION     "CT server secret key."
        ::= { ctServerEntry 6 }

ctServerTimeout         OBJECT-TYPE
        SYNTAX          INTEGER (100..1800)
        MAX-ACCESS      read-write
        STATUS          current
        DESCRIPTION     "CT server timeout."
        DEFVAL          { 200 }
        ::= { ctCoreProv 2 }

ctServerRetry           OBJECT-TYPE
        SYNTAX          INTEGER (0..255)
        MAX-ACCESS      read-write
        STATUS          current
        DESCRIPTION     "CT server maximum retry."
        DEFVAL          { 3 }
        ::= { ctCoreProv 3 }


-- L2 Admission Control
l2AcProv                OBJECT IDENTIFIER ::= { rrL2AdmissionCtrl 1 }

l2AcPagingCycle         OBJECT-TYPE
        SYNTAX          INTEGER
        MAX-ACCESS      read-write
        STATUS          current
        DESCRIPTION     "This object indicates how often, in superslots, a
                        sleeping mobile checks for incoming pages. The only
                        valid value is 200 cycles or 0 (mobile does not check
                        for pages)."
        DEFVAL          { 0 }
        ::= { l2AcProv 1 }

l2AcStats               OBJECT IDENTIFIER ::= { rrL2AdmissionCtrl 2 }

l2AcRegistrationReq     OBJECT-TYPE
        SYNTAX          Counter32
        MAX-ACCESS      read-only
        STATUS          current
        DESCRIPTION     "Layer 2 registration requests."
        ::= { l2AcStats 1 }

l2AcRegistrationReqFail OBJECT-TYPE
        SYNTAX          Counter32
        MAX-ACCESS      read-only
        STATUS          current
        DESCRIPTION     "Layer 2 registration request failures."
        ::= { l2AcStats 2 }

l2AcHandoffReq          OBJECT-TYPE
        SYNTAX          Counter32
        MAX-ACCESS      read-only
        STATUS          current
        DESCRIPTION     "Layer 2 handoff requests."
        ::= { l2AcStats 3 }

l2AcHandoffReqFailures  OBJECT-TYPE
        SYNTAX          Counter32
        MAX-ACCESS      read-only
        STATUS          current
        DESCRIPTION     "Layer 2 handoff request failures."
        ::= { l2AcStats 4 }

l2AcAaaAuthRequestsSent OBJECT-TYPE
        SYNTAX          Counter32
        MAX-ACCESS      read-only
        STATUS          current
        DESCRIPTION     "AAA Access-Request messages sent."
        ::= { l2AcStats 14 }

l2AcAaaAuthChallengesRecvd    OBJECT-TYPE
        SYNTAX          Counter32
        MAX-ACCESS      read-only
        STATUS          current
        DESCRIPTION     "AAA Access-Challenge messages received."
        ::= { l2AcStats 15 }

l2AcAaaAuthRejectsRecvd OBJECT-TYPE
        SYNTAX          Counter32
        MAX-ACCESS      read-only
        STATUS          current
        DESCRIPTION     "AAA Access-Reject messages received."
        ::= { l2AcStats 16 }

l2AcAaaAuthAcceptsRecvd OBJECT-TYPE
        SYNTAX          Counter32
        MAX-ACCESS      read-only
        STATUS          current
        DESCRIPTION     "AAA Access-Accept messages received."
        ::= { l2AcStats 17 }

l2AcAaaAuthNetworkTimeouts OBJECT-TYPE
        SYNTAX          Counter32
        MAX-ACCESS      read-only
        STATUS          current
        DESCRIPTION     "AAA network timeout events."
        ::= { l2AcStats 18 }

l2AcMobChallengeTimeouts OBJECT-TYPE
        SYNTAX          Counter32
        MAX-ACCESS      read-only
        STATUS          current
        DESCRIPTION     "Mobiles timeouts when challenged."
        ::= { l2AcStats 22 }

l2AcUnilateralKeyTimeouts  OBJECT-TYPE
        SYNTAX          Counter32
        MAX-ACCESS      read-only
        STATUS          current
        DESCRIPTION     "Layer 2 unilateral key timeouts."
        ::= { l2AcStats 23 }

l2AcUnilateralKeyReq    OBJECT-TYPE
        SYNTAX          Counter32
        MAX-ACCESS      read-only
        STATUS          current
        DESCRIPTION     "Layer 2 unilateral key requests."
        ::= { l2AcStats 24 }

l2AcUnilateralKeyResp   OBJECT-TYPE
        SYNTAX          Counter32
        MAX-ACCESS      read-only
        STATUS          current
        DESCRIPTION     "Layer 2 unilateral key responses."
        ::= { l2AcStats 25 }

l2AcRelayMsgRecvd       OBJECT-TYPE
        SYNTAX          Counter32
        MAX-ACCESS      read-only
        STATUS          current
        DESCRIPTION     "Relay from mobile messages received."
        ::= { l2AcStats 28 }

l2AcSmallestL2RegIntvl  OBJECT-TYPE
        SYNTAX          Counter32
        MAX-ACCESS      read-only
        STATUS          current
        DESCRIPTION     "Smaller L2 Registration interval, in msec."
        ::= { l2AcStats 29 }

l2AcLargestL2RegIntvl   OBJECT-TYPE
        SYNTAX          Counter32
        MAX-ACCESS      read-only
        STATUS          current
        DESCRIPTION     "Largest L2 Registration interval, in msec."
        ::= { l2AcStats 30 }

l2AcAverageL2RegIntvl   OBJECT-TYPE
        SYNTAX          Counter32
        MAX-ACCESS      read-only
        STATUS          current
        DESCRIPTION     "Average L2 Registration interval, in msec."
        ::= { l2AcStats 31 }

l2AcCoreCtMsgRecvdFail  OBJECT-TYPE
        SYNTAX          Counter32
        MAX-ACCESS      read-only
        STATUS          current
        DESCRIPTION     "Core-CT messages received failures."
        ::= { l2AcStats 33 }

l2AcCoreCtMsgRecvd      OBJECT-TYPE
        SYNTAX          Counter32
        MAX-ACCESS      read-only
        STATUS          current
        DESCRIPTION     "Core-CT messages received."
        ::= { l2AcStats 34 }

l2AcBadCoreCtMsgRecvd   OBJECT-TYPE
        SYNTAX          Counter32
        MAX-ACCESS      read-only
        STATUS          current
        DESCRIPTION     "Bad Core-CT messages received."
        ::= { l2AcStats 35 }

l2AcCoreCtAckRecvd      OBJECT-TYPE
        SYNTAX          Counter32
        MAX-ACCESS      read-only
        STATUS          deprecated
        DESCRIPTION     "Core-CT ACK messages received."
        ::= { l2AcStats 36 }

l2AcCoreCtAnswerRecvd   OBJECT-TYPE
        SYNTAX          Counter32
        MAX-ACCESS      read-only
        STATUS          deprecated
        DESCRIPTION     "Core-CT Answer received."
        ::= { l2AcStats 37 }

l2AcCoreCtCreates       OBJECT-TYPE
        SYNTAX          Counter32
        MAX-ACCESS      read-only
        STATUS          current
        DESCRIPTION     "Core-CT context transfer creates."
        ::= { l2AcStats 38 }

l2AcCoreCtCreateFailures    OBJECT-TYPE
        SYNTAX          Counter32
        MAX-ACCESS      read-only
        STATUS          current
        DESCRIPTION     "Core-CT context transfer create failures."
        ::= { l2AcStats 39 }

l2AcCoreCtUpdates       OBJECT-TYPE
        SYNTAX          Counter32
        MAX-ACCESS      read-only
        STATUS          current
        DESCRIPTION     "Core-CT context transfer updates."
        ::= { l2AcStats 40 }

l2AcCoreCtUpdateFailures    OBJECT-TYPE
        SYNTAX          Counter32
        MAX-ACCESS      read-only
        STATUS          current
        DESCRIPTION     "Core-CT context transfer update failures."
        ::= { l2AcStats 41 }

l2AcCoreCtDeletes       OBJECT-TYPE
        SYNTAX          Counter32
        MAX-ACCESS      read-only
        STATUS          current
        DESCRIPTION     "Core-CT context transfer deletes."
        ::= { l2AcStats 42 }

l2AcCoreCtDeleteFailures    OBJECT-TYPE
        SYNTAX          Counter32
        MAX-ACCESS      read-only
        STATUS          current
        DESCRIPTION     "Core-CT context transfer delete failures."
        ::= { l2AcStats 43 }

l2AcCoreCtRequest       OBJECT-TYPE
        SYNTAX          Counter32
        MAX-ACCESS      read-only
        STATUS          current
        DESCRIPTION     "Core-CT context transfer requests."
        ::= { l2AcStats 44 }

l2AcCoreCtRequestFailures   OBJECT-TYPE
        SYNTAX          Counter32
        MAX-ACCESS      read-only
        STATUS          current
        DESCRIPTION     "Core-CT context transfer request failures."
        ::= { l2AcStats 45 }

l2AcCoreCtRequestSuccesses   OBJECT-TYPE
        SYNTAX          Counter32
        MAX-ACCESS      read-only
        STATUS          current
        DESCRIPTION     "Core-CT context transfer request successes."
        ::= { l2AcStats 46 }

l2AcCoreCtCreateSuccesses   OBJECT-TYPE
        SYNTAX          Counter32
        MAX-ACCESS      read-only
        STATUS          current
        DESCRIPTION     "Core-CT context transfer Create Successes."
        ::= { l2AcStats 47 }

l2AcCoreCtUpdateSuccesses   OBJECT-TYPE
        SYNTAX          Counter32
        MAX-ACCESS      read-only
        STATUS          current
        DESCRIPTION     "Core-CT context transfer Update Successes."
        ::= { l2AcStats 48 }

l2AcCoreCtDeleteSuccesses   OBJECT-TYPE
        SYNTAX          Counter32
        MAX-ACCESS      read-only
        STATUS          current
        DESCRIPTION     "Core-CT context transfer Delete Successes."
        ::= { l2AcStats 49 }

l2AcCoreCtContextTransferGetResponses   OBJECT-TYPE
        SYNTAX          Counter32
        MAX-ACCESS      read-only
        STATUS          current
        DESCRIPTION     "Core-CT context transfer Get Responses."
        ::= { l2AcStats 50 }

l2AcCoreCtContextTransferCreateResponses   OBJECT-TYPE
        SYNTAX          Counter32
        MAX-ACCESS      read-only
        STATUS          current
        DESCRIPTION     "Core-CT context transfer Create Responses."
        ::= { l2AcStats 51 }

l2AcCoreCtContextTransferUpdateResponses   OBJECT-TYPE
        SYNTAX          Counter32
        MAX-ACCESS      read-only
        STATUS          current
        DESCRIPTION     "Core-CT context transfer Update Responses."
        ::= { l2AcStats 52 }

l2AcCoreCtContextTransferDeleteResponses   OBJECT-TYPE
        SYNTAX          Counter32
        MAX-ACCESS      read-only
        STATUS          current
        DESCRIPTION     "Core-CT context transfer Delete Responses."
        ::= { l2AcStats 53 }

l2AcCoreCtReceivedStaleMobile   OBJECT-TYPE
        SYNTAX          Counter32
        MAX-ACCESS      read-only
        STATUS          current
        DESCRIPTION     "Core-CT Messages received for a Mobile which
                         has already left the system."
        ::= { l2AcStats 54 }


--
--
-- System Software Upgrade Management
--
upgradeCurrRelease  OBJECT-TYPE
    SYNTAX          DisplayString
    MAX-ACCESS      read-only
    STATUS          current
    DESCRIPTION     "Current running release version."
    ::= { rrUpgrade 1 }


upgradeReleaseTable OBJECT-TYPE
    SYNTAX          SEQUENCE OF UpgradeReleaseEntry
    MAX-ACCESS      not-accessible
    STATUS          current
    DESCRIPTION     "A table showing the releases that are installed."
    ::= { rrUpgrade 2 }

upgradeReleaseEntry OBJECT-TYPE
    SYNTAX          UpgradeReleaseEntry
    MAX-ACCESS      not-accessible
    STATUS          current
    DESCRIPTION     ""
    INDEX           { releaseIndex }
    ::= { upgradeReleaseTable 1 }

UpgradeReleaseEntry ::= SEQUENCE {
    releaseIndex        INTEGER,
    releaseVersion      DisplayString
}

releaseIndex        OBJECT-TYPE
    SYNTAX          INTEGER
    MAX-ACCESS      read-only
    STATUS          current
    DESCRIPTION     "The table index value."
    ::= { upgradeReleaseEntry 1 }

releaseVersion      OBJECT-TYPE
    SYNTAX          DisplayString
    MAX-ACCESS      read-only
    STATUS          current
    DESCRIPTION     "The package name."
    ::= { upgradeReleaseEntry 2 }

upgradeServerAddr   OBJECT-TYPE
    SYNTAX          IpAddress
    MAX-ACCESS      read-write
    STATUS          current
    DESCRIPTION     "The IP address of the FTP server containing the
                    release."
    ::= { rrUpgrade 3 }

upgradeReleasePath  OBJECT-TYPE
    SYNTAX          DisplayString
    MAX-ACCESS      read-write
    STATUS          current
    DESCRIPTION     "The absolute path to the release image file on the FTP
                    server specified by upgradeServerAddr."
    ::= { rrUpgrade 4 }

upgradeAddRelease   OBJECT-TYPE
    SYNTAX          TruthValue
    MAX-ACCESS      write-only
    STATUS          current
    DESCRIPTION     "Set to 'true' to begin release upgrade. This object always
                    returns 'false'."
    ::= { rrUpgrade 5 }

upgradeActivateRelease  OBJECT-TYPE
    SYNTAX          DisplayString
    MAX-ACCESS      write-only
    STATUS          current
    DESCRIPTION     "This object takes a release version as its value. Setting
                    this object will cause the system to reboot and activate
                    the specified release. This object always returns a
                    zero-length string."
    ::= { rrUpgrade 6 }

upgradeRemoveRelease    OBJECT-TYPE
    SYNTAX          DisplayString
    MAX-ACCESS      write-only
    STATUS          current
    DESCRIPTION     "This object takes a release version as its value. Setting
                    this object will delete the specified release. The current
                    running release cannot be removed. This object always
                    returns a zero-length string."
    ::= { rrUpgrade 7 }

upgradeStatus       OBJECT-TYPE
    SYNTAX          DownloadState
    MAX-ACCESS      read-only
    STATUS          current
    DESCRIPTION     "The current download status."
    ::= { rrUpgrade 8 }

upgradePctComplete  OBJECT-TYPE
    SYNTAX          INTEGER
    MAX-ACCESS      read-only
    STATUS          current
    DESCRIPTION     "Download progress expressed as percentage complete."
    ::= { rrUpgrade 9 }

upgradeErrorReason  OBJECT-TYPE
    SYNTAX          DisplayString
    MAX-ACCESS      read-only
    STATUS          current
    DESCRIPTION     "If upgradeStatus reports failure, this object will
                    contain the reason for the failure."
    ::= { rrUpgrade 10 }

--
-- IGMP Proxy
--
igmpState           OBJECT-TYPE
    SYNTAX          OnOffState
    MAX-ACCESS      read-write
    STATUS          current
    DESCRIPTION     "Set this value to turn the IGMP proxy on or off."
    DEFVAL          { off }
    ::= { rrIgmp 1 }

igmpUseBroadcast    OBJECT-TYPE
    SYNTAX          TruthValue
    MAX-ACCESS      read-write
    STATUS          current
    DESCRIPTION     "Set this to true(1) to use broadcast at the PHY layer
                    for multicast."
    DEFVAL          { false }
    ::= { rrIgmp 2 }

igmpUpstreamIntf    OBJECT-TYPE
    SYNTAX          DisplayString
    MAX-ACCESS      read-write
    STATUS          current
    DESCRIPTION     "Upstream interface for IGMP proxy."
    DEFVAL          { "ppp0" }
    ::= { rrIgmp 3 }

igmpQueryInterval   OBJECT-TYPE
    SYNTAX          Unsigned32
    MAX-ACCESS      read-write
    STATUS          current
    DESCRIPTION     "IGMP general query interval (in seconds)."
    DEFVAL          { 60 }
    ::= { rrIgmp 4 }

igmpMaxQueryResp    OBJECT-TYPE
    SYNTAX          Unsigned32
    MAX-ACCESS      read-write
    STATUS          current
    DESCRIPTION     "Group timeout (in multiples of igmpQueryInterval)."
    DEFVAL          { 5 }
    ::= { rrIgmp 5 }

igmpMaxMembers      OBJECT-TYPE
    SYNTAX          INTEGER (1..31)
    MAX-ACCESS      read-write
    STATUS          current
    DESCRIPTION     "Maximum number of wireless terminals joined to any IGMP
                    group." 
    DEFVAL          { 4 }
    ::= { rrIgmp 6 }

igmpProxyStatus     OBJECT-TYPE
    SYNTAX          OnOffState
    MAX-ACCESS      read-only
    STATUS          current
    DESCRIPTION     "IGMP proxy current status."
    ::= { rrIgmp 7 }
    
--
-- Active Alarms Table
--

alarmTable          OBJECT-TYPE
    SYNTAX          SEQUENCE OF AlarmEntry
    MAX-ACCESS      not-accessible
    STATUS          current
    DESCRIPTION     "This is a table of active alarms."
    ::= { rrAlarms 1 }
 
alarmEntry          OBJECT-TYPE
    SYNTAX          AlarmEntry
    MAX-ACCESS      not-accessible
    STATUS          current
    DESCRIPTION     ""
    INDEX           { alarmIndex }
    ::= { alarmTable 1 }
 
AlarmEntry ::= SEQUENCE {
    alarmIndex      INTEGER,
    alarmName       DisplayString,
    alarmSeverity   AlarmSeverity,
    alarmMoType     MoType,
    alarmMoId       INTEGER,
    alarmSector     INTEGER,
    alarmTime       TimeTicks,
    alarmTimestamp  INTEGER
}

alarmIndex          OBJECT-TYPE
    SYNTAX          INTEGER
    MAX-ACCESS      read-only
    STATUS          current
    DESCRIPTION     "The alarm index."
    ::= { alarmEntry 1 }
 
alarmName           OBJECT-TYPE
    SYNTAX          DisplayString
    MAX-ACCESS      read-only
    STATUS          current
    DESCRIPTION     "A brief description of the alarm."
    ::= { alarmEntry 2 }
 
alarmSeverity       OBJECT-TYPE
    SYNTAX          AlarmSeverity
    MAX-ACCESS      read-only
    STATUS          current
    DESCRIPTION     "The alarm severity level."
    ::= { alarmEntry 3 }

alarmMoType         OBJECT-TYPE
    SYNTAX          MoType
    MAX-ACCESS      read-only
    STATUS          current
    DESCRIPTION     "The managed object associated which generated this alarm."
    ::= { alarmEntry 4 }

alarmMoId           OBJECT-TYPE
    SYNTAX          INTEGER (0..65535)
    MAX-ACCESS      read-only
    STATUS          current
    DESCRIPTION     "The managed object instance identifier."
    ::= { alarmEntry 5 }

alarmSector         OBJECT-TYPE
    SYNTAX          INTEGER
    MAX-ACCESS      read-only
    STATUS          current
    DESCRIPTION     "The sector which generated the alarm, if applicable."
    ::= { alarmEntry 6 }

alarmTime           OBJECT-TYPE
    SYNTAX          TimeTicks
    MAX-ACCESS      read-only
    STATUS          deprecated
    DESCRIPTION     "The time at which the alarm was generated.
                    This value is expressed in seconds since
                    00:00:00 UTC, January 1, 1970 (see time(2))."
    ::= { alarmEntry 7 }

alarmTimestamp      OBJECT-TYPE
    SYNTAX          INTEGER
    MAX-ACCESS      read-only
    STATUS          current
    DESCRIPTION     "The time at which the alarm was generated.
                    This value is expressed in seconds since
                    00:00:00 UTC, January 1, 1970 (see time(2))."
    ::= { alarmEntry 8 }

END
