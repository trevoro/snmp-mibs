--
--  Copyright(C) 2004 Lantronix, Inc.
--

    SLP1-MIB DEFINITIONS ::= BEGIN

    IMPORTS
        MODULE-IDENTITY, NOTIFICATION-TYPE,
        OBJECT-TYPE, enterprises                            FROM SNMPv2-SMI
        DisplayString                                       FROM SNMPv2-TC;


    slp1 MODULE-IDENTITY
        LAST-UPDATED "200412091740Z" -- 9 Dec 2004
        ORGANIZATION "Lantronix"
        CONTACT-INFO
            "Postal: Lantronix
             15353 Barranca Parkway
             Irvine, CA 92618
             Tel: (949) 453-7198
             Email: support@lantronix.com"
        DESCRIPTION
            "This is the MIB module for the SecureLinx Power Manager."
       ::= { slp 1 }

    lantronix OBJECT IDENTIFIER ::= { enterprises 244 }
    products  OBJECT IDENTIFIER ::= { lantronix 1 }
    slp       OBJECT IDENTIFIER ::= { products 9 }


--
--  System Group
--

    slp1SystemGroup OBJECT IDENTIFIER ::= { slp1 1 }

    slp1SystemVersion OBJECT-TYPE
        SYNTAX      DisplayString(SIZE(0..32))
        MAX-ACCESS  read-only
        STATUS      current
        DESCRIPTION
            "The firmware version of the system."
        ::= { slp1SystemGroup 1 }

    slp1SystemNICSerialNumber OBJECT-TYPE
        SYNTAX      DisplayString(SIZE(0..8))
        MAX-ACCESS  read-only
        STATUS      current
        DESCRIPTION
            "The serial number of the network interface card in the
             system."
        ::= { slp1SystemGroup 2 }

    slp1SystemLocation OBJECT-TYPE
        SYNTAX      DisplayString(SIZE(0..32))
        MAX-ACCESS  read-write
        STATUS      current
        DESCRIPTION
            "The location of the system."
        ::= { slp1SystemGroup 3 }

    slp1SystemTowerCount OBJECT-TYPE
        SYNTAX      INTEGER(0..2)
        MAX-ACCESS  read-only
        STATUS      current
        DESCRIPTION
            "The number of towers in the system."
        ::= { slp1SystemGroup 4 }

    slp1SystemEnvMonCount OBJECT-TYPE
        SYNTAX      INTEGER(0..4)
        MAX-ACCESS  read-only
        STATUS      current
        DESCRIPTION
            "The number of environmental monitors in the system."
        ::= { slp1SystemGroup 5 }

--
--  System Tables
--

    slp1SystemTables OBJECT IDENTIFIER ::= { slp1 2 }

    --
    --  Tower Table
    --

    slp1TowerTable OBJECT-TYPE
        SYNTAX      SEQUENCE OF Slp1TowerEntry
        MAX-ACCESS  not-accessible
        STATUS      current
        DESCRIPTION
            "A table of towers."
        ::= { slp1SystemTables 1 }

    slp1TowerEntry OBJECT-TYPE
        SYNTAX      Slp1TowerEntry
        MAX-ACCESS  not-accessible
        STATUS      current
        DESCRIPTION
            "Row definition for the tower table."
        INDEX       { slp1TowerIndex }
        ::= { slp1TowerTable 1 }

    Slp1TowerEntry ::= SEQUENCE {
        slp1TowerIndex       INTEGER,
        slp1TowerID          DisplayString,
        slp1TowerName        DisplayString,
        slp1TowerStatus      INTEGER,
        slp1TowerInfeedCount INTEGER
    }

    slp1TowerIndex OBJECT-TYPE
        SYNTAX      INTEGER(0..2)
        MAX-ACCESS  not-accessible
        STATUS      current
        DESCRIPTION
            "Index for the tower table."
        ::= { slp1TowerEntry 1 }

    slp1TowerID OBJECT-TYPE
        SYNTAX      DisplayString(SIZE(1))
        MAX-ACCESS  read-only
        STATUS      current
        DESCRIPTION
            "The ID of the tower."
        ::= { slp1TowerEntry 2 }

    slp1TowerName OBJECT-TYPE
        SYNTAX      DisplayString(SIZE(0..24))
        MAX-ACCESS  read-write
        STATUS      current
        DESCRIPTION
            "The name of the tower."
        ::= { slp1TowerEntry 3 }

    slp1TowerStatus OBJECT-TYPE
        SYNTAX      INTEGER {
                        normal(0),
                        noComm(1)
                    }
        MAX-ACCESS  read-only
        STATUS      current
        DESCRIPTION
            "The operational status of the tower."
        ::= { slp1TowerEntry 4 }

    slp1TowerInfeedCount OBJECT-TYPE
        SYNTAX      INTEGER(0..4)
        MAX-ACCESS  read-only
        STATUS      current
        DESCRIPTION
            "The number of input feeds on the tower."
        ::= { slp1TowerEntry 5 }

    --
    --  Input Feed Table
    --

    slp1InfeedTable OBJECT-TYPE
        SYNTAX      SEQUENCE OF Slp1InfeedEntry
        MAX-ACCESS  not-accessible
        STATUS      current
        DESCRIPTION
            "A table of input feeds."
        ::= { slp1SystemTables 2 }

    slp1InfeedEntry OBJECT-TYPE
        SYNTAX      Slp1InfeedEntry
        MAX-ACCESS  not-accessible
        STATUS      current
        DESCRIPTION
            "Row definition for the input feed table."
        INDEX       { slp1TowerIndex, slp1InfeedIndex }
        ::= { slp1InfeedTable 1 }

    Slp1InfeedEntry ::= SEQUENCE {
        slp1InfeedIndex          INTEGER,
        slp1InfeedID             DisplayString,
        slp1InfeedName           DisplayString,
        slp1InfeedCapabilities   BITS,
        slp1InfeedStatus         INTEGER,
        slp1InfeedLoadStatus     INTEGER,
        slp1InfeedLoadValue      INTEGER,
        slp1InfeedLoadHighThresh INTEGER,
        slp1InfeedOutletCount    INTEGER
    }

    slp1InfeedIndex OBJECT-TYPE
        SYNTAX      INTEGER(0..4)
        MAX-ACCESS  not-accessible
        STATUS      current
        DESCRIPTION
            "Index for the input feed table."
        ::= { slp1InfeedEntry 1 }

    slp1InfeedID OBJECT-TYPE
        SYNTAX      DisplayString(SIZE(2))
        MAX-ACCESS  read-only
        STATUS      current
        DESCRIPTION
            "The ID of the input feed."
        ::= { slp1InfeedEntry 2 }

    slp1InfeedName OBJECT-TYPE
        SYNTAX      DisplayString(SIZE(0..24))
        MAX-ACCESS  read-write
        STATUS      current
        DESCRIPTION
            "The name of the input feed."
        ::= { slp1InfeedEntry 3 }

    slp1InfeedCapabilities OBJECT-TYPE
        SYNTAX      BITS {
                        onSense(0),
                        loadSense(1),
                        powerControl(2),
                        failSafe(3),
                        defaultOff(4)
                    }
        MAX-ACCESS  read-only
        STATUS      current
        DESCRIPTION
            "The capabilities of the input feed."
        ::= { slp1InfeedEntry 4 }

    slp1InfeedStatus OBJECT-TYPE
        SYNTAX      INTEGER {
                        off(0),
                        on(1),
                        offWait(2),
                        onWait(3),
                        offError(4),
                        onError(5),
                        noComm(6)
                    }
        MAX-ACCESS  read-only
        STATUS      current
        DESCRIPTION
            "The status of the input feed.  If the slp1InfeedCapabilities
             'onSense' bit is TRUE, then all of the states are supported
             and indicate the sensed state of the input feed.  If the
             slp1InfeedCapabilities 'onSense' bit is FALSE, then only the
             'on' and 'noComm' states are supported, and 'on' indicates
             a derived state, not a sensed state."
        ::= { slp1InfeedEntry 5 }

    slp1InfeedLoadStatus OBJECT-TYPE
        SYNTAX      INTEGER {
                        normal(0),
                        notOn(1),
                        reading(2),
                        loadLow(3),
                        loadHigh(4),
                        overLoad(5),
                        readError(6),
                        noComm(7)
                    }
        MAX-ACCESS  read-only
        STATUS      current
        DESCRIPTION
            "The status of the load measured on the input feed.  If the
             slp1InfeedCapabilities 'loadSense' bit is TRUE, then all of
             the states are supported.  If the slp1InfeedCapabilities
             'loadSense' bit is FALSE, then only the 'normal' and 'noComm'
             states are supported."
        ::= { slp1InfeedEntry 6 }

    slp1InfeedLoadValue OBJECT-TYPE
        SYNTAX      INTEGER(-1..25500)
        UNITS       "hundredth Amps"
        MAX-ACCESS  read-only
        STATUS      current
        DESCRIPTION
            "The load measured on the input feed.  A non-negative value
             indicates the measured load in hundredths of Amps.  A
             negative value indicates that a load value was not able to
             be measured."
        ::= { slp1InfeedEntry 7 }

    slp1InfeedLoadHighThresh OBJECT-TYPE
        SYNTAX      INTEGER(0..255)
        UNITS       "Amps"
        MAX-ACCESS  read-write
        STATUS      current
        DESCRIPTION
            "The load high threshold value of the input feed in Amps."
        ::= { slp1InfeedEntry 8 }

    slp1InfeedOutletCount OBJECT-TYPE
        SYNTAX      INTEGER(0..16)
        MAX-ACCESS  read-only
        STATUS      current
        DESCRIPTION
            "The number of outlets on the input feed."
        ::= { slp1InfeedEntry 9 }

    --
    --  Outlet Table
    --

    slp1OutletTable OBJECT-TYPE
        SYNTAX      SEQUENCE OF Slp1OutletEntry
        MAX-ACCESS  not-accessible
        STATUS      current
        DESCRIPTION
            "A table of outlets."
        ::= { slp1SystemTables 3 }

    slp1OutletEntry OBJECT-TYPE
        SYNTAX      Slp1OutletEntry
        MAX-ACCESS  not-accessible
        STATUS      current
        DESCRIPTION
            "Row definition for the outlet table."
        INDEX       { slp1TowerIndex, slp1InfeedIndex, slp1OutletIndex }
        ::= { slp1OutletTable 1 }

    Slp1OutletEntry ::= SEQUENCE {
        slp1OutletIndex          INTEGER,
        slp1OutletID             DisplayString,
        slp1OutletName           DisplayString,
        slp1OutletCapabilities   BITS,
        slp1OutletStatus         INTEGER,
        slp1OutletLoadStatus     INTEGER,
        slp1OutletLoadValue      INTEGER,
        slp1OutletLoadLowThresh  INTEGER,
        slp1OutletLoadHighThresh INTEGER,
        slp1OutletControlState   INTEGER,
        slp1OutletControlAction  INTEGER
    }

    slp1OutletIndex OBJECT-TYPE
        SYNTAX      INTEGER(0..16)
        MAX-ACCESS  not-accessible
        STATUS      current
        DESCRIPTION
            "Index for the outlet table."
        ::= { slp1OutletEntry 1 }

    slp1OutletID OBJECT-TYPE
        SYNTAX      DisplayString(SIZE(4))
        MAX-ACCESS  read-only
        STATUS      current
        DESCRIPTION
            "The ID of the outlet."
        ::= { slp1OutletEntry 2 }

    slp1OutletName OBJECT-TYPE
        SYNTAX      DisplayString(SIZE(0..24))
        MAX-ACCESS  read-write
        STATUS      current
        DESCRIPTION
            "The name of the outlet."
        ::= { slp1OutletEntry 3 }

    slp1OutletCapabilities OBJECT-TYPE
        SYNTAX      BITS {
                        onSense(0),
                        loadSense(1),
                        powerControl(2),
                        shutdown(3),
                        defaultOn(4),
                        ownInfeed(5)
                    }
        MAX-ACCESS  read-only
        STATUS      current
        DESCRIPTION
            "The capabilities of the outlet."
        ::= { slp1OutletEntry 4 }

    slp1OutletStatus OBJECT-TYPE
        SYNTAX      INTEGER {
                        off(0),
                        on(1),
                        offWait(2),
                        onWait(3),
                        offError(4),
                        onError(5),
                        noComm(6),
                        reading(7)
                    }
        MAX-ACCESS  read-only
        STATUS      current
        DESCRIPTION
            "The status of the outlet.  If the slp1OutletCapabilities
             'onSense' bit is TRUE, then all of the states are supported
             and indicate the sensed state of the outlet.  If the
             slp1OutletCapabilities 'onSense' bit is FALSE, then only the
             'off', 'on', and 'noComm' states are supported, and 'off'
             and 'on' indicate a derived state, not a sensed state."
        ::= { slp1OutletEntry 5 }

    slp1OutletLoadStatus OBJECT-TYPE
        SYNTAX      INTEGER {
                        normal(0),
                        notOn(1),
                        reading(2),
                        loadLow(3),
                        loadHigh(4),
                        overLoad(5),
                        readError(6),
                        noComm(7)
                    }
        MAX-ACCESS  read-only
        STATUS      current
        DESCRIPTION
            "The status of the load measured on the outlet.  If the 
             slp1OutletCapabilities 'loadSense' bit is TRUE, then all of
             the states are supported.  If the slp1OutletCapabilities
             'loadSense' bit is FALSE, then only the 'normal' and 'noComm'
             states are supported."
        ::= { slp1OutletEntry 6 }

    slp1OutletLoadValue OBJECT-TYPE
        SYNTAX      INTEGER(-1..25500)
        UNITS       "hundredth Amps"
        MAX-ACCESS  read-only
        STATUS      current
        DESCRIPTION
            "The load measured on the outlet.  A non-negative value
             indicates the measured load in hundredths of Amps.  A
             negative value indicates that a load value was not able to
             be measured."
        ::= { slp1OutletEntry 7 }

    slp1OutletLoadLowThresh OBJECT-TYPE
        SYNTAX      INTEGER(0..255)
        UNITS       "Amps"
        MAX-ACCESS  read-write
        STATUS      current
        DESCRIPTION
            "The load low threshold value of the outlet in Amps."
        ::= { slp1OutletEntry 8 }

    slp1OutletLoadHighThresh OBJECT-TYPE
        SYNTAX      INTEGER(0..255)
        UNITS       "Amps"
        MAX-ACCESS  read-write
        STATUS      current
        DESCRIPTION
            "The load high threshold value of the outlet in Amps."
        ::= { slp1OutletEntry 9 }

    slp1OutletControlState OBJECT-TYPE
        SYNTAX      INTEGER {
                        idleOff(0),
                        idleOn(1),
                        wakeOff(2),
                        wakeOn(3),
                        off(4),
                        on(5),
                        lockedOff(6),
                        lockedOn(7),
                        reboot(8),
                        shutdown(9),
                        pendOn(10),
                        pendOff(11)
                    }
        MAX-ACCESS  read-only
        STATUS      current
        DESCRIPTION
            "The control state of the outlet.  The supported states are
             dependent upon the slp1OutletCapabilities 'powerControl' and
             'shutdown' bits, as well as the supported features of the
             firmware version."
        ::= { slp1OutletEntry 10 }

    slp1OutletControlAction OBJECT-TYPE
        SYNTAX      INTEGER {
                        none(0),
                        on(1),
                        off(2),
                        reboot(3)
                    }
        MAX-ACCESS  read-write
        STATUS      current
        DESCRIPTION
            "An action to change the control state of the outlet.  If the
             slp1OutletCapabilities 'powerControl' bit is TRUE, then the
             'on', 'off', and 'reboot' actions can be used to change the
             control state of the outlet.  If the slp1OutletCapabilities
             'powerControl' bit is FALSE, then the actions have no effect."
        ::= { slp1OutletEntry 11 }

    --
    --  Environmental Monitor Table
    --

    slp1EnvMonTable OBJECT-TYPE
        SYNTAX      SEQUENCE OF Slp1EnvMonEntry
        MAX-ACCESS  not-accessible
        STATUS      current
        DESCRIPTION
            "A table of environmental monitors."
        ::= { slp1SystemTables 4 }

    slp1EnvMonEntry OBJECT-TYPE
        SYNTAX      Slp1EnvMonEntry
        MAX-ACCESS  not-accessible
        STATUS      current
        DESCRIPTION
            "Row definition for the environmental monitor table."
        INDEX       { slp1EnvMonIndex }
        ::= { slp1EnvMonTable 1 }

    Slp1EnvMonEntry ::= SEQUENCE {
        slp1EnvMonIndex                INTEGER,
        slp1EnvMonID                   DisplayString,
        slp1EnvMonName                 DisplayString,
        slp1EnvMonStatus               INTEGER,
        slp1EnvMonWaterSensorName      DisplayString,
        slp1EnvMonWaterSensorStatus    INTEGER,
        slp1EnvMonADCName              DisplayString,
        slp1EnvMonADCStatus            INTEGER,
        slp1EnvMonADCCount             INTEGER,
        slp1EnvMonADCLowThresh         INTEGER,
        slp1EnvMonADCHighThresh        INTEGER,
        slp1EnvMonTempHumidSensorCount INTEGER,
        slp1EnvMonContactClosureCount  INTEGER
    }

    slp1EnvMonIndex OBJECT-TYPE
        SYNTAX      INTEGER(0..4)
        MAX-ACCESS  not-accessible
        STATUS      current
        DESCRIPTION
            "Index for the environmental monitor table."
        ::= { slp1EnvMonEntry 1 }

    slp1EnvMonID OBJECT-TYPE
        SYNTAX      DisplayString(SIZE(1))
        MAX-ACCESS  read-only
        STATUS      current
        DESCRIPTION
            "The ID of the environmental monitor."
        ::= { slp1EnvMonEntry 2 }

    slp1EnvMonName OBJECT-TYPE
        SYNTAX      DisplayString(SIZE(0..24))
        MAX-ACCESS  read-write
        STATUS      current
        DESCRIPTION
            "The name of the environmental monitor."
        ::= { slp1EnvMonEntry 3 }

    slp1EnvMonStatus OBJECT-TYPE
        SYNTAX      INTEGER {
                        normal(0),
                        noComm(1)
                    }
        MAX-ACCESS  read-only
        STATUS      current
        DESCRIPTION
            "The operational status of the environmental monitor."
        ::= { slp1EnvMonEntry 4 }

    slp1EnvMonWaterSensorName OBJECT-TYPE
        SYNTAX      DisplayString(SIZE(0..24))
        MAX-ACCESS  read-write
        STATUS      current
        DESCRIPTION
            "The name of the water sensor."
        ::= { slp1EnvMonEntry 5 }

    slp1EnvMonWaterSensorStatus OBJECT-TYPE
        SYNTAX      INTEGER {
                        normal(0),
                        alarm(1),
                        noComm(2)
                    }
        MAX-ACCESS  read-only
        STATUS      current
        DESCRIPTION
            "The status of the water sensor."
        ::= { slp1EnvMonEntry 6 }

    slp1EnvMonADCName OBJECT-TYPE
        SYNTAX      DisplayString(SIZE(0..24))
        MAX-ACCESS  read-write
        STATUS      current
        DESCRIPTION
            "The name of the analog-to-digital converter."
        ::= { slp1EnvMonEntry 7 }

    slp1EnvMonADCStatus OBJECT-TYPE
        SYNTAX      INTEGER {
                        normal(0),
                        reading(1),
                        countLow(2),
                        countHigh(3),
                        readError(4),
                        noComm(5)
                    }
        MAX-ACCESS  read-only
        STATUS      current
        DESCRIPTION
            "The status of the analog-to-digital converter."
        ::= { slp1EnvMonEntry 8 }

    slp1EnvMonADCCount OBJECT-TYPE
        SYNTAX      INTEGER(-1..255)
        MAX-ACCESS  read-only
        STATUS      current
        DESCRIPTION
            "The 8-bit count value from the analog-to-digital converter.
             A non-negative value indicates the digital value retrieved
             from the ADC.  A negative value indicates that a digital
             value was not able to be retrieved."
        ::= { slp1EnvMonEntry 9 }

    slp1EnvMonADCLowThresh OBJECT-TYPE
        SYNTAX      INTEGER(0..255)
        MAX-ACCESS  read-write
        STATUS      current
        DESCRIPTION
            "The 8-bit count low threshold value of the analog-to-digital
             converter."
        ::= { slp1EnvMonEntry 10 }

    slp1EnvMonADCHighThresh OBJECT-TYPE
        SYNTAX      INTEGER(0..255)
        MAX-ACCESS  read-write
        STATUS      current
        DESCRIPTION
            "The 8-bit count high threshold value of the analog-to-digital
             converter."
        ::= { slp1EnvMonEntry 11 }

    slp1EnvMonTempHumidSensorCount OBJECT-TYPE
        SYNTAX      INTEGER(0..2)
        MAX-ACCESS  read-only
        STATUS      current
        DESCRIPTION
            "The number of temperature/humidity sensors on the
             environmental monitor."
        ::= { slp1EnvMonEntry 12 }

    slp1EnvMonContactClosureCount OBJECT-TYPE
        SYNTAX      INTEGER(0..4)
        MAX-ACCESS  read-only
        STATUS      current
        DESCRIPTION
            "The number of contact closures on the environmental monitor."
        ::= { slp1EnvMonEntry 13 }

    --
    --  Temperature/Humidity Sensor Table
    --

    slp1TempHumidSensorTable OBJECT-TYPE
        SYNTAX      SEQUENCE OF Slp1TempHumidSensorEntry
        MAX-ACCESS  not-accessible
        STATUS      current
        DESCRIPTION
            "A table of temperature/humidity sensors."
        ::= { slp1SystemTables 5 }

    slp1TempHumidSensorEntry OBJECT-TYPE
        SYNTAX      Slp1TempHumidSensorEntry
        MAX-ACCESS  not-accessible
        STATUS      current
        DESCRIPTION
            "Row definition for the temperature/humidity sensor table."
        INDEX       { slp1EnvMonIndex, slp1TempHumidSensorIndex }
        ::= { slp1TempHumidSensorTable 1 }

    Slp1TempHumidSensorEntry ::= SEQUENCE {
        slp1TempHumidSensorIndex           INTEGER,
        slp1TempHumidSensorID              DisplayString,
        slp1TempHumidSensorName            DisplayString,
        slp1TempHumidSensorStatus          INTEGER,
        slp1TempHumidSensorTempStatus      INTEGER,
        slp1TempHumidSensorTempValue       INTEGER,
        slp1TempHumidSensorTempLowThresh   INTEGER,
        slp1TempHumidSensorTempHighThresh  INTEGER,
        slp1TempHumidSensorHumidStatus     INTEGER,
        slp1TempHumidSensorHumidValue      INTEGER,
        slp1TempHumidSensorHumidLowThresh  INTEGER,
        slp1TempHumidSensorHumidHighThresh INTEGER
    }

    slp1TempHumidSensorIndex OBJECT-TYPE
        SYNTAX      INTEGER(0..2)
        MAX-ACCESS  not-accessible
        STATUS      current
        DESCRIPTION
            "Index for the temperature/humidity sensor table."
        ::= { slp1TempHumidSensorEntry 1 }

    slp1TempHumidSensorID OBJECT-TYPE
        SYNTAX      DisplayString(SIZE(2))
        MAX-ACCESS  read-only
        STATUS      current
        DESCRIPTION
            "The ID of the temperature/humidity sensor."
        ::= { slp1TempHumidSensorEntry 2 }

    slp1TempHumidSensorName OBJECT-TYPE
        SYNTAX      DisplayString(SIZE(0..24))
        MAX-ACCESS  read-write
        STATUS      current
        DESCRIPTION
            "The name of the temperature/humidity sensor."
        ::= { slp1TempHumidSensorEntry 3 }

    slp1TempHumidSensorStatus OBJECT-TYPE
        SYNTAX      INTEGER {
                        found(0),
                        notFound(1),
                        lost(2),
                        noComm(3)
                    }
        MAX-ACCESS  read-only
        STATUS      current
        DESCRIPTION
            "The operational status of the temperature/humidity sensor."
        ::= { slp1TempHumidSensorEntry 4 }

    slp1TempHumidSensorTempStatus OBJECT-TYPE
        SYNTAX      INTEGER {
                        normal(0),
                        notFound(1),
                        reading(2),
                        tempLow(3),
                        tempHigh(4),
                        readError(5),
                        lost(6),
                        noComm(7)
                    }
        MAX-ACCESS  read-only
        STATUS      current
        DESCRIPTION
            "The status of the temperature sensor."
        ::= { slp1TempHumidSensorEntry 5 }

    slp1TempHumidSensorTempValue OBJECT-TYPE
        SYNTAX      INTEGER(-1..1235)
        UNITS       "tenth degrees Celsius"
        MAX-ACCESS  read-only
        STATUS      current
        DESCRIPTION
            "The temperature measured by the sensor.  A non-negative value
             indicates the measured temperature in tenths of degrees
             Celsius.  A negative value indicates that a temperature value
             was not able to be measured."
        ::= { slp1TempHumidSensorEntry 6 }

    slp1TempHumidSensorTempLowThresh OBJECT-TYPE
        SYNTAX      INTEGER(0..123)
        UNITS       "degrees Celsius"
        MAX-ACCESS  read-write
        STATUS      current
        DESCRIPTION
            "The temperature low threshold value of the sensor in degrees
             Celsius."
        ::= { slp1TempHumidSensorEntry 7 }

    slp1TempHumidSensorTempHighThresh OBJECT-TYPE
        SYNTAX      INTEGER(0..123)
        UNITS       "degrees Celsius"
        MAX-ACCESS  read-write
        STATUS      current
        DESCRIPTION
            "The temperature high threshold value of the sensor in degrees
             Celsius."
        ::= { slp1TempHumidSensorEntry 8 }

    slp1TempHumidSensorHumidStatus OBJECT-TYPE
        SYNTAX      INTEGER {
                        normal(0),
                        notFound(1),
                        reading(2),
                        humidLow(3),
                        humidHigh(4),
                        readError(5),
                        lost(6),
                        noComm(7)
                    }
        MAX-ACCESS  read-only
        STATUS      current
        DESCRIPTION
            "The status of the humidity sensor."
        ::= { slp1TempHumidSensorEntry 9 }

    slp1TempHumidSensorHumidValue OBJECT-TYPE
        SYNTAX      INTEGER(-1..100)
        UNITS       "percentage relative humidity"
        MAX-ACCESS  read-only
        STATUS      current
        DESCRIPTION
            "The humidity measured by the sensor.  A non-negative value
             indicates the measured humidity in percentage relative
             humidity.  A negative value indicates that a humidity value
             was not able to be measured."
        ::= { slp1TempHumidSensorEntry 10 }

    slp1TempHumidSensorHumidLowThresh OBJECT-TYPE
        SYNTAX      INTEGER(0..100)
        UNITS       "percentage relative humidity"
        MAX-ACCESS  read-write
        STATUS      current
        DESCRIPTION
            "The humidity low threshold value of the sensor in percentage
             relative humidity."
        ::= { slp1TempHumidSensorEntry 11 }

    slp1TempHumidSensorHumidHighThresh OBJECT-TYPE
        SYNTAX      INTEGER(0..100)
        UNITS       "percentage relative humidity"
        MAX-ACCESS  read-write
        STATUS      current
        DESCRIPTION
            "The humidity low threshold value of the sensor in percentage
             relative humidity."
        ::= { slp1TempHumidSensorEntry 12 }

    --
    --  Contact Closure Table
    --

    slp1ContactClosureTable OBJECT-TYPE
        SYNTAX      SEQUENCE OF Slp1ContactClosureEntry
        MAX-ACCESS  not-accessible
        STATUS      current
        DESCRIPTION
            "A table of contact closures."
        ::= { slp1SystemTables 6 }

    slp1ContactClosureEntry OBJECT-TYPE
        SYNTAX      Slp1ContactClosureEntry
        MAX-ACCESS  not-accessible
        STATUS      current
        DESCRIPTION
            "Row definition for the contact closure table."
        INDEX       { slp1EnvMonIndex, slp1ContactClosureIndex }
        ::= { slp1ContactClosureTable 1 }

    Slp1ContactClosureEntry ::= SEQUENCE {
        slp1ContactClosureIndex     INTEGER,
        slp1ContactClosureID        DisplayString,
        slp1ContactClosureName      DisplayString,
        slp1ContactClosureStatus    INTEGER
    }

    slp1ContactClosureIndex OBJECT-TYPE
        SYNTAX      INTEGER(0..4)
        MAX-ACCESS  not-accessible
        STATUS      current
        DESCRIPTION
            "Index for the contact closure table."
        ::= { slp1ContactClosureEntry 1 }

    slp1ContactClosureID OBJECT-TYPE
        SYNTAX      DisplayString(SIZE(2))
        MAX-ACCESS  read-only
        STATUS      current
        DESCRIPTION
            "The ID of the contact closure."
        ::= { slp1ContactClosureEntry 2 }

    slp1ContactClosureName OBJECT-TYPE
        SYNTAX      DisplayString(SIZE(0..24))
        MAX-ACCESS  read-write
        STATUS      current
        DESCRIPTION
            "The name of the contact closure."
        ::= { slp1ContactClosureEntry 3 }

    slp1ContactClosureStatus OBJECT-TYPE
        SYNTAX      INTEGER {
                        normal(0),
                        alarm(1),
                        noComm(2)
                    }
        MAX-ACCESS  read-only
        STATUS      current
        DESCRIPTION
            "The status of the contact closure."
        ::= { slp1ContactClosureEntry 4 }

--
--  Notifications
--

    slp1Traps OBJECT IDENTIFIER ::= { slp1 100 }

    slp1Events OBJECT IDENTIFIER ::= { slp1Traps 0 }
    -- the 0 is for V1 compatibility

    -- Tower Traps

    slp1TowerStatusEvent NOTIFICATION-TYPE
        OBJECTS {
            slp1SystemLocation,
            slp1TowerID,
            slp1TowerName,
            slp1TowerStatus
        }
        STATUS      current
        DESCRIPTION
            "Tower status event.  If enabled, this trap is sent when the
             slp1TowerStatus indicates an error state ('noComm').  This
             trap is repeated periodically while the slp1TowerStatus
             remains in an error state.  If the slp1TowerStatus returns
             to a non-error state ('normal'), this trap is sent once more
             with the non-error slp1TowerStatus, and then stops being
             repeated.

             While the slp1TowerStatus indicates an error state, all
             status and load traps are suppressed for input feeds and
             outlets on the tower."
        --#TYPE "SecureLinx SLP: Tower Status Event."
        --#SUMMARY "Status of Tower '%s' (%s) is '%d'."
        --#ARGUMENTS { 2, 1, 3 }
        --#SEVERITY CRITICAL
        --#GENERIC 6
        --#CATEGORY "Error Events"
        --#SOURCE_ID "A"
        --#TIMEINDEX 255
        --#HELP ""
        --#HELPTAG 0
        --#STATE UNKNOWN
        ::= { slp1Events 1 }

    -- Input Feed Traps

    slp1InfeedStatusEvent NOTIFICATION-TYPE
        OBJECTS {
            slp1SystemLocation,
            slp1InfeedID,
            slp1InfeedName,
            slp1InfeedStatus
        }
        STATUS      current
        DESCRIPTION
            "Input feed status event.  If enabled, this trap is sent when
             the slp1InfeedStatus indicates an error state ('offError',
             'onError', or 'noComm').  This trap is repeated periodically
             while the slp1InfeedStatus remains in an error state.  If
             the slp1InfeedStatus returns to a non-error state ('off' or
             'on'), this trap is sent once more with the non-error
             slp1InfeedStatus, and then stops being repeated.

             While the slp1InfeedStatus indicates an error state, load
             traps are suppressed for the input feed, and, if the
             slp1InfeedCapabilities 'failSafe' bit is FALSE, all status
             and load traps are suppressed for outlets on the input feed."
        --#TYPE "SecureLinx SLP: Input Feed Status Event."
        --#SUMMARY "Status of Input Feed '%s' (%s) is '%d'."
        --#ARGUMENTS { 2, 1, 3 }
        --#SEVERITY CRITICAL
        --#GENERIC 6
        --#CATEGORY "Error Events"
        --#SOURCE_ID "A"
        --#TIMEINDEX 255
        --#HELP ""
        --#HELPTAG 0
        --#STATE UNKNOWN
        ::= { slp1Events 2 }

    slp1InfeedLoadEvent NOTIFICATION-TYPE
        OBJECTS {
            slp1SystemLocation,
            slp1InfeedID,
            slp1InfeedName,
            slp1InfeedLoadStatus,
            slp1InfeedLoadValue,
            slp1InfeedLoadHighThresh
        }
        STATUS      current
        DESCRIPTION
            "Input feed load event.  If enabled, this trap is sent when
             the slp1InfeedLoadStatus indicates an error state ('loadLow',
             'loadHigh', 'overLoad', 'readError', or 'noComm').  This
             trap is repeated periodically while the slp1InfeedLoadStatus
             remains in an error state.  If the slp1InfeedLoadStatus
             returns to a non-error state ('normal' or 'notOn'), this trap
             is sent once more with the non-error slp1InfeedLoadStatus,
             and then stops being repeated."
        --#TYPE "SecureLinx SLP: Input Feed Load Event."
        --#SUMMARY "Load Status of Input Feed '%s' (%s) is '%d'."
        --#ARGUMENTS { 2, 1, 3 }
        --#SEVERITY CRITICAL
        --#GENERIC 6
        --#CATEGORY "Error Events"
        --#SOURCE_ID "A"
        --#TIMEINDEX 255
        --#HELP ""
        --#HELPTAG 0
        --#STATE UNKNOWN
        ::= { slp1Events 3 }

    -- Outlet Traps

    slp1OutletStatusEvent NOTIFICATION-TYPE
        OBJECTS {
            slp1SystemLocation,
            slp1OutletID,
            slp1OutletName,
            slp1OutletStatus
        }
        STATUS      current
        DESCRIPTION
            "Outlet status event.  If enabled, this trap is sent when the
             slp1OutletStatus indicates an error state ('offError',
             'onError', or 'noComm').  This trap is repeated periodically
             while the slp1OutletStatus remains in an error state.  If
             the slp1OutletStatus returns to a non-error state ('off' or
             'on'), this trap is sent once more with the non-error
             slp1OutletStatus, and then stops being repeated.

             While the slp1OutletStatus indicates an error state, load
             traps are suppressed for the outlet."
        --#TYPE "SecureLinx SLP: Outlet Status Event."
        --#SUMMARY "Status of Outlet '%s' (%s) is '%d'."
        --#ARGUMENTS { 2, 1, 3 }
        --#SEVERITY CRITICAL
        --#GENERIC 6
        --#CATEGORY "Error Events"
        --#SOURCE_ID "A"
        --#TIMEINDEX 255
        --#HELP ""
        --#HELPTAG 0
        --#STATE UNKNOWN
        ::= { slp1Events 4 }

    slp1OutletLoadEvent NOTIFICATION-TYPE
        OBJECTS {
            slp1SystemLocation,
            slp1OutletID,
            slp1OutletName,
            slp1OutletLoadStatus,
            slp1OutletLoadValue,
            slp1OutletLoadLowThresh,
            slp1OutletLoadHighThresh
        }
        STATUS      current
        DESCRIPTION
            "Outlet load event.  If enabled, this trap is sent when the
             slp1OutletLoadStatus indicates an error state ('loadLow',
             'loadHigh', 'overLoad', 'readError', or 'noComm').  This
             trap is repeated periodically while the slp1OutletLoadStatus
             remains in an error state.  If the slp1OutletLoadStatus
             returns to a non-error state ('normal' or 'notOn'), this trap
             is sent once more with the non-error slp1OutletLoadStatus,
             and then stops being repeated."
        --#TYPE "SecureLinx SLP: Outlet Load Event."
        --#SUMMARY "Load Status of Outlet '%s' (%s) is '%d'."
        --#ARGUMENTS { 2, 1, 3 }
        --#SEVERITY CRITICAL
        --#GENERIC 6
        --#CATEGORY "Error Events"
        --#SOURCE_ID "A"
        --#TIMEINDEX 255
        --#HELP ""
        --#HELPTAG 0
        --#STATE UNKNOWN
        ::= { slp1Events 5 }

    slp1OutletChangeEvent NOTIFICATION-TYPE
        OBJECTS {
            slp1SystemLocation,
            slp1OutletID,
            slp1OutletName,
            slp1OutletStatus,
            slp1OutletControlState
        }
        STATUS      current
        DESCRIPTION
            "Outlet on/off change event.  If enabled, this trap is sent
             when the slp1OutletStatus changes from any 'on' state ('on',
             'onWait' or 'onError') to any 'off' state ('off', 'offWait'
             or 'offError'), and vice-versa."
        --#TYPE "SecureLinx SLP: Outlet Change Event."
        --#SUMMARY "Outlet '%s' (%s) has changed to '%d'."
        --#ARGUMENTS { 2, 1, 3 }
        --#SEVERITY INFORMATIONAL
        --#GENERIC 6
        --#CATEGORY "Status Events"
        --#SOURCE_ID "A"
        --#TIMEINDEX 255
        --#HELP ""
        --#HELPTAG 0
        --#STATE UNKNOWN
        ::= { slp1Events 6 }

    -- Environmental Monitor Traps

    slp1EnvMonStatusEvent NOTIFICATION-TYPE
        OBJECTS {
            slp1SystemLocation,
            slp1EnvMonID,
            slp1EnvMonName,
            slp1EnvMonStatus
        }
        STATUS      current
        DESCRIPTION
            "Environmental monitor status event.  If enabled, this trap
             is sent when the slp1EnvMonStatus indicates an error state
             ('noComm').  This trap is repeated periodically while the
             slp1EnvMonStatus remains in an error state.  If the
             slp1EnvMonStatus returns to a non-error state ('normal'),
             this trap is sent once more with the non-error
             slp1EnvMonStatus, and then stops being repeated.

             While the slp1EnvMonStatus indicates an error state, all
             status traps are suppressed for the water sensor, ADC,
             temperature/humudity sensors, and contact closures on the
             environmental monitor."
        --#TYPE "SecureLinx SLP: Environmental Monitor Status Event."
        --#SUMMARY "Status of Environmental Monitor '%s' (%s) is '%d'."
        --#ARGUMENTS { 2, 1, 3 }
        --#SEVERITY CRITICAL
        --#GENERIC 6
        --#CATEGORY "Error Events"
        --#SOURCE_ID "A"
        --#TIMEINDEX 255
        --#HELP ""
        --#HELPTAG 0
        --#STATE UNKNOWN
        ::= { slp1Events 7 }

    slp1EnvMonWaterSensorEvent NOTIFICATION-TYPE
        OBJECTS {
            slp1SystemLocation,
            slp1EnvMonID,
            slp1EnvMonWaterSensorName,
            slp1EnvMonWaterSensorStatus
        }
        STATUS      current
        DESCRIPTION
            "Environmental monitor water sensor event.  If enabled, this
             trap is sent when the slp1EnvMonWaterSensorStatus indicates
             an error state ('alarm').  This trap is repeated periodically
             while the slp1EnvMonWaterSensorStatus remains in an error
             state.  If the slp1EnvMonWaterSensorStatus returns to a
             non-error state ('normal'), this trap is sent once more with
             the non-error slp1EnvMonWaterSensorStatus, and then stops
             being repeated."
        --#TYPE "SecureLinx SLP: Water Sensor Event."
        --#SUMMARY "Status of Water Sensor '%s' (%s) is '%d'."
        --#ARGUMENTS { 2, 1, 3 }
        --#SEVERITY CRITICAL
        --#GENERIC 6
        --#CATEGORY "Error Events"
        --#SOURCE_ID "A"
        --#TIMEINDEX 255
        --#HELP ""
        --#HELPTAG 0
        --#STATE UNKNOWN
        ::= { slp1Events 8 }

    slp1EnvMonADCEvent NOTIFICATION-TYPE
        OBJECTS {
            slp1SystemLocation,
            slp1EnvMonID,
            slp1EnvMonADCName,
            slp1EnvMonADCStatus,
            slp1EnvMonADCCount,
            slp1EnvMonADCLowThresh,
            slp1EnvMonADCHighThresh
        }
        STATUS      current
        DESCRIPTION
            "Environmental monitor analog-to-digital converter event.
             If enabled, this trap is sent when the slp1EnvMonADCStatus
             indicates an error state ('countLow' or 'countHigh').  This
             trap is repeated periodically while the slp1EnvMonADCStatus
             remains in an error state.  If the slp1EnvMonADCStatus
             returns to a non-error state ('normal'), this trap is sent
             once more with the non-error slp1EnvMonADCStatus, and then
             stops being repeated."
        --#TYPE "SecureLinx SLP: ADC Event."
        --#SUMMARY "Status of ADC '%s' (%s) is '%d'."
        --#ARGUMENTS { 2, 1, 3 }
        --#SEVERITY CRITICAL
        --#GENERIC 6
        --#CATEGORY "Error Events"
        --#SOURCE_ID "A"
        --#TIMEINDEX 255
        --#HELP ""
        --#HELPTAG 0
        --#STATE UNKNOWN
        ::= { slp1Events 9 }

    slp1TempHumidSensorStatusEvent NOTIFICATION-TYPE
        OBJECTS {
            slp1SystemLocation,
            slp1TempHumidSensorID,
            slp1TempHumidSensorName,
            slp1TempHumidSensorStatus
        }
        STATUS      current
        DESCRIPTION
            "Temperature/humidity sensor status event.  If enabled, this
             trap is sent when the slp1TempHumidSensorStatus indicates an
             error state ('lost').  This trap is repeated periodically
             while the slp1TempHumidSensorStatus remains in an error
             state.  If the slp1TempHumidSensorStatus returns to a
             non-error state ('found'), this trap is sent once more with
             the non-error slp1TempHumidSensorStatus, and then stops
             being repeated.

             While the slp1TempHumidSensorStatus indicates an error state,
             all temperature and humidity status traps are suppressed for
             the temperature/humudity sensor."
        --#TYPE "SecureLinx SLP: T/H Sensor Status Event."
        --#SUMMARY "Status of T/H Sensor '%s' (%s) is '%d'."
        --#ARGUMENTS { 2, 1, 3 }
        --#SEVERITY CRITICAL
        --#GENERIC 6
        --#CATEGORY "Error Events"
        --#SOURCE_ID "A"
        --#TIMEINDEX 255
        --#HELP ""
        --#HELPTAG 0
        --#STATE UNKNOWN
        ::= { slp1Events 10 }

    slp1TempHumidSensorTempEvent NOTIFICATION-TYPE
        OBJECTS {
            slp1SystemLocation,
            slp1TempHumidSensorID,
            slp1TempHumidSensorName,
            slp1TempHumidSensorTempStatus,
            slp1TempHumidSensorTempValue,
            slp1TempHumidSensorTempLowThresh,
            slp1TempHumidSensorTempHighThresh
        }
        STATUS      current
        DESCRIPTION
            "Temperature/humidity sensor temperature event.  If enabled,
             this trap is sent when the slp1TempHumidSensorTempStatus
             indicates an error state ('tempLow' or 'tempHigh').
             This trap is repeated periodically while the
             slp1TempHumidSensorTempStatus remains in an error state.
             If the slp1TempHumidSensorTempStatus returns to a non-error
             state ('normal'), this trap is sent once more with the
             non-error slp1TempHumidSensorTempStatus, and then stops
             being repeated."
        --#TYPE "SecureLinx SLP: T/H Sensor Temperature Event."
        --#SUMMARY "Temperature Status of T/H Sensor '%s' (%s) is '%d'."
        --#ARGUMENTS { 2, 1, 3 }
        --#SEVERITY CRITICAL
        --#GENERIC 6
        --#CATEGORY "Error Events"
        --#SOURCE_ID "A"
        --#TIMEINDEX 255
        --#HELP ""
        --#HELPTAG 0
        --#STATE UNKNOWN
        ::= { slp1Events 11 }

    slp1TempHumidSensorHumidEvent NOTIFICATION-TYPE
        OBJECTS {
            slp1SystemLocation,
            slp1TempHumidSensorID,
            slp1TempHumidSensorName,
            slp1TempHumidSensorHumidStatus,
            slp1TempHumidSensorHumidValue,
            slp1TempHumidSensorHumidLowThresh,
            slp1TempHumidSensorHumidHighThresh
        }
        STATUS      current
        DESCRIPTION
            "Temperature/humidity sensor humidity event.  If enabled,
             this trap is sent when the slp1TempHumidSensorHumidStatus
             indicates an error state ('humidLow' or 'humidHigh').
             This trap is repeated periodically while the
             slp1TempHumidSensorHumidStatus remains in an error state.
             If the slp1TempHumidSensorHumidStatus returns to a non-error
             state ('normal'), this trap is sent once more with the
             non-error slp1TempHumidSensorHumidStatus, and then stops
             being repeated."
        --#TYPE "SecureLinx SLP: T/H Sensor Humidity Event."
        --#SUMMARY "Humidity Status of T/H Sensor '%s' (%s) is '%d'."
        --#ARGUMENTS { 2, 1, 3 }
        --#SEVERITY CRITICAL
        --#GENERIC 6
        --#CATEGORY "Error Events"
        --#SOURCE_ID "A"
        --#TIMEINDEX 255
        --#HELP ""
        --#HELPTAG 0
        --#STATE UNKNOWN
        ::= { slp1Events 12 }

    slp1ContactClosureEvent NOTIFICATION-TYPE
        OBJECTS {
            slp1SystemLocation,
            slp1ContactClosureID,
            slp1ContactClosureName,
            slp1ContactClosureStatus
        }
        STATUS      current
        DESCRIPTION
            "Contact closure event.  If enabled, this trap is sent when
             the slp1ContactClosureStatus indicates an error state
             ('alarm').  This trap is repeated periodically while the
             slp1ContactClosureStatus remains in an error state.  If the
             slp1ContactClosureStatus returns to a non-error state
             ('normal'), this trap is sent once more with the non-error
             slp1ContactClosureStatus, and then stops being repeated."
        --#TYPE "SecureLinx SLP: Contact Closure Event."
        --#SUMMARY "Status of Contact Closure '%s' (%s) is '%d'."
        --#ARGUMENTS { 2, 1, 3 }
        --#SEVERITY CRITICAL
        --#GENERIC 6
        --#CATEGORY "Error Events"
        --#SOURCE_ID "A"
        --#TIMEINDEX 255
        --#HELP ""
        --#HELPTAG 0
        --#STATE UNKNOWN
        ::= { slp1Events 13 }

END
