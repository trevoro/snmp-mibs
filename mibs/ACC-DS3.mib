ACC-DS3 DEFINITIONS ::= BEGIN

    IMPORTS
	 OBJECT-TYPE, Counter FROM RFC1155-SMI
                         accTrapLogSeqNum FROM ACC-SYSTEM
accBRG, DisplayString, RowStatus, IfIndex, SmdsAddress
             FROM ACC-MIB;
-- DS3/E3 Interface 
	-- the DS3/E3 Interface 
            accDs3InfcTable OBJECT-TYPE
                SYNTAX SEQUENCE OF AccDs3InfcEntry
                ACCESS not-accessible
                STATUS mandatory
                DESCRIPTION
                " The DS3 interface table."
                ::= { accBRG 79 }
            accDs3InfcEntry OBJECT-TYPE
                SYNTAX AccDs3InfcEntry
                ACCESS not-accessible
                STATUS mandatory
                DESCRIPTION
                " An entry in the DS3 interface table."
                INDEX { accDs3InfcServiceState }
                ::= { accDs3InfcTable 1 }
            AccDs3InfcEntry ::= SEQUENCE {
                accDs3InfcServiceState INTEGER,
                accDs3InfcLoopbackOp INTEGER,
                accDs3InfcLoopbackCO INTEGER,
                accDs3InfcLineLength INTEGER,
                accDs3InfcMdlProtocol INTEGER,
                accDs3InfcTxMdlEic DisplayString,
                accDs3InfcTxMdlLic DisplayString,
                accDs3InfcTxMdlFic DisplayString,
                accDs3InfcTxMdlUnit DisplayString,
                accDs3InfcTxMdlFac DisplayString,
                accDs3InfcTxMdlPort DisplayString,
                accDs3InfcTxMdlGen DisplayString,
                accDs3InfcRxMdlPathAges Counter,
                accDs3InfcRxMdlIdleAges Counter,
                accDs3InfcRxMdlTestAges Counter,
                accDs3InfcRxMdlEic DisplayString,
                accDs3InfcRxMdlLic DisplayString,
                accDs3InfcRxMdlFic DisplayString,
                accDs3InfcRxMdlUnit DisplayString,
                accDs3InfcRxMdlFac DisplayString,
                accDs3InfcRxMdlPort DisplayString,
                accDs3InfcRxMdlGen DisplayString 
                }
          accDs3InfcServiceState OBJECT-TYPE
             SYNTAX INTEGER {
                          ds3InfcInService(1),
                          ds3InfcOutOfServer(2)
                          }
              ACCESS read-write
              STATUS mandatory
              DESCRIPTION
              "Indicates DS3 interface service state.  
               Certain attributes require that the service 
               state be in a certain state before they can
               be altered."
              ::= { accDs3InfcEntry 1 }
          accDs3InfcLoopbackOp OBJECT-TYPE
              SYNTAX  INTEGER {
                        accDs3NoInfcLoop(1),
                        accDs3PaybackLoop(2),
                        accDs3InfcLineLoop(3),
                        accDs3InfcEquipLoop(4),
                        ds1loop-1(33),
                        ds1loop-2(34),
                        ds1loop-3(35),
                        ds1loop-4(36),
                        ds1loop-5(37),
                        ds1loop-6(38),
                        ds1loop-7(39),
                        ds1loop-8(40),
                        ds1loop-9(41),
                        ds1loop-10(42),
                        ds1loop-11(43),
                        ds1loop-12(44),
                        ds1loop-13(45),
                        ds1loop-14(46),
                        ds1loop-15(47),
                        ds1loop-16(48),
                        ds1loop-17(49),
                        ds1loop-18(50),
                        ds1loop-19(51),
                        ds1loop-20(52),
                        ds1loop-21(53),
                        ds1loop-22(54),
                        ds1loop-23(55),
                        ds1loop-24(56),
                        ds1loop-25(57),
                        ds1loop-26(58),
                        ds1loop-27(59),
                        ds1loop-28(60)
                  }
              ACCESS read-write
              STATUS mandatory
              DESCRIPTION
              "The local loopback mode of a DS3 interface. 
               The entire DS3 line can be set or each individual
               DS1 line within the DS3 can be set separately."
              ::= { accDs3InfcEntry 2 }
          accDs3InfcLoopbackCO OBJECT-TYPE
              SYNTAX  INTEGER {
                        accDs3NoLoop(1),
                        accDs3DS1LoopAll(19),
                        accDs3LineLoop(27),
                        ds1loop-1(33),
                        ds1loop-2(34),
                        ds1loop-3(35),
                        ds1loop-4(36),
                        ds1loop-5(37),
                        ds1loop-6(38),
                        ds1loop-7(39),
                        ds1loop-8(40),
                        ds1loop-9(41),
                        ds1loop-10(42),
                        ds1loop-11(43),
                        ds1loop-12(44),
                        ds1loop-13(45),
                        ds1loop-14(46),
                        ds1loop-15(47),
                        ds1loop-16(48),
                        ds1loop-17(49),
                        ds1loop-18(50),
                        ds1loop-19(51),
                        ds1loop-20(52),
                        ds1loop-21(53),
                        ds1loop-22(54),
                        ds1loop-23(55),
                        ds1loop-24(56),
                        ds1loop-25(57),
                        ds1loop-26(58),
                        ds1loop-27(59),
                        ds1loop-28(60)
                  }
              ACCESS read-only
              STATUS mandatory
              DESCRIPTION
              "The loopback state of a DS3 interface when
               loopback is initiated remotely. A DS3 line 
               can be set, or individual DS1 lines within
               the DS3 can be set separately."
              ::= { accDs3InfcEntry 3 }
          accDs3InfcLineLength OBJECT-TYPE
              SYNTAX  INTEGER {
                          ds3ShortLine(1),     --0..133 feet
                          ds3LongLine(2)       --133..655 feet
                  }
              ACCESS read-write
              STATUS mandatory
              DESCRIPTION
              " The approximate line length. The default is
                short. "
              ::= { accDs3InfcEntry 4 }
          accDs3InfcMdlProtocol OBJECT-TYPE
              SYNTAX  INTEGER {
                          ds3Ansi(1),
                          ds3NoProtocol(2)
                  }
              ACCESS read-write
              STATUS mandatory
              DESCRIPTION
              " The terminal to terminal path maintenance
                data link protocol of the DS3 interface. "
              ::= { accDs3InfcEntry 5 }
          accDs3InfcTxMdlEic OBJECT-TYPE
              SYNTAX DisplayString 
              ACCESS read-write
              STATUS mandatory
              DESCRIPTION
              " The local MDL equipment identification
                code for the DS3 interface. Describes the 
                equipment."
              ::= { accDs3InfcEntry 6 }
          accDs3InfcTxMdlLic OBJECT-TYPE
              SYNTAX DisplayString 
              ACCESS read-write
              STATUS mandatory
              DESCRIPTION
              " The local MDL location identification
                code for the DS3 interface. Describes
                specific location of the equipment."
              ::= { accDs3InfcEntry 7 }
          accDs3InfcTxMdlFic OBJECT-TYPE
              SYNTAX DisplayString 
              ACCESS read-write
              STATUS mandatory
              DESCRIPTION
              " The local MDL frame identification
                code for the DS3 interface. Identifies
                where the specific piece of equipment
                is located in a building"
              ::= { accDs3InfcEntry 8 }
          accDs3InfcTxMdlUnit OBJECT-TYPE
              SYNTAX DisplayString 
              ACCESS read-write
              STATUS mandatory
              DESCRIPTION
              " The local MDL unit identification
                for the DS3 interface. It identifies where
                the specific piece of equipment is located
                within a bay."
              ::= { accDs3InfcEntry 9 }
          accDs3InfcTxMdlFac OBJECT-TYPE
              SYNTAX DisplayString 
              ACCESS read-write
              STATUS mandatory
              DESCRIPTION
              " The local MDL facility identification
                code for the DS3 interface. Describes
                a specific DS3 path. "
              ::= { accDs3InfcEntry 10 }
          accDs3InfcTxMdlPort OBJECT-TYPE
              SYNTAX DisplayString 
              ACCESS read-write
              STATUS mandatory
              DESCRIPTION
              " The local MDL port identification
                code for the DS3 interface. Describes
                port on the equipment that will initiate
                the idle signal. "
              ::= { accDs3InfcEntry 11 }
          accDs3InfcTxMdlGen OBJECT-TYPE
              SYNTAX DisplayString 
              ACCESS read-write
              STATUS mandatory
              DESCRIPTION
              " The local MDL generator number
                for the DS3 interface. Describes
                the signal generator that will 
                initiate the test signal."
              ::= { accDs3InfcEntry 12 }
          accDs3InfcRxMdlEic OBJECT-TYPE
              SYNTAX DisplayString 
              ACCESS read-only
              STATUS mandatory
              DESCRIPTION
              " The remote MDL equipment identification
                code for the DS3 interface. Describes the 
                equipment."
              ::= { accDs3InfcEntry 13 }
          accDs3InfcRxMdlLic OBJECT-TYPE
              SYNTAX DisplayString 
              ACCESS read-only
              STATUS mandatory
              DESCRIPTION
              " The remote MDL location identification
                code for the DS3 interface. Describes
                specific location of the equipment."
              ::= { accDs3InfcEntry 14 }
          accDs3InfcRxMdlFic OBJECT-TYPE
              SYNTAX DisplayString 
              ACCESS read-only
              STATUS mandatory
              DESCRIPTION
              " The remote MDL frame identification
                code for the DS3 interface. Identifies
                where the specific piece of equipment
                is located in a building"
              ::= { accDs3InfcEntry 15 }
          accDs3InfcRxMdlUnit OBJECT-TYPE
              SYNTAX DisplayString
              ACCESS read-only
              STATUS mandatory
              DESCRIPTION
              " The remote MDL unit identification
                for the DS3 interface. It identifies where
                the specific piece of equipment is located
                within a bay."
              ::= { accDs3InfcEntry 16 }
          accDs3InfcRxMdlFac OBJECT-TYPE
              SYNTAX DisplayString 
              ACCESS read-only
              STATUS mandatory
              DESCRIPTION
              " The remote MDL unit identification
                for the DS3 interface. It identifies where
                the specific piece of equipment is located
                within a bay."
              ::= { accDs3InfcEntry 17 }
          accDs3InfcRxMdlPort OBJECT-TYPE
              SYNTAX DisplayString
              ACCESS read-only
              STATUS mandatory
              DESCRIPTION
              " The remote MDL port identification
                code for the DS3 interface. Describes
                port on the equipment that will initiate
                the idle signal. "
              ::= { accDs3InfcEntry 18 }
          accDs3InfcRxMdlGen OBJECT-TYPE
              SYNTAX DisplayString
              ACCESS read-only
              STATUS mandatory
              DESCRIPTION
              " The remote MDL generator number
                for the DS3 interface. Describes
                the signal generator that will 
                initiate the test signal."
              ::= { accDs3InfcEntry 19 }
          accDs3InfcRxMdlPathAges OBJECT-TYPE
              SYNTAX Counter
              ACCESS read-only
              STATUS mandatory
              DESCRIPTION ""
              ::= { accDs3InfcEntry 20 }
          accDs3InfcRxMdlIdleAges OBJECT-TYPE
              SYNTAX Counter
              ACCESS read-only
              STATUS mandatory
              DESCRIPTION ""
              ::= { accDs3InfcEntry 21 }
          accDs3InfcRxMdlTestAges OBJECT-TYPE
              SYNTAX Counter
              ACCESS read-only
              STATUS mandatory
              DESCRIPTION ""
              ::= { accDs3InfcEntry 22 }

END
