-- 
-- Copyright 1999 by Fore Systems, Inc. 
-- Converted to SMIv2 rfc 2578,2579,2580 - STD 58
--

-- Copyright 1996 by Fore Systems, Inc.  All rights reserved.
--
-- This file contains definitions for management information for
-- an SNMP over ILMI proxy.
------------------------------------------------------------------

Fore-IlmiSnmpProxy-MIB DEFINITIONS ::= BEGIN

IMPORTS
        Integer32,
	OBJECT-TYPE,
	MODULE-IDENTITY		FROM SNMPv2-SMI
	DisplayString,
	RowStatus		FROM SNMPv2-TC
	ilmisnmp		FROM Fore-Common-MIB;

foreIlmiSnmpProxyModule MODULE-IDENTITY
	LAST-UPDATED	"9609120000Z"
	ORGANIZATION	"FORE"
	CONTACT-INFO	"
		Postal:	FORE Systems Inc.
			1000 FORE Drive
			Warrendale, PA 15086-7502
		Tel:	+1 724 742 6900
		Email:	nm_mibs@fore.com
		Web:	http://www.fore.com"
	DESCRIPTION
		"This MIB module defines the FORE Systems specific
             SNMP Proxy information for the ILMI VCI.  It provides
             for an ISP table.  Each table entry contains the
             information necessary for a device to complete an
             SNMP request over the ILMI VCI specified.  Each table
             entry also contains information as to the status
             of the request and the values returned in response
             by the connected device."
	::= { ilmisnmp 1 }

------------------------------------------------------------------


ispTable OBJECT-TYPE
	SYNTAX	SEQUENCE OF IspEntry
	MAX-ACCESS	not-accessible
	STATUS	current
	DESCRIPTION
		"A table of SNMP requests to be made over the
		ILMI VCI."
	::= { ilmisnmp 2 }

ispEntry OBJECT-TYPE
	SYNTAX	IspEntry
	MAX-ACCESS	not-accessible
	STATUS	current
	DESCRIPTION
		"A table entry consisting of one SNMP request."
	INDEX	{ ispPort, ispVPI, ispIndex }
	::= { ispTable 1 }

IspEntry ::=
	SEQUENCE {
		ispPort				Integer32,
		ispVPI				Integer32,
		ispIndex			Integer32,		
		ispOperation			INTEGER,
		ispOID				OBJECT IDENTIFIER,
		ispConfStatus			INTEGER,
		ispOperStatus			INTEGER,
		ispCommunityName		DisplayString,
		ispRespOID			OBJECT IDENTIFIER,
		ispValue			OCTET STRING,
		ispRowStatus			RowStatus
	}	

ispPort OBJECT-TYPE
	SYNTAX	Integer32
	MAX-ACCESS	not-accessible
	STATUS	current
	DESCRIPTION
		"The port index of the ILMI instance to use for 
		SNMP requests."
	::= { ispEntry 1 }

ispVPI OBJECT-TYPE
	SYNTAX	Integer32
	MAX-ACCESS	not-accessible
	STATUS	current
	DESCRIPTION
		"The VPI of the ILMI instance to use for SNMP requests."
	::= { ispEntry 2 }

ispIndex OBJECT-TYPE
	SYNTAX	Integer32
	MAX-ACCESS	not-accessible
	STATUS	current
	DESCRIPTION
		"A unique index used to differentiate SNMP requests."
	::= { ispEntry 3 }

ispOperation OBJECT-TYPE
	SYNTAX	INTEGER {
			get(1),
			getnext(2)
		}
	MAX-ACCESS 	read-write
	STATUS	current
	DESCRIPTION
		"Whether the SNMP request is a get or getnext. This
		MIB does not support set requests at this time"
	::= { ispEntry 4 }

ispOID OBJECT-TYPE
	SYNTAX	OBJECT IDENTIFIER
	MAX-ACCESS 	read-write
	STATUS	current
	DESCRIPTION
		"The OID for the SNMP request."
	::= { ispEntry 5 }

ispConfStatus OBJECT-TYPE
	SYNTAX	INTEGER {
			doOnce(1),
			doEveryIlmiRestart(2)
		}
	MAX-ACCESS	read-write
	STATUS	current
	DESCRIPTION
		"When to perform the SNMP request."
	::= { ispEntry 6 }

ispOperStatus OBJECT-TYPE
	SYNTAX	INTEGER {
			idle(1),
                       	inProgress(2),
			success(3),
			failure(4)
		}
	MAX-ACCESS	read-only
	STATUS	current
	DESCRIPTION
		"The state of the request at the current time.  Idle
                denotes that the request has not been made.  InProgress
                denotes that the request is currently being made.  
                Success denotes that the last request was successful
                and ispRespOID and ispValue are valid.  Failure denotes
                that the last request was not successful."
	::= { ispEntry 7 }

ispCommunityName OBJECT-TYPE
	SYNTAX	DisplayString
	MAX-ACCESS	read-write
	STATUS	current
	DESCRIPTION
		"The community string for the SNMP request."
	::= { ispEntry 8 }	

ispRespOID OBJECT-TYPE
	SYNTAX	OBJECT IDENTIFIER
	MAX-ACCESS 	read-only
	STATUS	current
	DESCRIPTION
		"The OID in the response packet of the SNMP request.
		This is only valid if ispOperStatus has a value of
                success."
	::= { ispEntry 9 }

ispValue OBJECT-TYPE
	SYNTAX	OCTET STRING
	MAX-ACCESS	read-only
	STATUS	current
	DESCRIPTION
		"The value returned by a get, or getnext. This is
                encoded in ASCII format and is only valid if
                ispOperStatus has a value of success."
	::= { ispEntry 10 }

ispRowStatus OBJECT-TYPE
	SYNTAX	RowStatus
	MAX-ACCESS	read-write
	STATUS	current
	DESCRIPTION
		"The status of this entry."
	::= { ispEntry 11 }

ispNextIndex OBJECT-TYPE
	SYNTAX Integer32 
	MAX-ACCESS  read-write
	STATUS  current
	DESCRIPTION 
		"The next free ispIndex in the ispTable."
	::= { ispTable 2 }
--------------------------------------------------------------------
END
