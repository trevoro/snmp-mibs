--
-- Based on Frame Relay Specifications Rev. 0.0 Dated: 5-3-96
-- Default values missing
-- MIB Revision Dated: 6-5-96
-- Updated on 07/01/96 by Krishna Durairaj
-- 
-- MIB Revision : 1.0 dated 1-17-97
-- Change Desc. : None. 
-- 
-- 
-- MIB Revision : 1.1 dated 3-13-97
-- Change Desc. : enumeration changed for DlcmiState. - A.Llanes. 
-- 
-- MIB Revision : 1.2 dated 3-20-97
-- Change Desc. : Specified ranges for different objects. 
-- 
-- 
-- MIB Revision : 1.3 dated 3-26-97
-- Change Desc. : The timer descriptions have been updated 
-- 		  from 100ms to 1 second units. 
-- 
-- MIB Revision : 1.4 dated 3-31-97
-- Change Desc. : Additional ranges specified for different objects. 
-- 
-- 
-- MIB Revision : 1.5 dated 4-23-97
-- Change Desc. : Changed access field of nvmFrDlcmiMonitoredEvents
--		  to read-only.
-- 
--
-- *** 4400 RELEASE 1.1 ***
-- MIB Revision : 1.6 dated 4-30-97
-- Change Desc. : Added access privileges to capabilities field - S.Gaur. 
-- Added FR DCE related changes as per FR DCE/HTDS MIB Req't Document
-- (dated 4/20/97) - R. Carmona.
--
-- 
-- MIB Revision : 1.7 dated 5-12-97
-- Change Desc. : Correction to restore 4400 release 1.0 OIDs - R. Carmona
-- 
-- 
-- MIB Revision : 1.8 dated 6-18-97
-- Change Desc. : FR DCE related All/SVC circuit additions  - B. Jafari
-- 
--
-- MIB Revision : 1.9 dated 7-8-97
-- Change Desc. : Range changes for committed/excess burst objects  - B. Jafari
-- 
--
-- MIB Revision : 1.10 dated 7-23-97
-- Change Desc. : Introduction of nvmFrSVCMapRowStatus object in the 
--		  nvmFrSVCMapTable  - B. Jafari
--
--
-- MIB Revision : 1.11 dated 8-15-97
-- Change Desc. : Range changes for various objects  - B. Jafari
-- 
-- MIB Revision : 1.12 dated 9-16-97
-- Change Desc  : Renamed nodes to unique names in order to comply 
--                with Nortel CSU tool - S. Gaur
--
-- MIB Revision : 1.13 dated 10-8-97
-- Change Desc. : Replaced MPA with 4400 - B. Jafari. 
-- 
--
-- MIB Revision : 1.14 dated 10-27-97
-- Change Desc. : Added tables (mcm/nvm)FrLANSpvcTable, (mcm/nvm)FrLanSpvcSVCTable.
--                Also obsoleted :
--                 mcmFrVirtualPortPhyPortIfIndex. nvmFrVirtualPortPhyPortIfIndex
--                Deprecated (replaced by other object, see descriptions) :
--                 mcmFrSVCCircuitCommittedBurst,    mcmFrSVCCircuitExcessBurst and
--                 mcmFrAllSVCCircuitCommittedBurst, mcmFrAllSVCCircuitExcessBurst
--                As per Melanies request stated in Frcmd3.doc.           -  S. Gaur
-- 
--
-- MIB Revision : 1.15 dated 10-28-97
-- Change Desc. : Introduced (mcm/nvm)FrDNANumberingPlan in both mcm and nvm 
--                Global Groups.                                          -  S. Gaur 
--  
--
-- MIB Revision : 1.16 dated 10-30-97
-- Change Desc. : Added the mcmFrSVCCircuitSvcIfIndex object. Part of the original 
--                requirement(rev 1.14 dated 10-27-97 above)              -  S. Gaur
-- 
-- MIB Revision : 1.17 dated 11-25-97
-- Change Desc. : Added new type to the mcmFrAllSVCCircuitType object. - B. Jafari
--
-- 
-- MIB Revision : 1.18 dated 12-12-97
-- Change Desc. : Introduced (nvm/mcm)FrSVCMapDiscardPriority, mcmFrSVCCircuitDiscardPriority,
--                mcmFrAllSVCCircuitDiscardPriority, and (nvm/mcm)FrLanSpvcSVCDiscardPriority.
--                Allows the user to set the discard priority for voice and data.
-- 
-- MIB Revision : 1.19 dated 3-23-98
-- Change Desc. : Expanded the enumerations for FrSVCMapDisableCause and
--                FrLANSpvcSVCReasonForDisconnect                       -S. Gaur
--
-- *** RELEASE 3.0 ***
-- MIB Revision : 1.20 dated 6-26-98
-- Change Desc. : Changes based on 3.0 mcmfr.mib Requirements Spec, Rev 6.0,
--		   dated 6/1/98.
--		Obsoleted Counter Reset tables mcmFrPhyPortCntrTable,
--		   mcmFrVirtualPortCntrTable, mcmFrPVCCntrTable, mcmFrSVCCntrTable,
--		   and Counter Reset object mcmFrGlobalGroupCntrAction.
--		Replaced use of '4400' with 'access device'.
--		Added new table mcmFrDlcmiSvcStatusTable.
--		Revisions to tables mcmFrPhyPortTable, nvmFrPhyPortTable:
--		   Obsoleted object mcmFrPhyPortSVCLMIStatus (mcm table only);
--		   Added 11 new statistical Counter objects (mcm table only);
--		   Added DEFVAL statements to 3 existing objects - FlowControl,
--		      ConsecutiveFrames, PortDelta (nvm table only);
--		   Revised INTEGER range of existing object PortDelta (nvm table only);
--		   Deprecated objects mcm(nvm)FrPhyPortThroughput and replaced
--		      with TxThroughput, RxThroughput;
--		   Deprecated objects mcm(nvm)FrPhyPortMtuSize and replaced
--		      with TxMaxFrameSize, RxMaxFrameSize;
--		   Added 5 new objects RateEnf, TxBc, RxBc, TxBe, RxBe (mcm & nvm).
--		Added new tables mcmFrTunnelPvcTable, nvmFrTunnelPvcTable.
--		Revisions to FR Global groups mcmFRGlobalGroup, nvmFRGlobalGroup:
--		   Added 3 new Counter objects (mcm group only);
--		   Added 4 new Trap enable/disable objects (both mcm & nvm groups).
--		Revisions to tables mcmFrLANSpvcSVCTable, nvmFrLANSpvcSVCTable:
--		   Added 2 new objects SetupPriority, HoldingPriority (both mcm & nvm).
--		Revisions to tables mcmFrSVCMapTable, nvmFrSVCMapTable:
--		   Added 2 new objects SetupPriority, HoldingPriority (both mcm & nvm).
--		Revisions to table mcmFrSVCCircuitTable:
--		   Added 2 new objects SetupPriority, HoldingPriority.
--		Revisions to table mcmFrAllSVCCircuitTable:
--		   Added 2 new objects SetupPriority, HoldingPriority.
--		Revised the DESCRIPTION of the following 5 ifIndex objects:
--		   mcmFrLANSpvcIfIndex, mcmFrLANSpvcSVCIfIndex,
--		   mcmFrAllSVCCircuitSVCIfIndex, mcmFrSVCMapSVCIfIndex,
--		   mcmFrSVCCircuitSVCIfindex.
--		Added DEFVAL statements to 18 objects in nvmFrSVCPhyTable.
--		- R. Carmona
--
-- MIB Revision : 1.21 dated 7-2-98
-- Change Desc. : Revised INDEX object definitions in FR Tunnel PVC tables (mcm/nvm);
--		  Revised enumerations for object PVC Type...as per requirements
--		  from P. Lupo dated 7/2/98.  - R. Carmona
--
-- MIB Revision : 1.22 dated 7-7-98
-- Change Desc. : Revised mcmFrDlcmiSVCStatusTable to declare object
--		     mcmFrDlcmiSVCStatusDlci as a table index;
--		     ...as per e-mail from M. Kim dated 7/3/98. 
--		  In the table mcmFrPhyPortTable, deprecated the two objects
--		     mcmFrPhyPortRx(Tx)DataFrames and replaced them with 
--		     the single object mcmFrPhyPortDataFrames;
--		     ...as per e-mail from M. Kim dated 7/6/98.
--		  - R. Carmona
--
-- MIB Revision : 1.23 dated 7-8-98
-- Change Desc. : Changes resulting from discussions with Bernd, Klaus, and
--		     Moon on 7/8/98.
--		  Obsoleted tables mcmFrPVCMapTable, nvmFrPVCMapTable.
--		  Added new tables mcmFrNetlinkMapTable, nvmFrNetlinkMapTable.
--		  Revisions to tables mcm(nvm)FrVirtualPortTable:
--		     Obsoleted objects mcm(nvm)FrVirtualPortPPA;
--		     Added objects mcm(nvm)FrVirtualPortNumber.
--		  - R. Carmona
--
-- MIB Revision : 1.24 dated 8-7-98
-- Change Desc. : Increased the range to 1 to 34 for mcmFrSVCCircuitDNA,
--                mcmFrSVCCircuitCallOriginator, mcmFrAllSVCCircuitDNA,
--                mcmFrAllSVCCircuitCallOriginator, (mcm/nvm)FrLANSpvcRemoteDNA,
--                (mcm/nvm)FrLANSpvcSVCDNA, and nvmFrSVCMapDNA objects.
--                                                         -S. Gaur 
-- MIB Revision : 1.25 dated 10-6-98
-- Change Desc. : Renamed the following objects: (mcm/nvm)FrTunnelPvcRxCIR and 
--                (mcm/nvm)FrTunnelPvcTxCIR to: (mcm/nvm)FrTunnelPvcMaxRxCIR
--                (mcm/nvm)FrTunnelPvcMaxTxCIR.
--                Added new objects:(mcm/nvm)FrTunnelPvcConsecFrames, 
--                (mcm/nvm)FrTunnelPvcMinTxCIR, (mcm/nvm)FrTunnelPvcMinRxCIR, and to 
--                the (mcm/nvm)FrTunnelPvcTable to support FECN and BECN functionality.
--
-- MIB Revision : 1.26 dated 11-03-98
-- Change Desc. : Add Severity Levels to Traps
-- 					-F. Kottab
--				  Removed mcm(nvm)FrTunnelPvcMinRxCIR object from mcm(nvm)FrTunnelPVCTable.
--				    -S. Gaur
--
-- MIB Revision : 1.27 dated 1-15-99
-- Change Desc. : Added 2 enumerations to mcmFrVirtualPortProtocolBinding and 
--		  nvmFrVirtualPortProtocolBinding to support SNA and X.25.
--							-K. Chan
 
MICOM-FRAMERELAY-MIB DEFINITIONS ::= BEGIN
	IMPORTS
	TRAP-TYPE FROM RFC-1215
		Counter 
                   		 	FROM RFC1155-SMI
		OBJECT-TYPE
                    			FROM RFC-1212
             	TimeTicks
                     			FROM RFC1155-SMI
	    	micom-oscar 
		    			FROM MICOM-OSCAR-MIB
                mcmSysAsciiTimeOfDay, mcmSysIfExtModule, mcmSysIfExtPPA
					FROM MICOM-SYS-MIB
		DisplayString 
					FROM SNMPv2-TC;

     --
     --      the range of ifIndex
     --
     Index ::= INTEGER       -- 1..ifNumber

-- group OBJECT IDENTIFIERs

        micom-frame-relay	                OBJECT IDENTIFIER ::= {micom-oscar 7 }
	fr-configuration			OBJECT IDENTIFIER ::= {micom-frame-relay 1}
	fr-control				OBJECT IDENTIFIER ::= {micom-frame-relay 2}


-- Global Group

mcmFrGlobalGroup    OBJECT IDENTIFIER ::= {fr-configuration 1}

mcmFrMaxDLCI OBJECT-TYPE
	SYNTAX	INTEGER
	ACCESS	read-only
	STATUS	mandatory
	DESCRIPTION
	  "NAME = ;
	   DESC = The maximum number of DLCIs that \
		  may be configured for the entire \
		  box;
	   HELP = ;
	   CAPABILITIES = NET_CFG, VPN_DISP;"
	::= {mcmFrGlobalGroup 1}

mcmFrMaxVirtualPorts OBJECT-TYPE
	SYNTAX	INTEGER (1..32)
	ACCESS	read-only
	STATUS	mandatory
	DESCRIPTION
	  "NAME = ;
	   DESC = The maximum number of Virtual Ports that \
		  may be configured for the entire \
		  box;
	   HELP = ;
	   CAPABILITIES = NET_CFG, VPN_DISP;"
	::= {mcmFrGlobalGroup 2}

mcmFrMaxDlciPerLine OBJECT-TYPE
	SYNTAX	INTEGER (1..255)
	ACCESS	read-only
	STATUS	mandatory
	DESCRIPTION
	  "NAME = ;
	   DESC = The maximum number of DLCIs that may \
		  be configured for a Frame Relay line;
	   HELP = ;
	   CAPABILITIES = NET_CFG, VPN_DISP;"
	::= {mcmFrGlobalGroup 3}

mcmFrConnectTime OBJECT-TYPE
        SYNTAX   TimeTicks
	ACCESS	read-only
	STATUS	mandatory
	DESCRIPTION
	  "NAME = ;
	   DESC = The sysUpTime when the FR Driver was \
		  initialized;
	   HELP = ;
	   CAPABILITIES = NET_CFG, VPN_DISP;"
	::= {mcmFrGlobalGroup 4}

mcmFrOctetsSent OBJECT-TYPE
	SYNTAX	Counter
	ACCESS	read-only
	STATUS	mandatory
	DESCRIPTION
	  "NAME = ;
	   DESC = Total number of Frame Relay Information \
		  field octets that were sent out all FR \
		  ports;
	   HELP = ;
	   CAPABILITIES = NET_CFG, VPN_DISP;"
	::= {mcmFrGlobalGroup 5}

mcmFrOctetsReceived OBJECT-TYPE
	SYNTAX	Counter
	ACCESS	read-only
	STATUS	mandatory
	DESCRIPTION
	  "NAME = ;
	   DESC = Total number of Frame Relay Information \
		  Field octets that were received across all \
		  FR ports;
	   HELP = ;
	   CAPABILITIES = NET_CFG, VPN_DISP;"
	::= {mcmFrGlobalGroup 6}

mcmFrFramesSent OBJECT-TYPE
	SYNTAX	Counter
	ACCESS	read-only
	STATUS	mandatory
	DESCRIPTION
	  "NAME = ;
	   DESC = Total number of Frame Relay Frames \
		  sent out all FR ports;
	   HELP = ;
	   CAPABILITIES = NET_CFG, VPN_DISP;"
	::= {mcmFrGlobalGroup 7}

mcmFrFramesReceived OBJECT-TYPE
	SYNTAX	Counter
	ACCESS	read-only
	STATUS	mandatory
	DESCRIPTION
	  "NAME = ;
	   DESC = Total number of Frame Relay Frames \
		  received in on all FR ports;
	   HELP = 
	   CAPABILITIES = NET_CFG, VPN_DISP;"
	::= {mcmFrGlobalGroup 8}

mcmFrGlobalGroupCntrAction OBJECT-TYPE
	SYNTAX	INTEGER {
		reset (1),
		other (2)
	}
	ACCESS	write-only
	STATUS	obsolete
	DESCRIPTION
	  "NAME = ;
	   DESC = This object has been OBSOLETED for  software \
		  releases beginning with Release 3.0. \
		  Setting this object to reset will reset \
		  counters in this group;
	   HELP = All objects will be reset in this group \
		  except mcmFrMaxDLCI, mcmFrMaxVirtualPorts, \
		  mcmFrMaxDlciPerLine and mcmFrConnectTime \
		  which are not counters;
	   CAPABILITIES = NET_CFG, VPN_CFG;"
	::= {mcmFrGlobalGroup 9}

mcmFrDNANumberingPlan OBJECT-TYPE
	SYNTAX	INTEGER {
                e164 (1),
                x121 (3)
                }
	ACCESS	read-only
	STATUS	mandatory
	DESCRIPTION
	  "NAME = ;
	   DESC = The value of this object designates the \
                  numbering plan of the DNA; 
	   HELP = The number plan is used in conjunction \
                  with a DNA.  This object identifies the \
                  type of call as E.164 or X.121 ;
	   CAPABILITIES = NET_CFG, VPN_DISP;"
	::= {mcmFrGlobalGroup 10}

mcmFrActivePanlDlciSVCs OBJECT-TYPE
	SYNTAX	Counter
	ACCESS	read-only
	STATUS	mandatory
	DESCRIPTION
	  "NAME = ;
	   DESC = The number of active PANL DLCI SVCs \
		  for all FR ports.; 
	   HELP = ;
	   CAPABILITIES = NET_CFG, VPN_DISP;"
	::= {mcmFrGlobalGroup 11}

mcmFrTotalTunnelingPVCs OBJECT-TYPE
	SYNTAX	Counter
	ACCESS	read-only
	STATUS	mandatory
	DESCRIPTION
	  "NAME = ;
	   DESC = The total number of tunneling PVCs configured.; 
	   HELP = ;
	   CAPABILITIES = NET_CFG, VPN_DISP;"
	::= {mcmFrGlobalGroup 12}

mcmFrActiveTunnelingPVCs OBJECT-TYPE
	SYNTAX	Counter
	ACCESS	read-only
	STATUS	mandatory
	DESCRIPTION
	  "NAME = ;
	   DESC = The number of active tunneling PVCs configured.; 
	   HELP = ;
	   CAPABILITIES = NET_CFG, VPN_DISP;"
	::= {mcmFrGlobalGroup 13}

mcmFrPanlLmiTrapEnable OBJECT-TYPE
	SYNTAX	INTEGER {
		enabled (1),
		disabled (2)
		}
	ACCESS	read-only
	STATUS	mandatory
	DESCRIPTION
	  "NAME = ;
	   DESC = This object indicates whether the generation of \
		  Trap messages are enabled/disabled for the FR \
		  PANL LMI module.; 
	   HELP = ;
	   CAPABILITIES = NET_CFG, VPN_DISP;"
	DEFVAL { disabled }
	::= {mcmFrGlobalGroup 14}

mcmFrMsmTrapEnable OBJECT-TYPE
	SYNTAX	INTEGER {
		enabled (1),
		disabled (2)
		}
	ACCESS	read-only
	STATUS	mandatory
	DESCRIPTION
	  "NAME = ;
	   DESC = This object indicates whether the generation of \
		  Trap messages are enabled/disabled for the FR \
		  MSM module.; 
	   HELP = ;
	   CAPABILITIES = NET_CFG, VPN_DISP;"
	DEFVAL { disabled }
	::= {mcmFrGlobalGroup 15}

mcmFrCoreTrapEnable OBJECT-TYPE
	SYNTAX	INTEGER {
		enabled (1),
		disabled (2)
		}
	ACCESS	read-only
	STATUS	mandatory
	DESCRIPTION
	  "NAME = ;
	   DESC = This object indicates whether the generation of \
		  Trap messages are enabled/disabled for the FR \
		  Core module.; 
	   HELP = ;
	   CAPABILITIES = NET_CFG, VPN_DISP;"
	DEFVAL { disabled }
	::= {mcmFrGlobalGroup 16}

mcmFrPlmTrapEnable OBJECT-TYPE
	SYNTAX	INTEGER {
		enabled (1),
		disabled (2)
		}
	ACCESS	read-only
	STATUS	mandatory
	DESCRIPTION
	  "NAME = ;
	   DESC = This object indicates whether the generation of \
		  Trap messages are enabled/disabled for the FR \
		  Plm module.; 
	   HELP = ;
	   CAPABILITIES = NET_CFG, VPN_DISP;"
	DEFVAL { disabled }
	::= {mcmFrGlobalGroup 17}



-- Frame Relay Physical Port Group

mcmFrPhyPortTable OBJECT-TYPE
	SYNTAX	SEQUENCE OF McmFrPhyPortEntry
	ACCESS	not-accessible
	STATUS	mandatory
	DESCRIPTION
	  "NAME = ;
	   DESC = Table of physical port entries \
		  containing flow control info \
		  and statistics;
	   HELP = ;
	   CAPABILITIES = NET_CFG, VPN_DISP;"
	::= {fr-configuration 2}

mcmFrPhyPortEntry OBJECT-TYPE
	SYNTAX	McmFrPhyPortEntry
	ACCESS	not-accessible
	STATUS	mandatory
	DESCRIPTION
	  "NAME = ;
	   DESC = Entry for a Frame Relay physical \
		  port;
           HELP = Entry for a Frame Relay physical \
		  port, containing flow control \
		  information and statistics NOT \
		  included in the RFC 1315 mib;
	   CAPABILITIES = ;"
	INDEX	{ mcmFrPhyPortExtIfIndex }
	::= {mcmFrPhyPortTable 1}

McmFrPhyPortEntry ::= SEQUENCE {
		mcmFrPhyPortExtIfIndex		INTEGER,
		mcmFrPhyPortFlowControl		INTEGER,
		mcmFrPhyPortThroughput		INTEGER,
		mcmFrPhyPortDelta    		INTEGER,
		mcmFrPhyPortConsectiveFrames	INTEGER,
		mcmFrPhyPortMtuSize		INTEGER,
		mcmFrPhyPortConnectTime		TimeTicks,
		mcmFrPhyPortLMISent		Counter,
		mcmFrPhyPortLMIReceived		Counter,
		mcmFrPhyPortXIDSent		Counter,
		mcmFrPhyPortXIDReceived		Counter,
		mcmFrPhyPortCLLMSent		Counter,
		mcmFrPhyPortCLLMReceived	Counter,
		mcmFrPhyPortHeaderErrors   	Counter,
		mcmFrPhyPortInvalidDLCI		Counter,
		mcmFrPhyPortShortFrames		Counter,
		mcmFrPhyPortLongFrames		Counter,
		mcmFrPhyPortIgnoredFrames	Counter,
		mcmFrPhyPortXIDExpirations	Counter,
		mcmFrPhyPortTxExpirations  	Counter,
		mcmFrPhyPortPVCLMIStatus	INTEGER,
		mcmFrPhyPortSVCLMIStatus	INTEGER,
		mcmFrPhyPortActivePanlDlciSVCs	Counter,
		mcmFrPhyPortRxDataFrames 	Counter,
		mcmFrPhyPortTxDataFrames 	Counter,
		mcmFrPhyPortRxActivations  	Counter,
		mcmFrPhyPortRxDeactivations	Counter,
		mcmFrPhyPortRxOkAcks		Counter,
		mcmFrPhyPortRxErrAcks		Counter,
		mcmFrPhyPortRxUnknowns  	Counter,
		mcmFrPhyPortRxErrors		Counter,
		mcmFrPhyPortRxOctets		Counter,
		mcmFrPhyPortTxOctets		Counter,
		mcmFrPhyPortTxThroughput 	INTEGER,
		mcmFrPhyPortRxThroughput 	INTEGER,
		mcmFrPhyPortTxMaxFrameSize	INTEGER,
		mcmFrPhyPortRxMaxFrameSize	INTEGER,
		mcmFrPhyPortRateEnf		INTEGER,
		mcmFrPhyPortTxBc   		INTEGER,
		mcmFrPhyPortRxBc   		INTEGER,
		mcmFrPhyPortTxBe   		INTEGER,
		mcmFrPhyPortRxBe   		INTEGER,
		mcmFrPhyPortDataFrames		Counter
		}

mcmFrPhyPortExtIfIndex OBJECT-TYPE
	SYNTAX	INTEGER
	ACCESS	read-only
	STATUS	mandatory
	DESCRIPTION
	  "NAME = ;
	   DESC = The ifIndex of the physical port;
	   HELP = ;
	   CAPABILITIES = ;"
	::= { mcmFrPhyPortEntry 1}

mcmFrPhyPortFlowControl OBJECT-TYPE
	SYNTAX	INTEGER {
		enabled (1),
		disabled (2)
		}
	ACCESS	read-only
	STATUS	mandatory
	DESCRIPTION
	  "NAME = ;
	   DESC = Determines whether or not rate enforcement \
		  based on congestion should be enforced;
	   HELP = Enabling this feature will allow packets \
		  exceeding the current allowable rate \ 
		  to be dropped if congestion has been \
		  detected on the network.;
	   CAPABILITIES = ;"
	::= { mcmFrPhyPortEntry 2}

mcmFrPhyPortThroughput OBJECT-TYPE
	SYNTAX	INTEGER
	ACCESS	read-only
	STATUS	deprecated
	DESCRIPTION
	  "NAME = Frame Relay DLCI Throughput;
	   DESC = This object has been DEPRECATED for  software \
		  releases beginning with Release 3.0, and replaced with \
		  new objects TxThroughput, RxThroughput. \
		  Default throughput for a PVC;
	   HELP = Defalut throughput used for all \
		  PVCs on the same frame relay \
		  physical interface.  Will be \
		  assigned to a PVC when the PVC \
		  is created. valid if flow cntl \
                  is enabled. ;
	   CAPABILITIES = ;"
	::= { mcmFrPhyPortEntry 3}

mcmFrPhyPortDelta OBJECT-TYPE
	SYNTAX	INTEGER
	ACCESS	read-only
	STATUS	mandatory
	DESCRIPTION
	  "NAME = Frame Relay Delta;
	   DESC = Delta time interval to increase or \
		  decrease the transmit rate by monitoring \
		  the number of frames rcvd or txd with the \
		  FECN bit cleared or set;
	   HELP = Default used for adding PVCs. The \
		  delta time interval to increase or \
		  decrease the current transmit rate \
		  based on then number of frames \
		  received with the FECN bit cleared \
		  or set. Typically 4 types end-to-end \
		  transit delay. Used only if flow \
		  control is enabled.  (In 1 second \
		  units.).  Valid if flow cntl is enabled;
	   CAPABILITIES = ;"
	::= { mcmFrPhyPortEntry 4}

mcmFrPhyPortConsectiveFrames OBJECT-TYPE
	SYNTAX	INTEGER
	ACCESS	read-only
	STATUS	mandatory
	DESCRIPTION
	  "NAME = ;
	   DESC = Number of consecutive frames received \
		  with the BECN bit set before reducing \
		  the transmit rate;
	   HELP = Number of consecutive frames that must \
		  have BECN bit set before reducing \
		  transmit rate. Transmit rate is \
		  increased when S/2 consecutive frames \
		  are received with teh BECN bit cleared. \
		  Valid only when flow control is enabled.\
		  See CCITT Q.922 Appendix I, for the \
		  method to compute parameter S.\
                  Valid if flow cntl is enabled;
	   CAPABILITIES = ;"
	::= { mcmFrPhyPortEntry 5}

mcmFrPhyPortMtuSize OBJECT-TYPE
	SYNTAX	INTEGER
	ACCESS	read-only
	STATUS	deprecated
	DESCRIPTION
	  "NAME = ;
	   DESC = This object has been DEPRECATED for  software \
		  releases beginning with Release 3.0, and replaced with \
		  new objects TxMaxFrameSize, RxMaxFrameSize. \
		  Maximum Transmission Unit Size;
	   HELP = Maximum Packet size that can be \
		  passed to Frame Relay and will \
		  be sent across the Frame Relay \
		  network.;
	   CAPABILITIES = ;"
	::= { mcmFrPhyPortEntry 6}

mcmFrPhyPortConnectTime OBJECT-TYPE
	SYNTAX   TimeTicks
	ACCESS	read-only
	STATUS	mandatory
	DESCRIPTION
	  "NAME = ;
	   DESC = sysUpTime when the port was created;
	   HELP = ;
	   CAPABILITIES = ;"
	::= { mcmFrPhyPortEntry 7}

mcmFrPhyPortLMISent OBJECT-TYPE
	SYNTAX	Counter
	ACCESS	read-only
	STATUS	mandatory
	DESCRIPTION
	  "NAME = ;
	   DESC = Number of PVC LMI frames sent on \
		  physical port (DLCI 0);
	   HELP = ;
	   CAPABILITIES = ;"
	::= { mcmFrPhyPortEntry 8}

mcmFrPhyPortLMIReceived OBJECT-TYPE
	SYNTAX	Counter
	ACCESS	read-only
	STATUS	mandatory
	DESCRIPTION
	  "NAME = ;
	   DESC = Number of PVC LMI frames received \
		  on this port (DLCI 0);
	   HELP = ;
	   CAPABILITIES = ;"
	::= { mcmFrPhyPortEntry 9}

mcmFrPhyPortXIDSent OBJECT-TYPE
	SYNTAX	Counter
	ACCESS	read-only
	STATUS	mandatory
	DESCRIPTION
	  "NAME = ;
	   DESC = Number of XID frames sent on \
		  this interface;
	   HELP = Valid only if packet negotiation is enabled. \
		  Network must support XID frames;
	   CAPABILITIES = ;"
	::= { mcmFrPhyPortEntry 10}

mcmFrPhyPortXIDReceived OBJECT-TYPE
	SYNTAX	Counter
	ACCESS	read-only
	STATUS	mandatory
	DESCRIPTION
	  "NAME = ;
	   DESC = Number of XID frames received on \
		  this interface;
	   HELP = Valid only if packet negotiation is enabled. \
		  Network must support XID frames;
	   CAPABILITIES = ;"
	::= { mcmFrPhyPortEntry 11}

mcmFrPhyPortCLLMSent OBJECT-TYPE
	SYNTAX	Counter
	ACCESS	read-only
	STATUS	mandatory
	DESCRIPTION
	  "NAME = ;
	   DESC = Number of CLLM frames sent on \
		  this interface;
	   HELP = Network must support CLLM before \
		  this feature is enabled;
	   CAPABILITIES = ;"
	::= { mcmFrPhyPortEntry 12}

mcmFrPhyPortCLLMReceived OBJECT-TYPE
	SYNTAX	Counter
	ACCESS	read-only
	STATUS	mandatory
	DESCRIPTION
	  "NAME = ;
	   DESC = Number of CLLM frames received on \
		  this interface;
	   HELP = Network must support CLLM before \
		  this feature is enabled;
	   CAPABILITIES = ;"
	::= { mcmFrPhyPortEntry 13}

mcmFrPhyPortHeaderErrors OBJECT-TYPE
	SYNTAX	Counter
	ACCESS	read-only
	STATUS	mandatory
	DESCRIPTION
	  "NAME = ;
	   DESC = Number of frames received with \
		  incomplete or missing address \
		  field;
	   HELP = ;
	   CAPABILITIES = ;"
	::= { mcmFrPhyPortEntry 14}

mcmFrPhyPortInvalidDLCI OBJECT-TYPE
	SYNTAX	Counter
	ACCESS	read-only
	STATUS	mandatory
	DESCRIPTION
	  "NAME = ;
	   DESC = Number of frames on an unassigned \
		  or invalid number;
	   HELP = ;
	   CAPABILITIES = ;"
	::= { mcmFrPhyPortEntry 15}

mcmFrPhyPortShortFrames OBJECT-TYPE
	SYNTAX	Counter
	ACCESS	read-only
	STATUS	mandatory
	DESCRIPTION
	  "NAME = ;
	   DESC = Number of short frames received;
	   HELP = ;
	   CAPABILITIES = ;"
	::= { mcmFrPhyPortEntry 16}

mcmFrPhyPortLongFrames OBJECT-TYPE
	SYNTAX	Counter
	ACCESS	read-only
	STATUS	mandatory
	DESCRIPTION
	  "NAME = ;
	   DESC = Number of long frames received that \
		  were too long (larger than MTU);
	   HELP = ;
	   CAPABILITIES = ;"
	::= { mcmFrPhyPortEntry 17}

mcmFrPhyPortIgnoredFrames OBJECT-TYPE
	SYNTAX	Counter
	ACCESS	read-only
	STATUS	mandatory
	DESCRIPTION
	  "NAME = ;
	   DESC = Number of frames received that were \
		  ignored (no errors);
	   HELP = ;
	   CAPABILITIES = ;"
	::= { mcmFrPhyPortEntry 18}

mcmFrPhyPortXIDExpirations OBJECT-TYPE
	SYNTAX	Counter
	ACCESS	read-only
	STATUS	mandatory
	DESCRIPTION
	  "NAME = ;
	   DESC = Number of XID TM21 timer expirations;
	   HELP = Valid only if MTU negotiation is \
		  enabled;
	   CAPABILITIES = ;"
	::= { mcmFrPhyPortEntry 19}

mcmFrPhyPortTxExpirations OBJECT-TYPE
	SYNTAX	Counter
	ACCESS	read-only
	STATUS	mandatory
	DESCRIPTION
	  "NAME = ;
	   DESC = Number of flow control (CLLM) timer \
		  expirations;
	   HELP = Valid only if flow control negotiation is configured;
	   CAPABILITIES = ;"
	::= { mcmFrPhyPortEntry 20}

mcmFrPhyPortPVCLMIStatus OBJECT-TYPE
	SYNTAX	INTEGER {
		up (1),
		down (2)
		}
	ACCESS	read-only
	STATUS	mandatory
	DESCRIPTION
	  "NAME = ;
	   DESC = The status of the PVC LMI (up or down). ;
	   HELP = ;
	   CAPABILITIES = ;"
	::= { mcmFrPhyPortEntry 21}

mcmFrPhyPortSVCLMIStatus OBJECT-TYPE
	SYNTAX	INTEGER {
		up (1),
		down (2)
		}
	ACCESS	read-only
	STATUS	obsolete
	DESCRIPTION
	  "NAME = ;
	   DESC = This object has been OBSOLETED for  software \
		  releases beginning with Release 3.0. \
		  The status of the SVC LMI (up or down). ;
	   HELP = ;
	   CAPABILITIES = ;"
	::= { mcmFrPhyPortEntry 22}

mcmFrPhyPortActivePanlDlciSVCs OBJECT-TYPE
	SYNTAX	Counter
	ACCESS	read-only
	STATUS	mandatory
	DESCRIPTION
	  "NAME = ;
	   DESC = Number of active PANL DLCI SVCs on \
		  this interface.;
	   HELP =;
	   CAPABILITIES = ;"
	::= { mcmFrPhyPortEntry 23}

mcmFrPhyPortRxDataFrames OBJECT-TYPE
	SYNTAX	Counter
	ACCESS	read-only
	STATUS	deprecated
	DESCRIPTION
	  "NAME = ;
	   DESC = This object has been DEPRECATED for software \
		  releases beginning with Release 3.0, and replaced \
		  with the new object mcmFrPhyPortDataFrames. \
		  Number of data frames received on all assigned \
		  DLCIs.;
	   HELP =;
	   CAPABILITIES = ;"
	::= { mcmFrPhyPortEntry 24}

mcmFrPhyPortTxDataFrames OBJECT-TYPE
	SYNTAX	Counter
	ACCESS	read-only
	STATUS	deprecated
	DESCRIPTION
	  "NAME = ;
	   DESC = This object has been DEPRECATED for software \
		  releases beginning with Release 3.0, and replaced \
		  with the new object mcmFrPhyPortDataFrames. \
		  Number of data frames sent on all assigned \
		  DLCIs.;
	   HELP =;
	   CAPABILITIES = ;"
	::= { mcmFrPhyPortEntry 25}

mcmFrPhyPortRxActivations OBJECT-TYPE
	SYNTAX	Counter
	ACCESS	read-only
	STATUS	mandatory
	DESCRIPTION
	  "NAME = ;
	   DESC = Number of activations received on this interface.;
	   HELP =;
	   CAPABILITIES = ;"
	::= { mcmFrPhyPortEntry 26}

mcmFrPhyPortRxDeactivations OBJECT-TYPE
	SYNTAX	Counter
	ACCESS	read-only
	STATUS	mandatory
	DESCRIPTION
	  "NAME = ;
	   DESC = Number of deactivations received on this interface.;
	   HELP =;
	   CAPABILITIES = ;"
	::= { mcmFrPhyPortEntry 27}

mcmFrPhyPortRxOkAcks OBJECT-TYPE
	SYNTAX	Counter
	ACCESS	read-only
	STATUS	mandatory
	DESCRIPTION
	  "NAME = ;
	   DESC = Number of OK ACK messages received on this \
		  interface.;
	   HELP =;
	   CAPABILITIES = ;"
	::= { mcmFrPhyPortEntry 28}

mcmFrPhyPortRxErrAcks OBJECT-TYPE
	SYNTAX	Counter
	ACCESS	read-only
	STATUS	mandatory
	DESCRIPTION
	  "NAME = ;
	   DESC = Number of Error ACK messages received on this \
		  interface.;
	   HELP =;
	   CAPABILITIES = ;"
	::= { mcmFrPhyPortEntry 29}

mcmFrPhyPortRxUnknowns OBJECT-TYPE
	SYNTAX	Counter
	ACCESS	read-only
	STATUS	mandatory
	DESCRIPTION
	  "NAME = ;
	   DESC = Number of Unknown messages received on this \
		  interface.;
	   HELP =;
	   CAPABILITIES = ;"
	::= { mcmFrPhyPortEntry 30}

mcmFrPhyPortRxErrors OBJECT-TYPE
	SYNTAX	Counter
	ACCESS	read-only
	STATUS	mandatory
	DESCRIPTION
	  "NAME = ;
	   DESC = Number of Error messages received on this \
		  interface.;
	   HELP =;
	   CAPABILITIES = ;"
	::= { mcmFrPhyPortEntry 31}

mcmFrPhyPortRxOctets OBJECT-TYPE
	SYNTAX	Counter
	ACCESS	read-only
	STATUS	mandatory
	DESCRIPTION
	  "NAME = ;
	   DESC = Number of data bytes received.;
	   HELP =;
	   CAPABILITIES = ;"
	::= { mcmFrPhyPortEntry 32}

mcmFrPhyPortTxOctets OBJECT-TYPE
	SYNTAX	Counter
	ACCESS	read-only
	STATUS	mandatory
	DESCRIPTION
	  "NAME = ;
	   DESC = Number of data bytes sent.;
	   HELP =;
	   CAPABILITIES = ;"
	::= { mcmFrPhyPortEntry 33}

mcmFrPhyPortTxThroughput OBJECT-TYPE
	SYNTAX	INTEGER
	ACCESS	read-only
	STATUS	mandatory
	DESCRIPTION
	  "NAME = Frame Relay DLCI Tx Throughput;
	   DESC = The transmission CIR expressed in bits/sec.;
	   HELP = ;
	   CAPABILITIES = ;"
	::= { mcmFrPhyPortEntry 34}

mcmFrPhyPortRxThroughput OBJECT-TYPE
	SYNTAX	INTEGER
	ACCESS	read-only
	STATUS	mandatory
	DESCRIPTION
	  "NAME = Frame Relay DLCI Rx Throughput;
	   DESC = The receive CIR expressed in bits/sec.;
	   HELP = ;
	   CAPABILITIES = ;"
	::= { mcmFrPhyPortEntry 35}

mcmFrPhyPortTxMaxFrameSize OBJECT-TYPE
	SYNTAX	INTEGER
	ACCESS	read-only
	STATUS	mandatory
	DESCRIPTION
	  "NAME = ;
	   DESC = The maximum transmission FR packet size \
		  expressed in bytes.;
	   HELP = ;
	   CAPABILITIES = ;"
	::= { mcmFrPhyPortEntry 36}

mcmFrPhyPortRxMaxFrameSize OBJECT-TYPE
	SYNTAX	INTEGER
	ACCESS	read-only
	STATUS	mandatory
	DESCRIPTION
	  "NAME = ;
	   DESC = The maximum receive FR packet size \
		  expressed in bytes.;
	   HELP = ;
	   CAPABILITIES = ;"
	::= { mcmFrPhyPortEntry 37}

mcmFrPhyPortRateEnf OBJECT-TYPE
	SYNTAX	INTEGER {
		enabled (1),
		disabled (2)
		}
	ACCESS	read-only
	STATUS	mandatory
	DESCRIPTION
	  "NAME = ;
	   DESC = The rate enforcement enabled or disabled \
		  parameter for FR congestion management \
		  processing.;
	   HELP = ;
	   CAPABILITIES = ;"
	::= { mcmFrPhyPortEntry 38}

mcmFrPhyPortTxBc OBJECT-TYPE
	SYNTAX	INTEGER
	ACCESS	read-only
	STATUS	mandatory
	DESCRIPTION
	  "NAME = ;
	   DESC = The transmission committed burst size \
		  expressed in bits.;
	   HELP = ;
	   CAPABILITIES = ;"
	::= { mcmFrPhyPortEntry 39}

mcmFrPhyPortRxBc OBJECT-TYPE
	SYNTAX	INTEGER
	ACCESS	read-only
	STATUS	mandatory
	DESCRIPTION
	  "NAME = ;
	   DESC = The receive committed burst size \
		  expressed in bits.;
	   HELP = ;
	   CAPABILITIES = ;"
	::= { mcmFrPhyPortEntry 40}

mcmFrPhyPortTxBe OBJECT-TYPE
	SYNTAX	INTEGER
	ACCESS	read-only
	STATUS	mandatory
	DESCRIPTION
	  "NAME = ;
	   DESC = The transmission excess burst size \
		  expressed in bits.;
	   HELP = ;
	   CAPABILITIES = ;"
	::= { mcmFrPhyPortEntry 41}

mcmFrPhyPortRxBe OBJECT-TYPE
	SYNTAX	INTEGER
	ACCESS	read-only
	STATUS	mandatory
	DESCRIPTION
	  "NAME = ;
	   DESC = The receive excess burst size \
		  expressed in bits.;
	   HELP = ;
	   CAPABILITIES = ;"
	::= { mcmFrPhyPortEntry 42}

mcmFrPhyPortDataFrames OBJECT-TYPE
	SYNTAX	Counter
	ACCESS	read-only
	STATUS	mandatory
	DESCRIPTION
	  "NAME = ;
	   DESC = Total number of data frames on all assigned \
		  DLCIs.;
	   HELP =;
	   CAPABILITIES = ;"
	::= { mcmFrPhyPortEntry 43}



-- Frame Relay Physical Port PVC Parameters

mcmFrPVCPhyTable OBJECT-TYPE
	SYNTAX	SEQUENCE OF McmFrPVCPhyEntry
	ACCESS	not-accessible
	STATUS	mandatory
	DESCRIPTION
	  "NAME = ;
	   DESC = Table that extends the RFC 1315 \
		  DLCMI table contianing info \
		  about the PVC LMI;
	   HELP = ;
	   CAPABILITIES = NET_CFG, VPN_DISP;"
	::= {fr-configuration 3}

mcmFrPVCPhyEntry OBJECT-TYPE
	SYNTAX	McmFrPVCPhyEntry
	ACCESS	not-accessible
	STATUS	mandatory
	DESCRIPTION
	  "NAME = ;
	   DESC = Entry into the micom PVC LMI \
		  configuration extensions;
	   HELP = Entry in the PVC Phys Table. \
		  Additional information required \
		  (not in RFC 1315 DLCI table);
	   CAPABILITIES = ;"
	INDEX	{mcmFrPVCPhyIfIndex}
	::= {mcmFrPVCPhyTable 1}

McmFrPVCPhyEntry ::= SEQUENCE {
		mcmFrPVCPhyIfIndex	INTEGER,
		mcmFrPVCLMIMode		INTEGER,
		mcmFrPVCBiDir		INTEGER
		}

mcmFrPVCPhyIfIndex OBJECT-TYPE
	SYNTAX	INTEGER
	ACCESS	read-only
	STATUS	mandatory
	DESCRIPTION
	  "NAME = ;
	   DESC = IfIndex of the physical port;
	   HELP = ;
	   CAPABILITIES = ;"
	::= {mcmFrPVCPhyEntry 1}

mcmFrPVCLMIMode OBJECT-TYPE
	SYNTAX	INTEGER {
		dte (1),
		dce (2)
	}
	ACCESS	read-only
	STATUS	mandatory
	DESCRIPTION
	  "NAME = ;
	   DESC = Indicates whether the local PVC \
		  LMI is operating in the DTE or \
		  DCE mode;
	   HELP = In DTE mode the Status Enquiry messages \
		  will be sent.  In DCE mode, Status \
		  Reports will be sent in response \
		  to Status Enquiry mesages.;
	   CAPABILITIES = ;"
	::= {mcmFrPVCPhyEntry 2}

mcmFrPVCBiDir OBJECT-TYPE
	SYNTAX	INTEGER {
		true (1),
		false (2)
	}
	ACCESS	read-only
	STATUS	mandatory
	DESCRIPTION
	  "NAME = ;
	   DESC = Indicates whether the PVC LMI \
		  should perform both the sending \
		  of status enquiries and sending \
		  of status reports;
	   HELP = Must be with bilateral agreement \
		  with the switch enabled. Switch \
		  may send status enquiry messages \
		  as defined for the DTEs and allows\
		  the DTE to respond with a status \
		  messages in the same way as switch \
		  does (in this mode Status Enquiries \
		  will still be transmitted normally;
	   CAPABILITIES = ;"
	::= {mcmFrPVCPhyEntry 3}

-- Frame Relay Physical Port SVC Parameters

mcmFrSVCPhyTable OBJECT-TYPE
	SYNTAX	SEQUENCE OF McmFrSVCPhyEntry
	ACCESS	not-accessible
	STATUS	mandatory
	DESCRIPTION
	  "NAME = ;
	   DESC = Table containing the SVC default \
		  parameters ;
	   HELP = Table containing default SVC \
		  parameters to be used if none \
		  are specified when configuring \
		  an SVC;
	   CAPABILITIES = NET_CFG, VPN_DISP;"
	::= {fr-configuration 4}

mcmFrSVCPhyEntry OBJECT-TYPE
	SYNTAX	McmFrSVCPhyEntry
	ACCESS	not-accessible
	STATUS	mandatory
	DESCRIPTION
	  "NAME = ;
	   DESC = Entry into the SVC Default\
		  parameter table;
	   HELP = Each entry contains the default \
		  SVC parameters for the specified \
		  interface;
	   CAPABILITIES = ;"
	INDEX	{ mcmFrSVCPhyIfIndex }
	::= {mcmFrSVCPhyTable 1}

McmFrSVCPhyEntry ::= SEQUENCE {
		mcmFrSVCPhyIfIndex			INTEGER,
		mcmFrSVCState				INTEGER,
		mcmFrSVCT303				INTEGER,
		mcmFrSVCT305				INTEGER,
		mcmFrSVCT308				INTEGER,
		mcmFrSVCT310				INTEGER,
		mcmFrSVCMaxCalls			INTEGER,
		mcmFrSVCMaxTxSize			INTEGER,
		mcmFrSVCMaxRxSize			INTEGER,
		mcmFrSVCMinDLCI				INTEGER,
		mcmFrSVCMaxDLCI				INTEGER,
		mcmFrSVCMinTxThroughput			INTEGER,
		mcmFrSVCMinRxThroughput			INTEGER,
		mcmFrSVCMaxTxThroughput			INTEGER,
		mcmFrSVCMaxRxThroughput			INTEGER, 
		mcmFrSVCTxBurstSize			INTEGER,
		mcmFrSVCRxBurstSize			INTEGER,
		mcmFrSVCExcessTxBurstSize		INTEGER,
		mcmFrSVCExcessRxBurstSize		INTEGER
		}

mcmFrSVCPhyIfIndex OBJECT-TYPE
	SYNTAX	INTEGER
	ACCESS	read-only
	STATUS	mandatory
	DESCRIPTION
	  "NAME = ;
	   DESC = IfIndex of the physical port \
		  the SVC information is \ 
		  associated with;
	   HELP = ;
	   CAPABILITIES = ;"
	::= {mcmFrSVCPhyEntry 1}

mcmFrSVCState OBJECT-TYPE
	SYNTAX	INTEGER {
		q933svc (1)
	}	
	ACCESS	read-only
	STATUS	mandatory
	DESCRIPTION
	  "NAME = ;
	   DESC = SVC LMI Protocol to be used;
	   HELP = All SVC connection setup must \ 
		  use the same LMI protocol;
	   CAPABILITIES = ;"
	::= {mcmFrSVCPhyEntry 2}

mcmFrSVCT303 OBJECT-TYPE
	SYNTAX	INTEGER
	ACCESS	read-only
	STATUS	mandatory
	DESCRIPTION
	  "NAME = ;
	   DESC = The duration, in seconds, \
		  of the setup timer for SVCs.;
	   HELP = Causes at most one Setup retransmission.\
		  How long the SVC LMI will wait \
		  for a response from the network \
		  (e.g. call proceeding, connect) \
		  before the setup message will be \
		  retransmitted.  In 1 second unit. \
		  Q.931 recommends 4 seconds;
	   CAPABILITIES = ;"
	::= {mcmFrSVCPhyEntry 3}

mcmFrSVCT305 OBJECT-TYPE
	SYNTAX	INTEGER
	ACCESS	read-only
	STATUS	mandatory
	DESCRIPTION
	  "NAME = ;
	   DESC = The duration of the Disconnect \
		  timer (in seconds) for SVCs.;
	   HELP = Causes at most one release \
		  transmission. How long the SVC LMI will wait \
		  for a release message from the \
		  network before it will transmit \
		  a release message.  (The SVC LMI \
		  will then  wait for a release \
		  message from the network.) In 1 second \
		  unit.  Q.931 recommends 30 seconds;
	   CAPABILITIES = ;"
	::= {mcmFrSVCPhyEntry 4}

mcmFrSVCT308 OBJECT-TYPE
	SYNTAX	INTEGER
	ACCESS	read-only
	STATUS	mandatory
	DESCRIPTION
	  "NAME = ;
	   DESC = The duration of Release timer (in \
		  seconds) for SVCs.;
		  
	   HELP = Causes at most one release transmission. \
		  How long the SVC LMI will wait \
		  for a response from the network \
		  before the release message will \
		  be retransmitted.  (When the \
		  second release is transmitted, \
		  the local SVC LMI considers \
		  the corresponding SVC to have \
		  been released by the network \
		  as well - even if no response \
		  is received.) In 1 second units. \
                  Q.931 recommends 4 seconds;
	   CAPABILITIES = ;"
	::= {mcmFrSVCPhyEntry 5}

mcmFrSVCT310 OBJECT-TYPE
	SYNTAX	INTEGER
	ACCESS	read-only
	STATUS	mandatory
	DESCRIPTION
	  "NAME = ;
	   DESC = The duration of Connect Timer (in seconds) \
		  for SVCs.;
	   HELP = Causes connection disconnection. \
		  How long the SVC LMI will wait \
		  (in seconds) for a Connect  message \
		  (after receiving the  Call Proceeding \
		  message) before sending a Release \
		  message.  In 1 second units.  Q.931 \
		  recommends a duration between 30\
		  to 120 seconds on the DTE side and \
		  10 seconds on the DC#E side;
	   CAPABILITIES = ;"
	::= {mcmFrSVCPhyEntry 6}

mcmFrSVCMaxCalls OBJECT-TYPE
	SYNTAX	INTEGER (1..255)
	ACCESS	read-only
	STATUS	mandatory
	DESCRIPTION
	  "NAME = ;
	   DESC = Maximum number of SVC Connections;
	   HELP = The sum of both the incoming and outgoing
		  SVCs;
	   CAPABILITIES = ;"
	::= {mcmFrSVCPhyEntry 7}

mcmFrSVCMaxTxSize OBJECT-TYPE
	SYNTAX	INTEGER
	ACCESS	read-only
	STATUS	mandatory
	DESCRIPTION
	  "NAME = ;
	   DESC = Default Maximum transmit frame size, \
		  in bytes, to negotiate with the remote;
	   HELP = This value will be used only if a \
		  specific value is not included in the \
		  Connect Request primitive.  A value of \
		  0 indicates the network default values \
		  are to be used (unless it is passed down \
		  at connect time). Expressed in bytes.
	   CAPABILITIES = ;"
	::= {mcmFrSVCPhyEntry 8}

mcmFrSVCMaxRxSize OBJECT-TYPE
	SYNTAX	INTEGER
	ACCESS	read-only
	STATUS	mandatory
	DESCRIPTION
	  "NAME = ;
	   DESC = Maximum receive frame size in bytes;
	   HELP = Default value for the maximum receive \
		  frame size to negotiate with the remote. \
		  This value will be used only if a \
		  specific value is not included in the \
		  Connect Request primitive.  A value of \
		  0 indicates the network default values \
		  are to be used (unless it is passed down \
		  at connect time). Expressed in bytes.
	   CAPABILITIES = ;"
	::= {mcmFrSVCPhyEntry 9}

mcmFrSVCMinDLCI OBJECT-TYPE
	SYNTAX	INTEGER
	ACCESS	read-only
	STATUS	mandatory
	DESCRIPTION
	  "NAME = ;
	   DESC = Lowest DLCI value for SVCs on \
		  this network link;
	   HELP = This value applies only to SVC connections. \
		  PVC DLCI connections may be established \
		  above or below this value.;
	   CAPABILITIES = ;"
	::= {mcmFrSVCPhyEntry 10}

mcmFrSVCMaxDLCI OBJECT-TYPE
	SYNTAX	INTEGER
	ACCESS	read-only
	STATUS	mandatory
	DESCRIPTION
	  "NAME = ;
	   DESC = Highest DLCI value for SVCs on \
		  the this network;
	   HELP = This value applies only to SVC connections. \
		  PVC DLCI connections may be established \
		  above or below this value.;
	   CAPABILITIES = ;"
	::= {mcmFrSVCPhyEntry 11}

mcmFrSVCMinTxThroughput OBJECT-TYPE
	SYNTAX	INTEGER
	ACCESS	read-only
	STATUS	mandatory
	DESCRIPTION
	  "NAME = ;
	   DESC = Minimum transmit throughput in \
		  bits per seconds;
	   HELP = To negotiate with the remote when used with the \
		  maximum transmit throughput \
		  unless overwritten at connect time. \
		  A value of 0 indicates the network \
		  default values are to be used;
	   CAPABILITIES = ;"
	::= {mcmFrSVCPhyEntry 12}

mcmFrSVCMinRxThroughput OBJECT-TYPE
	SYNTAX	INTEGER
	ACCESS	read-only
	STATUS	mandatory
	DESCRIPTION
	  "NAME = ;
	   DESC = Minimum receive throughput in \
		  bits per seconds;
	   HELP = To negotiate with the remote when used with the \
		  maximum receive throughput \
		  unless overwritten at connect time. \
		  A value of 0 indicates the network \
		  default values are to be used;
	   CAPABILITIES = ;"
	::= {mcmFrSVCPhyEntry 13}

mcmFrSVCMaxTxThroughput OBJECT-TYPE
	SYNTAX	INTEGER
	ACCESS	read-only
	STATUS	mandatory
	DESCRIPTION
	  "NAME = ;
	   DESC = Maximum transmit throughput in \
		  bits per seconds;
	   HELP = To negotiate with the remote when used with the \
		  minimum transmit throughput \
		  unless overwritten at connect time. \
		  A value of 0 indicates the network \
		  default values are to be used;
	   CAPABILITIES = ;"
	::= {mcmFrSVCPhyEntry 14}

mcmFrSVCMaxRxThroughput OBJECT-TYPE
	SYNTAX	INTEGER
	ACCESS	read-only
	STATUS	mandatory
	DESCRIPTION
	  "NAME = ;
	   DESC = Maximum receive throughput in \
		  bits per seconds;
	   HELP = To negotiate with the remote when used with the \
		  minimum receive throughput \
		  unless overwritten at connect time. \
		  A value of 0 indicates the network \
		  default values are to be used;
	   CAPABILITIES = ;"
	::= {mcmFrSVCPhyEntry 15}

mcmFrSVCTxBurstSize OBJECT-TYPE
	SYNTAX	INTEGER
	ACCESS	read-only
	STATUS	mandatory
	DESCRIPTION
	  "NAME = ;
	   DESC = Transmit burst size in bytes;
	   HELP = Default Committed Transmit burst \
		  size, in bytes, to negotiate with \
		  the remote unless overwritten at \
		  connect time.  A value of 0 \
		  indicates the network default \
		  values are to be used;
	   CAPABILITIES = ;"
	::= {mcmFrSVCPhyEntry 16}

mcmFrSVCRxBurstSize OBJECT-TYPE
	SYNTAX	INTEGER
	ACCESS	read-only
	STATUS	mandatory
	DESCRIPTION
	  "NAME = ;
	   DESC = Receive burst size in bytes;
	   HELP = Default Committed Receive burst \
		  size, in bytes, to negotiate with \
		  the remote unless overwritten at \
		  connect time.  A value of 0 \
		  indicates the network default \
		  values are to be used;
	   CAPABILITIES = ;"
	::= {mcmFrSVCPhyEntry 17}

mcmFrSVCExcessTxBurstSize OBJECT-TYPE
	SYNTAX	INTEGER
	ACCESS	read-only
	STATUS	mandatory
	DESCRIPTION
	  "NAME = ;
	   DESC = Excess transmit burst size in bytes;
	   HELP = Default Uncommitted Transmit burst \
		  size, in bytes, to negotiate with \
		  the remote unless overwritten at \
		  connect time.  A value of 0 \
		  indicates the network default \
		  values are to be used;
	   CAPABILITIES = ;"
	::= {mcmFrSVCPhyEntry 18}

mcmFrSVCExcessRxBurstSize OBJECT-TYPE
	SYNTAX	INTEGER
	ACCESS	read-only
	STATUS	mandatory
	DESCRIPTION
	  "NAME = ;
	   DESC = Excess receive burst size in bytes;
	   HELP = Default Uncommitted Receive burst \
		  size, in bytes, to negotiate with \
		  the remote unless overwritten at \
		  connect time.  A value of 0 \
		  indicates the network default \
		  values are to be used;
	   CAPABILITIES = ;"
	::= {mcmFrSVCPhyEntry 19}


-- Frame Relay MICOM Virtual Port Extension

mcmFrVirtualPortTable OBJECT-TYPE
	SYNTAX	SEQUENCE OF McmFrVirtualPortEntry
	ACCESS	not-accessible
	STATUS	mandatory
	DESCRIPTION
	  "NAME = ;
	   DESC = Table to define the virtual port;
	   HELP = Table to provide the mapping between \
		  virtual ports and physical ports \
		  and to define the virtual port \
		  parameters;
	   CAPABILITIES = NET_CFG, VPN_DISP;"
	::= {fr-configuration 5}

mcmFrVirtualPortEntry OBJECT-TYPE
	SYNTAX	McmFrVirtualPortEntry
	ACCESS	not-accessible
	STATUS	mandatory
	DESCRIPTION
	  "NAME = ;
	   DESC = Entry into the Virtual port table;
	   HELP = Each entry in this table contains \
		  information to define a virtual \
		  port;
	   CAPABILITIES = ;"
	INDEX	{mcmFrVirtualPortIfIndex}
	::= {mcmFrVirtualPortTable 1}

McmFrVirtualPortEntry ::= SEQUENCE {
		mcmFrVirtualPortIfIndex		INTEGER,
		mcmFrVirtualPortPhyPortIfIndex	INTEGER,
		mcmFrVirtualPortPPA		INTEGER,
		mcmFrVirtualPortMode		INTEGER,
		mcmFrVirtualPortState		INTEGER,
		mcmFrVirtualPortEntryStatus	INTEGER,
		mcmFrVirtualPortProtocolBinding	INTEGER,
		mcmFrVirtualPortNumber		INTEGER
		}

mcmFrVirtualPortIfIndex OBJECT-TYPE
	SYNTAX	INTEGER (1..255)
	ACCESS	read-only
	STATUS	mandatory
	DESCRIPTION
	  "NAME = Virtual Port Interface Number;
	   DESC = IfIndex associated with this Virtual Port;
	   HELP = ;
	   CAPABILITIES = ;"
	::=  {mcmFrVirtualPortEntry 1}

mcmFrVirtualPortPhyPortIfIndex OBJECT-TYPE
	SYNTAX	INTEGER (1..255)
	ACCESS	read-only
	STATUS	obsolete
	DESCRIPTION
	  "NAME = ;
	   DESC = *******NOTE: THIS OBJECT IS OBSOLETE*******  
                  This information is no longer useful for \
                  virtual ports.  The virtual ports no longer \
                  have an underlying network. Only SVC DNAs \
                  and PVC DLCIs are associated with VPs now. \
                  The underlying MPANL will take care of which \
                  link the SVC is to be made on and a Physical \
                  Line IfIndex has been added to the PVCs.  VP \
                  are no longer required to provide the backup \
                  link support (MPANL now does that).\  

	          IfIndex of the Frame Relay physical \
		  port for which the virtual port is \
		  (or will be) linked to;
	   HELP = ;
	   CAPABILITIES = ;"
	::=  {mcmFrVirtualPortEntry 2}

mcmFrVirtualPortPPA OBJECT-TYPE
	SYNTAX	INTEGER (0..254)
	ACCESS	read-only
	STATUS	obsolete
	DESCRIPTION
	  "NAME = This object has been OBSOLETED for software \
		  releases beginning with Release 3.0. \
		  Virtual Port PPA Number ;
	   DESC = Point of Physical attachment for \
		  this Virtual Port;
	   HELP = ;
	   CAPABILITIES = ;"
	::=  {mcmFrVirtualPortEntry 3}

mcmFrVirtualPortMode OBJECT-TYPE
	SYNTAX	INTEGER {
		basic (1),
		easyRouting (2)
		}
	ACCESS	read-only
	STATUS	mandatory
	DESCRIPTION
	  "NAME = Virtual Port Mode;
	   HELP = Mode of the virtual port;
	   DESC = Easy Routing requires that data  \
		  will be switched between the \
		  Virtual Circuits on the this \
		  virutal port.  Basic mode turns \
		  off the switching mode;
	   CAPABILITIES = ;"
	::=  {mcmFrVirtualPortEntry 4}

mcmFrVirtualPortState OBJECT-TYPE
	SYNTAX	INTEGER{
		up(1),
		down(2),
		uninitialized(3)
	}
	ACCESS	read-only
	STATUS	mandatory
	DESCRIPTION
	  "NAME = Virtual Port State;
	   DESC = State of the virtual port;
	   HELP = ;
	   CAPABILITIES = ;"
	::=  {mcmFrVirtualPortEntry 5}


mcmFrVirtualPortEntryStatus OBJECT-TYPE
	SYNTAX	INTEGER {
		enable (1),
		disable (2)
		}
	ACCESS	read-only
	STATUS	mandatory
	DESCRIPTION
	  "NAME = ;
	   DESC = Virtual port row status;
	   HELP = Indicates whether or not this \
		  entry is valid;
	   CAPABILITIES = ;"
	::=  {mcmFrVirtualPortEntry 6}

mcmFrVirtualPortProtocolBinding OBJECT-TYPE
	SYNTAX	INTEGER {
		ip-configured (1),
		ipx-configured (2),
		ip-and-ipx-configured (3),
		bridge-configured (4),
		ip-and-bridge-configured (5),
		ipx-and-bridge-configured (6),
		ip-and-ipx-and-bridge-configured (7),
		sNA-configured (8),
		x25-configured (9)
		}
	ACCESS	read-only
	STATUS	mandatory
	DESCRIPTION
	  "NAME = ;
	   DESC = Bitmap that contains the protocols bound \
		  to this Virtual Port.;
	   HELP = ;
	   CAPABILITIES = ;"
	::=  {mcmFrVirtualPortEntry 7}

mcmFrVirtualPortNumber OBJECT-TYPE
	SYNTAX	INTEGER 
	ACCESS	read-only
	STATUS	mandatory
	DESCRIPTION
	  "NAME = ;
	   DESC = This object indicates the Virtual \
		  Port Number used as an identifier \
		  for a Virtual Port. (Operational);
	   HELP = ;
	   CAPABILITIES = ;"
	::=  {mcmFrVirtualPortEntry 8}


-- Frame Relay Associated SVC MIB

mcmFrSVCMapTable OBJECT-TYPE
	SYNTAX	SEQUENCE OF McmFrSVCMapEntry
	ACCESS	not-accessible
	STATUS	mandatory
	DESCRIPTION
	  "NAME = ;
	   DESC = Table for SVC to VP bindings;
	   HELP = This table will give the SVC \
		  DNA address to be bound to the \
		  specified Virtual Port;
	   CAPABILITIES = NET_CFG, VPN_DISP;"
	::= {fr-configuration 6}

mcmFrSVCMapEntry OBJECT-TYPE
	SYNTAX	McmFrSVCMapEntry
	ACCESS	not-accessible
	STATUS	mandatory
	DESCRIPTION
	  "NAME = ;
	   DESC = Entry in the SVC to VP binding \
		  table;
	   HELP = SVC/VP binding entry in the SVC \
		  binding table.  Multiple SVCS \
		  (DNAs) may be bound to a single \
		  VP (ifindex);
	   CAPABILITIES = ;"
	INDEX	{mcmFrSVCMapVirtualPortIfIndex, mcmFrSVCMapDNA}
	::= {mcmFrSVCMapTable 1}

McmFrSVCMapEntry ::= SEQUENCE {
	mcmFrSVCMapVirtualPortIfIndex		INTEGER,
	mcmFrSVCMapDNA				OCTET STRING,
	mcmFrSVCMapDLCI				INTEGER,
	mcmFrSVCMapMaxTxSize			INTEGER,
	mcmFrSVCMapMaxRxSize			INTEGER,
	mcmFrSVCMapMinTxThroughput		INTEGER,
	mcmFrSVCMapMinRxThroughput		INTEGER,
	mcmFrSVCMapMaxTxThroughput		INTEGER,
	mcmFrSVCMapMaxRxThroughput		INTEGER,
	mcmFrSVCMapTxBurstSize			INTEGER,
	mcmFrSVCMapRxBurstSize			INTEGER,
	mcmFrSVCMapExcessTxBurstSize		INTEGER,
	mcmFrSVCMapExcessRxBurstSize		INTEGER,
	mcmFrSVCMapPriority			INTEGER,
	mcmFrSVCMapEntryStatus			INTEGER,
	mcmFrSVCMapTransferPriority		INTEGER,
	mcmFrSVCMapDisableCause			INTEGER,
	mcmFrSvcMapSvcIfIndex                   INTEGER,
	mcmFrSVCMapDiscardPriority              INTEGER,
	mcmFrSVCMapSetupPriority                INTEGER,
	mcmFrSVCMapHoldingPriority              INTEGER
	}

mcmFrSVCMapVirtualPortIfIndex OBJECT-TYPE
	SYNTAX	INTEGER
	ACCESS	read-only
	STATUS	mandatory
	DESCRIPTION
	  "NAME = ;
	   DESC = Virtual Port ifIndex associated \
		  with this DNA;
	   HELP = ;
	   CAPABILITIES = ;"
	::=  {mcmFrSVCMapEntry 1}

mcmFrSVCMapDNA OBJECT-TYPE
	SYNTAX	OCTET STRING
	ACCESS	read-only
	STATUS	mandatory
	DESCRIPTION
	  "NAME = ;
	   DESC = Remote DNA to associate SVC with \
		  the corresponding virtual port;
	   HELP = DNA to be mapped to the \
		  corresponding virtual port. \
		  This will be used to create \
		  an SVC to the corresponding \
		  remote DNA;
	   CAPABILITIES = ;"
	::=  {mcmFrSVCMapEntry 2}

mcmFrSVCMapDLCI OBJECT-TYPE
	SYNTAX	INTEGER
	ACCESS	read-only
	STATUS	mandatory
	DESCRIPTION
	  "NAME = ;
	   DESC = DLCI for the connected SVC;
	   HELP = Valid only when the SVC is up;
	   CAPABILITIES = ;"
	::=  {mcmFrSVCMapEntry 3}

mcmFrSVCMapMaxTxSize OBJECT-TYPE
	SYNTAX	INTEGER
	ACCESS	read-only
	STATUS	mandatory
	DESCRIPTION
	  "NAME = ;
	   DESC = Maximum transmit frame size to \
		  negotiate with the remote (in \
		  bytes);
	   HELP = This value will override the default values for \
		  the physical interface.  A value \
		  of 0 indicates the networks default \
		  values are to be used. Experessed in \
		  bytes;
	   CAPABILITIES = ;"
	::=  {mcmFrSVCMapEntry 4}

mcmFrSVCMapMaxRxSize OBJECT-TYPE
	SYNTAX	INTEGER
	ACCESS	read-only
	STATUS	mandatory
	DESCRIPTION
	  "NAME = ;
	   DESC = Maximum receive frame size to \
		  negotiate with the remote (in \
		  bytes);
	   HELP = This value will override the default values for \
		  the physical interface.  A value \
		  of 0 indicates the networks default \
		  values are to be used. Experessed in \
		  bytes;
	   CAPABILITIES = ;"
	::=  {mcmFrSVCMapEntry 5}

mcmFrSVCMapMinTxThroughput OBJECT-TYPE
	SYNTAX	INTEGER
	ACCESS	read-only
	STATUS	mandatory
	DESCRIPTION
	  "NAME = ;
	   DESC = Minimum transmit throughput in \
		  bits per second to negotiate with \
		  the remote;
	   HELP = Used with the maximum transmit throughput. \
		  This value will override default \
		  values given for this physical \
		  interface.  A value of 0 indicates \
		  the network default values are to \
		  be used;
	   CAPABILITIES = ;"
	::=  {mcmFrSVCMapEntry 6}

mcmFrSVCMapMinRxThroughput OBJECT-TYPE
	SYNTAX	INTEGER
	ACCESS	read-only
	STATUS	mandatory
	DESCRIPTION
	  "NAME = ;
	   DESC = Minimum receive throughput in \
		  bits per second to negotiate with \
		  the remote;
	   HELP = Used with the maximum receive throughput. \
		  This value will override default \
		  values given for this physical \
		  interface.  A value of 0 indicates \
		  the network default values are to \
		  be used;
	   CAPABILITIES = ;"
	::=  {mcmFrSVCMapEntry 7}

mcmFrSVCMapMaxTxThroughput OBJECT-TYPE
	SYNTAX	INTEGER
	ACCESS	read-only
	STATUS	mandatory
	DESCRIPTION
	  "NAME = ;
	   DESC = Maximum transmit throughput in \
		  bits per second to negotiate with \
		  the remote;
	   HELP = Used with the minimum transmit throughput. \
		  This value will override default \
		  values given for this physical \
		  interface.  A value of 0 indicates \
		  the network default values are to \
		  be used;
	   CAPABILITIES = ;"
	::=  {mcmFrSVCMapEntry 8}

mcmFrSVCMapMaxRxThroughput OBJECT-TYPE
	SYNTAX	INTEGER
	ACCESS	read-only
	STATUS	mandatory
	DESCRIPTION
	  "NAME = ;
	   DESC = Maximum receive throughput in \
		  bits per second to negotiate with \
		  the remote;
	   HELP = Used with the minimum receive throughput. \
		  This value will override default \
		  values given for this physical \
		  interface.  A value of 0 indicates \
		  the network default values are to \
		  be used;
	   CAPABILITIES = ;"
	::=  {mcmFrSVCMapEntry 9}

mcmFrSVCMapTxBurstSize OBJECT-TYPE
	SYNTAX	INTEGER
	ACCESS	read-only
	STATUS	mandatory
	DESCRIPTION
	  "NAME = ;
	   DESC = Transmit burst size in bytes;
	   HELP = Committed transmit burst size, \
		  in bytes, to negotiate with the \
		  remote. This value will override \
		  default values entered for the \
		  network.  A value of 0 indicates \
		  the network default values are to \
		  be used;
	   CAPABILITIES = ;"
	::=  {mcmFrSVCMapEntry 10}

mcmFrSVCMapRxBurstSize OBJECT-TYPE
	SYNTAX	INTEGER
	ACCESS	read-only
	STATUS	mandatory
	DESCRIPTION
	  "NAME = ;
	   DESC = Receive burst size in bytes;
	   HELP = Committed receive burst size, \
		  in bytes, to negotiate with the \
		  remote. This value will override \
		  default values entered for the \
		  network.  A value of 0 indicates \
		  the network default values are to \
		  be used;
	   CAPABILITIES = ;"
	::=  {mcmFrSVCMapEntry 11}

mcmFrSVCMapExcessTxBurstSize OBJECT-TYPE
	SYNTAX	INTEGER
	ACCESS	read-only
	STATUS	mandatory
	DESCRIPTION
	  "NAME = ;
	   DESC = Excess transmit burst size in bytes;
	   HELP = Uncommitted transmit burst size, \
		  in bytes, to negotiate with the \
		  remote. This value will override \
		  default values entered for the \
		  network.  A value of 0 indicates \
		  the network default values are to \
		  be used;
	   CAPABILITIES = ;"
	::=  {mcmFrSVCMapEntry 12}

mcmFrSVCMapExcessRxBurstSize OBJECT-TYPE
	SYNTAX	INTEGER
	ACCESS	read-only
	STATUS	mandatory
	DESCRIPTION
	  "NAME = ;
	   DESC = Excess receive burst size in bytes;
	   HELP = Uncommitted transmit burst size, \
		  in bytes, to negotiate with the \
		  remote. This value will override \
		  default values entered for the \
		  network.  A value of 0 indicates \
		  the network default values are to \
		  be used;
	   CAPABILITIES = ;"
	::=  {mcmFrSVCMapEntry 13}

mcmFrSVCMapPriority OBJECT-TYPE
	SYNTAX	INTEGER
	ACCESS	read-only
	STATUS	mandatory
	DESCRIPTION
	  "NAME = ;
	   DESC = Transfer priority level for data on \
		  this SVC;
	   HELP = All data on this SVC will be sent \
		  through the switches at \
		  the requested transfer priority level;
	   CAPABILITIES = ;"
	::=  {mcmFrSVCMapEntry 14}


mcmFrSVCMapEntryStatus OBJECT-TYPE
	SYNTAX	INTEGER {
		enable (1),
		disable (2)
	}
	ACCESS	read-only
	STATUS	mandatory
	DESCRIPTION
	  "NAME = ;
	   DESC = Indicates whether or not this entry is \
		  enabled;
	   HELP = Enabled indicates this entry will be used \
		  to establish an SVC connection.  Disabled \
		  indicates this entry is to be ignored when \
		  establishing SVC connections.  This allows \
		  these SVCs entries to be disabled/enabled \
		  without having to reenter the entire entry;
	   CAPABILITIES = ;"
	::=  {mcmFrSVCMapEntry 15}

mcmFrSVCMapTransferPriority OBJECT-TYPE
	SYNTAX	INTEGER (0..15)
	ACCESS	read-only
	STATUS	mandatory
	DESCRIPTION
	  "NAME = ;
	   DESC = The transfer priority for the corresponding \
		  pass-through network connection.;
	   HELP = ;
	   CAPABILITIES = ;"
	::=  {mcmFrSVCMapEntry 16}

mcmFrSVCMapDisableCause OBJECT-TYPE
	SYNTAX	INTEGER {
		the-PVC-does-not-exist-ie-unassigned (1),
                no-route-to-specified-transit-network (2),
                no-route-to-destination (3),
                channel-unacceptable (6),
                call-awarded-and-being-delivered-in-an-est-channel (7),
                normal-call-clearing (16),
		remote-PVC-already-connected-ie-busy (17),
		no-user-present-in-call (18),
		remote-PVC-down-ie-unavailable (21),
                destination-out-of-order (27),
                invalid-number-format (28),
                facility-rejected (29),
		response-to-status-inquiry (30),
                normal-unspecified (31),
		no-DLCI-available (34),
                network-out-of-order (38),
                permanent-frame-mode-connection-out-of-service (39),
                permanent-frame-mode-connection-operational (40),
                temporary-failure (41),
                switching-equipment-congestion (42),
                access-information-discarded (43),
		specified-DLCI-unavailable (44),
		resource-unavailable (47),
                quality-of-service-not-available (49),
                requested-facility-not-subscribed (50),
                bearer-capability-not-authorized (57),
                bearer-capability-not-presently-available (58),
                service-or-option-not-available-unspecified (63),
                bearer-capability-not-implemented (65),
                channel-type-not-implemented (66),
                only-restricted-digital-capability-is-available (70),
                service-or-option-not-implemented-unspecified (79),
		invalid-call-reference (81),
                identified-channel-does-not-exist (82),
                user-not-member-of-CUG (87),
                incompatible-destination (88),
                non-existent-CUG (90),
                invalid-transit-network-selection (91),
                invalid-message-unspecified (95),
		missing-element (96),
		message-type-unknown (97),
                message-not-compatible (98),
                element-non-existent-or-not-implemented (99),
		invalid-element (100),
		invalid-message-for-state (101),
		timer-recovery (102),
                protocol-error-unspecified (111),
                interworking-unspecified (127),
                normal-condition (128)
		}
	ACCESS	read-only
	STATUS	mandatory
	DESCRIPTION
	  "NAME = ;
	   DESC = The cause code describing the reason that \
		  the SVC was not established.; \
	   HELP = ;
	   CAPABILITIES = ;"
	::=  {mcmFrSVCMapEntry 17}

mcmFrSvcMapSvcIfIndex OBJECT-TYPE
	SYNTAX	INTEGER 
	ACCESS	read-only
	STATUS	mandatory
	DESCRIPTION
	  "NAME = ;
	   DESC = For Software releases beginning with R3.0, \
		  this object indicates the ifIndex of the tunneling \
		  PVC in which the SVC is established.  Prior to \
		  R3.0, this object indicates the physical Interface \
		  this SVC DLCI is associated with.;
	   HELP = ;
	   CAPABILITIES = ;"
	::=  {mcmFrSVCMapEntry 18}


mcmFrSVCMapDiscardPriority OBJECT-TYPE
        SYNTAX INTEGER {
           low-discard-level     (1),
           medium-discard-level  (2),
           high-discard-level    (3)
           }
        ACCESS read-only
        STATUS mandatory
        DESCRIPTION
	  "NAME = ;
	   DESC = The discard priority used for connection \
		  setup of this SVC map.; 
	   HELP = ;
	   CAPABILITIES = ;"
	::=  {mcmFrSVCMapEntry 19}

mcmFrSVCMapSetupPriority OBJECT-TYPE
        SYNTAX INTEGER (1..5)
	ACCESS	read-only
	STATUS	mandatory
	DESCRIPTION
	  "NAME = ;
           DESC = This object indicates the priority of a path at \
		  call-establishment time, and also determines \
		  the potential for bumping established paths \
		  to acquire their bandwidth.  A value of 1 is \
		  the highest priority, and 5 is the lowest.;
           HELP = ;
	   CAPABILITIES = ;"
	::= {mcmFrSVCMapEntry 20}

mcmFrSVCMapHoldingPriority OBJECT-TYPE
        SYNTAX INTEGER (1..5)
	ACCESS	read-only
	STATUS	mandatory
	DESCRIPTION
	  "NAME = ;
           DESC = This object indicates the priority that a path \
		  maintains once the path is established, and \
		  also determines the likelihood of being bumped \
		  by a new path, thus losing the bandwidth.  A value \
		  of 1 is the highest priority, and 5 is the lowest.;
           HELP = ;
	   CAPABILITIES = ;"
	::= {mcmFrSVCMapEntry 21}



-- Frame Relay Associated PVC Parameters

-- *** This table OBSOLETED beginning with software Release 3.0. ***

mcmFrPVCMapTable OBJECT-TYPE
	SYNTAX	SEQUENCE OF McmFrPVCMapEntry
	ACCESS	not-accessible
	STATUS	obsolete
	DESCRIPTION
	  "NAME = ;
	   DESC = This table has been OBSOLETED for software \
		  releases beginning with Release 3.0. \
		  Table for PVC to VP bindings;
	   HELP = This table will give the PVC \
	          DLCI address to be bound to the \
		  specified Virtual Port;
	   CAPABILITIES = NET_CFG, VPN_DISP;"
	::= {fr-configuration 7}

mcmFrPVCMapEntry OBJECT-TYPE
	SYNTAX	McmFrPVCMapEntry
	ACCESS	not-accessible
	STATUS	obsolete
	DESCRIPTION
	  "NAME = ;
	   DESC = Entry in the PVC to VP binding \
		  table;
	   HELP = PVC/VP binding entry in the PVC \
		  binding table.  Multiple PVCs \
		  (DLCIs) may be bound to a single \
		  VP (ifindex).;
	   CAPABILITIES = ;"
	INDEX	{mcmFrPVCMapVirtualPortIfIndex, mcmFrPVCMapDLCI}
	::= {mcmFrPVCMapTable 1}

McmFrPVCMapEntry ::= SEQUENCE {
	mcmFrPVCMapVirtualPortIfIndex	INTEGER,
	mcmFrPVCMapDLCI			INTEGER,
	mcmFrPVCMapState		INTEGER,
	mcmFrPVCMapEntryStatus		INTEGER,
        mcmFrPVCMapPhysIfIndex          INTEGER
	}

mcmFrPVCMapVirtualPortIfIndex OBJECT-TYPE
	SYNTAX	INTEGER
	ACCESS	read-only
	STATUS	obsolete
	DESCRIPTION
	  "NAME = ;
	   DESC = Virtual port ifIndex associated \
		  with this PVC DLCI;
	   HELP = ;
	   CAPABILITIES = ;"
	::=  { mcmFrPVCMapEntry 1}

mcmFrPVCMapDLCI OBJECT-TYPE
	SYNTAX	INTEGER
	ACCESS	read-only
	STATUS	obsolete
	DESCRIPTION
	  "NAME = ;
	   DESC = Local DLCI to the remote that is \
		  associated with the corresponding \
		  virtual port;
	   HELP = A DLCI for any given interface \
		  may be bound to only one virtual \
		  port;
	   CAPABILITIES = ;"
	::=  { mcmFrPVCMapEntry 2}

mcmFrPVCMapState OBJECT-TYPE
	SYNTAX	INTEGER {
		invalid (1),
		active (2),
		inactive (3)
	}
	ACCESS	read-only
	STATUS	obsolete
	DESCRIPTION
	  "NAME = ;
	   DESC = Indicates the current state of \
		  the PVC DLCI;
	   HELP = States may be invalid, active or \
		  inactive;
	   CAPABILITIES = ;"
	::=  { mcmFrPVCMapEntry 3}


mcmFrPVCMapEntryStatus OBJECT-TYPE
	SYNTAX	INTEGER {
		enable (1),
		disable (2)
	}
	ACCESS	read-only
	STATUS	obsolete
	DESCRIPTION
	  "NAME = ;
	   DESC = Indicates whether or not this entry is \
		  enabled;
	   HELP = Enabled indicates this entry will be used \
		  to associate a PVC DLCI with a virtual \
		  port.  Disable indicates this entry is to \
		  be ignored when mapping PVC dlcis to \
		  virtual ports.  This allows the PVC map \
		  entries to be disabled/enabled without \
		  having to reenter the entire entry;
	   CAPABILITIES = ;"
	::=  {mcmFrPVCMapEntry 4}

mcmFrPVCMapPhysIfIndex OBJECT-TYPE
	SYNTAX	INTEGER 
	ACCESS	read-only
	STATUS	obsolete
	DESCRIPTION
	  "NAME = ;
	   DESC = Physical interface this PVC \
                  is associated with.;
	   HELP = ;
	   CAPABILITIES = ;"
	::=  {mcmFrPVCMapEntry 5}


     -- A Frame Relay service is a multiplexing service.  Data
     -- Link Connection Identifiers enumerate virtual circuits
     -- (permanent or dynamic) which are layered onto the underlying
     -- circuit, represented by ifEntry.  Therefore, each of the entries
     -- in the Standard MIB's Interface Table with an IfType of
     -- Frame Relay represents a Q.922 interface.  Zero or more
     -- virtual circuits are layered onto this interface and provide
     -- interconnection with various remote destinations.
     -- Each such dynamic virtual circuit is represented by an entry in the
     -- SVC circuit table.

     --   SVC 1490 (LAN) Data Circuit Table

     -- The table describing the use of the SVC DLCIs attached to
     -- each Frame Relay Interface (for LAN data SVCs only).

mcmFrSVCCircuitTable OBJECT-TYPE
        SYNTAX   SEQUENCE OF McmFrCircuitEntry
        ACCESS   not-accessible
        STATUS   mandatory
	DESCRIPTION
	  "NAME = ;
	   DESC = Table of entries for SVCs on this \
		  access device;
	   HELP = A table containing information \
		  about specific SVC Data Link \
		  Connection Identifiers;
	   CAPABILITIES = NET_CFG, VPN_DISP;"
         ::= { fr-configuration 8 }

mcmFrSVCCircuitEntry OBJECT-TYPE
        SYNTAX   McmFrCircuitEntry
        ACCESS   not-accessible
        STATUS   mandatory
	DESCRIPTION
	  "NAME = ;
	   DESC = The information regarding a \
		  single SVC DLCI circuit;
	   HELP = An entry into the SVC circuit \
		  table;
	   CAPABILITIES = ;"
           INDEX { mcmFrSVCCircuitIfIndex, mcmFrSVCCircuitDNA }
            ::= { mcmFrSVCCircuitTable 1 }

         McmFrCircuitEntry ::= SEQUENCE {
                 mcmFrSVCCircuitIfIndex 		INTEGER,
                 mcmFrSVCCircuitDNA 			OCTET STRING,
                 mcmFrSVCCircuitDlci 			INTEGER,
                 mcmFrSVCCircuitState 			INTEGER,
                 mcmFrSVCCircuitReceivedFECNs 		Counter,
                 mcmFrSVCCircuitReceivedBECNs 		Counter,
                 mcmFrSVCCircuitSentFrames 		Counter,
                 mcmFrSVCCircuitSentOctets 		Counter,
                 mcmFrSVCCircuitReceivedFrames 		Counter,
                 mcmFrSVCCircuitReceivedOctets 		Counter,
                 mcmFrSVCCircuitCreationTime 		TimeTicks,
                 mcmFrSVCCircuitCallOriginator 		OCTET STRING,
                 mcmFrSVCCircuitLastTimeChange 		TimeTicks,
                 mcmFrSVCCircuitCommittedBurst 		INTEGER,
                 mcmFrSVCCircuitExcessBurst 		INTEGER,
                 mcmFrSVCCircuitThroughput 		INTEGER,
                 mcmFrSVCCircuitNegMaxTxSize 		INTEGER,
                 mcmFrSVCCircuitNegMaxRxSize 		INTEGER,
                 mcmFrSVCCircuitNegTxThroughput 	INTEGER,
                 mcmFrSVCCircuitNegRxThroughput 	INTEGER,
                 mcmFrSVCCircuitNegTxBurst 		INTEGER,
                 mcmFrSVCCircuitNegRxBurst 		INTEGER,
                 mcmFrSVCCircuitNegTxExcess 		INTEGER,
                 mcmFrSVCCircuitNegRxExcess 		INTEGER,
                 mcmFrSVCCircuitTxDiscardCIRPolice 	Counter,
                 mcmFrSVCCircuitPriority 		INTEGER,
                 mcmFrSVCCircuitSvcIfIndex              INTEGER,
                 mcmFrSVCCircuitDiscardPriority         INTEGER,
                 mcmFrSVCCircuitSetupPriority           INTEGER,
                 mcmFrSVCCircuitHoldingPriority         INTEGER
                 }


mcmFrSVCCircuitIfIndex OBJECT-TYPE
        SYNTAX   INTEGER (1..255)
        ACCESS   read-only
        STATUS   mandatory
	DESCRIPTION
	  "NAME = ;
	   DESC = The ifIndex Value of the ifEntry \
		  this SVC virtual circuit is 
		  linked with;
	   HELP = The ifIndex for the interface on \
		  which this PVC belongs;
	   CAPABILITIES = ;"
            ::= { mcmFrSVCCircuitEntry 1 }

mcmFrSVCCircuitDNA OBJECT-TYPE
        SYNTAX   OCTET STRING (SIZE(1..34))
        ACCESS   read-only
        STATUS   mandatory
	DESCRIPTION
	  "NAME = ;
	   DESC = The destination DNA for the SVC;
	   HELP = ;
	   CAPABILITIES = ;"
            ::= { mcmFrSVCCircuitEntry 2 }


mcmFrSVCCircuitDlci OBJECT-TYPE
        SYNTAX   INTEGER (16..991)
        ACCESS   read-only
        STATUS   mandatory
	DESCRIPTION
	  "NAME = ;
	   DESC = The Data Link Connection Identifier \
		  for this virtual circuit;
	   HELP = The local DLCI for this SVC, valid \
		  only when the connection has been \
		  established;
	   CAPABILITIES = ;"
            REFERENCE
               "Draft American National  Standard  T1.618-1991,
               Section 3.3.6"
           ::= { mcmFrSVCCircuitEntry 3 }


mcmFrSVCCircuitState OBJECT-TYPE
        SYNTAX   INTEGER {
                 invalid (1),
                 active (2),
                 inactive (3)
                      }
        ACCESS   read-only
        STATUS   mandatory
	DESCRIPTION
	  "NAME = ;
	   DESC = Indication for the state of this SVC (active \
		  or inactive).
	   HELP = Only the configured SVCs can be in \
		  the inactive state (all learned \
		  SVCs will be deleted when the connection \
		  has been released);
	   CAPABILITIES = ;"
            DEFVAL { active }
            ::= { mcmFrSVCCircuitEntry 4 }


mcmFrSVCCircuitReceivedFECNs OBJECT-TYPE
        SYNTAX   Counter
        ACCESS   read-only
        STATUS   mandatory
	DESCRIPTION
	  "NAME = ;
	   DESC = Number of frames received from \
		  the network indicating forward \
		  congestion.;
	   HELP = Number of Frame Relay Packets \
		  received on the corresponding \
		  DLCI with the Forward congestion \
		  bit set since this SVC was created;
	   CAPABILITIES = ;"
            REFERENCE
               "Draft American National  Standard  T1.618-1991, Section 3.3.3"
           ::= { mcmFrSVCCircuitEntry 5 }



mcmFrSVCCircuitReceivedBECNs OBJECT-TYPE
        SYNTAX   Counter
        ACCESS   read-only
        STATUS   mandatory
	DESCRIPTION
	  "NAME = ;
	   DESC = Number of frames received from \
		  the network indicating backward \	
		  congestion;
	   HELP = Number of Frame Relay Packets received \
		  on the corresponding interface with the \
		  backwards congestion bit set  since this \
		  SVC was created.;
	   CAPABILITIES = ;"
            REFERENCE
               "Draft American National  Standard  T1.618-1991, Section 3.3.4"
           ::= { mcmFrSVCCircuitEntry 6 }



mcmFrSVCCircuitSentFrames OBJECT-TYPE
        SYNTAX   Counter
        ACCESS   read-only
        STATUS   mandatory
	DESCRIPTION
	  "NAME = ;
	   DESC = The number of frames sent from \
		  this switched virtual circuit \
		  since this was counter was last \
		  reset;
	   HELP = Number of Frame Relay Packets sent \
		  on the corresponding SVC since this \
		  counter was last reset (either by \
		  reboot of access device or a counter reset \
		  initiated by a user...Note that user initiated \
		  counter resets have been OBSOLETED for \
		  software releases beginning with Release 3.0.);
	   CAPABILITIES = ;"
            ::= { mcmFrSVCCircuitEntry 7 }



mcmFrSVCCircuitSentOctets OBJECT-TYPE
        SYNTAX   Counter
        ACCESS   read-only
        STATUS   mandatory
	DESCRIPTION
	  "NAME = ;
	   DESC = The number of octets sent from \
		  this switched virtual circuit since \
		  it was last created or reset;
	   HELP = Number of bytes sent on the \
		  corresponding SVC since this counter \
		  was last reset (either by reboot of access device \
		  or a counter reset initiated by a user...Note that \
		  user initiated counter resets have been OBSOLETED \
		  for software releases beginning with Release 3.0.);
	   CAPABILITIES = ;"
            ::= { mcmFrSVCCircuitEntry 8 }



mcmFrSVCCircuitReceivedFrames OBJECT-TYPE
        SYNTAX   Counter
        ACCESS   read-only
        STATUS   mandatory
	DESCRIPTION
	  "NAME = ;
	   DESC = Number of frames received over \
		  this virtual circuit since it \
		  was created or the counter was \
		  last reset;
	   HELP = Number of Frame Relay Packets received \
		  on the corresponding SVC since this \
		  counter was last reset (either by reboot \
		  or a counter reset initiated by a user...Note that \
		  user initiated counter resets have been OBSOLETED \
		  for software releases beginning with Release 3.0.);
	   CAPABILITIES = ;"
            ::= { mcmFrSVCCircuitEntry 9 }



mcmFrSVCCircuitReceivedOctets OBJECT-TYPE
        SYNTAX   Counter
        ACCESS   read-only
        STATUS   mandatory
	DESCRIPTION
	  "NAME = ;
	   DESC = Number of octets received  over \
		  this virtual circuit since it \
		  was created or the counter was \
		  last reset;
	   HELP = Number of octets received \
		  on the corresponding SVC since this \
		  counter was last reset (either by reboot \
		  or a counter reset initiated by a user...Note that \
		  user initiated counter resets have been OBSOLETED \
		  for software releases beginning with Release 3.0.);
	   CAPABILITIES = ;"
            ::= { mcmFrSVCCircuitEntry 10 }


mcmFrSVCCircuitCreationTime OBJECT-TYPE
        SYNTAX   TimeTicks
        ACCESS   read-only
        STATUS   mandatory
	DESCRIPTION
	  "NAME = ;
	   DESC = The value of sysUpTime when the \
		  switched virtual circuit was \
		  created.;;
	   HELP = The sysUpTime when the SVC was created \
		  either at bootup time or when the SVC \
		  was set up through Q.933, whether by the \
		  Data Link Connection Management Interface or \
		  by a SetRequest;
	   CAPABILITIES = ;"
            ::= { mcmFrSVCCircuitEntry 11 }

mcmFrSVCCircuitCallOriginator OBJECT-TYPE
        SYNTAX   OCTET STRING (SIZE(1..34))
        ACCESS   read-only
        STATUS   mandatory
	DESCRIPTION
	  "NAME = ;
	   DESC = DNA of the SVC call originator.;
	   HELP = DNA of the node that originated \
		  the call that resulted in \
		  the establishment of the SVC;
	   CAPABILITIES = ;"
            ::= { mcmFrSVCCircuitEntry 12 }



mcmFrSVCCircuitLastTimeChange OBJECT-TYPE
        SYNTAX   TimeTicks
        ACCESS   read-only
        STATUS   mandatory
	DESCRIPTION
	  "NAME = ;
	   DESC = The value of sysUpTime when the state \
		  of the SVC last changed.;
	   HELP = The sysUpTime of the last status change \
		  in the SVC.  (For SVCs established by the \
		  remote, the last time change should be \
		  equal to the SVC creation time);
	   CAPABILITIES = ;"
            ::= { mcmFrSVCCircuitEntry 13 }



mcmFrSVCCircuitCommittedBurst OBJECT-TYPE
        SYNTAX   INTEGER (0..2560000)
        ACCESS   read-only
        STATUS   deprecated
	DESCRIPTION
	  "NAME = ;
	   DESC = *******NOTE: THIS OBJECT IS DEPRECATED******* \
                  This information is redundant. It has been 
                  replaced by mcmFrSVCCircuitNedTxThroughput and
                  mcmFrCircuitNexRxThroughput which are objects \
                  from this same table(mcmFrSVCCircuitTable).;\

                  Maximum amount of data that the network agrees \
		  transfer under normal conditions over a set \
		  measurement interval.;
	   HELP = The maximum rate at which the network \
		  agrees to transfer under normal (non- \
		  congested) conditions (expressed in bits \
		  per second).;
	   CAPABILITIES = ;"
            REFERENCE
               "Draft American National  Standard  T1.617-1991,
               Section 6.5.19"
           DEFVAL   { 0 }  -- the default indicates no commitment
           ::= { mcmFrSVCCircuitEntry 14 }


mcmFrSVCCircuitExcessBurst OBJECT-TYPE
        SYNTAX   INTEGER (0..2560000)
        ACCESS   read-only 
        STATUS   deprecated
	DESCRIPTION
	  "NAME = ;
	   DESC = *******NOTE: THIS OBJECT IS DEPRECATED*******\
                  This information is redundant. It has been 
                  replaced by  mcmFrSVCCircuitNegTxExceess and \
                  and mcmFrSVCCircuitNegRxExceess which are objects \
                  from this same table.(mcmFrSVCCircuitTable);\   

                  The maximum number of uncommited bits \
		  that the frame relay network will attempt \
		  to deliver (expressed in bits per second).; \
	   HELP = This variable indicates the maximum \
		  amount  of uncommitted data bits \
		  that the network will attempt to \
		  deliver over the measurement interval. \
		  By default, if not configured when \
		  creating the entry, the Excess \
		  information Burst Size is set \
		  to the value of ifSpeed;
	   CAPABILITIES = ;"
            REFERENCE
               "Draft American National  Standard  T1.617-1991, Section 6.5.19"
                   ::= { mcmFrSVCCircuitEntry 15 }



mcmFrSVCCircuitThroughput OBJECT-TYPE
        SYNTAX   INTEGER (0..2560000)
        ACCESS read-only 
        STATUS   mandatory
	DESCRIPTION
	  "NAME = ;
	   DESC = The average number of 'Frame Relay \
		  Information Field' bits transferred \
		  per second across a physical frame relay \
		  interface.;
	   HELP = Throughput is the average number of \
		  'Frame Relay Information  Field'  \
		  bits  transferred per second across a \
		  user network interface  in  one \
		  direction, measured over the \
		  measurement interval. If the  configured \
		  commited burst  rate  and throughput  \
		  are both non-zero, the measurement interval \
		  T=mcmFrSVCCircuitCommittedBurst/mcmFrSVC- \
		  CircuitThroughput. If the  configured  \
		  committed  burst  rate  and throughput  are  \
		  both zero, the measurement interval\
                  T=mcmFrSVCCircuitExcessBurst/ifSpeed;
	   CAPABILITIES = ;"
            REFERENCE
               "Draft American National  Standard  T1.617-1991, Section 6.5.19"
           DEFVAL {0}  -- the default value of Throughput is "no commitment".
           ::= { mcmFrSVCCircuitEntry 16 }


mcmFrSVCCircuitNegMaxTxSize OBJECT-TYPE
        SYNTAX   INTEGER (0..4096)
        ACCESS   read-only
        STATUS   mandatory
	DESCRIPTION
	  "NAME = ;
	   DESC = The negotiated maximum Tx size to \
		  be sent on this interface (in bytes).; 
	   HELP =;
	   CAPABILITIES = ;"
::= { mcmFrSVCCircuitEntry 17 }


mcmFrSVCCircuitNegMaxRxSize OBJECT-TYPE
        SYNTAX   INTEGER (0..4096)
        ACCESS   read-only
        STATUS   mandatory
	DESCRIPTION
	  "NAME = ;
	   DESC = The negotiated maximum Rx size to \
		  be received on this interface (in bytes).; 
	   HELP =;
	   CAPABILITIES = ;"
::= { mcmFrSVCCircuitEntry 18 }


mcmFrSVCCircuitNegTxThroughput OBJECT-TYPE
        SYNTAX   INTEGER (0..2560000)
        ACCESS   read-only
        STATUS   mandatory
	DESCRIPTION
	  "NAME = ;
	   DESC = The negotiated Tx throughput to \
		  be sent on this interface (in bits/sec).; 
	   HELP =;
	   CAPABILITIES = ;"
::= { mcmFrSVCCircuitEntry 19 }


mcmFrSVCCircuitNegRxThroughput OBJECT-TYPE
        SYNTAX   INTEGER (0..2560000)
        ACCESS   read-only
        STATUS   mandatory
	DESCRIPTION
	  "NAME = ;
	   DESC = The negotiated Rx throughput to \
		  be received on this interface (in bits/sec).; 
	   HELP =;
	   CAPABILITIES = ;"
::= { mcmFrSVCCircuitEntry 20 }


mcmFrSVCCircuitNegTxBurst OBJECT-TYPE
        SYNTAX   INTEGER (0..2560000)
        ACCESS   read-only
        STATUS   mandatory
	DESCRIPTION
	  "NAME = ;
	   DESC = The negotiated Tx committed burst to \
		  be sent on this interface (in bits/sec).; 
	   HELP =;
	   CAPABILITIES = ;"
::= { mcmFrSVCCircuitEntry 21 }


mcmFrSVCCircuitNegRxBurst OBJECT-TYPE
        SYNTAX   INTEGER (0..2560000)
        ACCESS   read-only
        STATUS   mandatory
	DESCRIPTION
	  "NAME = ;
	   DESC = The negotiated Rx committed burst to \
		  be received on this interface (in bits/sec).; 
	   HELP =;
	   CAPABILITIES = ;"
::= { mcmFrSVCCircuitEntry 22 }


mcmFrSVCCircuitNegTxExcess OBJECT-TYPE
        SYNTAX   INTEGER (0..2560000)
        ACCESS   read-only
        STATUS   mandatory
	DESCRIPTION
	  "NAME = ;
	   DESC = The negotiated Tx excess burst to \
		  be sent on this interface (in bits/sec).; 
	   HELP =;
	   CAPABILITIES = ;"
::= { mcmFrSVCCircuitEntry 23 }


mcmFrSVCCircuitNegRxExcess OBJECT-TYPE
        SYNTAX   INTEGER (0..2560000)
        ACCESS   read-only
        STATUS   mandatory
	DESCRIPTION
	  "NAME = ;
	   DESC = The negotiated Rx excess burst to \
		  be received on this interface (in bits/sec).; 
	   HELP =;
	   CAPABILITIES = ;"
::= { mcmFrSVCCircuitEntry 24 }


mcmFrSVCCircuitTxDiscardCIRPolice OBJECT-TYPE
        SYNTAX   Counter
        ACCESS   read-only
        STATUS   mandatory
	DESCRIPTION
	  "NAME = ;
	   DESC = The number of packets that have been discarded \
		  due to policing of the CIR.; 
	   HELP =;
	   CAPABILITIES = ;"
::= { mcmFrSVCCircuitEntry 25 }


mcmFrSVCCircuitPriority OBJECT-TYPE
        SYNTAX   INTEGER (0..15)
        ACCESS   read-only
        STATUS   mandatory
	DESCRIPTION
	  "NAME = ;
	   DESC = The transfer priority used for connection \
		  setup of this SVC.; 
	   HELP =;
	   CAPABILITIES = ;"
::= { mcmFrSVCCircuitEntry 26 }


mcmFrSVCCircuitSvcIfIndex OBJECT-TYPE
        SYNTAX   INTEGER 
        ACCESS   read-only
        STATUS   mandatory
	DESCRIPTION
	  "NAME = ;
	   DESC = For Software releases beginning with R3.0, \
		  this object indicates the ifIndex of the tunneling \
		  PVC in which the SVC is established.  Prior to \
		  R3.0, this object indicates the physical interface \
		  this SVC DLCI is assoiciated with.;
	   HELP = ;
	   CAPABILITIES = ;"
::= { mcmFrSVCCircuitEntry 27 }

mcmFrSVCCircuitDiscardPriority OBJECT-TYPE
        SYNTAX INTEGER {
           low-discard-level     (1),
           medium-discard-level  (2),
           high-discard-level    (3)
           }
        ACCESS read-only
        STATUS mandatory
        DESCRIPTION
	  "NAME = ;
	   DESC = The discard priority used for SVC circuit \
                  connection setup of this SVC map.; 
	   HELP = ;
	   CAPABILITIES = ;"
	::=  { mcmFrSVCCircuitEntry 28 }

mcmFrSVCCircuitSetupPriority OBJECT-TYPE
        SYNTAX INTEGER (1..5)
	ACCESS	read-only
	STATUS	mandatory
	DESCRIPTION
	  "NAME = ;
           DESC = This object indicates the priority of a path at \
		  call-establishment time, and also determines \
		  the potential for bumping established paths \
		  to acquire their bandwidth.  A value of 1 is \
		  the highest priority, and 5 is the lowest.;
           HELP = ;
	   CAPABILITIES = ;"
	::= {mcmFrSVCCircuitEntry 29}

mcmFrSVCCircuitHoldingPriority OBJECT-TYPE
        SYNTAX INTEGER (1..5)
	ACCESS	read-only
	STATUS	mandatory
	DESCRIPTION
	  "NAME = ;
           DESC = This object indicates the priority that a path \
		  maintains once the path is established, and \
		  also determines the likelihood of being bumped \
		  by a new path, thus losing the bandwidth.  A value \
		  of 1 is the highest priority, and 5 is the lowest.;
           HELP = ;
	   CAPABILITIES = ;"
	::= {mcmFrSVCCircuitEntry 30}



--   All SVC Circuit Parameters Table

     -- The table describing the use of the SVC DLCIs attached to
     -- each Frame Relay Interface (for all SVCs).  This table has been
     -- added for the access device 1.1 release, and may replace the previous
     -- FR SVC Circuit table in future access device releases.

mcmFrAllSVCCircuitTable OBJECT-TYPE
        SYNTAX   SEQUENCE OF McmFrAllCircuitEntry
        ACCESS   not-accessible
        STATUS   mandatory
	DESCRIPTION
	  "NAME = ;
	   DESC = Table of entries for all SVCs on this \
		  access device.;
	   HELP = A table containing information \
		  about specific SVC DLCIs;
	   CAPABILITIES = NET_CFG, VPN_DISP;"
         ::= { fr-configuration 17}

mcmFrAllSVCCircuitEntry OBJECT-TYPE
        SYNTAX   McmFrAllCircuitEntry
        ACCESS   not-accessible
        STATUS   mandatory
	DESCRIPTION
	  "NAME = ;
	   DESC = The information regarding a \
		  single, established SVC DLCI;
	   HELP = ;
	   CAPABILITIES = ;"
           INDEX { mcmFrAllSVCCircuitIfIndex, mcmFrAllSVCCircuitDlci }
            ::= { mcmFrAllSVCCircuitTable 1 }


         McmFrAllCircuitEntry ::= SEQUENCE {
                 mcmFrAllSVCCircuitIfIndex 		INTEGER,
                 mcmFrAllSVCCircuitDlci 		INTEGER,
                 mcmFrAllSVCCircuitType 		INTEGER,
                 mcmFrAllSVCCircuitDNA 			OCTET STRING,
                 mcmFrAllSVCCircuitState 		INTEGER,
                 mcmFrAllSVCCircuitReceivedFECNs 	Counter,
                 mcmFrAllSVCCircuitReceivedBECNs 	Counter,
                 mcmFrAllSVCCircuitSentFrames 		Counter,
                 mcmFrAllSVCCircuitSentOctets 		Counter,
                 mcmFrAllSVCCircuitReceivedFrames 	Counter,
                 mcmFrAllSVCCircuitReceivedOctets 	Counter,
                 mcmFrAllSVCCircuitCreationTime 	TimeTicks,
                 mcmFrAllSVCCircuitCallOriginator 	OCTET STRING,
                 mcmFrAllSVCCircuitLastTimeChange 	TimeTicks,
                 mcmFrAllSVCCircuitCommittedBurst 	INTEGER,
                 mcmFrAllSVCCircuitExcessBurst 		INTEGER,
                 mcmFrAllSVCCircuitThroughput 		INTEGER,
                 mcmFrAllSVCCircuitNegMaxTxSize		INTEGER,
                 mcmFrAllSVCCircuitNegMaxRxSize		INTEGER,
                 mcmFrAllSVCCircuitNegTxThroughput	INTEGER,
                 mcmFrAllSVCCircuitNegRxThroughput	INTEGER,
                 mcmFrAllSVCCircuitNegTxBurst 		INTEGER,
                 mcmFrAllSVCCircuitNegRxBurst 		INTEGER,
                 mcmFrAllSVCCircuitNegTxExcess 		INTEGER,
                 mcmFrAllSVCCircuitNegRxExcess 		INTEGER,
                 mcmFrAllSVCCircuitTxDiscardCIRPolice	Counter,
                 mcmFrAllSVCCircuitPriority 		INTEGER,
                 mcmFrAllSVCCircuitSvcIfIndex           INTEGER,
                 mcmFrAllSVCCircuitDiscardPriority      INTEGER,
                 mcmFrAllSVCCircuitSetupPriority      	INTEGER,
                 mcmFrAllSVCCircuitHoldingPriority      INTEGER
         }



mcmFrAllSVCCircuitIfIndex OBJECT-TYPE
        SYNTAX   INTEGER (1..255)
        ACCESS   read-only
        STATUS   mandatory
	DESCRIPTION
	  "NAME = ;
	   DESC = The ifIndex Value of the ifEntry \
		  this SVC virtual circuit is 
		  associated with;
	   HELP = ;
	   CAPABILITIES = ;"
            ::= { mcmFrAllSVCCircuitEntry 1 }


mcmFrAllSVCCircuitDlci OBJECT-TYPE
        SYNTAX   INTEGER (16..991)
        ACCESS   read-only
        STATUS   mandatory
	DESCRIPTION
	  "NAME = ;
	   DESC = The local DLCI for this SVC, valid \
		  only when the connection has been \
		  established;
	   HELP = ;
	   CAPABILITIES = ;"
            REFERENCE
               "Draft American National  Standard  T1.618-1991,
               Section 3.3.6"
           ::= { mcmFrAllSVCCircuitEntry 2 }


mcmFrAllSVCCircuitType OBJECT-TYPE
        SYNTAX   INTEGER {
		rfc1490 (1),
		voice (2),
		switched (3),
		rfc1490switched (4)
		}
        ACCESS   read-only
        STATUS   mandatory
	DESCRIPTION
	  "NAME = ;
	   DESC = The type of this SVC.;
	   HELP = Valid types include voice, switched or \
		  rfc1490;
	   CAPABILITIES = ;"
::= { mcmFrAllSVCCircuitEntry 3 }


mcmFrAllSVCCircuitDNA OBJECT-TYPE
        SYNTAX   OCTET STRING (SIZE(1..34))
        ACCESS   read-only
        STATUS   mandatory
	DESCRIPTION
	  "NAME = ;
	   DESC = DNA of the destination node associated \
		  with the SVC;
	   HELP = ;
	   CAPABILITIES = ;"
            ::= { mcmFrAllSVCCircuitEntry 4 }


mcmFrAllSVCCircuitState OBJECT-TYPE
        SYNTAX   INTEGER {
                 invalid (1),
                 active (2),
                 inactive (3)
                      }
        ACCESS   read-only
        STATUS   mandatory
	DESCRIPTION
	  "NAME = ;
	   DESC = Indication for the state of this SVC (active \
		  or inactive).;
	   HELP = Only the configured SVCs \
		  can be in the inactive state (all learned \
		  SVCs will be deleted when the connection \
		  has been released);
	   CAPABILITIES = ;"
            DEFVAL { active }
            ::= { mcmFrAllSVCCircuitEntry 5 }


mcmFrAllSVCCircuitReceivedFECNs OBJECT-TYPE
        SYNTAX   Counter
        ACCESS   read-only
        STATUS   mandatory
	DESCRIPTION
	  "NAME = ;
	   DESC = Number of frames received from \
		  the network indicating forward \
		  congestion since this switched \
		  virtual circuit was created;
	   HELP = Number of Frame Relay Packets \
		  received on the corresponding \
		  DLCI with the Forward congestion \
		  bit set;
	   CAPABILITIES = ;"
            REFERENCE
               "Draft American National  Standard  T1.618-1991, Section 3.3.3"
           ::= { mcmFrAllSVCCircuitEntry 6 }



mcmFrAllSVCCircuitReceivedBECNs OBJECT-TYPE
        SYNTAX   Counter
        ACCESS   read-only
        STATUS   mandatory
	DESCRIPTION
	  "NAME = ;
	   DESC = Number of frames received from \
		  the network indicating backward \	
		  congestion since this switched \
		  virtual circuit was created;
	   HELP = Number of Frame Relay Packets received \
		  on the corresponding interface with the \
		  backward congestion bit set.;
	   CAPABILITIES = ;"
            REFERENCE
               "Draft American National  Standard  T1.618-1991, Section 3.3.4"
           ::= { mcmFrAllSVCCircuitEntry 7 }



mcmFrAllSVCCircuitSentFrames OBJECT-TYPE
        SYNTAX   Counter
        ACCESS   read-only
        STATUS   mandatory
	DESCRIPTION
	  "NAME = ;
	   DESC = The number of frames sent from \
		  this switched virtual circuit \
		  since this counter was last \
		  reset;
	   HELP = Number of Frame Relay Packets sent \
		  on the corresponding SVC since this \
		  counter was last reset (either by \
		  reboot of access device or a counter reset \
		  initiated by a user...Note that \
		  user initiated counter resets have been OBSOLETED \
		  for software releases beginning with Release 3.0.);
	   CAPABILITIES = ;"
            ::= { mcmFrAllSVCCircuitEntry 8 }



mcmFrAllSVCCircuitSentOctets OBJECT-TYPE
        SYNTAX   Counter
        ACCESS   read-only
        STATUS   mandatory
	DESCRIPTION
	  "NAME = ;
	   DESC = The number of octets sent from \
		  this switched virtual circuit since \
		  it was last created or reset;
	   HELP = Number of bytes sent on the \
		  corresponding SVC since this counter \
		  was last reset (either by reboot of access device \
		  or a counter reset initiated by a user...Note that \
		  user initiated counter resets have been OBSOLETED \
		  for software releases beginning with Release 3.0.);
	   CAPABILITIES = ;"
            ::= { mcmFrAllSVCCircuitEntry 9 }



mcmFrAllSVCCircuitReceivedFrames OBJECT-TYPE
        SYNTAX   Counter
        ACCESS   read-only
        STATUS   mandatory
	DESCRIPTION
	  "NAME = ;
	   DESC = Number of frames received over \
		  this virtual circuit since it \
		  was created or the counter was \
		  last reset;
	   HELP = Reset may occur either by reboot \
		  or a counter reset initiated by a user...Note that \
		  user initiated counter resets have been OBSOLETED \
		  for software releases beginning with Release 3.0.;
	   CAPABILITIES = ;"
            ::= { mcmFrAllSVCCircuitEntry 10 }



mcmFrAllSVCCircuitReceivedOctets OBJECT-TYPE
        SYNTAX   Counter
        ACCESS   read-only
        STATUS   mandatory
	DESCRIPTION
	  "NAME = ;
	   DESC = Number of octets received  over \
		  this virtual circuit since it \
		  was created or the counter was \
		  last reset;
	   HELP = Reset may occur either by reboot \
		  or a counter reset initiated by a user...Note that \
		  user initiated counter resets have been OBSOLETED \
		  for software releases beginning with Release 3.0.;
	   CAPABILITIES = ;"
            ::= { mcmFrAllSVCCircuitEntry 11 }


mcmFrAllSVCCircuitCreationTime OBJECT-TYPE
        SYNTAX   TimeTicks
        ACCESS   read-only
        STATUS   mandatory
	DESCRIPTION
	  "NAME = ;
	   DESC = The value of sysUpTime when the \
		  switched virtual circuit was \
		  created;
	   HELP = The sysUpTime when the SVC was created \
		  either at bootup time or when the SVC \
		  was set up through Q.933, whether by the Data \
		  Link Connection Management Interface or \
		  by a SetRequest;
	   CAPABILITIES = ;"
            ::= { mcmFrAllSVCCircuitEntry 12 }

mcmFrAllSVCCircuitCallOriginator OBJECT-TYPE
        SYNTAX   OCTET STRING (SIZE(1..34))
        ACCESS   read-only
        STATUS   mandatory
	DESCRIPTION
	  "NAME = ;
	   DESC = DNA of the node that originated \
		  the call that resulted in \
		  the establishment of the SVC;
	   HELP = ;
	   CAPABILITIES = ;"
            ::= { mcmFrAllSVCCircuitEntry 13 }



mcmFrAllSVCCircuitLastTimeChange OBJECT-TYPE
        SYNTAX   TimeTicks
        ACCESS   read-only
        STATUS   mandatory
	DESCRIPTION
	  "NAME = ;
	   DESC = The value of sysUpTime when last 
		  there was a change in the SVC;
	   HELP = SVCs established by the remote will set \
		  the last time change to the creation time;
	   CAPABILITIES = ;"
            ::= { mcmFrAllSVCCircuitEntry 14 }



mcmFrAllSVCCircuitCommittedBurst OBJECT-TYPE
        SYNTAX   INTEGER (0..2560000)
        ACCESS   read-only
        STATUS   deprecated
	DESCRIPTION
	  "NAME = ;
	   DESC = *******NOTE: THIS OBJECT IS DEPRECATED******* \
                  This information is redundant. This object has been \  
                  replaced by mcmFrAllSVCCircuitNedTxThroughput and \
                  mcmAllFrCircuitNexRxThroughput which are objects \
                  from this same table(mcmFrAllSVCCircuitTable).;\


	          Maximum amount of data that the network agrees \
		  transfer under normal conditions over a set \
		  measurement interval.;
	   HELP = The maximum rate at which the network \
		  agrees to transfer under normal (non- \
		  congested) conditions (expressed in bits \
		  per second).;
	   CAPABILITIES = ;"
            REFERENCE
               "Draft American National  Standard  T1.617-1991,
               Section 6.5.19"
           DEFVAL   { 0 }  -- the default indicates no commitment
           ::= { mcmFrAllSVCCircuitEntry 15 }



mcmFrAllSVCCircuitExcessBurst OBJECT-TYPE
        SYNTAX   INTEGER (0..2560000)
        ACCESS   read-only
        STATUS   deprecated
	DESCRIPTION
	  "NAME = ;
	   DESC = *******NOTE: THIS OBJECT IS DEPRECATED******* \
                  This information is redundant. This object has been \  
                  replaced by mcmFrAllSVCCircuitNedTxThroughput and \
                  mcmAllFrCircuitNexRxThroughput which are objects \
                  from this same table(mcmFrAllSVCCircuitTable).;\

	          The maximum number of uncommited bits \
		  that the frame relay network will attempt \
		  to deliver (expressed in bits per second).; \
	   HELP = By default, if not configured when \
		  creating the entry, the Excess \
		  information Burst Size is set \
		  to the value of ifSpeed;
	   CAPABILITIES = ;"
            REFERENCE
               "Draft American National  Standard  T1.617-1991, Section 6.5.19"
                   ::= { mcmFrAllSVCCircuitEntry 16 }



mcmFrAllSVCCircuitThroughput OBJECT-TYPE
        SYNTAX   INTEGER (0..2560000)
        ACCESS read-only 
        STATUS   mandatory
	DESCRIPTION
	  "NAME = ;
	   DESC = The average number of 'Frame Relay \
		  Information Field' bits transferred \
		  per second across a physical frame relay \
		  interface.;
	   HELP = Throughput is the average number of \
		  'Frame Relay Information  Field'  \
		  bits  transferred per second across a \
		  user network interface  in  one \
		  direction, measured over the set \
		  measurement interval. If the  configured \
		  commited burst  rate  and throughput  \
		  are both non-zero, the measurement interval \
		  T=mcmFrAllSVCCircuitCommittedBurst/mcmFrSVC- \
		  CircuitThroughput. If the  configured  \
		  committed  burst  rate  and throughput  are  \
		  both zero, the measurement interval\
                  T=mcmFrAllSVCCircuitExcessBurst/ifSpeed;
	   CAPABILITIES = ;"
            REFERENCE
               "Draft American National  Standard  T1.617-1991, Section 6.5.19"
           DEFVAL {0}  -- the default value of Throughput is "no commitment".
           ::= { mcmFrAllSVCCircuitEntry 17 }


mcmFrAllSVCCircuitNegMaxTxSize OBJECT-TYPE
        SYNTAX   INTEGER (0..4096)
        ACCESS   read-only
        STATUS   mandatory
	DESCRIPTION
	  "NAME = ;
	   DESC = The negotiated maximum Tx size to \
		  be sent on this interface (in bytes).; 
	   HELP =;
	   CAPABILITIES = ;"
::= { mcmFrAllSVCCircuitEntry 18 }


mcmFrAllSVCCircuitNegMaxRxSize OBJECT-TYPE
        SYNTAX   INTEGER (0..4096)
        ACCESS   read-only
        STATUS   mandatory
	DESCRIPTION
	  "NAME = ;
	   DESC = The negotiated maximum Rx size to \
		  be received on this interface (in bytes).; 
	   HELP =;
	   CAPABILITIES = ;"
::= { mcmFrAllSVCCircuitEntry 19 }


mcmFrAllSVCCircuitNegTxThroughput OBJECT-TYPE
        SYNTAX   INTEGER (0..2560000)
        ACCESS   read-only
        STATUS   mandatory
	DESCRIPTION
	  "NAME = ;
	   DESC = The negotiated Tx throughput to \
		  be sent on this interface (in bits/sec).; 
	   HELP =;
	   CAPABILITIES = ;"
::= { mcmFrAllSVCCircuitEntry 20 }


mcmFrAllSVCCircuitNegRxThroughput OBJECT-TYPE
        SYNTAX   INTEGER (0..2560000)
        ACCESS   read-only
        STATUS   mandatory
	DESCRIPTION
	  "NAME = ;
	   DESC = The negotiated Rx throughput to \
		  be received on this interface (in bits/sec).; 
	   HELP =;
	   CAPABILITIES = ;"
::= { mcmFrAllSVCCircuitEntry 21 }


mcmFrAllSVCCircuitNegTxBurst OBJECT-TYPE
        SYNTAX   INTEGER (0..2560000)
        ACCESS   read-only
        STATUS   mandatory
	DESCRIPTION
	  "NAME = ;
	   DESC = The negotiated Tx committed burst to \
		  be sent on this interface (in bits/sec).; 
	   HELP =;
	   CAPABILITIES = ;"
::= { mcmFrAllSVCCircuitEntry 22 }


mcmFrAllSVCCircuitNegRxBurst OBJECT-TYPE
        SYNTAX   INTEGER (0..2560000)
        ACCESS   read-only
        STATUS   mandatory
	DESCRIPTION
	  "NAME = ;
	   DESC = The negotiated Rx committed burst to \
		  be received on this interface (in bits/sec).; 
	   HELP =;
	   CAPABILITIES = ;"
::= { mcmFrAllSVCCircuitEntry 23 }


mcmFrAllSVCCircuitNegTxExcess OBJECT-TYPE
        SYNTAX   INTEGER (0..2560000)
        ACCESS   read-only
        STATUS   mandatory
	DESCRIPTION
	  "NAME = ;
	   DESC = The negotiated Tx excess burst to \
		  be sent on this interface (in bits/sec).; 
	   HELP =;
	   CAPABILITIES = ;"
::= { mcmFrAllSVCCircuitEntry 24 }


mcmFrAllSVCCircuitNegRxExcess OBJECT-TYPE
        SYNTAX   INTEGER (0..2560000)
        ACCESS   read-only
        STATUS   mandatory
	DESCRIPTION
	  "NAME = ;
	   DESC = The negotiated Rx excess burst to \
		  be received on this interface (in bits/sec).; 
	   HELP =;
	   CAPABILITIES = ;"
::= { mcmFrAllSVCCircuitEntry 25 }


mcmFrAllSVCCircuitTxDiscardCIRPolice OBJECT-TYPE
        SYNTAX   Counter
        ACCESS   read-only
        STATUS   mandatory
	DESCRIPTION
	  "NAME = ;
	   DESC = The number of packets that have been discarded \
		  due to policing of the CIR.; 
	   HELP =;
	   CAPABILITIES = ;"
::= { mcmFrAllSVCCircuitEntry 26 }


mcmFrAllSVCCircuitPriority OBJECT-TYPE
        SYNTAX   INTEGER (0..15)
        ACCESS   read-only
        STATUS   mandatory
	DESCRIPTION
	  "NAME = ;
	   DESC = The transfer priority used for connection \
		  setup of this SVC.; 
	   HELP = Valid priorities are 0 (LAN), 6 (NMSNAS) \
		  and 11 (voice);
	   CAPABILITIES = ;"
::= { mcmFrAllSVCCircuitEntry 27 }


mcmFrAllSVCCircuitSvcIfIndex OBJECT-TYPE
        SYNTAX   INTEGER 
        ACCESS   read-only
        STATUS   mandatory
	DESCRIPTION
	  "NAME = ;
	   DESC = For Software releases beginning with R3.0, \
		  this object indicates the ifIndex of the tunneling \
		  PVC in which the SVC is established.  Prior to \
		  R3.0, this object indicates the physical interface \
		  this SVC DLCI is assoiciated with.;
	   HELP = ;
	   CAPABILITIES = ;"
::= { mcmFrAllSVCCircuitEntry 28 }


mcmFrAllSVCCircuitDiscardPriority OBJECT-TYPE
        SYNTAX INTEGER {
           low-discard-level     (1),
           medium-discard-level  (2),
           high-discard-level    (3)
           }
        ACCESS read-write
        STATUS mandatory
        DESCRIPTION
	  "NAME = ;
	   DESC = The discard priority used in \
                  setting the SVC circuit.; 
	   HELP = ;
	   CAPABILITIES = ;"
::=  { mcmFrAllSVCCircuitEntry 29 }


mcmFrAllSVCCircuitSetupPriority OBJECT-TYPE
        SYNTAX INTEGER (1..5)
	ACCESS	read-only
	STATUS	mandatory
	DESCRIPTION
	  "NAME = ;
           DESC = This object indicates the priority of a path at \
		  call-establishment time, and also determines \
		  the potential for bumping established paths \
		  to acquire their bandwidth.  A value of 1 is \
		  the highest priority, and 5 is the lowest.;
           HELP = ;
	   CAPABILITIES = ;"
	::= {mcmFrAllSVCCircuitEntry 30}


mcmFrAllSVCCircuitHoldingPriority OBJECT-TYPE
        SYNTAX INTEGER (1..5)
	ACCESS	read-only
	STATUS	mandatory
	DESCRIPTION
	  "NAME = ;
           DESC = This object indicates the priority that a path \
		  maintains once the path is established, and \
		  also determines the likelihood of being bumped \
		  by a new path, thus losing the bandwidth.  A value \
		  of 1 is the highest priority, and 5 is the lowest.;
           HELP = ;
	   CAPABILITIES = ;"
	::= {mcmFrAllSVCCircuitEntry 31}



-- This table provides the fields necessary for viewing
-- the status of LAN SPVC (for MPA/PP LAN Interworking)
-- mappings.

mcmFrLANSpvcTable OBJECT-TYPE
        SYNTAX SEQUENCE OF McmFrLANSpvcEntry
        ACCESS not-accessible
        STATUS mandatory
        DESCRIPTION
          "NAME = ;
           DESC = The Frame Relay LAN SPVC Connections \
                  table(Operational);
           HELP = ;
           CAPABILITIES =NET_CFG, VPN_CFG;"
         ::= {fr-configuration 18}

mcmFrLANSpvcEntry OBJECT-TYPE
        SYNTAX   McmFrLANSpvcEntry
        ACCESS   not-accessible
        STATUS   mandatory
	DESCRIPTION
	  "NAME = ;
	   DESC = An entry in the Frame Relay LAN SPVC \
                  Connections table. (Operational);
           HELP = ;
	   CAPABILITIES = ;"
           INDEX { mcmFrLANSpvcVirtualPortIfIndex, mcmFrLANSpvcRemoteDLCI }
            ::= { mcmFrLANSpvcTable 1 }

 
McmFrLANSpvcEntry ::= SEQUENCE {
           mcmFrLANSpvcVirtualPortIfIndex   INTEGER,
           mcmFrLANSpvcRemoteDLCI           INTEGER,
           mcmFrLANSpvcConnectId            INTEGER,
           mcmFrLANSpvcRemoteDNA            DisplayString,
           mcmFrLANSpvcDLCI                 INTEGER,
           mcmFrLANSpvcIfIndex              INTEGER,
           mcmFrLANSpvcVPState              INTEGER,
           mcmFrLANSpvcSVCState             INTEGER,
           mcmFrLANSpvcConnType             INTEGER,
           mcmFrLANSpvcLastChange           TimeTicks,
           mcmFrLANSpvcDisconnectReason     INTEGER
          }

mcmFrLANSpvcVirtualPortIfIndex OBJECT-TYPE
	SYNTAX	INTEGER (1..255)
	ACCESS	read-only
	STATUS	mandatory
	DESCRIPTION
	  "NAME = ;
           DESC = The ifIndex of the local Virtual Port \
                  (Analogous to the ifIndex pointer in the \
                  MIB II Interfaces Group, but specific to \
                  the FR End-to-End Connections table.)
                  (Operationsl);
           HELP = ; 
	   CAPABILITIES = ;"
	::= {mcmFrLANSpvcEntry 1}

mcmFrLANSpvcRemoteDLCI OBJECT-TYPE
	SYNTAX	INTEGER (16..991)
	ACCESS	read-only
	STATUS	mandatory
	DESCRIPTION
	  "NAME = ;
           DESC = The DLCI value on the remote DCE interface.
           HELP = ;
	   CAPABILITIES = ;"
	::= {mcmFrLANSpvcEntry 2}

mcmFrLANSpvcConnectId OBJECT-TYPE
	SYNTAX	INTEGER (0..65535)
	ACCESS	read-only
	STATUS	mandatory
	DESCRIPTION
	  "NAME = ;
           DESC = The connect ID of this SPVC mapping.\
                  Used to associate SVCs and Connect \
                  mappings.(Operational)
           HELP = ;
	   CAPABILITIES = ;"
	::= {mcmFrLANSpvcEntry 3}

mcmFrLANSpvcRemoteDNA OBJECT-TYPE
	SYNTAX	DisplayString (SIZE(1..34))
	ACCESS	read-only
	STATUS	mandatory
	DESCRIPTION
	  "NAME = ;
           DESC = The DNA of the remote node with which \
                  the SVC will be established. (Operational);
           HELP = ;
	   CAPABILITIES = ;"
	::= {mcmFrLANSpvcEntry 4}

mcmFrLANSpvcDLCI OBJECT-TYPE
	SYNTAX	INTEGER (16..991)
	ACCESS	read-only
	STATUS	mandatory
	DESCRIPTION
	  "NAME = ;
           DESC = The DLCI value of the SVC once \
                  the SVC has been established.
                  (Operational);
           HELP = ;
	   CAPABILITIES = ;"
	::= {mcmFrLANSpvcEntry 5}

mcmFrLANSpvcIfIndex OBJECT-TYPE
	SYNTAX	INTEGER (1..255)
	ACCESS	read-only
	STATUS	mandatory
	DESCRIPTION
	  "NAME = ;
           DESC = For Software releases beginning with R3.0, \
		  this object indicates the ifIndex of the tunneling \
		  PVC in which the SVC is established.  Prior to \
		  R3.0, this object indicates the ifIndex used for the \
		  SVC connection. (Operational)
           HELP = ;
	   CAPABILITIES = ;"
	::= {mcmFrLANSpvcEntry 6}

mcmFrLANSpvcVPState OBJECT-TYPE
	SYNTAX	INTEGER {
                active   (1),
                inactive (2)
                }
	ACCESS	read-only
	STATUS	mandatory
	DESCRIPTION
	  "NAME = ;
           DESC = The value of this object indicates \
                  whether the local Virtual Port with \
                  this mapping is active or inactive. \
                  (Operational);
           HELP = ;
	   CAPABILITIES = ;"
	::= {mcmFrLANSpvcEntry 7}

mcmFrLANSpvcSVCState OBJECT-TYPE
	SYNTAX	INTEGER {
                active   (1),
                inactive (2)
                }
	ACCESS	read-only
	STATUS	mandatory
	DESCRIPTION
	  "NAME = ;
           DESC = The value of this object indicates \
                  whether the local DCE considers the \
                  SVC associated with this mapping \
                  active or inactive.(Operational); 
           HELP = ;
	   CAPABILITIES = ;"
	::= {mcmFrLANSpvcEntry 8}

mcmFrLANSpvcConnType OBJECT-TYPE
	SYNTAX	INTEGER { 
                slave  (1),
                master (2)
                }
	ACCESS	read-only
	STATUS	mandatory
	DESCRIPTION
	  "NAME = ;
           DESC =  The value of this object indicates \
                   whether this end of the SPVC segment \
                   initiated the SVC call.;
           HELP = ;
	   CAPABILITIES = ;"
	::= {mcmFrLANSpvcEntry 9}

mcmFrLANSpvcLastChange OBJECT-TYPE
	SYNTAX	TimeTicks
	ACCESS	read-only
	STATUS	mandatory
	DESCRIPTION
	  "NAME = ;
           DESC = The value of MIB II's sysUpTime at \
                  the time this SVC mapping entered \
                  its current operations state the \
                  high to low direction;
           HELP = ;
	   CAPABILITIES = ;"
	::= {mcmFrLANSpvcEntry 10}

mcmFrLANSpvcDisconnectReason OBJECT-TYPE
	SYNTAX	INTEGER {
                local-VP-is-down           (1),
                local-SVC-LMI-is-Down      (2),
                remote-PVC-LMI-is-down     (3),
                the-SVC-connection-is-down (4)
                }
	ACCESS	read-only
	STATUS	mandatory
	DESCRIPTION
	  "NAME = ;
           DESC = The value of this object indicates \
                  the reason why the SPVC is not \
                  active. (Operational); 
           HELP = ;
	   CAPABILITIES = ;"
	::= {mcmFrLANSpvcEntry 11}


-- This table provides the information to identify the traffic
-- parameters for a bi-directional SVC segment

mcmFrLANSpvcSVCTable OBJECT-TYPE
        SYNTAX SEQUENCE OF McmFrLANSpvcSVCEntry 
        ACCESS not-accessible
        STATUS mandatory
        DESCRIPTION
          "NAME = ;
           DESC = The Frame Relay SVC Connect (Switched) \
                  Segment Configuration table.
           HELP = ;
           CAPABILITIES =NET_CFG, VPN_CFG;"
            ::= {fr-configuration 19}

mcmFrLANSpvcSVCEntry OBJECT-TYPE
        SYNTAX   McmFrLANSpvcSVCEntry
        ACCESS   not-accessible
        STATUS   mandatory
	DESCRIPTION
	  "NAME = ;
	   DESC = An entry in the Frame Relay LAN SPVC \
                  Connections table.;
           HELP = ;
	   CAPABILITIES = ;"
           INDEX { mcmFrLANSpvcSVCConnectId }
            ::= { mcmFrLANSpvcSVCTable 1 }
 
McmFrLANSpvcSVCEntry ::= SEQUENCE {
           mcmFrLANSpvcSVCConnectId                    INTEGER,
           mcmFrLANSpvcSVCIfIndex                      INTEGER,
           mcmFrLANSpvcSVCDNA                          DisplayString,
           mcmFrLANSpvcSVCDLCI                         INTEGER,
           mcmFrLANSpvcSVCMaxTxSize                    INTEGER,
           mcmFrLANSpvcSVCMaxRxSize                    INTEGER,
           mcmFrLANSpvcSVCMinTxThroughput              INTEGER,
           mcmFrLANSpvcSVCMinRxThroughput              INTEGER,
           mcmFrLANSpvcSVCMaxTxThroughput              INTEGER,
           mcmFrLANSpvcSVCMaxRxThroughput              INTEGER,
           mcmFrLANSpvcSVCMaxTxBurstSize               INTEGER,
           mcmFrLANSpvcSVCMaxRxBurstSize               INTEGER,
           mcmFrLANSpvcSVCExcessTxBurstSize            INTEGER,
           mcmFrLANSpvcSVCExcessRxBurstSize            INTEGER,
           mcmFrLANSpvcSVCTransferPriority             INTEGER,
           mcmFrLANSpvcSVCReasonForDisconnect          INTEGER,
           mcmFrLANSpvcSVCDiscardPriority              INTEGER,
           mcmFrLANSpvcSVCSetupPriority		       INTEGER,
           mcmFrLANSpvcSVCHoldingPriority  	       INTEGER
          }

mcmFrLANSpvcSVCConnectId OBJECT-TYPE
	SYNTAX	INTEGER (1..65535)
	ACCESS	read-only
	STATUS	mandatory
	DESCRIPTION
	  "NAME = ;
           DESC = The Connect Id of the Connection \
                  group entry to which this SVC \
		  belongs.
           HELP = ;
	   CAPABILITIES = ;"
	::= {mcmFrLANSpvcSVCEntry 1}

mcmFrLANSpvcSVCIfIndex OBJECT-TYPE
	SYNTAX	INTEGER (1..255)
	ACCESS	read-only
	STATUS	mandatory
	DESCRIPTION
	  "NAME = ;
           DESC = For Software releases beginning with R3.0, \
		  this object indicates the ifIndex of the tunneling \
		  PVC in which the SVC is established.  Prior to \
		  R3.0, this object indicates the ifIndex of the local \
		  frame relay physical line interface.
           HELP = ;
	   CAPABILITIES = ;"
	::= {mcmFrLANSpvcSVCEntry 2}

mcmFrLANSpvcSVCDNA OBJECT-TYPE
	SYNTAX	DisplayString (SIZE(1..34))
	ACCESS	read-only
	STATUS	mandatory
	DESCRIPTION
	  "NAME = ;
           DESC = The DNA for the destination of \
                  the virtual circuit.;
           HELP = ;
	   CAPABILITIES = ;"
	::= {mcmFrLANSpvcSVCEntry 3}

mcmFrLANSpvcSVCDLCI OBJECT-TYPE
	SYNTAX	INTEGER (16..991)
	ACCESS	read-only
	STATUS	mandatory
	DESCRIPTION
	  "NAME = ;
           DESC = The local DLCI for this SVC. \
                  Valid only when the SVC is \
                  established. ;
           HELP = ;
	   CAPABILITIES = ;"
	::= {mcmFrLANSpvcSVCEntry 4}

mcmFrLANSpvcSVCMaxTxSize OBJECT-TYPE
	SYNTAX	INTEGER (0..4096)
	ACCESS	read-only
	STATUS	mandatory
	DESCRIPTION
	  "NAME = ;
           DESC = The maximum transmission frame size. \
                  This should be equal to (or greater \
                  than) the Rx size for the corresponding \
                  PVC. Expressed in bytes.; 
           HELP = ;
	   CAPABILITIES = ;"
	::= {mcmFrLANSpvcSVCEntry 5}

mcmFrLANSpvcSVCMaxRxSize OBJECT-TYPE
	SYNTAX	INTEGER (0..4096)
	ACCESS	read-only
	STATUS	mandatory
	DESCRIPTION
	  "NAME = ;
           DESC = The maximum receivable frame size. \
                  This should be equal to (or less than) \
                  the Tx size for the corresponding PVC. \
                  Expressed in bytes.;
           HELP = ;
	   CAPABILITIES = ;"
	::= {mcmFrLANSpvcSVCEntry 6}

mcmFrLANSpvcSVCMinTxThroughput OBJECT-TYPE
	SYNTAX	INTEGER (0..2560000)
	ACCESS	read-only
	STATUS	mandatory
	DESCRIPTION
	  "NAME = ;
           DESC = The minimum transmission throughput. \
                  This should be equal to (or greater than) \
                  the Rx CIR for the corresponding PVC. \
                  Expressed in bits/sec.;
           HELP = ;
	   CAPABILITIES = ;"
	::= {mcmFrLANSpvcSVCEntry 7}

mcmFrLANSpvcSVCMinRxThroughput OBJECT-TYPE
	SYNTAX	INTEGER (0..2560000)
	ACCESS	read-only
	STATUS	mandatory
	DESCRIPTION
	  "NAME = ;
           DESC = The minimum receive throughput.\
                  This should be equal to (or less \
                  than) the Tx CIR for the corresponding \
                  PVC. Expressed in bits/sec.
           HELP = ;
	   CAPABILITIES = ;"
	::= {mcmFrLANSpvcSVCEntry 8}

mcmFrLANSpvcSVCMaxTxThroughput OBJECT-TYPE
	SYNTAX	INTEGER (0..2560000)
	ACCESS	read-only
	STATUS	mandatory
	DESCRIPTION
	  "NAME = ;
           DESC = The maximum transmission throughput.\
                  Always set to the value of \
                   mcmFrLANSpvcSVCMinTxThroughput.;
           HELP = ;
	   CAPABILITIES = ;"
	::= {mcmFrLANSpvcSVCEntry 9}

mcmFrLANSpvcSVCMaxRxThroughput OBJECT-TYPE
	SYNTAX	INTEGER (0..2560000)
	ACCESS	read-only
	STATUS	mandatory
	DESCRIPTION
	  "NAME = ;
           DESC = The maximum receive throughput. \
                  Always set to the value of \
                  mcmFrLANSpvcSVCMinRxThroughput.;
           HELP = ;
	   CAPABILITIES = ;"
	::= {mcmFrLANSpvcSVCEntry 10}

mcmFrLANSpvcSVCMaxTxBurstSize OBJECT-TYPE
	SYNTAX	INTEGER (0..2560000)
	ACCESS	read-only
	STATUS	mandatory
	DESCRIPTION
	  "NAME = ;
           DESC = The maximum transmission burst size \
                  Computation based on throughput and \
                  Excess Burst. Expressed in bits/sec.;
           HELP = ;
	   CAPABILITIES = ;"
	::= {mcmFrLANSpvcSVCEntry 11}

mcmFrLANSpvcSVCMaxRxBurstSize OBJECT-TYPE
	SYNTAX	INTEGER (0..2560000)
	ACCESS	read-only
	STATUS	mandatory
	DESCRIPTION
	  "NAME = ;
           DESC = The maximum receive burst size. \
                  Computation based on throughput and \
                  Excess Burst. Expressed in bits/sec.;
           HELP = ;
	   CAPABILITIES = ;"
	::= {mcmFrLANSpvcSVCEntry 12}

mcmFrLANSpvcSVCExcessTxBurstSize OBJECT-TYPE
	SYNTAX	INTEGER (0..2560000)
	ACCESS	read-only
	STATUS	mandatory
	DESCRIPTION
	  "NAME = ;
           DESC = The maximum number of uncommitted \
                  bits that the network will attempt \
                  to accept. This should be equal to \
                  (or greater than) the Rx Be configured for
                  the corresponding PVC. Expressed in \
                  bits/sec.;
           HELP = ;
	   CAPABILITIES = ;"
	::= {mcmFrLANSpvcSVCEntry 13}

mcmFrLANSpvcSVCExcessRxBurstSize OBJECT-TYPE
	SYNTAX	INTEGER (0..2560000)
	ACCESS	read-only
	STATUS	mandatory
	DESCRIPTION
	  "NAME = ;
           DESC = The maximum number of uncommitted bits \
                  that the network will attempt to deliver. \
                  This should be equal to (or less than) the \
                  Tx Be configured for the corresponding PVC \
                  Expressed in bits/sec.;
           HELP = ;
	   CAPABILITIES = ;"
	::= {mcmFrLANSpvcSVCEntry 14}

mcmFrLANSpvcSVCTransferPriority OBJECT-TYPE
	SYNTAX	INTEGER (0..15)
	ACCESS	read-only
	STATUS	mandatory
	DESCRIPTION
	  "NAME = ;
           DESC = The transfer priority for the corresponding \
                  pass-through connection.
                    
           HELP = ;
	   CAPABILITIES = ;"
	::= {mcmFrLANSpvcSVCEntry 15}

mcmFrLANSpvcSVCReasonForDisconnect OBJECT-TYPE
	SYNTAX	INTEGER {
		the-PVC-does-not-exist-ie-unassigned (1),
                no-route-to-specified-transit-network (2),
                no-route-to-destination (3),
                channel-unacceptable (6),
                call-awarded-and-being-delivered-in-an-est-channel (7),
                normal-call-clearing (16),
		remote-PVC-already-connected-ie-busy (17),
		no-user-present-in-call (18),
		remote-PVC-down-ie-unavailable (21),
                destination-out-of-order (27),
                invalid-number-format (28),
                facility-rejected (29),
		response-to-status-inquiry (30),
                normal-unspecified (31),
		no-DLCI-available (34),
                network-out-of-order (38),
                permanent-frame-mode-connection-out-of-service (39),
                permanent-frame-mode-connection-operational (40),
                temporary-failure (41),
                switching-equipment-congestion (42),
                access-information-discarded (43),
		specified-DLCI-unavailable (44),
		resource-unavailable (47),
                quality-of-service-not-available (49),
                requested-facility-not-subscribed (50),
                bearer-capability-not-authorized (57),
                bearer-capability-not-presently-available (58),
                service-or-option-not-available-unspecified (63),
                bearer-capability-not-implemented (65),
                channel-type-not-implemented (66),
                only-restricted-digital-capability-is-available (70),
                service-or-option-not-implemented-unspecified (79),
		invalid-call-reference (81),
                identified-channel-does-not-exist (82),
                user-not-member-of-CUG (87),
                incompatible-destination (88),
                non-existent-CUG (90),
                invalid-transit-network-selection (91),
                invalid-message-unspecified (95),
		missing-element (96),
		message-type-unknown (97),
                message-not-compatible (98),
                element-non-existent-or-not-implemented (99),
		invalid-element (100),
		invalid-message-for-state (101),
		timer-recovery (102),
                protocol-error-unspecified (111),
                interworking-unspecified (127),
                normal-condition (128)
                }
	ACCESS	read-only
	STATUS	mandatory
	DESCRIPTION
	  "NAME = ;
           DESC = The reason for the SVC Disconnect.;
           HELP = ;
	   CAPABILITIES = ;"
	::= {mcmFrLANSpvcSVCEntry 16}

mcmFrLANSpvcSVCDiscardPriority OBJECT-TYPE
        SYNTAX INTEGER {
           low-discard-level     (1),
           medium-discard-level  (2),
           high-discard-level    (3)
           }
	ACCESS	read-only
	STATUS	mandatory
	DESCRIPTION
	  "NAME = ;
           DESC = The discard priority setup for \
                  the LAN SPVC SVC.;
           HELP = ;
	   CAPABILITIES = ;"
	::= {mcmFrLANSpvcSVCEntry 17}

mcmFrLANSpvcSVCSetupPriority OBJECT-TYPE
        SYNTAX INTEGER (1..5)
	ACCESS	read-only
	STATUS	mandatory
	DESCRIPTION
	  "NAME = ;
           DESC = This object indicates the priority of a path at \
		  call-establishment time, and also determines \
		  the potential for bumping established paths \
		  to acquire their bandwidth.  A value of 1 is \
		  the highest priority, and 5 is the lowest.;
           HELP = ;
	   CAPABILITIES = ;"
	::= {mcmFrLANSpvcSVCEntry 18}

mcmFrLANSpvcSVCHoldingPriority OBJECT-TYPE
        SYNTAX INTEGER (1..5)
	ACCESS	read-only
	STATUS	mandatory
	DESCRIPTION
	  "NAME = ;
           DESC = This object indicates the priority that a path \
		  maintains once the path is established, and \
		  also determines the likelihood of being bumped \
		  by a new path, thus losing the bandwidth.  A value \
		  of 1 is the highest priority, and 5 is the lowest.;
           HELP = ;
	   CAPABILITIES = ;"
	::= {mcmFrLANSpvcSVCEntry 19}



--   Frame Relay Dlcmi SVC Status Table (Operational only)

--	This table was added to this MIB module for software releases
--	beginning with Release 3.0.

mcmFrDlcmiSVCStatusTable OBJECT-TYPE
        SYNTAX   SEQUENCE OF McmFrDlcmiSVCStatusEntry
        ACCESS   not-accessible
        STATUS   mandatory
	DESCRIPTION
	  "NAME = ;
	   DESC = Table of entries for Frame Relay Dlcmi SVC \
		  status for this access device. (Operational);
	   HELP =;
	   CAPABILITIES = NET_CFG, VPN_DISP;"
         ::= { fr-configuration 22}

mcmFrDlcmiSVCStatusEntry OBJECT-TYPE
        SYNTAX   McmFrDlcmiSVCStatusEntry
        ACCESS   not-accessible
        STATUS   mandatory
	DESCRIPTION
	  "NAME = ;
	   DESC = A row or entry in the Frame Relay Dlcmi SVC \
		  status Table. (Operational);
	   HELP = ;
	   CAPABILITIES = ;"
           INDEX { mcmFrDlcmiSVCStatusIfIndex, mcmFrDlcmiSVCStatusDlci }
            ::= { mcmFrDlcmiSVCStatusTable 1 }

         McmFrDlcmiSVCStatusEntry ::= SEQUENCE {
                 mcmFrDlcmiSVCStatusIfIndex 		INTEGER,
                 mcmFrDlcmiSVCStatusDlci 		INTEGER,
                 mcmFrDlcmiSVCStatusCardNumber 		INTEGER,
                 mcmFrDlcmiSVCStatusPortNumber		INTEGER,
                 mcmFrDlcmiSVCStatusTunnelPvcDlci	INTEGER,
                 mcmFrDlcmiSVCStatusPeerCardNumber  	INTEGER,
                 mcmFrDlcmiSVCStatusPeerPortNumber   	INTEGER,
                 mcmFrDlcmiSVCStatusPeerTunPvcDlci 	INTEGER,
                 mcmFrDlcmiSVCStatusPeerSvcDlci 	INTEGER
		}

mcmFrDlcmiSVCStatusIfIndex OBJECT-TYPE
        SYNTAX   INTEGER (1..255)
        ACCESS   read-only
        STATUS   mandatory
	DESCRIPTION
	  "NAME = ;
	   DESC = The ifIndex Value associated with the \
		  netlink. (Operational);
	   HELP = ;
	   CAPABILITIES = ;"
            ::= { mcmFrDlcmiSVCStatusEntry 1 }

mcmFrDlcmiSVCStatusDlci OBJECT-TYPE
        SYNTAX   INTEGER (17..991)
        ACCESS   read-only
        STATUS   mandatory
	DESCRIPTION
	  "NAME = ;
	   DESC = The SVC DLCI number associated with the \
		  netlink. (Operational);
	   HELP = ;
	   CAPABILITIES = ;"
            ::= { mcmFrDlcmiSVCStatusEntry 2 }

mcmFrDlcmiSVCStatusCardNumber OBJECT-TYPE
        SYNTAX   INTEGER (1..5)
        ACCESS   read-only
        STATUS   mandatory
	DESCRIPTION
	  "NAME = ;
	   DESC = The card number linked to this \
		  netlink. (Operational);
	   HELP = ;
	   CAPABILITIES = ;"
            ::= { mcmFrDlcmiSVCStatusEntry 3 }

mcmFrDlcmiSVCStatusPortNumber OBJECT-TYPE
        SYNTAX   INTEGER (1..8)
        ACCESS   read-only
        STATUS   mandatory
	DESCRIPTION
	  "NAME = ;
	   DESC = The physical port number linked to this \
		  netlink. (Operational);
	   HELP = ;
	   CAPABILITIES = ;"
            ::= { mcmFrDlcmiSVCStatusEntry 4 }

mcmFrDlcmiSVCStatusTunnelPvcDlci OBJECT-TYPE
        SYNTAX   INTEGER (16..991)
        ACCESS   read-only
        STATUS   mandatory
	DESCRIPTION
	  "NAME = ;
	   DESC = The tunneling PVC DLCI number linked to \
		  this netlink. (Operational);
	   HELP = ;
	   CAPABILITIES = ;"
            ::= { mcmFrDlcmiSVCStatusEntry 5 }

mcmFrDlcmiSVCStatusPeerCardNumber OBJECT-TYPE
        SYNTAX   INTEGER (1..5)
        ACCESS   read-only
        STATUS   mandatory
	DESCRIPTION
	  "NAME = ;
	   DESC = The card number linked to this netlink \
		  at the other side of the connection. (Operational);
	   HELP = ;
	   CAPABILITIES = ;"
            ::= { mcmFrDlcmiSVCStatusEntry 6 }

mcmFrDlcmiSVCStatusPeerPortNumber OBJECT-TYPE
        SYNTAX   INTEGER (1..8)
        ACCESS   read-only
        STATUS   mandatory
	DESCRIPTION
	  "NAME = ;
	   DESC = The physical port number linked to this netlink \
		  at the other side of the connection. (Operational);
	   HELP = ;
	   CAPABILITIES = ;"
            ::= { mcmFrDlcmiSVCStatusEntry 7 }

mcmFrDlcmiSVCStatusPeerTunPvcDlci OBJECT-TYPE
        SYNTAX   INTEGER (16..991)
        ACCESS   read-only
        STATUS   mandatory
	DESCRIPTION
	  "NAME = ;
	   DESC = The tunneling PVC DLCI number linked to this \
		  netlink at the other side of the connection. (Operational);
	   HELP = ;
	   CAPABILITIES = ;"
            ::= { mcmFrDlcmiSVCStatusEntry 8 }

mcmFrDlcmiSVCStatusPeerSvcDlci OBJECT-TYPE
        SYNTAX   INTEGER (17..991)
        ACCESS   read-only
        STATUS   mandatory
	DESCRIPTION
	  "NAME = ;
	   DESC = The SVC DLCI number linked to this netlink \
		  at the other side of the connection. (Operational);
	   HELP = ;
	   CAPABILITIES = ;"
            ::= { mcmFrDlcmiSVCStatusEntry 9 }



--   Frame Relay Tunnel PVC Table (Operational)

--	This table was added to this MIB module for software releases
--	beginning with Release 3.0.

mcmFrTunnelPvcTable OBJECT-TYPE
        SYNTAX   SEQUENCE OF McmFrTunnelPvcEntry
        ACCESS   not-accessible
        STATUS   mandatory
	DESCRIPTION
	  "NAME = ;
	   DESC = Table of entries for Frame Relay Tunnel PVCs \
		  for this access device. (Operational);
	   HELP =;
	   CAPABILITIES = NET_CFG, VPN_DISP;"
         ::= { fr-configuration 23}

mcmFrTunnelPvcEntry OBJECT-TYPE
        SYNTAX   McmFrTunnelPvcEntry
        ACCESS   not-accessible
        STATUS   mandatory
	DESCRIPTION
	  "NAME = ;
	   DESC = A row or entry in the Frame Relay Tunnel PVC \
		  Table. (Operational);
	   HELP = ;
	   CAPABILITIES = ;"
           INDEX { mcmFrTunnelPvcIfIndex }
            ::= { mcmFrTunnelPvcTable 1 }

         McmFrTunnelPvcEntry ::= SEQUENCE {
	mcmFrTunnelPvcIfIndex 			INTEGER,
	mcmFrTunnelPvcDlciNumber		INTEGER,
	mcmFrTunnelPvcPhysicalCard 		INTEGER,
	mcmFrTunnelPvcPhysicalPort		INTEGER,
	mcmFrTunnelPvcType			INTEGER,
	mcmFrTunnelPvcPhysPortIfIndex 		INTEGER,
	mcmFrTunnelPvcMaxRxFrameSize    	INTEGER,
	mcmFrTunnelPvcRxBc			INTEGER,
	mcmFrTunnelPvcRxBe 			INTEGER,
	mcmFrTunnelPvcMaxRxCIR			INTEGER,
	mcmFrTunnelPvcMaxTxFrameSize		INTEGER,
       	mcmFrTunnelPvcTxBc			INTEGER,
	mcmFrTunnelPvcTxBe			INTEGER,
	mcmFrTunnelPvcMaxTxCIR			INTEGER,
	mcmFrTunnelPvcState			INTEGER,
	mcmFrTunnelPvcRxFrames			Counter,
	mcmFrTunnelPvcTxFrames			Counter,
	mcmFrTunnelPvcRxDeFrames		Counter,
	mcmFrTunnelPvcRxExcessFrames		Counter,
	mcmFrTunnelPvcTxExcessFrames		Counter,
	mcmFrTunnelPvcRxDiscards  		Counter,
	mcmFrTunnelPvcRxOctets			Counter,
	mcmFrTunnelPvcTxOctets			Counter,
        mcmFrTunnelPvcConsecFrames              INTEGER,
        mcmFrTunnelPvcMinTxCIR                  INTEGER
		}

mcmFrTunnelPvcIfIndex OBJECT-TYPE
        SYNTAX   INTEGER (1..255)
        ACCESS   read-only
        STATUS   mandatory
	DESCRIPTION
	  "NAME = ;
	   DESC = The ifIndex of the tunnel PVC itself. \
		  (Operational);
	   HELP = ;
	   CAPABILITIES = ;"
            ::= { mcmFrTunnelPvcEntry 1 }

mcmFrTunnelPvcDlciNumber OBJECT-TYPE
        SYNTAX   INTEGER (16..991)
        ACCESS   read-only
        STATUS   mandatory
	DESCRIPTION
	  "NAME = ;
	   DESC = The DLCI number for this PVC tunnel. \
		  (Operational);
	   HELP = ;
	   CAPABILITIES = ;"
            ::= { mcmFrTunnelPvcEntry 2 }

mcmFrTunnelPvcPhysicalCard OBJECT-TYPE
        SYNTAX   INTEGER {
		limA (1),
		lim1 (2),
		lim2 (3),
		lim3 (4),
		lim4 (5)
		}
        ACCESS   read-only
        STATUS   mandatory
	DESCRIPTION
	  "NAME = ;
	   DESC = The Card (Logical Interface Module - LIM) \
		  of the WAN port (physical FR link). \
		  (Operational);
	   HELP = ;
	   CAPABILITIES = ;"
            ::= { mcmFrTunnelPvcEntry 3 }

mcmFrTunnelPvcPhysicalPort OBJECT-TYPE
        SYNTAX   INTEGER (1..8)
        ACCESS   read-only
        STATUS   mandatory
	DESCRIPTION
	  "NAME = ;
	   DESC = The channel number of this WAN port. \
		  (Operational);
	   HELP = ;
	   CAPABILITIES = ;"
            ::= { mcmFrTunnelPvcEntry 4 }

mcmFrTunnelPvcType OBJECT-TYPE
        SYNTAX   INTEGER {
		dte-panl (1),
		dce-panl (2),
		standard (3)
		}
        ACCESS   read-only
        STATUS   mandatory
	DESCRIPTION
	  "NAME = ;
	   DESC = The FR tunnel PVC type. (Operational);
	   HELP = ;
	   CAPABILITIES = ;"
            ::= { mcmFrTunnelPvcEntry 5 }

mcmFrTunnelPvcPhysPortIfIndex OBJECT-TYPE
        SYNTAX   INTEGER (1..255)
        ACCESS   read-only
        STATUS   mandatory
	DESCRIPTION
	  "NAME = ;
	   DESC = The ifIndex of the FR physical port. \
		  (Operational);
	   HELP = ;
	   CAPABILITIES = ;"
            ::= { mcmFrTunnelPvcEntry 6 }

mcmFrTunnelPvcMaxRxFrameSize OBJECT-TYPE
        SYNTAX   INTEGER (1..4096)
        ACCESS   read-only
        STATUS   mandatory
	DESCRIPTION
	  "NAME = ;
	   DESC = The maximum receive frame size in \
		  octets for this PVC tunnel data (sent into \
		  this unit). (Operational);
	   HELP = ;
	   CAPABILITIES = ;"
            ::= { mcmFrTunnelPvcEntry 7 }

mcmFrTunnelPvcRxBc OBJECT-TYPE
        SYNTAX   INTEGER (0..2560000)
        ACCESS   read-only
        STATUS   mandatory
	DESCRIPTION
	  "NAME = ;
	   DESC = The receive committed burst size (Bc) in bits \
		  for this PVC tunnel data (sent into this unit). \
		  (Operational);
	   HELP = ;
	   CAPABILITIES = ;"
            ::= { mcmFrTunnelPvcEntry 8 }

mcmFrTunnelPvcRxBe OBJECT-TYPE
        SYNTAX   INTEGER (0..2560000)
        ACCESS   read-only
        STATUS   mandatory
	DESCRIPTION
	  "NAME = ;
	   DESC = The receive excess burst size (Be) in bits \
		  for this PVC tunnel data (sent into this unit). \
		  (Operational);
	   HELP = ;
	   CAPABILITIES = ;"
            ::= { mcmFrTunnelPvcEntry 9 }

mcmFrTunnelPvcMaxRxCIR OBJECT-TYPE
        SYNTAX   INTEGER (0..256000)
        ACCESS   read-only
        STATUS   mandatory
	DESCRIPTION
	  "NAME = ;
	   DESC = The maximum received throughput in \
                  bits per second. Used for FECN/BECN \
                  management. (Operation);
	   HELP = ;
	   CAPABILITIES = ;"
            ::= { mcmFrTunnelPvcEntry 10 }

mcmFrTunnelPvcMaxTxFrameSize OBJECT-TYPE
        SYNTAX   INTEGER (1..4096)
        ACCESS   read-only
        STATUS   mandatory
	DESCRIPTION
	  "NAME = ;
	   DESC = The maximum transmission frame size in \
		  octets for this PVC tunnel data (sent out of \
		  this unit). (Operational);
	   HELP = ;
	   CAPABILITIES = ;"
            ::= { mcmFrTunnelPvcEntry 11 }

mcmFrTunnelPvcTxBc OBJECT-TYPE
        SYNTAX   INTEGER (0..2560000)
        ACCESS   read-only
        STATUS   mandatory
	DESCRIPTION
	  "NAME = ;
	   DESC = The transmission committed burst size (Bc) in bits \
		  for this PVC tunnel data (sent out of this unit). \
		  (Operational);
	   HELP = ;
	   CAPABILITIES = ;"
            ::= { mcmFrTunnelPvcEntry 12 }

mcmFrTunnelPvcTxBe OBJECT-TYPE
        SYNTAX   INTEGER (0..2560000)
        ACCESS   read-only
        STATUS   mandatory
	DESCRIPTION
	  "NAME = ;
	   DESC = The transmission excess burst size (Be) in bits \
		  for this PVC tunnel data (sent out of this unit). \
		  (Operational);
	   HELP = ;
	   CAPABILITIES = ;"
            ::= { mcmFrTunnelPvcEntry 13 }

mcmFrTunnelPvcMaxTxCIR OBJECT-TYPE
        SYNTAX   INTEGER (0..256000)
        ACCESS   read-only
        STATUS   mandatory
	DESCRIPTION
	  "NAME = ;
	   DESC = The maximum transmit throughput in \
		  bits per second. Used for FECN/BECN \
                  management.  (Operation);
	   HELP = ;
	   CAPABILITIES = ;"
            ::= { mcmFrTunnelPvcEntry 14 }

mcmFrTunnelPvcState OBJECT-TYPE
        SYNTAX   INTEGER {
		invalid (1),
		active (2),
		inactive (3)
		}
        ACCESS   read-only
        STATUS   mandatory
	DESCRIPTION
	  "NAME = ;
	   DESC = This object indicates the current state \
		  of the PVC DLCI. (Operational);
	   HELP = ;
	   CAPABILITIES = ;"
            ::= { mcmFrTunnelPvcEntry 15 }

mcmFrTunnelPvcRxFrames OBJECT-TYPE
        SYNTAX   Counter
        ACCESS   read-only
        STATUS   mandatory
	DESCRIPTION
	  "NAME = ;
	   DESC = The number of frames received for this \
		  PVC tunnel. (Operational);
	   HELP = ;
	   CAPABILITIES = ;"
            ::= { mcmFrTunnelPvcEntry 16 }

mcmFrTunnelPvcTxFrames OBJECT-TYPE
        SYNTAX   Counter
        ACCESS   read-only
        STATUS   mandatory
	DESCRIPTION
	  "NAME = ;
	   DESC = The number of frames transmitted in this \
		  PVC tunnel (regardless whether they are Bc \
		  or Be frames). (Operational);
	   HELP = ;
	   CAPABILITIES = ;"
            ::= { mcmFrTunnelPvcEntry 17 }

mcmFrTunnelPvcRxDeFrames OBJECT-TYPE
        SYNTAX   Counter
        ACCESS   read-only
        STATUS   mandatory
	DESCRIPTION
	  "NAME = ;
	   DESC = The number of frames received for this \
		  PVC tunnel (ingress) with the DE bit set \
		  to one. (Operational);
	   HELP = ;
	   CAPABILITIES = ;"
            ::= { mcmFrTunnelPvcEntry 18 }

mcmFrTunnelPvcRxExcessFrames OBJECT-TYPE
        SYNTAX   Counter
        ACCESS   read-only
        STATUS   mandatory
	DESCRIPTION
	  "NAME = ;
	   DESC = The number of frames received for this \
		  PVC tunnel (ingress) which were treated as \
		  excess traffic. (Operational);
	   HELP = ;
	   CAPABILITIES = ;"
            ::= { mcmFrTunnelPvcEntry 19 }

mcmFrTunnelPvcTxExcessFrames OBJECT-TYPE
        SYNTAX   Counter
        ACCESS   read-only
        STATUS   mandatory
	DESCRIPTION
	  "NAME = ;
	   DESC = The number of frames transmitted in this \
		  PVC tunnel (egress) which were treated as \
		  excess traffic.  The DE bit may be set to one.\
		  (Operational);
	   HELP = ;
	   CAPABILITIES = ;"
            ::= { mcmFrTunnelPvcEntry 20 }

mcmFrTunnelPvcRxDiscards OBJECT-TYPE
        SYNTAX   Counter
        ACCESS   read-only
        STATUS   mandatory
	DESCRIPTION
	  "NAME = ;
	   DESC = The number of frames received for this \
		  PVC tunnel (ingress) that were discarded due \
		  to traffic enforcement. (Operational);
	   HELP = ;
	   CAPABILITIES = ;"
            ::= { mcmFrTunnelPvcEntry 21 }

mcmFrTunnelPvcRxOctets OBJECT-TYPE
        SYNTAX   Counter
        ACCESS   read-only
        STATUS   mandatory
	DESCRIPTION
	  "NAME = ;
	   DESC = The number of octets received for this \
		  PVC tunnel (ingress). (Operational);
	   HELP = ;
	   CAPABILITIES = ;"
            ::= { mcmFrTunnelPvcEntry 22 }

mcmFrTunnelPvcTxOctets OBJECT-TYPE
        SYNTAX   Counter
        ACCESS   read-only
        STATUS   mandatory
	DESCRIPTION
	  "NAME = ;
	   DESC = The number of octets transmitted in this \
		  PVC tunnel (egress). (Operational);
	   HELP = ;
	   CAPABILITIES = ;"
            ::= { mcmFrTunnelPvcEntry 23 }

mcmFrTunnelPvcConsecFrames OBJECT-TYPE
        SYNTAX   INTEGER (1..100)
        ACCESS   read-only
        STATUS   mandatory
	DESCRIPTION
	  "NAME = ;
	   DESC = The number of consecutive frames received\
		  with the BECN bit set before reducing \
                  the transmit rate. Used for FECN/BECN \
                  management.  (Operation);
	   HELP = ;
	   CAPABILITIES = ;"
            ::= { mcmFrTunnelPvcEntry 24 }

mcmFrTunnelPvcMinTxCIR OBJECT-TYPE
        SYNTAX   INTEGER (0..256000)
        ACCESS   read-only
        STATUS   mandatory
	DESCRIPTION
	  "NAME = ;
	   DESC = The minimum transmit throughput in \
		  bits per second. Used for FECN/BECN \
                  management.  (Operation);
	   HELP = ;
	   CAPABILITIES = ;"
            ::= { mcmFrTunnelPvcEntry 25 }

-- Frame Relay Virtual Port to Netlink (Tunnel PVC) Map Table

mcmFrNetlinkMapTable OBJECT-TYPE
	SYNTAX	SEQUENCE OF McmFrNetlinkMapEntry
	ACCESS	not-accessible
	STATUS	mandatory
	DESCRIPTION
	  "NAME = ;
	   DESC = Table for mapping Netlinks (Tunnel PVC ifIndex \
	 	  values) to Virtual Ports. (Operational);
	   HELP = ;
	   CAPABILITIES = NET_CFG, VPN_DISP;"
	::= {fr-configuration 25}

mcmFrNetlinkMapEntry OBJECT-TYPE
	SYNTAX	McmFrNetlinkMapEntry
	ACCESS	not-accessible
	STATUS	mandatory
	DESCRIPTION
	  "NAME = ;
	   DESC = Entry in the table for mapping Netlinks \
		  (Tunnel PVC ifIndex values) to Virtual \
		  Ports. (Operational);
	   HELP = ;
	   CAPABILITIES = ;"
	INDEX	{mcmFrNetlinkMapVPIfIndex, 
		mcmFrNetlinkMapNetlinkIfIndex}
	::= {mcmFrNetlinkMapTable 1}

McmFrNetlinkMapEntry ::= SEQUENCE {
	mcmFrNetlinkMapVPIfIndex	INTEGER,
	mcmFrNetlinkMapNetlinkIfIndex	INTEGER,
	mcmFrNetlinkMapOperStatus	INTEGER
	}

mcmFrNetlinkMapVPIfIndex OBJECT-TYPE
	SYNTAX	INTEGER (1..255)
	ACCESS	read-only
	STATUS	mandatory
	DESCRIPTION
	  "NAME = ;
	   DESC = Virtual port ifIndex associated \
		  with this Netlink (Tunnel PVC). \
		  (Operational);
	   HELP = ;
	   CAPABILITIES = ;"
	::=  { mcmFrNetlinkMapEntry 1}

mcmFrNetlinkMapNetlinkIfIndex OBJECT-TYPE
	SYNTAX	INTEGER (1..255)
	ACCESS	read-only
	STATUS	mandatory
	DESCRIPTION
	  "NAME = ;
	   DESC = Netlink (Tunnel PVC) ifIndex associated \
		  with the specified Virtual Port. \
		  (Operational);
	   HELP = ;
	   CAPABILITIES = ;"
	::=  { mcmFrNetlinkMapEntry 2}

mcmFrNetlinkMapOperStatus OBJECT-TYPE
	SYNTAX	INTEGER {
		up (1),
		down (2)
		}
	ACCESS	read-only
	STATUS	mandatory
	DESCRIPTION
	  "NAME = ;
	   DESC = This object is used to indicate the operational \
		  status of the Tunnel PVC. (Operational);
	   HELP = ;
	   CAPABILITIES = ;"
	::=  {mcmFrNetlinkMapEntry 3}


-- Parallel Objects

nvmFrGlobalGroup    OBJECT IDENTIFIER ::= {fr-configuration 9}

nvmFrMaxDLCI OBJECT-TYPE
	SYNTAX	INTEGER (1..255)
	ACCESS	read-write
	STATUS	mandatory
	DESCRIPTION
	  "NAME = ;
           DESC = The maximum number of DLCI that \
                  may be configured for the entire \
                  access device;
           HELP = ;
	   CAPABILITIES = NET_CFG, VPN_DISP;"
	DEFVAL	{32}
	::= {nvmFrGlobalGroup 1}

nvmFrMaxVirtualPorts OBJECT-TYPE
	SYNTAX	INTEGER (1..32)
	ACCESS	read-write
	STATUS	mandatory
	DESCRIPTION
	  "NAME = ;
           DESC = The maximum number of ports that \
                  may be configured for the entire \
                  access device;
           HELP = ;
	   CAPABILITIES = NET_CFG, VPN_DISP;"
	DEFVAL	{3}
	::= {nvmFrGlobalGroup 2}

nvmFrMaxDlciPerLine OBJECT-TYPE
	SYNTAX	INTEGER (1..255)
	ACCESS	read-write
	STATUS	mandatory
	DESCRIPTION
	  "NAME = ;
           DESC = The maximum number of DLCIs that may \
                  be configured for a Frame Relay  line;
           HELP = ;
	   CAPABILITIES = NET_CFG, VPN_DISP;"
	::= {nvmFrGlobalGroup 3}

nvmFrDNANumberingPlan OBJECT-TYPE
	SYNTAX	INTEGER {
                e164 (1),
                x121 (3)
                }
	ACCESS	read-write
	STATUS	mandatory
	DESCRIPTION
	  "NAME = ;
	   DESC = The value of this object designates the \
                  numbering plan of the DNA; 
	   HELP = The number plan is used in conjunction \
                  with a DNA.  This object identifies the \
                  type of call as E.164 or X.121;
	   CAPABILITIES = NET_CFG, VPN_DISP;"
	::= {nvmFrGlobalGroup 4}

nvmFrPanlLmiTrapEnable OBJECT-TYPE
	SYNTAX	INTEGER {
		enabled (1),
		disabled (2)
		}
	ACCESS	read-write
	STATUS	mandatory
	DESCRIPTION
	  "NAME = ;
	   DESC = This object specifies whether the generation of \
		  Trap messages are enabled/disabled for the FR \
		  PANL LMI module.; 
	   HELP = ;
	   CAPABILITIES = NET_CFG, VPN_DISP;"
	DEFVAL { disabled }
	::= {nvmFrGlobalGroup 5}

nvmFrMsmTrapEnable OBJECT-TYPE
	SYNTAX	INTEGER {
		enabled (1),
		disabled (2)
		}
	ACCESS	read-write
	STATUS	mandatory
	DESCRIPTION
	  "NAME = ;
	   DESC = This object specifies whether the generation of \
		  Trap messages are enabled/disabled for the FR \
		  MSM module.; 
	   HELP = ;
	   CAPABILITIES = NET_CFG, VPN_DISP;"
	DEFVAL { disabled }
	::= {nvmFrGlobalGroup 6}

nvmFrCoreTrapEnable OBJECT-TYPE
	SYNTAX	INTEGER {
		enabled (1),
		disabled (2)
		}
	ACCESS	read-write
	STATUS	mandatory
	DESCRIPTION
	  "NAME = ;
	   DESC = This object specifies whether the generation of \
		  Trap messages are enabled/disabled for the FR \
		  Core module.; 
	   HELP = ;
	   CAPABILITIES = NET_CFG, VPN_DISP;"
	DEFVAL { disabled }
	::= {nvmFrGlobalGroup 7}

nvmFrPlmTrapEnable OBJECT-TYPE
	SYNTAX	INTEGER {
		enabled (1),
		disabled (2)
		}
	ACCESS	read-write
	STATUS	mandatory
	DESCRIPTION
	  "NAME = ;
	   DESC = This object specifies whether the generation of \
		  Trap messages are enabled/disabled for the FR \
		  Plm module.; 
	   HELP = ;
	   CAPABILITIES = NET_CFG, VPN_DISP;"
	DEFVAL { disabled }
	::= {nvmFrGlobalGroup 8}



-- Parallel Frame Relay Physical Port Group

nvmFrPhyPortTable OBJECT-TYPE
	SYNTAX	SEQUENCE OF NvmFrPhyPortEntry
	ACCESS	not-accessible
	STATUS	mandatory
	DESCRIPTION
	  "NAME = ;
	   DESC = Table of physical port entries \
		  contianing flow control info and \
		  statistics;
	   HELP = ;
	   CAPABILITIES = NET_CFG, VPN_DISP;"
	::= {fr-configuration 10}

nvmFrPhyPortEntry OBJECT-TYPE
	SYNTAX	NvmFrPhyPortEntry
	ACCESS	not-accessible
	STATUS	mandatory
	DESCRIPTION
	  "NAME = ;
	   DESC = Entry for a Frame Relay physical \
		  port;
	   HELP = Entry for a Frame Relay physical \
		  port, containing flow control \
		  information and statistics NOT \
		  included in the RFC 1315 mib;
	   CAPABILITIES = ;"
	INDEX	{ nvmFrPhyPortExtIfIndex }
	::= {nvmFrPhyPortTable 1}

NvmFrPhyPortEntry ::= SEQUENCE {
		nvmFrPhyPortExtIfIndex		INTEGER,
		nvmFrPhyPortFlowControl		INTEGER,
		nvmFrPhyPortThroughput		INTEGER,
		nvmFrPhyPortDelta     		INTEGER,
		nvmFrPhyPortConsectiveFrames	INTEGER,
		nvmFrPhyPortMtuSize		INTEGER,
		nvmFrPhyPortTxThroughput  	INTEGER,
		nvmFrPhyPortRxThroughput 	INTEGER,
		nvmFrPhyPortTxMaxFrameSize	INTEGER,
		nvmFrPhyPortRxMaxFrameSize	INTEGER,
		nvmFrPhyPortRateEnf		INTEGER,
		nvmFrPhyPortTxBc    		INTEGER,
		nvmFrPhyPortRxBc    		INTEGER,
		nvmFrPhyPortTxBe    		INTEGER,
		nvmFrPhyPortRxBe    		INTEGER
		}

nvmFrPhyPortExtIfIndex OBJECT-TYPE
	SYNTAX	INTEGER
	ACCESS	read-only
	STATUS	mandatory
	DESCRIPTION
	  "NAME = ;
           DESC = IfIndex of the physical port the \
                  extention information (this entry) \
                  is associated with;
           HELP = ;
	   CAPABILITIES = ;"
	::= { nvmFrPhyPortEntry 1}

nvmFrPhyPortFlowControl OBJECT-TYPE
	SYNTAX	INTEGER {
		enabled (1),
		disabled (2)
		}
	ACCESS	read-write
	STATUS	mandatory
	DESCRIPTION
	  "NAME = Frame Relay Flow Control;
           DESC = Whether or not policing, based on \
                  congestion should be enforced;
           HELP = Enabling this feature will allow packets \
                  exceeding the current allowable rate \
                  to be dropped if congestion has been \
                  detected on the network.;
	   CAPABILITIES = ;"
	DEFVAL { disabled }
	::= { nvmFrPhyPortEntry 2}

nvmFrPhyPortThroughput OBJECT-TYPE
	SYNTAX	INTEGER (0..2560000)
	ACCESS	read-write
	STATUS	deprecated
	DESCRIPTION
	  "NAME = Frame Relay DLCI Throughput;
           DESC = This object has been DEPRECATED for  software \
		  releases beginning with Release 3.0, and replaced with \
		  new objects TxThroughput, RxThroughput. \
		  Default throughput for a PVC;
           HELP = Defalut throughput used for all \
                  PVCs on the same frame relay \
                  physical interface.  Will be \
                  assigned to a PVC when the PVC \
                  is created. valid if flow cntl \
                  is enabled ;
	   CAPABILITIES = ;"
	::= { nvmFrPhyPortEntry 3}

nvmFrPhyPortDelta OBJECT-TYPE
	SYNTAX	INTEGER (1..100)
	ACCESS	read-write
	STATUS	mandatory
	DESCRIPTION
	  "NAME = Frame Relay Delta;
           DESC = Delta time interval to increase or \
                  decrease the transmit rate by \
                  monitoring the number of frames \
                  received with the FECN bit cleared \
                  or set.  Note that for software releases \
                  beginning with R3.0, the range has been \
                  expanded from (1..100) to (1..255).;
           HELP = Typically 4 types end-to-end \
                  transit delay. Used only if flow \
                  control is enabled.  (In 1 second \
                  units.)  Valid if flow cntl is enabled;
	   CAPABILITIES =;"
	DEFVAL { 1 }
	::= { nvmFrPhyPortEntry 4}

nvmFrPhyPortConsectiveFrames OBJECT-TYPE
	SYNTAX	INTEGER (1..100)
	ACCESS	read-write
	STATUS	mandatory
	DESCRIPTION
	  "NAME = ;
           DESC = Number of consecutive frames received \
                  with the BECN bit set before reducing \
                  the transmit rate;
           HELP = Transmit rate is increased \
                  when S/2 consecutive frames \
                  are received with teh BECN bit cleared. \
                  Valid only when flow control is enabled.\
                  See CCITT Q.922 Appendix I, for the \
                  method to compute parameter S.;
	   CAPABILITIES = ;"
	DEFVAL { 5 }
	::= { nvmFrPhyPortEntry 5}

nvmFrPhyPortMtuSize OBJECT-TYPE
	SYNTAX	INTEGER
	ACCESS	read-write
	STATUS	deprecated
	DESCRIPTION
	  "NAME = ;
           DESC = This object has been DEPRECATED for  software \
		  releases beginning with Release 3.0, and replaced with \
		  new objects TxMaxFrameSize, RxMaxFrameSize. \
		  Maximum Transmission Unit Size;
           HELP = Maximum Packet size that can be \
                  passed to frame Relay and will \
                  be sent across the Frame Relay \
                  network.;
	   CAPABILITIES = ;"
	::= { nvmFrPhyPortEntry 6}

nvmFrPhyPortTxThroughput OBJECT-TYPE
	SYNTAX	INTEGER (0..2560000)
	ACCESS	read-write
	STATUS	mandatory
	DESCRIPTION
	  "NAME = Frame Relay DLCI Tx Throughput;
	   DESC = The transmission CIR expressed in bits/sec.;
	   HELP = ;
	   CAPABILITIES = ;"
	DEFVAL { 64000 }
	::= { nvmFrPhyPortEntry 7}

nvmFrPhyPortRxThroughput OBJECT-TYPE
	SYNTAX	INTEGER (0..2560000)
	ACCESS	read-write
	STATUS	mandatory
	DESCRIPTION
	  "NAME = Frame Relay DLCI Rx Throughput;
	   DESC = The receive CIR expressed in bits/sec.;
	   HELP = ;
	   CAPABILITIES = ;"
	DEFVAL { 64000 }
	::= { nvmFrPhyPortEntry 8}

nvmFrPhyPortTxMaxFrameSize OBJECT-TYPE
	SYNTAX	INTEGER (1..4096)
	ACCESS	read-write
	STATUS	mandatory
	DESCRIPTION
	  "NAME = ;
	   DESC = The maximum transmission FR packet size \
		  expressed in bytes.;
	   HELP = ;
	   CAPABILITIES = ;"
	DEFVAL { 1604 }
	::= { nvmFrPhyPortEntry 9}

nvmFrPhyPortRxMaxFrameSize OBJECT-TYPE
	SYNTAX	INTEGER (1..4096)
	ACCESS	read-write
	STATUS	mandatory
	DESCRIPTION
	  "NAME = ;
	   DESC = The maximum receive FR packet size \
		  expressed in bytes.;
	   HELP = ;
	   CAPABILITIES = ;"
	DEFVAL { 1604 }
	::= { nvmFrPhyPortEntry 10}

nvmFrPhyPortRateEnf OBJECT-TYPE
	SYNTAX	INTEGER {
		enabled (1),
		disabled (2)
		}
	ACCESS	read-write
	STATUS	mandatory
	DESCRIPTION
	  "NAME = ;
	   DESC = The rate enforcement enabled or disabled \
		  parameter for FR congestion management \
		  processing.;
	   HELP = ;
	   CAPABILITIES = ;"
	DEFVAL { disabled }
	::= { nvmFrPhyPortEntry 11}

nvmFrPhyPortTxBc OBJECT-TYPE
	SYNTAX	INTEGER (0..2560000)
	ACCESS	read-write
	STATUS	mandatory
	DESCRIPTION
	  "NAME = ;
	   DESC = The transmission committed burst size \
		  expressed in bits.;
	   HELP = ;
	   CAPABILITIES = ;"
	DEFVAL { 64000 }
	::= { nvmFrPhyPortEntry 12}

nvmFrPhyPortRxBc OBJECT-TYPE
	SYNTAX	INTEGER  (0..2560000)
	ACCESS	read-write
	STATUS	mandatory
	DESCRIPTION
	  "NAME = ;
	   DESC = The receive committed burst size \
		  expressed in bits.;
	   HELP = ;
	   CAPABILITIES = ;"
	DEFVAL { 64000 }
	::= { nvmFrPhyPortEntry 13}

nvmFrPhyPortTxBe OBJECT-TYPE
	SYNTAX	INTEGER (0..2560000)
	ACCESS	read-write
	STATUS	mandatory
	DESCRIPTION
	  "NAME = ;
	   DESC = The transmission excess burst size \
		  expressed in bits.;
	   HELP = ;
	   CAPABILITIES = ;"
	DEFVAL { 64000 }
	::= { nvmFrPhyPortEntry 14}

nvmFrPhyPortRxBe OBJECT-TYPE
	SYNTAX	INTEGER (0..2560000)
	ACCESS	read-write
	STATUS	mandatory
	DESCRIPTION
	  "NAME = ;
	   DESC = The receive excess burst size \
		  expressed in bits.;
	   HELP = ;
	   CAPABILITIES = ;"
	DEFVAL { 64000 }
	::= { nvmFrPhyPortEntry 15}



-- Parallel Frame Relay Physical Port PVC Parameters

nvmFrPVCPhyTable OBJECT-TYPE
	SYNTAX	SEQUENCE OF NvmFrPVCPhyEntry
	ACCESS	not-accessible
	STATUS	mandatory
	DESCRIPTION
	  "NAME = ;
           DESC = Table that extends the RFC 1315 \
                  DLCMI table contianing info \
                  about the PVC LMI;
           HELP = ;
	   CAPABILITIES = NET_CFG, VPN_DISP;"
	::= {fr-configuration 11}

nvmFrPVCPhyEntry OBJECT-TYPE
	SYNTAX	NvmFrPVCPhyEntry
	ACCESS	not-accessible
	STATUS	mandatory
	DESCRIPTION
	  "NAME = ;
           DESC = Entry into the micom PVC LMI \
                  configuration extensions;
           HELP = Entry in the PVC Phys Table. \
                  Additional information required \
                  (not in RFC 1315 DLCI table);
	   CAPABILITIES = ;"
	INDEX	{nvmFrPVCPhyIfIndex}
	::= {nvmFrPVCPhyTable 1}

NvmFrPVCPhyEntry ::= SEQUENCE {
		nvmFrPVCPhyIfIndex	INTEGER,
		nvmFrPVCLMIMode	INTEGER,
		nvmFrPVCBiDir		INTEGER
		}

nvmFrPVCPhyIfIndex OBJECT-TYPE
	SYNTAX	INTEGER
	ACCESS	read-only
	STATUS	mandatory
	DESCRIPTION
	  "NAME = ;
	   DESC = IfIndex of the physical port \
		  the extension information \
		  is associated with;
	   HELP = ;
	   CAPABILITIES = ;"
	::= {nvmFrPVCPhyEntry 1}

nvmFrPVCLMIMode OBJECT-TYPE
	SYNTAX	INTEGER {
		dte (1),
		dce (2)
	}
	ACCESS	read-write
	STATUS	mandatory
	DESCRIPTION
	  "NAME = ;
           DESC = Indicates whether the local PVC \
                  LMI is performing in the DTE or \
                  DCE mode;
           HELP = DTE or DCE mode of operation for \
                  the Frame Relay PVC LMI. (In DTE \
                  mode the Status Enquiry messages \
                  will be sent.  In DCE mode, Status \
                  Reports will be sent in response \
                  to Status Enquiry mesages.;
	   CAPABILITIES = ;"
	::= {nvmFrPVCPhyEntry 2}

nvmFrPVCBiDir OBJECT-TYPE
	SYNTAX	INTEGER {
		true (1),
		false (2)
	}
	ACCESS	read-write
	STATUS	mandatory
	DESCRIPTION
	  "NAME = ;
 
           DESC = Indicates whether the PVC LMI \
                  should perform both sending \
                  status enquiries and sending \
                  status reports;
           HELP = Must be with bilateral agreement \
                  with the switch enabled. Switch \
                  may send status enquiry messages \
                  as defined for the DTEs and allows \
                  the DTE to respond with a status \
                  messages in the same way as switch \
                  does (in this mode Status Enquiries \
                  will still be transmitted normally;
	   CAPABILITIES = ;"
	::= {nvmFrPVCPhyEntry 3}


-- Parallel Frame Relay Physical Port SVC Parameters

nvmFrSVCPhyTable OBJECT-TYPE
	SYNTAX	SEQUENCE OF NvmFrSVCPhyEntry
	ACCESS	not-accessible
	STATUS	mandatory
	DESCRIPTION
	  "NAME = ;
           DESC = Table containing the SVC default \
                  parameters ;
           HELP = Table containing default SVC \
                  parameters to be used if none \
                  are specified when configuring \
                  an SVC;
	   CAPABILITIES = NET_CFG, VPN_DISP;"
	::= {fr-configuration 12}

nvmFrSVCPhyEntry OBJECT-TYPE
	SYNTAX	NvmFrSVCPhyEntry
	ACCESS	not-accessible
	STATUS	mandatory
	DESCRIPTION
	  "NAME = ;
           DESC = Entry into the SVC Default\
                  parameter table;
           HELP = Each entry contains the default \
                  SVC parameters for the specified \
                  interface;
	   CAPABILITIES = ;"
	INDEX	{ nvmFrSVCPhyIfIndex }
	::= {nvmFrSVCPhyTable 1}

NvmFrSVCPhyEntry ::= SEQUENCE {
		nvmFrSVCPhyIfIndex			INTEGER,
		nvmFrSVCState				INTEGER,
		nvmFrSVCT303				INTEGER,
		nvmFrSVCT305				INTEGER,
		nvmFrSVCT308				INTEGER,
		nvmFrSVCT310				INTEGER,
		nvmFrSVCMaxCalls			INTEGER,
		nvmFrSVCMaxTxSize			INTEGER,
		nvmFrSVCMaxRxSize			INTEGER,
		nvmFrSVCMinDLCI				INTEGER,
		nvmFrSVCMaxDLCI				INTEGER,
		nvmFrSVCMinTxThroughput			INTEGER,
		nvmFrSVCMinRxThroughput			INTEGER,
		nvmFrSVCMaxTxThroughput			INTEGER,
		nvmFrSVCMaxRxThroughput			INTEGER, 
		nvmFrSVCTxBurstSize			INTEGER,
		nvmFrSVCRxBurstSize			INTEGER,
		nvmFrSVCExcessTxBurstSize		INTEGER,
		nvmFrSVCExcessRxBurstSize		INTEGER
		}

nvmFrSVCPhyIfIndex OBJECT-TYPE
	SYNTAX	INTEGER
	ACCESS	read-only
	STATUS	mandatory
	DESCRIPTION
	  "NAME = ;
           DESC = IfIndex of the physical port \
		  the SVC information is \
		  associated with;
	   HELP = ;
	   CAPABILITIES = ;"
	::= {nvmFrSVCPhyEntry 1}

nvmFrSVCState OBJECT-TYPE
	SYNTAX	INTEGER {
		q933svc (1)
	}	
	ACCESS	read-write
	STATUS	mandatory
	DESCRIPTION
	  "NAME = ;
           DESC = SVC LMI Protocol to be used;
           HELP = SVC LMI Protocol to be used \
                  on this interface.  (All \
                  SVC connection setup must \
                  use the same protocol);
	   CAPABILITIES = ;"
	DEFVAL { q933svc }
	::= {nvmFrSVCPhyEntry 2}

nvmFrSVCT303 OBJECT-TYPE
	SYNTAX	INTEGER (1..255)
	ACCESS	read-write
	STATUS	mandatory
	DESCRIPTION
	  "NAME = ;
           DESC = The duration, in seconds, \
                  of the setup timer for SVCs. \
                  ;
           HELP = How long the SVC LMI will wait \
                  for a response from the network \
                  (e.g. call proceeding, connect) \
                  before the setup message will be \
                  retransmitted.  In 1 second unit. \
                  Q.931 recommends 4 seconds. Causes at \
		  most one Setup retransmission;
	   CAPABILITIES = ;"
	DEFVAL { 4 }
	::= {nvmFrSVCPhyEntry 3}

nvmFrSVCT305 OBJECT-TYPE
	SYNTAX	INTEGER (1..255)
	ACCESS	read-write
	STATUS	mandatory
	DESCRIPTION
	  "NAME = ;
           DESC = The duration of the Disconnect \
                  timer (in seconds) for SVCs.;
           HELP = How long the SVC LMI will wait \
                  for a release message from the \
                  network before it will transmit \
                  a release message.  (The SVC LMI \
                  will then  wait for a release \
                  message from the network.) In 1 second \
                  unit.  Q.931 recommends 30 seconds.\
                  Causes at most one release \
                  transmit;
	   CAPABILITIES = ;"
	DEFVAL { 30 }
	::= {nvmFrSVCPhyEntry 4}

nvmFrSVCT308 OBJECT-TYPE
	SYNTAX	INTEGER (1..255)
	ACCESS	read-write
	STATUS	mandatory
	DESCRIPTION
	  "NAME = ;
           DESC = The duration of Release timer. ;
           HELP = How long the SVC LMI will wait \
                  for a response from the network \
                  before the release message will \
                  be retransmitted.  (When the \
                  second release is transmitted, \
                  the local SVC LMI considers \
                  the corresponding SVC to have \
                  been released by the network \
                  as well - even if no response \
                  is received.) In 1 second unit. \
                  Q.931 recommends 4 seconds. \
                  Causes at most one release transmit;
	   CAPABILITIES = ;"
	DEFVAL { 4 }
	::= {nvmFrSVCPhyEntry 5}

nvmFrSVCT310 OBJECT-TYPE
	SYNTAX	INTEGER (1..255)
	ACCESS	read-write
	STATUS	mandatory
	DESCRIPTION
	  "NAME = ;
           DESC = The duration of Connect Timer.;
           HELP = How long the SVC LMI will wait \
                  (in seconds) for a Connect  message \
                  (after receiving the  Call Proceeding \
                  message) before sending a Release \
                  message.  In 1 second units.  Q.931 \
                  recommends a duration between 30\
                  to 120 seconds on the DTE side and \
                  10 seconds on the DCE side
                  Causes connection disconnection;
	   CAPABILITIES = ;"
	DEFVAL { 30 }
	::= {nvmFrSVCPhyEntry 6}

nvmFrSVCMaxCalls OBJECT-TYPE
	SYNTAX	INTEGER (1..255)
	ACCESS	read-write
	STATUS	mandatory
	DESCRIPTION
	  "NAME = ;
           DESC = Maximum number of SVC Connections;
           HELP = For all SVCs, including both \
                  incoming and outgoing;
	   CAPABILITIES = ;"
	DEFVAL { 255 }
	::= {nvmFrSVCPhyEntry 7}

nvmFrSVCMaxTxSize OBJECT-TYPE
	SYNTAX	INTEGER (0..4096)
	ACCESS	read-write
	STATUS	mandatory
	DESCRIPTION
	  "NAME = ;
           DESC = Default Maximum transmit frame size, \
                  in bytes, to negotiate with the remote;
           HELP = This value will be used only if a \
                  specific value is not included in the \
                  Connect Request primitive.  A value of \
                  0 indicates the network default values \
                  are to be used (unless it is passed down \
                  at connect time). Expressed in bytes.
	   CAPABILITIES = ;"
	DEFVAL { 1604 }
	::= {nvmFrSVCPhyEntry 8}

nvmFrSVCMaxRxSize OBJECT-TYPE
	SYNTAX	INTEGER (0..4096)
	ACCESS	read-write
	STATUS	mandatory
	DESCRIPTION
	  "NAME = ;
           DESC = Maximum receive frame size in bytes;
           HELP = Default value for the maximum receive \
                  frame size to negotiate with the remote \
                  This value will be used only if a \
                  specific value is not included in the \
                  Connect Request primitive.  A value of \
                  0 indicates the network default values \
                  are to be used (unless it is passed down \
                  at connect time). Expressed in bytes.
	   CAPABILITIES = ;"
	DEFVAL { 1604 }
	::= {nvmFrSVCPhyEntry 9}

nvmFrSVCMinDLCI OBJECT-TYPE
	SYNTAX	INTEGER (17..991)
	ACCESS	read-write
	STATUS	mandatory
	DESCRIPTION
	  "NAME = ;
           DESC = Lowest DLCI value for SVCs on \
                  this network;
           HELP = This value applies only to SVC connections. \
		  PVC DLCI connections may be established \
		  above or below this value.;
	   CAPABILITIES = ;"
	DEFVAL { 17 }
	::= {nvmFrSVCPhyEntry 10}

nvmFrSVCMaxDLCI OBJECT-TYPE
	SYNTAX	INTEGER (17..991)
	ACCESS	read-write
	STATUS	mandatory
	DESCRIPTION
	  "NAME = ;
           DESC = Highest DLCI value for SVCs on \
                  the this network;
           HELP = This value applies only to SVC connections. \
		  PVC DLCI connections may be established \
		  above or below this value.;
	   CAPABILITIES = ;"
	DEFVAL { 991 }
	::= {nvmFrSVCPhyEntry 11}

nvmFrSVCMinTxThroughput OBJECT-TYPE
	SYNTAX	INTEGER (0..2560000)
	ACCESS	read-write
	STATUS	mandatory
	DESCRIPTION
	  "NAME = ;
           DESC = Minimum transmit throughput in \
                  bits per seconds;
           HELP = Minimum transmit throughput in \
                  bits per second, to negotiate with \
                  the remote (used along with the \
                  maximum transmit  throughput) \
                  unless overwritten at connect time. \
                  A value of 0 indicates the network \
                  default values are to be used;
	   CAPABILITIES = ;"
	DEFVAL { 64000 }
	::= {nvmFrSVCPhyEntry 12}

nvmFrSVCMinRxThroughput OBJECT-TYPE
	SYNTAX	INTEGER (0..2560000)
	ACCESS	read-write
	STATUS	mandatory
	DESCRIPTION
	  "NAME = ;
           DESC = Minimum receive throughput in \
                  bits per seconds;
           HELP = To negotiate with the remote when used with the \
		  maximum receive throughput \
		  unless overwritten at connect time. \
		  A value of 0 indicates the network \
		  default values are to be used;
	   CAPABILITIES = ;"
	DEFVAL { 64000 }
	::= {nvmFrSVCPhyEntry 13}

nvmFrSVCMaxTxThroughput OBJECT-TYPE
	SYNTAX	INTEGER (0..2560000)
	ACCESS	read-write
	STATUS	mandatory
	DESCRIPTION
	  "NAME = ;
           DESC = Maximum transmit throughput in \
                  bits per seconds;
           HELP = To negotiate with the remote when used with the \
		  minimum transmit throughput \
		  unless overwritten at connect time. \
		  A value of 0 indicates the network \
		  default values are to be use;
	   CAPABILITIES = ;"
	DEFVAL { 64000 }
	::= {nvmFrSVCPhyEntry 14}

nvmFrSVCMaxRxThroughput OBJECT-TYPE
	SYNTAX	INTEGER (0..2560000)
	ACCESS	read-write
	STATUS	mandatory
	DESCRIPTION
	  "NAME = ;
           DESC = Maximum receive throughput in \
                  bits per seconds;
           HELP = To negotiate with the remote when used with the \
		  minimum receive throughput \
		  unless overwritten at connect time. \
		  A value of 0 indicates the network \
		  default values are to be used;
	   CAPABILITIES = ;"
	DEFVAL { 64000 }
	::= {nvmFrSVCPhyEntry 15}

nvmFrSVCTxBurstSize OBJECT-TYPE
	SYNTAX	INTEGER (0..2560000)
	ACCESS	read-write
	STATUS	mandatory
	DESCRIPTION
	  "NAME = ;
           DESC = Transmit burst size in bytes;
           HELP = Default Committed Transmit burst \
                  size, in bytes, to negotiate with \
                  the remote unless overwritten at \
                  connect time.  A value of 0 \
                  indicates the network default \
                  values are to be used;
	   CAPABILITIES = ;"
	DEFVAL { 64000 }
	::= {nvmFrSVCPhyEntry 16}

nvmFrSVCRxBurstSize OBJECT-TYPE
	SYNTAX	INTEGER (0..2560000)
	ACCESS	read-write
	STATUS	mandatory
	DESCRIPTION
	  "NAME = ;
           DESC = Receive burst size in bytes;
           HELP = Default Committed Receive burst \
                  size, in bytes, to negotiate with \
                  the remote unless overwritten at \
                  connect time.  A value of 0 \
                  indicates the network default \
                  values are to be used;
	   CAPABILITIES = ;"
	DEFVAL { 64000 }
	::= {nvmFrSVCPhyEntry 17}

nvmFrSVCExcessTxBurstSize OBJECT-TYPE
	SYNTAX	INTEGER (0..2560000)
	ACCESS	read-write
	STATUS	mandatory
	DESCRIPTION
	  "NAME = ;
           DESC = Excess transmit burst size in bytes;
           HELP = Default Uncommitted Transmit burst \
                  size, in bytes, to negotiate with \
                  the remote unless overwritten at \
                  connect time.  A value of 0 \
                  indicates the network default \
                  values are to be used;
	   CAPABILITIES = ;"
	DEFVAL { 64000 }
	::= {nvmFrSVCPhyEntry 18}

nvmFrSVCExcessRxBurstSize OBJECT-TYPE
	SYNTAX	INTEGER (0..2560000)
	ACCESS	read-write
	STATUS	mandatory
	DESCRIPTION
	  "NAME = ;
           DESC = Excess receive burst size in bytes;
           HELP = Default Uncommitted Receive burst \
                  size, in bytes, to negotiate with \
                  the remote unless overwritten at \
                  connect time.  A value of 0 \
                  indicates the network default \
                  values are to be used;
	   CAPABILITIES = ;"
	DEFVAL { 64000 }
	::= {nvmFrSVCPhyEntry 19}



-- Parallel Frame Relay MICOM Virtual Port Extension

nvmFrVirtualPortTable OBJECT-TYPE
	SYNTAX	SEQUENCE OF NvmFrVirtualPortEntry
	ACCESS	not-accessible
	STATUS	mandatory
	DESCRIPTION
	  "NAME = ;
           DESC = Table to provide the mapping between \
                  virtual ports and physical ports \
                  and to define the virtual port \
                  parameters;
           HELP = ;
	   CAPABILITIES = NET_CFG, VPN_DISP;"
	::= {fr-configuration 13}

nvmFrVirtualPortEntry OBJECT-TYPE
	SYNTAX	NvmFrVirtualPortEntry
	ACCESS	not-accessible
	STATUS	mandatory
	DESCRIPTION
	  "NAME = ;
           DESC = Each entry in this table contains \
                  information to define a virtual \
                  port;
           HELP = ;
	   CAPABILITIES = ;"
	INDEX	{nvmFrVirtualPortIfIndex}
	::= {nvmFrVirtualPortTable 1}

NvmFrVirtualPortEntry ::= SEQUENCE {
		nvmFrVirtualPortIfIndex		INTEGER,
		nvmFrVirtualPortPhyPortIfIndex	INTEGER,
		nvmFrVirtualPortPPA 		INTEGER,
		nvmFrVirtualPortMode		INTEGER,
		nvmFrVirtualPortEntryStatus	INTEGER,
		nvmFrVirtualPortProtocolBinding	INTEGER,
		nvmFrVirtualPortNumber		INTEGER
		}

nvmFrVirtualPortIfIndex OBJECT-TYPE
	SYNTAX	INTEGER (1..255)
	ACCESS	read-write
	STATUS	mandatory
	DESCRIPTION
	  "NAME = Virtual Port Interface Number;
           DESC = IfIndex associated with this port;
           HELP = ;
	   CAPABILITIES = ;"
	::=  {nvmFrVirtualPortEntry 1}

nvmFrVirtualPortPhyPortIfIndex OBJECT-TYPE
	SYNTAX	INTEGER (1..255)
	ACCESS	read-write
	STATUS	obsolete
	DESCRIPTION
	  "NAME = ;
	   DESC = *******NOTE: THIS OBJECT IS OBSOLETE*******  
                  This information is no longer useful for \
                  virtual ports.  The virtual ports no longer \
                  have an underlying network. Only SVC DNAs \
                  and PVC DLCIs are associated with VPs now. \
                  The underlying MPANL will take care of which \
                  link the SVC is to be made on and a Physical \
                  Line IfIndex has been added to the PVCs.  VP \
                  are no longer required to provide the backup \
                  link support (MPANL now does that).\  

                  IfIndex of the Frame Relay physical \
                  port for which the virtual port is \
                  (or will be) linked to;
           HELP = ;
	   CAPABILITIES = ;"
	::=  {nvmFrVirtualPortEntry 2}

nvmFrVirtualPortPPA OBJECT-TYPE
	SYNTAX	INTEGER (0..254)
	ACCESS	read-write
	STATUS	obsolete
	DESCRIPTION
	  "NAME = This object has been OBSOLETED for software \
		  releases beginning with Release 3.0. \
		  Virtual Port PPA Number;
           DESC = Point of Physical attachment for \
                  this port;
           HELP = ;
	   CAPABILITIES = ;"
	::=  {nvmFrVirtualPortEntry 3}

nvmFrVirtualPortMode OBJECT-TYPE
	SYNTAX	INTEGER {
		basic (1),
		easyRouting (2)
		}
	ACCESS	read-write
	STATUS	mandatory
	DESCRIPTION
	  "NAME = Virtual Port Mode;
           HELP = Mode of the virtual port;
           DESC = Easy Routing requires that data  \
                  will be switched between the \
                  Virtual Circuits on the this \
                  virutal port. Basic mode turns \
                  off the switching mode;
	   CAPABILITIES = ;"
	::=  {nvmFrVirtualPortEntry 4}

nvmFrVirtualPortEntryStatus OBJECT-TYPE
	SYNTAX	INTEGER {
		enable (1),
		disable (2),
		delete (3)
		}
	ACCESS	read-write
	STATUS	mandatory
	DESCRIPTION
	  "NAME = Virtual Port Mode;
           DESC = Virtual port row status;
           HELP = Indicates whether or not this \
                  entry is valid;
	   CAPABILITIES = ;"
	::=  {nvmFrVirtualPortEntry 5}


nvmFrVirtualPortProtocolBinding OBJECT-TYPE
	SYNTAX	INTEGER {
		ip-configured (1),
		ipx-configured (2),
		ip-and-ipx-configured (3),
		bridge-configured (4),
		ip-and-bridge-configured (5),
		ipx-and-bridge-configured (6),
		ip-and-ipx-and-bridge-configured (7),
		sNA-configured (8),
		x25-configured (9)
		}
	ACCESS	read-only
	STATUS	mandatory
	DESCRIPTION
	  "NAME = ;
	   DESC = Bitmap that contains the protocols bound. \
		  to this Virtual Port;
	   HELP = ;
	   CAPABILITIES = ;"
	::=  {nvmFrVirtualPortEntry 6}

nvmFrVirtualPortNumber OBJECT-TYPE
	SYNTAX	INTEGER (0..254)
	ACCESS	read-write
	STATUS	mandatory
	DESCRIPTION
	  "NAME = ;
	   DESC = This object specifies the Virtual \
		  Port Number used as an identifier \
		  for a Virtual Port. (Configuration);
	   HELP = ;
	   CAPABILITIES = ;"
	::=  {nvmFrVirtualPortEntry 7}


-- Parallel Frame Relay Associated SVC MIB8

nvmFrSVCMapTable OBJECT-TYPE
	SYNTAX	SEQUENCE OF NvmFrSVCMapEntry
	ACCESS	not-accessible
	STATUS	mandatory
	DESCRIPTION
	  "NAME = ;
           DESC = Table for SVC to VP bindings;
           HELP = This table will give the SVC \
                  DNA address to be bound to the \
                  specified Virtual Port;
	   CAPABILITIES = NET_CFG, VPN_DISP;"
	::= {fr-configuration 14}

nvmFrSVCMapEntry OBJECT-TYPE
	SYNTAX	NvmFrSVCMapEntry
	ACCESS	not-accessible
	STATUS	mandatory
	DESCRIPTION
	  "NAME = ;
           DESC = Entry in the SVC to VP binding \
                  table;
           HELP = SVC/VP binding entry in the SVC \
                  binding table.  Multiple SVCS \
                  (DNAs) may be bound to a single \
                  VP (ifindex);
	   CAPABILITIES = ;"
	INDEX	{nvmFrSVCMapVirtualPortIfIndex, nvmFrSVCMapDNA}
	::= {nvmFrSVCMapTable 1}

NvmFrSVCMapEntry ::= SEQUENCE {
	nvmFrSVCMapVirtualPortIfIndex		INTEGER,
	nvmFrSVCMapDNA				OCTET STRING,
	nvmFrSVCMapMaxTxSize			INTEGER,
	nvmFrSVCMapMaxRxSize			INTEGER,
	nvmFrSVCMapMinTxThroughput		INTEGER,
	nvmFrSVCMapMinRxThroughput		INTEGER,
	nvmFrSVCMapMaxTxThroughput		INTEGER,
	nvmFrSVCMapMaxRxThroughput		INTEGER,
	nvmFrSVCMapTxBurstSize			INTEGER,
	nvmFrSVCMapRxBurstSize			INTEGER,
	nvmFrSVCMapExcessTxBurstSize		INTEGER,
	nvmFrSVCMapExcessRxBurstSize		INTEGER,
	nvmFrSVCMapPriority			INTEGER,
	nvmFrSVCMapEntryStatus			INTEGER,
	nvmFrSVCMapTransferPriority		INTEGER,
	nvmFrSVCMapRowStatus			INTEGER,
	nvmFrSVCMapDiscardPriority		INTEGER,
	nvmFrSVCMapSetupPriority  		INTEGER,
	nvmFrSVCMapHoldingPriority		INTEGER
	}

nvmFrSVCMapVirtualPortIfIndex OBJECT-TYPE
	SYNTAX	INTEGER
	ACCESS	read-write
	STATUS	mandatory
	DESCRIPTION
	  "NAME = ;
	   DESC = Virtual Port ifIndex associated \
		  with this DNA;
	   HELP = ;
	   CAPABILITIES = ;"
	::=  {nvmFrSVCMapEntry 1}

nvmFrSVCMapDNA OBJECT-TYPE
	SYNTAX	OCTET STRING (SIZE(1..34)) 
	ACCESS	read-write
	STATUS	mandatory
	DESCRIPTION
	  "NAME = ;
           DESC = Remote DNA to associate with \
                  the corresponding virtual port;
           HELP = DNA to be mapped to the \
                  corresponding virtual port. \
                  This will be used to create \
                  an SVC to the corresponding \
                  remote DNA;
	   CAPABILITIES = ;"
	::=  {nvmFrSVCMapEntry 2}

nvmFrSVCMapMaxTxSize OBJECT-TYPE
	SYNTAX	INTEGER (0..4096)
	ACCESS	read-write
	STATUS	mandatory
	DESCRIPTION
	  "NAME = ;
           DESC = Maximum transmit frame size to \
                  negotiate with the remote (in \
                  bytes);
           HELP = This value will override the default values for \
		  the physical interface.  A value \
		  of 0 indicates the networks default \
		  values are to be used. Experessed in \
		  bytes;
	   CAPABILITIES = ;"
	::=  {nvmFrSVCMapEntry 3}

nvmFrSVCMapMaxRxSize OBJECT-TYPE
	SYNTAX	INTEGER (0..4096)
	ACCESS	read-write
	STATUS	mandatory
	DESCRIPTION
	  "NAME = ;
           DESC = Maximum receive frame size to \
                  negotiate with the remote (in \
                  bytes);
           HELP = This value will override the default values for \
		  the physical interface.  A value \
		  of 0 indicates the networks default \
		  values are to be used. Experessed in \
		  bytes;
	   CAPABILITIES = ;"
	::=  {nvmFrSVCMapEntry 4}

nvmFrSVCMapMinTxThroughput OBJECT-TYPE
	SYNTAX	INTEGER (0..2560000)
	ACCESS	read-write
	STATUS	mandatory
	DESCRIPTION
	  "NAME = ;
           DESC = Minimum transmit throughput in \
                  bits per second;
           HELP = Used with the maximum transmit throughput. \
		  This value will override default \
		  values given for this physical \
		  interface.  A value of 0 indicates \
		  the network default values are to \
		  be used;
	   CAPABILITIES = ;"
	::=  {nvmFrSVCMapEntry 5}

nvmFrSVCMapMinRxThroughput OBJECT-TYPE
	SYNTAX	INTEGER (0..2560000)
	ACCESS	read-write
	STATUS	mandatory
	DESCRIPTION
	  "NAME = ;
           DESC = Minimum receive throughput in \
                  bits per second;
           HELP = Used with the maximum receive throughput. \
		  This value will override default \
		  values given for this physical \
		  interface.  A value of 0 indicates \
		  the network default values are to \
		  be used;
	   CAPABILITIES = ;"
	::=  {nvmFrSVCMapEntry 6}

nvmFrSVCMapMaxTxThroughput OBJECT-TYPE
	SYNTAX	INTEGER (0..2560000)
	ACCESS	read-write
	STATUS	mandatory
	DESCRIPTION
	  "NAME = ;
           DESC = Maximum transmit throughput in \
                  bits per second;
           HELP = Used with the minimum transmit throughput. \
		  This value will override default \
		  values given for this physical \
		  interface.  A value of 0 indicates \
		  the network default values are to \
		  be used;
	   CAPABILITIES = ;"
	::=  {nvmFrSVCMapEntry 7}

nvmFrSVCMapMaxRxThroughput OBJECT-TYPE
	SYNTAX	INTEGER (0..2560000)
	ACCESS	read-write
	STATUS	mandatory
	DESCRIPTION
	  "NAME = ;
           DESC = Maximum receive throughput in \
                  bits per second;
           HELP = Used with the minimum receive throughput. \
		  This value will override default \
		  values given for this physical \
		  interface.  A value of 0 indicates \
		  the network default values are to \
		  be used;
	   CAPABILITIES = ;"
	::=  {nvmFrSVCMapEntry 8}

nvmFrSVCMapTxBurstSize OBJECT-TYPE
	SYNTAX	INTEGER (0..2560000)
	ACCESS	read-write
	STATUS	mandatory
	DESCRIPTION
	  "NAME = ;
           DESC = Transmit burst size in bytes;
           HELP = Committed transmit busrt size, \
                  in bytes, to negotiate with the \
                  remote. This value will override \
                  default values entered for the \
                  network.  A value of 0 indicates \
                  the network default values are to \
                  be used;
	   CAPABILITIES = ;"
	::=  {nvmFrSVCMapEntry 9}

nvmFrSVCMapRxBurstSize OBJECT-TYPE
	SYNTAX	INTEGER (0..2560000)
	ACCESS	read-write
	STATUS	mandatory
	DESCRIPTION
	  "NAME = ;
           DESC = Receive burst size in bytes;
           HELP = Committed receive busrt size, \
                  in bytes, to negotiate with the \
                  remote. This value will override \
                  default values entered for the \
                  network.  A value of 0 indicates \
                  the network default values are to \
                  be used;
	   CAPABILITIES = ;"
	::=  {nvmFrSVCMapEntry 10}

nvmFrSVCMapExcessTxBurstSize OBJECT-TYPE
	SYNTAX	INTEGER (0..2560000)
	ACCESS	read-write
	STATUS	mandatory
	DESCRIPTION
	  "NAME = ;
           DESC = Excess transmit burst size in bytes;
           HELP = Uncommitted transmit busrt size, \
                  in bytes, to negotiate with the \
                  remote. This value will override \
                  default values entered for the \
                  network.  A value of 0 indicates \
                  the network default values are to \
                  be used;
	   CAPABILITIES = ;"
	::=  {nvmFrSVCMapEntry 11}

nvmFrSVCMapExcessRxBurstSize OBJECT-TYPE
	SYNTAX	INTEGER (0..2560000)
	ACCESS	read-write
	STATUS	mandatory
	DESCRIPTION
	  "NAME = ;
           DESC = Excess receive burst size in bytes;
           HELP = Uncommitted transmit busrt size, \
                  in bytes, to negotiate with the \
                  remote. This value will override \
                  default values entered for the \
                  network.  A value of 0 indicates \
                  the network default values are to \
                  be used;
	   CAPABILITIES = ;"
	::=  {nvmFrSVCMapEntry 12}

nvmFrSVCMapPriority OBJECT-TYPE
	SYNTAX	INTEGER (0..15)
	ACCESS	read-write
	STATUS	mandatory
	DESCRIPTION
	  "NAME = ;
           DESC = Transfer priority level for data on \
                  this SVC;
           HELP = All data on this SVC will be sent \
		  through the switches at \
		  the requested transfer priority level;
	   CAPABILITIES = ;"
	::=  {nvmFrSVCMapEntry 13}

nvmFrSVCMapEntryStatus OBJECT-TYPE
	SYNTAX	INTEGER {
		enable (1),
		disable (2),
		delete (3)
	}
	ACCESS	read-write
	STATUS	mandatory
	DESCRIPTION
	  "NAME = ;
           DESC = Indicates whether or not this entry is \
                  enabled;
           HELP = Enabled indicates this entry will be used \
                  to establish an SVC connection.  Disabled \
                  indicates this entry is to be ignored when \
                  establishing SVC connections.  This allows \
                  these SVCs entries to be disabled/enabled \
                  without having to reenter the entire entry;
	   CAPABILITIES = ;"
	::=  {nvmFrSVCMapEntry 14}

nvmFrSVCMapTransferPriority OBJECT-TYPE
	SYNTAX	INTEGER (0..15)
	ACCESS	read-write
	STATUS	mandatory
	DESCRIPTION
	  "NAME = ;
	   DESC = The transfer priority for the corresponding \
		  pass-through connection. (Configuration);
	   HELP = ;
	   CAPABILITIES = ;"
	::=  {nvmFrSVCMapEntry 15}

nvmFrSVCMapRowStatus OBJECT-TYPE
	SYNTAX	INTEGER {
		active (1),
		createAndGo (4),
		destroy (6)
		}
    	ACCESS  read-write
     	STATUS  mandatory
     	DESCRIPTION
          "NAME = ; 
	   DESC = This object is used to add new rows \
		  in the SVC to VP bindings table, modify existing \
		  rows,and to delete existing rows (Configuration);
	   HELP = To add a new row, createAndGo (4) is used. \
		  To modify an existing row, active (1) is \
		  used.  To delete an existing row, \
		  destroy (6) is used. ;
	   CAPABILITIES = ;"
	::= { nvmFrSVCMapEntry 16 }

nvmFrSVCMapDiscardPriority OBJECT-TYPE
        SYNTAX INTEGER {
           low-discard-level     (1),
           medium-discard-level  (2),
           high-discard-level    (3)
           }
        ACCESS read-write
        STATUS mandatory
        DESCRIPTION
	  "NAME = ;
	   DESC = The discard priority used for connection \
		  setup of this SVC map.; 
	   HELP = ;
	   CAPABILITIES = ;"
	::=  {nvmFrSVCMapEntry 17}

nvmFrSVCMapSetupPriority OBJECT-TYPE
        SYNTAX INTEGER (1..5)
	ACCESS	read-write
	STATUS	mandatory
	DESCRIPTION
	  "NAME = ;
           DESC = This object specifies the priority of a path at \
		  call-establishment time, and also determines \
		  the potential for bumping established paths \
		  to acquire their bandwidth.  A value of 1 is \
		  the highest priority, and 5 is the lowest.;
           HELP = ;
	   CAPABILITIES = ;"
	DEFVAL { 2 }
	::= {nvmFrSVCMapEntry 18}

nvmFrSVCMapHoldingPriority OBJECT-TYPE
        SYNTAX INTEGER (1..5)
	ACCESS	read-write
	STATUS	mandatory
	DESCRIPTION
	  "NAME = ;
           DESC = This object specifies the priority that a path \
		  maintains once the path is established, and \
		  also determines the likelihood of being bumped \
		  by a new path, thus losing the bandwidth.  A value \
		  of 1 is the highest priority, and 5 is the lowest.;
           HELP = ;
	   CAPABILITIES = ;"
	DEFVAL { 2 }
	::= {nvmFrSVCMapEntry 19}



-- Parallel Frame Relay Associated PVC Parameters

-- *** This table OBSOLETED beginning with software Release 3.0. ***

nvmFrPVCMapTable OBJECT-TYPE
	SYNTAX	SEQUENCE OF NvmFrPVCMapEntry
	ACCESS	not-accessible
	STATUS	obsolete
	DESCRIPTION
	  "NAME = ;
           DESC = This table has been OBSOLETED for software \
		  releases beginning with Release 3.0. \
		  Table for PVC to VP bindings;
           HELP = This table will give the PVC \
                  DLCI address to be bound to the \
                  specified Virtual Port;
	   CAPABILITIES = NET_CFG, VPN_DISP;"
	::= {fr-configuration 15}

nvmFrPVCMapEntry OBJECT-TYPE
	SYNTAX	NvmFrPVCMapEntry
	ACCESS	not-accessible
	STATUS	obsolete
	DESCRIPTION
	  "NAME = ;
           DESC = Entry in the PVC to VP binding \
                  table;
           HELP = PVC/VP binding entry in the PVC \
                  binding table.  Multiple PVCs \
                  (DLCIs) may be bound to a single \
                  VP (ifindex).;
	   CAPABILITIES = ;"
	INDEX	{nvmFrPVCMapVirtualPortIfIndex, nvmFrPVCMapDLCI}
	::= {nvmFrPVCMapTable 1}

NvmFrPVCMapEntry ::= SEQUENCE {
	nvmFrPVCMapVirtualPortIfIndex	INTEGER,
	nvmFrPVCMapDLCI			INTEGER,
	nvmFrPVCMapEntryStatus		INTEGER,
        nvmFrPVCMapPhysIfIndex          INTEGER 
	}

nvmFrPVCMapVirtualPortIfIndex OBJECT-TYPE
	SYNTAX	INTEGER
	ACCESS	read-write
	STATUS	obsolete
	DESCRIPTION
	  "NAME = ;
           DESC = Virtual port ifIndex associated \
                  with this PVC DLCI;
           HELP = ;
	   CAPABILITIES = ;"
	::=  { nvmFrPVCMapEntry 1}


nvmFrPVCMapDLCI OBJECT-TYPE
	SYNTAX	INTEGER (17..126975)
	ACCESS	read-write
	STATUS	obsolete
	DESCRIPTION
	  "NAME = ;
           DESC = Local DLCI to the remote that is \
                  to be associated with the \
                  corresponding virtual port;
           HELP = A DLCI for any given interface \
                  may be bound to only one virtual \
                  port;
	   CAPABILITIES = ;"
	::=  { nvmFrPVCMapEntry 2}

nvmFrPVCMapEntryStatus OBJECT-TYPE
	SYNTAX	INTEGER {
		enable (1),
		disable (2),
		delete (3)
	}
	ACCESS	read-write
	STATUS	obsolete
	DESCRIPTION
	  "NAME = ;
           DESC = Indicates whether or not this entry is \
                  enabled;
           HELP = Enabled indicates this entry will be used \
                  to associate a PVC DLCI with a virtual \
                  port.  Disable indicates this entry is to \
                  be ignored when mapping PVC dlcis to \
                  virtual ports.  This allows the PVC map \
                  entries to be disabled/enabled without \
                  having to reenter the entire entry;
	   CAPABILITIES = ;"
	::=  {nvmFrPVCMapEntry 3}

nvmFrPVCMapPhysIfIndex OBJECT-TYPE
	SYNTAX	INTEGER 
	ACCESS	read-write
	STATUS	obsolete
	DESCRIPTION
	  "NAME = ;
	   DESC = Physical interface this PVC \
                  is associated with.;
	   HELP = ;
	   CAPABILITIES = ;"
	::=  {nvmFrPVCMapEntry 4}

     --  NVM Data Link Connection Management Interface

     --  This table is the parallel table to  
     --  the DLCMI table defined in RFC 1315.

nvmFrDlcmiTable OBJECT-TYPE
        SYNTAX   SEQUENCE OF NvmFrDlcmiEntry
        ACCESS   not-accessible
        STATUS   mandatory
	DESCRIPTION
	  "NAME = ;
           DESC = The Parameters for the Data Link Connection \
                  Management Interface for the frame \
                  relay service on this interface.;
           HELP = Table of standard RFC 1315 PVC LMI \
                  Parameters per interface (physical \
                  port);
	   CAPABILITIES = NET_CFG, VPN_DISP;"
        REFERENCE
            "Draft American National Standard T1.617-1991, Annex D"
         ::= { fr-configuration 16 }

nvmFrDlcmiEntry OBJECT-TYPE
        SYNTAX   NvmFrDlcmiEntry
        ACCESS   not-accessible
        STATUS   mandatory
	DESCRIPTION
	  "NAME = ;
                DESC = The Parameters for a particular Data \
                       Link Connection Management Interface.;
                HELP = Entry for the standard RFC 1315 PVC \
                       LMI parameters for an interface \
                       (physical port);
	   CAPABILITIES = ;"
            INDEX { nvmFrDlcmiIfIndex }
            ::= { nvmFrDlcmiTable 1 }

NvmFrDlcmiEntry ::= SEQUENCE {
                 nvmFrDlcmiIfIndex 			INTEGER,
                 nvmFrDlcmiState 			INTEGER,
                 nvmFrDlcmiAddress 			INTEGER,
                 nvmFrDlcmiAddressLen 			INTEGER,
                 nvmFrDlcmiPollingInterval 		INTEGER,
                 nvmFrDlcmiFullEnquiryInterval 		INTEGER,
                 nvmFrDlcmiErrorThreshold 		INTEGER,
                 nvmFrDlcmiMonitoredEvents 		INTEGER,
                 nvmFrDlcmiMaxSupportedVCs 		INTEGER,
                 nvmFrDlcmiMulticast 			INTEGER
         }

nvmFrDlcmiIfIndex OBJECT-TYPE
        SYNTAX   INTEGER (1..255)
        ACCESS   read-only
        STATUS   mandatory
	DESCRIPTION
	  "NAME = ;
                DESC = The ifIndex of the physical interface \
                       for the corresponding PVC LMI \
                       parameters to be updated;
                HELP = ;
	   CAPABILITIES = ;"
            ::= { nvmFrDlcmiEntry 1 }

nvmFrDlcmiState OBJECT-TYPE
        SYNTAX INTEGER {
           noLmiConfigured (1),
           lmi (2),
           itut933A        (5),  -- CCITT Q933 Annex A
           ansiT1617D1994  (6)   -- ANSI T1.617a-1994 Annex D
        }
        ACCESS   read-write
        STATUS   mandatory
	DESCRIPTION
	  "NAME = ;
                DESC = This variable states which Data  Link \
                       Connection Management scheme is \
                       active (and by implication, what \
                       DLCI it uses) on the  Frame  Relay \
                       interface.;
                HELP = The type of PVC LMI active on this \
                       interface.  The PVC LMI selected \
                       must be compatable with the network \
                       PVC LMI running.  (If no PVCs are to \
                       be used, the 'noLmiConfigured' option \
                       may be selected.);
	   CAPABILITIES = ;"
        REFERENCE
               "Draft American National Standard T1.617-1991"
           ::= { nvmFrDlcmiEntry 2 }



nvmFrDlcmiAddress OBJECT-TYPE
        SYNTAX      INTEGER {
                   q921           (1),  -- 13 bit DLCI
                   q922March90    (2),  -- 11 bit DLCI
                   q922November90 (3),  -- 10 bit DLCI
                   q922           (4)   -- Final Standard
        }
        ACCESS  read-write
        STATUS  mandatory
	DESCRIPTION
	  "NAME = ;
                DESC = This variable states which address  \
                       format  is in use on the Frame Relay \
                       interface.;
                HELP = Must match the address format used by the \
                       network;
	   CAPABILITIES = ;"
            ::= { nvmFrDlcmiEntry 3 }


nvmFrDlcmiAddressLen OBJECT-TYPE
        SYNTAX  INTEGER {
                two-octets (2),
                three-octets (3),
                four-octets (4)
        }
        ACCESS  read-write
        STATUS  mandatory
	DESCRIPTION
	  "NAME = ;
                DESC = This variable states which address  \
                       length  in octets.;
                HELP = In the case of \
                       Q922 format, the length indicates the \
                       entire length of the address  including \
                       the control portion.  Used with \
                       the address type to identify \
                       a PVC.  This value must match the \
                       address length used by the network;
	   CAPABILITIES = ;"
            ::= { nvmFrDlcmiEntry 4 }



nvmFrDlcmiPollingInterval OBJECT-TYPE
        SYNTAX   INTEGER (5..30)
        ACCESS   read-write
        STATUS   mandatory
	DESCRIPTION
	  "NAME = ;
                DESC = This is the number of seconds between \
                       successive status enquiry messages.;
                HELP = How often the PVC LMI status enquiry \
                       messages will be sent on the \
                       corresponding interface (measured \
                       in seconds);
	   CAPABILITIES = ;"
        REFERENCE
          "Draft American National  Standard  T1.617-1991,
           Section D.7 Timer T391."
        DEFVAL { 10 }
           ::= { nvmFrDlcmiEntry 5 }


nvmFrDlcmiFullEnquiryInterval OBJECT-TYPE
        SYNTAX   INTEGER (1..255)
        ACCESS   read-write
        STATUS   mandatory
	DESCRIPTION
	  "NAME = ;
                DESC = Number of status enquiry intervals  \
                       that  pass before  issuance  of a full \
                       status enquiry message.;
                HELP = How often a full status enquiry message \
                       will be sent.  Measured in units of \
                       status enquiry interval.  (Every nth \
                       status enquiry will be a full status \
                       enquiry.);
	   CAPABILITIES = ;"
        REFERENCE
           "Draft American National  Standard  T1.617-1991,
           Section D.7 Counter N391."
        DEFVAL { 6 }
           ::= { nvmFrDlcmiEntry 6 }


nvmFrDlcmiErrorThreshold OBJECT-TYPE
        SYNTAX   INTEGER (1..10)
        ACCESS   read-write
        STATUS   mandatory
	DESCRIPTION
	  "NAME = ;
                DESC = This  is  the  maximum  number  of  \
                       unanswered Status Enquiries the equipment \
                       shall accept before declaring the LMI \
                       down.;
                HELP = ;
	   CAPABILITIES = ;"
        REFERENCE
           "Draft American National  Standard  T1.617-1991,
            Section D.5.1 Counter N392."
        DEFVAL { 3 }
           ::= { nvmFrDlcmiEntry 7 }

nvmFrDlcmiMonitoredEvents OBJECT-TYPE
        SYNTAX   INTEGER (1..10)
        ACCESS   read-only
        STATUS   mandatory
	DESCRIPTION
	  "NAME = ;
                DESC = This is the number of status polling \
                       intervals over which the error threshold \
                       is counted.;
                HELP = If within \
                       'MonitoredEvents' number  of events \
                       the  station  receives 'ErrorThreshold' \
                       number of errors, the interface  is \
                       marked  as down.;
	   CAPABILITIES = ;"
        REFERENCE
           "Draft American National  Standard  T1.617-1991,
           Section D.5.2 Counter N393."
        DEFVAL { 4 }
           ::= { nvmFrDlcmiEntry 8 }



nvmFrDlcmiMaxSupportedVCs OBJECT-TYPE
        SYNTAX   INTEGER
        ACCESS   read-write
        STATUS   mandatory
	DESCRIPTION
	  "NAME = ;
                DESC = The maximum number of Virtual Circuits \
                       allowed for this interface.;
                HELP = Dictated by the Frame Relay network. In \
                       response to a SET, if a value less \
                       than zero or  higher  than the agent's \
                       maximal capability is configured, the \
                       agent  should  respond  bad- Value;
	   CAPABILITIES = ;"
            ::= { nvmFrDlcmiEntry 9 }


nvmFrDlcmiMulticast OBJECT-TYPE
       	SYNTAX   INTEGER {
                 nonBroadcast (1),
                 broadcast (2)
                 }
       	ACCESS   read-write
       	STATUS   mandatory
	DESCRIPTION
	  "NAME = ;
                DESC = This indicates whether the Frame Relay \
                       interface is using a multicast service.;
                HELP = The network \
                       must support a multicast service;
	   CAPABILITIES = ;"
            ::= { nvmFrDlcmiEntry 10 }

-- Parralel LAN SPVC table object

nvmFrLANSpvcTable OBJECT-TYPE
        SYNTAX SEQUENCE OF NvmFrLANSpvcEntry
        ACCESS not-accessible
        STATUS mandatory
        DESCRIPTION
          "NAME = ;
           DESC = The Frame Relay LAN SPVC Connections \
                  table(Configurational);
           HELP = ;
           CAPABILITIES =NET_CFG, VPN_CFG;"
         ::= {fr-configuration 20}

nvmFrLANSpvcEntry OBJECT-TYPE
        SYNTAX   NvmFrLANSpvcEntry
        ACCESS   not-accessible
        STATUS   mandatory
	DESCRIPTION
	  "NAME = ;
	   DESC = An entry in the Frame Relay LAN SPVC \
                  Connections table. (Configurational);
           HELP = ;
	   CAPABILITIES = ;"
           INDEX { nvmFrLANSpvcVirtualPortIfIndex, nvmFrLANSpvcRemoteDLCI }
            ::= { nvmFrLANSpvcTable 1 }

NvmFrLANSpvcEntry ::= SEQUENCE {
           nvmFrLANSpvcVirtualPortIfIndex   INTEGER,
           nvmFrLANSpvcRemoteDLCI           INTEGER,
           nvmFrLANSpvcConnectId            INTEGER,
           nvmFrLANSpvcRemoteDNA            DisplayString,
           nvmFrLANSpvcConnType             INTEGER,
           nvmFrLANSpvcRowStatus            INTEGER
          }

nvmFrLANSpvcVirtualPortIfIndex OBJECT-TYPE
	SYNTAX	INTEGER (1..255)
	ACCESS	read-write
	STATUS	mandatory
	DESCRIPTION
	  "NAME = ;
           DESC = The ifIndex of the local Virtual Port \
                  (Analogous to the ifIndex pointer in the \
                  MIB II Interfaces Group, but specific to \
                  the FR End-to-End Connections table.);
           HELP = ; 
	   CAPABILITIES = ;"
	::= {nvmFrLANSpvcEntry 1}

nvmFrLANSpvcRemoteDLCI OBJECT-TYPE
	SYNTAX	INTEGER (16..991)
	ACCESS	read-write
	STATUS	mandatory
	DESCRIPTION
	  "NAME = ;
           DESC = The DLCI value on the remote DCE interface.
           HELP = ;
	   CAPABILITIES = ;"
	::= {nvmFrLANSpvcEntry 2}

nvmFrLANSpvcConnectId OBJECT-TYPE
	SYNTAX	INTEGER (0..65535)
	ACCESS	read-only
	STATUS	mandatory
	DESCRIPTION
	  "NAME = ;
           DESC = The connect ID of this SPVC mapping.\
                  Used to associate SVCs and Connect \
                  mappings.;
           HELP = ;
	   CAPABILITIES = ;"
	::= {nvmFrLANSpvcEntry 3}

nvmFrLANSpvcRemoteDNA OBJECT-TYPE
	SYNTAX	DisplayString (SIZE(1..34))
	ACCESS	read-write
	STATUS	mandatory
	DESCRIPTION
	  "NAME = ;
           DESC = The DNA of the remote node with which \
                  the SVC will be established.;
           HELP = ;
	   CAPABILITIES = ;"
	::= {nvmFrLANSpvcEntry 4}


nvmFrLANSpvcConnType OBJECT-TYPE
	SYNTAX	INTEGER { 
                slave  (1),
                master (2)
                }
	ACCESS	read-write
	STATUS	mandatory
	DESCRIPTION
	  "NAME = ;
           DESC =  The value of this object indicates \
                   whether this end of the SPVC segment \
                   initiated the SVC call.;
           HELP = ;
	   CAPABILITIES = ;"
	::= {nvmFrLANSpvcEntry 5}

nvmFrLANSpvcRowStatus OBJECT-TYPE
	SYNTAX	INTEGER { 
                active      (1),
                createAndGo (4),
                destroy     (6)
                }
	ACCESS	read-write
	STATUS	mandatory
	DESCRIPTION
	  "NAME = ;
           DESC =  This object is used to add new rows \
                   in the connection table, modify \
                   existing rows and to delete existing \
                   rows.;
           HELP = ;
	   CAPABILITIES = ;"
	::= {nvmFrLANSpvcEntry 6}

-- Parallel configuration table which provides the information
-- to identify the traffic parameters for a bi-directional
-- SVC segment.

nvmFrLANSpvcSVCTable OBJECT-TYPE
        SYNTAX SEQUENCE OF NvmFrLANSpvcSVCEntry 
        ACCESS not-accessible
        STATUS mandatory
        DESCRIPTION
          "NAME = ;
           DESC = The Frame Relay SVC Connect (Switched) \
                  Segment Configuration table.
           HELP = ;
           CAPABILITIES =NET_CFG, VPN_CFG;"
            ::= { fr-configuration 21}

nvmFrLANSpvcSVCEntry OBJECT-TYPE
        SYNTAX   NvmFrLANSpvcSVCEntry
        ACCESS   not-accessible
        STATUS   mandatory
	DESCRIPTION
	  "NAME = ;
	   DESC = An entry in the Frame Relay LAN SPVC \
                  Connections table.;
           HELP = ;
	   CAPABILITIES = ;"
           INDEX { nvmFrLANSpvcSVCConnectId }
            ::= { nvmFrLANSpvcSVCTable 1 }

 
NvmFrLANSpvcSVCEntry ::= SEQUENCE {
           nvmFrLANSpvcSVCConnectId                    INTEGER,
           nvmFrLANSpvcSVCDNA                          DisplayString,
           nvmFrLANSpvcSVCMaxTxSize                    INTEGER,
           nvmFrLANSpvcSVCMaxRxSize                    INTEGER,
           nvmFrLANSpvcSVCMinTxThroughput              INTEGER,
           nvmFrLANSpvcSVCMinRxThroughput              INTEGER,
           nvmFrLANSpvcSVCMaxTxThroughput              INTEGER,
           nvmFrLANSpvcSVCMaxRxThroughput              INTEGER,
           nvmFrLANSpvcSVCMaxTxBurstSize               INTEGER,
           nvmFrLANSpvcSVCMaxRxBurstSize               INTEGER,
           nvmFrLANSpvcSVCExcessTxBurstSize            INTEGER,
           nvmFrLANSpvcSVCExcessRxBurstSize            INTEGER,
           nvmFrLANSpvcSVCTransferPriority             INTEGER,
           nvmFrLANSpvcSVCDiscardPriority              INTEGER,
           nvmFrLANSpvcSVCSetupPriority                INTEGER,
           nvmFrLANSpvcSVCHoldingPriority              INTEGER
          }

nvmFrLANSpvcSVCConnectId OBJECT-TYPE
	SYNTAX	INTEGER (1..65535)
	ACCESS	read-only
	STATUS	mandatory
	DESCRIPTION
	  "NAME = ;
           DESC = The Connect Id of the Connection \
                  group entry to which this SVC \
		  belongs.
           HELP = ;
	   CAPABILITIES = ;"
	::= {nvmFrLANSpvcSVCEntry 1}

nvmFrLANSpvcSVCDNA OBJECT-TYPE
	SYNTAX	DisplayString (SIZE(1..34))
	ACCESS	read-write
	STATUS	mandatory
	DESCRIPTION
	  "NAME = ;
           DESC = The DNA for the destination of \
                  the virtual circuit.;
           HELP = ;
	   CAPABILITIES = ;"
	::= {nvmFrLANSpvcSVCEntry 2}

nvmFrLANSpvcSVCMaxTxSize OBJECT-TYPE
	SYNTAX	INTEGER (0..4096)
	ACCESS	read-write
	STATUS	mandatory
	DESCRIPTION
	  "NAME = ;
           DESC = The maximum transmission frame size. \
                  This should be equal to (or greater \
                  than) the Rx size for the corresponding \
                  PVC. Expressed in bytes.; 
           HELP = ;
	   CAPABILITIES = ;"
	::= {nvmFrLANSpvcSVCEntry 3}

nvmFrLANSpvcSVCMaxRxSize OBJECT-TYPE
	SYNTAX	INTEGER (0..4096)
	ACCESS	read-write
	STATUS	mandatory
	DESCRIPTION
	  "NAME = ;
           DESC = The maximum receivable frame size. \
                  This should be equal to (or less than) \
                  the Tx size for the corresponding PVC. \
                  Expressed in bytes.;
           HELP = ;
	   CAPABILITIES = ;"
	::= {nvmFrLANSpvcSVCEntry 4}

nvmFrLANSpvcSVCMinTxThroughput OBJECT-TYPE
	SYNTAX	INTEGER (0..2560000)
	ACCESS	read-write
	STATUS	mandatory
	DESCRIPTION
	  "NAME = ;
           DESC = The minimum transmission throughput. \
                  This should be equal to (or greater than) \
                  the Rx CIR for the corresponding PVC. \
                  Expressed in bits/sec.;
           HELP = ;
	   CAPABILITIES = ;"
	::= {nvmFrLANSpvcSVCEntry 5}

nvmFrLANSpvcSVCMinRxThroughput OBJECT-TYPE
	SYNTAX	INTEGER (0..2560000)
	ACCESS	read-write
	STATUS	mandatory
	DESCRIPTION
	  "NAME = ;
           DESC = The minimum receive throughput.\
                  This should be equal to (or less \
                  than) the Tx CIR for the corresponding \
                  PVC. Expressed in bits/sec.
           HELP = ;
	   CAPABILITIES = ;"
	::= {nvmFrLANSpvcSVCEntry 6}

nvmFrLANSpvcSVCMaxTxThroughput OBJECT-TYPE
	SYNTAX	INTEGER (0..2560000)
	ACCESS	read-write
	STATUS	mandatory
	DESCRIPTION
	  "NAME = ;
           DESC = The maximum transmission throughput.\
                  Always set to the value of \
                   nvmFrLANSpvcSVCMinTxThroughput.;
           HELP = ;
	   CAPABILITIES = ;"
	::= {nvmFrLANSpvcSVCEntry 7}

nvmFrLANSpvcSVCMaxRxThroughput OBJECT-TYPE
	SYNTAX	INTEGER (0..2560000)
	ACCESS	read-write
	STATUS	mandatory
	DESCRIPTION
	  "NAME = ;
           DESC = The maximum receive throughput. \
                  Always set to the value of \
                  nvmFrLANSpvcSVCMinRxThroughput.;
           HELP = ;
	   CAPABILITIES = ;"
	::= {nvmFrLANSpvcSVCEntry 8}

nvmFrLANSpvcSVCMaxTxBurstSize OBJECT-TYPE
	SYNTAX	INTEGER (0..2560000)
	ACCESS	read-write
	STATUS	mandatory
	DESCRIPTION
	  "NAME = ;
           DESC = The maximum transmission burst size \
                  Computation based on throughput and \
                  Excess Burst. Expressed in bits/sec.;
           HELP = ;
	   CAPABILITIES = ;"
	::= {nvmFrLANSpvcSVCEntry 9}

nvmFrLANSpvcSVCMaxRxBurstSize OBJECT-TYPE
	SYNTAX	INTEGER (0..2560000)
	ACCESS	read-write
	STATUS	mandatory
	DESCRIPTION
	  "NAME = ;
           DESC = The maximum receive burst size. \
                  Computation based on throughput and \
                  Excess Burst. Expressed in bits/sec.;
           HELP = ;
	   CAPABILITIES = ;"
	::= {nvmFrLANSpvcSVCEntry 10}

nvmFrLANSpvcSVCExcessTxBurstSize OBJECT-TYPE
	SYNTAX	INTEGER (0..2560000)
	ACCESS	read-write
	STATUS	mandatory
	DESCRIPTION
	  "NAME = ;
           DESC = The maximum number of uncommitted \
                  bits that the network will attempt \
                  to accept. This should be equal to \
                  (or greater than) the Rx Be configured for
                  the corresponding PVC. Expressed in \
                  bits/sec.;
           HELP = ;
	   CAPABILITIES = ;"
	::= {nvmFrLANSpvcSVCEntry 11}

nvmFrLANSpvcSVCExcessRxBurstSize OBJECT-TYPE
	SYNTAX	INTEGER (0..2560000)
	ACCESS	read-write
	STATUS	mandatory
	DESCRIPTION
	  "NAME = ;
           DESC = The maximum number of uncommitted bits \
                  that the network will attempt to deliver. \
                  This should be equal to (or less than) the \
                  Tx Be configured for the corresponding PVC \
                  Expressed in bits/sec.;
           HELP = ;
	   CAPABILITIES = ;"
	::= {nvmFrLANSpvcSVCEntry 12}

nvmFrLANSpvcSVCTransferPriority OBJECT-TYPE
	SYNTAX	INTEGER (0..15)
	ACCESS	read-write
	STATUS	mandatory
	DESCRIPTION
	  "NAME = ;
           DESC = The transfer priority for the corresponding \
                  pass-through connection.
                    
           HELP = ;
	   CAPABILITIES = ;"
	::= {nvmFrLANSpvcSVCEntry 13}


nvmFrLANSpvcSVCDiscardPriority OBJECT-TYPE
        SYNTAX INTEGER {
           low-discard-level     (1),
           medium-discard-level  (2),
           high-discard-level    (3)
           }
	ACCESS	read-write
	STATUS	mandatory
	DESCRIPTION
	  "NAME = ;
           DESC = The discard priority setup for \
                  the LAN SPVC SVC.;
           HELP = ;
	   CAPABILITIES = ;"
	::= {nvmFrLANSpvcSVCEntry 14}

nvmFrLANSpvcSVCSetupPriority OBJECT-TYPE
        SYNTAX INTEGER (1..5)
	ACCESS	read-write
	STATUS	mandatory
	DESCRIPTION
	  "NAME = ;
           DESC = This object specifies the priority of a path at \
		  call-establishment time, and also determines \
		  the potential for bumping established paths \
		  to acquire their bandwidth.  A value of 1 is \
		  the highest priority, and 5 is the lowest.;
           HELP = ;
	   CAPABILITIES = ;"
	DEFVAL { 2 }
	::= {nvmFrLANSpvcSVCEntry 15}

nvmFrLANSpvcSVCHoldingPriority OBJECT-TYPE
        SYNTAX INTEGER (1..5)
	ACCESS	read-write
	STATUS	mandatory
	DESCRIPTION
	  "NAME = ;
           DESC = This object specifies the priority that a path \
		  maintains once the path is established, and \
		  also determines the likelihood of being bumped \
		  by a new path, thus losing the bandwidth.  A value \
		  of 1 is the highest priority, and 5 is the lowest.;
           HELP = ;
	   CAPABILITIES = ;"
	DEFVAL { 2 }
	::= {nvmFrLANSpvcSVCEntry 16}



--   Parallel Frame Relay Tunnel PVC Table (Configuration)

--	This table was added to this MIB module for software releases
--	beginning with Release 3.0.

nvmFrTunnelPvcTable OBJECT-TYPE
        SYNTAX   SEQUENCE OF NvmFrTunnelPvcEntry
        ACCESS   not-accessible
        STATUS   mandatory
	DESCRIPTION
	  "NAME = ;
	   DESC = Table of entries for Frame Relay Tunnel PVCs \
		  for this access device. (Configuration);
	   HELP =;
	   CAPABILITIES = NET_CFG, VPN_DISP;"
         ::= { fr-configuration 24}

nvmFrTunnelPvcEntry OBJECT-TYPE
        SYNTAX   NvmFrTunnelPvcEntry
        ACCESS   not-accessible
        STATUS   mandatory
	DESCRIPTION
	  "NAME = ;
	   DESC = A row or entry in the Frame Relay Tunnel PVC \
		  Table. (Configuration);
	   HELP = ;
	   CAPABILITIES = ;"
           INDEX { nvmFrTunnelPvcIfIndex }
            ::= { nvmFrTunnelPvcTable 1 }

         NvmFrTunnelPvcEntry ::= SEQUENCE {
	nvmFrTunnelPvcIfIndex			INTEGER,
	nvmFrTunnelPvcDlciNumber 		INTEGER,
	nvmFrTunnelPvcPhysicalCard		INTEGER,
	nvmFrTunnelPvcPhysicalPort 		INTEGER,
	nvmFrTunnelPvcType 			INTEGER,
	nvmFrTunnelPvcPhysPortIfIndex 		INTEGER,
	nvmFrTunnelPvcMaxRxFrameSize    	INTEGER,
	nvmFrTunnelPvcRxBc			INTEGER,
	nvmFrTunnelPvcRxBe 			INTEGER,
        nvmFrTunnelPvcMaxRxCIR                  INTEGER,
	nvmFrTunnelPvcMaxTxFrameSize		INTEGER,
	nvmFrTunnelPvcTxBc			INTEGER,
	nvmFrTunnelPvcTxBe			INTEGER,
        nvmFrTunnelPvcMaxTxCIR                  INTEGER,
	nvmFrTunnelPvcRowStatus			INTEGER,
        nvmFrTunnelPvcConsecFrames              INTEGER,
        nvmFrTunnelPvcMinTxCIR                  INTEGER
		}

nvmFrTunnelPvcIfIndex OBJECT-TYPE
        SYNTAX   INTEGER (1..255)
        ACCESS   read-only
        STATUS   mandatory
	DESCRIPTION
	  "NAME = ;
	   DESC = The ifIndex of the tunnel PVC itself. \
		  (Configuration);
	   HELP = ;
	   CAPABILITIES = ;"
            ::= { nvmFrTunnelPvcEntry 1 }

nvmFrTunnelPvcDlciNumber OBJECT-TYPE
        SYNTAX   INTEGER (16..991)
        ACCESS   read-write
        STATUS   mandatory
	DESCRIPTION
	  "NAME = ;
	   DESC = The DLCI number for this PVC tunnel. \
		  Note that this object may only be configured \
		  during row creation.  (Configuration);
	   HELP = ;
	   CAPABILITIES = ;"
            ::= { nvmFrTunnelPvcEntry 2 }

nvmFrTunnelPvcPhysicalCard OBJECT-TYPE
        SYNTAX   INTEGER {
		limA (1),
		lim1 (2),
		lim2 (3),
		lim3 (4),
		lim4 (5)
		}
        ACCESS   read-write
        STATUS   mandatory
	DESCRIPTION
	  "NAME = ;
	   DESC = The Card (Logical Interface Module - LIM) \
		  of the WAN port (physical FR link). \
		  Note that this object may only be configured \
		  during row creation.  (Configuration);
	   HELP = ;
	   CAPABILITIES = ;"
            ::= { nvmFrTunnelPvcEntry 3 }

nvmFrTunnelPvcPhysicalPort OBJECT-TYPE
        SYNTAX   INTEGER (1..8)
        ACCESS   read-write
        STATUS   mandatory
	DESCRIPTION
	  "NAME = ;
	   DESC = The channel number of this WAN port. \
		  Note that this object may only be configured \
		  during row creation.  (Configuration);
	   HELP = ;
	   CAPABILITIES = ;"
            ::= { nvmFrTunnelPvcEntry 4 }

nvmFrTunnelPvcType OBJECT-TYPE
        SYNTAX   INTEGER {
		dte-panl (1),
		dce-panl (2),
		standard (3)
		}
        ACCESS   read-write
        STATUS   mandatory
	DESCRIPTION
	  "NAME = ;
	   DESC = The FR tunnel PVC type. \
		  Note that this object may only be configured \
		  during row creation.  (Configuration);
	   HELP = ;
	   CAPABILITIES = ;"
            ::= { nvmFrTunnelPvcEntry 5 }

nvmFrTunnelPvcPhysPortIfIndex OBJECT-TYPE
        SYNTAX   INTEGER (1..255)
        ACCESS   read-only
        STATUS   mandatory
	DESCRIPTION
	  "NAME = ;
	   DESC = The ifIndex of the FR physical port. \
		  (Configuration);
	   HELP = ;
	   CAPABILITIES = ;"
            ::= { nvmFrTunnelPvcEntry 6 }

nvmFrTunnelPvcMaxRxFrameSize OBJECT-TYPE
        SYNTAX   INTEGER (1..4096)
        ACCESS   read-write
        STATUS   mandatory
	DESCRIPTION
	  "NAME = ;
	   DESC = The maximum receive frame size in \
		  octets for this PVC tunnel data (sent into \
		  this unit). (Configuration);
	   HELP = ;
	   CAPABILITIES = ;"
	DEFVAL { 1604 }
            ::= { nvmFrTunnelPvcEntry 7 }

nvmFrTunnelPvcRxBc OBJECT-TYPE
        SYNTAX   INTEGER (0..2560000)
        ACCESS   read-write
        STATUS   mandatory
	DESCRIPTION
	  "NAME = ;
	   DESC = The receive committed burst size (Bc) in bits \
		  for this PVC tunnel data (sent into this unit). \
		  (Configuration);
	   HELP = ;
	   CAPABILITIES = ;"
	DEFVAL { 64000 }
            ::= { nvmFrTunnelPvcEntry 8 }

nvmFrTunnelPvcRxBe OBJECT-TYPE
        SYNTAX   INTEGER (0..2560000)
        ACCESS   read-only
        STATUS   mandatory
	DESCRIPTION
	  "NAME = ;
	   DESC = The receive excess burst size (Be) in bits \
		  for this PVC tunnel data (sent into this unit). \
		  (Configuration);
	   HELP = ;
	   CAPABILITIES = ;"
	DEFVAL { 64000 }
            ::= { nvmFrTunnelPvcEntry 9 }

nvmFrTunnelPvcMaxRxCIR OBJECT-TYPE
        SYNTAX   INTEGER (0..256000)
        ACCESS   read-write
        STATUS   mandatory
	DESCRIPTION
	  "NAME = ;
	   DESC = The maximum received throughput in \
                  bits per second. Used for FECN/BECN \
                  management. (Configuration);
	   HELP = ;
	   CAPABILITIES = ;"
	DEFVAL { 64000 }
            ::= { nvmFrTunnelPvcEntry 10 }

nvmFrTunnelPvcMaxTxFrameSize OBJECT-TYPE
        SYNTAX   INTEGER (1..4096)
        ACCESS   read-write
        STATUS   mandatory
	DESCRIPTION
	  "NAME = ;
	   DESC = The maximum transmission frame size in \
		  octets for this PVC tunnel data (sent out of \
		  this unit). (Configuration);
	   HELP = ;
	   CAPABILITIES = ;"
	DEFVAL { 1604 }
            ::= { nvmFrTunnelPvcEntry 11 }


nvmFrTunnelPvcTxBc OBJECT-TYPE
        SYNTAX   INTEGER (0..2560000)
        ACCESS   read-write
        STATUS   mandatory
	DESCRIPTION
	  "NAME = ;
	   DESC = The transmission committed burst size (Bc) in bits \
		  for this PVC tunnel data (sent out of this unit). \
		  (Configuration);
	   HELP = ;
	   CAPABILITIES = ;"
	DEFVAL { 64000 }
            ::= { nvmFrTunnelPvcEntry 12 }

nvmFrTunnelPvcTxBe OBJECT-TYPE
        SYNTAX   INTEGER (0..2560000)
        ACCESS   read-only
        STATUS   mandatory
	DESCRIPTION
	  "NAME = ;
	   DESC = The transmission excess burst size (Be) in bits \
		  for this PVC tunnel data (sent out of this unit). \
		  (Configuration);
	   HELP = ;
	   CAPABILITIES = ;"
	DEFVAL { 64000 }
            ::= { nvmFrTunnelPvcEntry 13 }

nvmFrTunnelPvcMaxTxCIR OBJECT-TYPE
        SYNTAX   INTEGER (0..256000)
        ACCESS   read-write
        STATUS   mandatory
	DESCRIPTION
	  "NAME = ;
	   DESC = The maximum transmit throughput in \
		  bits per second. Used for FECN/BECN \
                  management.  (Configuration);
	   HELP = ;
	   CAPABILITIES = ;"
	DEFVAL { 64000 }
            ::= { nvmFrTunnelPvcEntry 14 }

nvmFrTunnelPvcRowStatus OBJECT-TYPE
        SYNTAX   INTEGER {
		add (1),
		delete (2),
		active (3)
		}
        ACCESS   read-write
        STATUS   mandatory
	DESCRIPTION
	  "NAME = ;
	   DESC = This object is used to add new rows or delete \
		  existing rows in this FR Tunneling PVC \
		  table. (Configuration);
	   HELP = ;
	   CAPABILITIES = ;"
            ::= { nvmFrTunnelPvcEntry 15 }

nvmFrTunnelPvcConsecFrames OBJECT-TYPE
        SYNTAX   INTEGER (1..100)
        ACCESS   read-write
        STATUS   mandatory
	DESCRIPTION
	  "NAME = ;
	   DESC = The number of consecutive frames received\
		  with the BECN bit set before reducing \
                  the transmit rate. Used for FECN/BECN \
                  management.  (Configuration);
	   HELP = ;
	   CAPABILITIES = ;"
	DEFVAL { 10 }
            ::= { nvmFrTunnelPvcEntry 16 }

nvmFrTunnelPvcMinTxCIR OBJECT-TYPE
        SYNTAX   INTEGER (0..256000)
        ACCESS   read-write
        STATUS   mandatory
	DESCRIPTION
	  "NAME = ;
	   DESC = The minimum transmit throughput in \
		  bits per second. Used for FECN/BECN \
                  management.  (Configuration);
	   HELP = ;
	   CAPABILITIES = ;"
	DEFVAL { 64000 }
            ::= { nvmFrTunnelPvcEntry 17 }



-- Parallel Frame Relay Virtual Port to Netlink 
--	(Tunnel PVC) Map Table

nvmFrNetlinkMapTable OBJECT-TYPE
	SYNTAX	SEQUENCE OF NvmFrNetlinkMapEntry
	ACCESS	not-accessible
	STATUS	mandatory
	DESCRIPTION
	  "NAME = ;
	   DESC = Table for mapping Netlinks (Tunnel PVC ifIndex \
	 	  values) to Virtual Ports. (Configuration);
	   HELP = ;
	   CAPABILITIES = NET_CFG, VPN_DISP;"
	::= {fr-configuration 26}

nvmFrNetlinkMapEntry OBJECT-TYPE
	SYNTAX	NvmFrNetlinkMapEntry
	ACCESS	not-accessible
	STATUS	mandatory
	DESCRIPTION
	  "NAME = ;
	   DESC = Entry in the table for mapping Netlinks \
		  (Tunnel PVC ifIndex values) to Virtual \
		  Ports. (Configuration);
	   HELP = ;
	   CAPABILITIES = ;"
	INDEX	{nvmFrNetlinkMapVPIfIndex, 
		nvmFrNetlinkMapNetlinkIfIndex}
	::= {nvmFrNetlinkMapTable 1}

NvmFrNetlinkMapEntry ::= SEQUENCE {
	nvmFrNetlinkMapVPIfIndex	INTEGER,
	nvmFrNetlinkMapNetlinkIfIndex	INTEGER,
	nvmFrNetlinkMapRowStatus	INTEGER
	}

nvmFrNetlinkMapVPIfIndex OBJECT-TYPE
	SYNTAX	INTEGER (1..255)
	ACCESS	read-only
	STATUS	mandatory
	DESCRIPTION
	  "NAME = ;
	   DESC = Virtual port ifIndex associated \
		  with this Netlink (Tunnel PVC). \
		  (Configuration);
	   HELP = ;
	   CAPABILITIES = ;"
	::=  { nvmFrNetlinkMapEntry 1}

nvmFrNetlinkMapNetlinkIfIndex OBJECT-TYPE
	SYNTAX	INTEGER (1..255)
	ACCESS	read-only
	STATUS	mandatory
	DESCRIPTION
	  "NAME = ;
	   DESC = Netlink (Tunnel PVC) ifIndex associated \
		  with the specified Virtual Port. \
		  (Configuration);
	   HELP = ;
	   CAPABILITIES = ;"
	::=  { nvmFrNetlinkMapEntry 2}

nvmFrNetlinkMapRowStatus OBJECT-TYPE
	SYNTAX	INTEGER {
		add (1),
		delete (2),
		active (3)
		}
	ACCESS	read-write
	STATUS	mandatory
	DESCRIPTION
	  "NAME = ;
	   DESC = This object is used to add new rows or delete \
		  existing rows in this Virtual Port to Netlink \
		  Mapping table. (Configuration) ;
	   HELP = ;
	   CAPABILITIES = ;"
	::=  {nvmFrNetlinkMapEntry 3}



  -- The Frame Relay Counter Reset Group

  -- The FR Physical Port Counter Table

mcmFrPhyPortCntrTable OBJECT-TYPE
	SYNTAX  SEQUENCE OF McmFrPhyPortCntrEntry
	ACCESS  not-accessible
	STATUS  obsolete
	DESCRIPTION
	  "NAME = ;
	   DESC = This table has been OBSOLETED for software \
		  releases beginning with Release 3.0. \
		  Table to reset Frame Relay physical \
		  port counters;
	   HELP = ;
	   CAPABILITIES = NET_CFG, VPN_DISP;"
			::= { fr-control 1 }

mcmFrPhyPortCntrEntry OBJECT-TYPE
	SYNTAX  McmFrPhyPortCntrEntry
	ACCESS  not-accessible
	STATUS obsolete
	DESCRIPTION
	  "NAME = ;
	   DESC = Entry in the Frame Relay Physical \
		  port counters table;
	   HELP = ;
	   CAPABILITIES = ;"
	INDEX   { mcmFrPhyPortCntrIfIndex }
		::= { mcmFrPhyPortCntrTable 1 }

	McmFrPhyPortCntrEntry ::= SEQUENCE {
		mcmFrPhyPortCntrIfIndex 	INTEGER,
		mcmFrPhyPortCntrAction 		INTEGER
	}


mcmFrPhyPortCntrIfIndex	OBJECT-TYPE
	SYNTAX	INTEGER
	ACCESS	read-write
	STATUS	obsolete
	DESCRIPTION
	  "NAME = ;
	   DESC = The ifIndex of the physical port whose \
		  counters are to be reset;
	   HELP = ;
	   CAPABILITIES = ;"
	::= { mcmFrPhyPortCntrEntry 1 }

mcmFrPhyPortCntrAction OBJECT-TYPE
	SYNTAX  INTEGER { reset(1), other(2) }
	ACCESS	write-only
	STATUS  obsolete
	DESCRIPTION
	  "NAME = ;
	   DESC = Action to be taken on counters (reset);
	   HELP = When set to reset, the physical port \
		  counters should be zeroed out for the \
		  specified ifIndex;
	   CAPABILITIES = ;"
	::= { mcmFrPhyPortCntrEntry 2 }

  -- The FR Virtual Port Counter Table

mcmFrVirtualPortCntrTable OBJECT-TYPE
	SYNTAX  SEQUENCE OF McmFrVirtualPortCntrEntry
	ACCESS  not-accessible
	STATUS  obsolete
	DESCRIPTION
	  "NAME = ;
	   DESC = This table has been OBSOLETED for  software \
		  releases beginning with Release 3.0. \
		  Table to reset the Frame Relay \
		  virtual port counters;
	   HELP = ;
	   CAPABILITIES = NET_CFG, VPN_DISP;"
			::= { fr-control 2 }

mcmFrVirtualPortCntrEntry OBJECT-TYPE
	SYNTAX  McmFrVirtualPortCntrEntry
	ACCESS  not-accessible
	STATUS  obsolete
	DESCRIPTION
	  "NAME = ;
	   DESC = Entry in the virtual port counter \
		  table;
	   HELP = ;
	   CAPABILITIES = ;"
	INDEX   { mcmFrVirtualPortCntrIfIndex }
		::= { mcmFrVirtualPortCntrTable 1 }

	McmFrVirtualPortCntrEntry ::= SEQUENCE {
		mcmFrVirtualPortCntrIfIndex 		INTEGER,
		mcmFrVirtualPortCntrAction 		INTEGER
	}


mcmFrVirtualPortCntrIfIndex	OBJECT-TYPE
	SYNTAX	INTEGER
	ACCESS	read-write
	STATUS	obsolete
	DESCRIPTION
	  "NAME = ;
	   DESC = The ifIndex of the virtual port whose \
		  counters are to be reset;
	   HELP = ;
	   CAPABILITIES = ;"
	::= { mcmFrVirtualPortCntrEntry 1 }

mcmFrVirtualPortCntrAction OBJECT-TYPE
	SYNTAX  INTEGER { reset(1), other(2) }
	ACCESS	write-only
	STATUS  obsolete
	DESCRIPTION
	  "NAME = ;
	   DESC = Action to be taken on the counters (reset);
	   HELP = When set to reset, the virtual port \
		  counters should be zeroed out for the \
		  specified ifIndex;
	   CAPABILITIES = ;"
	::= { mcmFrVirtualPortCntrEntry 2 }

  -- The FR PVC Counter Table

mcmFrPVCCntrTable OBJECT-TYPE
	SYNTAX  SEQUENCE OF McmFrPVCCntrEntry
	ACCESS  not-accessible
	STATUS  obsolete
	DESCRIPTION
	  "NAME = ;
	   DESC = This table has been OBSOLETED for  software \
		  releases beginning with Release 3.0. \
		  Table used to reset counters \
		  associated with the PVC;
	   HELP = ;
	   CAPABILITIES = NET_CFG, VPN_DISP;"
			::= { fr-control 3 }

mcmFrPVCCntrEntry OBJECT-TYPE
	SYNTAX  McmFrPVCCntrEntry
	ACCESS  not-accessible
	STATUS  obsolete
	DESCRIPTION
	  "NAME = ;
	   DESC = Entry in the PVC counter reset \
		  table;
	   HELP = ;
	   CAPABILITIES = ;"
	INDEX   { mcmFrPVCCntrIfIndex, mcmFrPVCCntrDLCI }
		::= { mcmFrPVCCntrTable 1 }

	McmFrPVCCntrEntry ::= SEQUENCE {
		mcmFrPVCCntrIfIndex 		INTEGER,
		mcmFrPVCCntrDLCI 		INTEGER,
		mcmFrPVCCntrAction 		INTEGER
	}


mcmFrPVCCntrIfIndex	OBJECT-TYPE
	SYNTAX	INTEGER
	ACCESS	read-write
	STATUS	obsolete
	DESCRIPTION
	  "NAME = ;
	   DESC = Ifindex associated with the pvc.;
	   HELP = The ifIndex of the physical port \
		  associated with the PVC whose \
		  counters are to be reset;
	   CAPABILITIES = ;"
	::= { mcmFrPVCCntrEntry 1 }

mcmFrPVCCntrDLCI	OBJECT-TYPE
	SYNTAX	INTEGER (17..126975)
	ACCESS	read-write
	STATUS	obsolete
	DESCRIPTION
	  "NAME = ;
	   DESC = The DLCI number of the PVC whose \
		  counters are to be reset;
	   HELP = ;
	   CAPABILITIES = ;"
	::= { mcmFrPVCCntrEntry 2 }

mcmFrPVCCntrAction OBJECT-TYPE
	SYNTAX  INTEGER { reset(1), other(2) }
	ACCESS	write-only
	STATUS  obsolete
	DESCRIPTION
	  "NAME = ;
	   DESC = Action to be taken on the PVC \
		  counter (reset);
	   HELP = When set to reset, the PVC Counters \
		  get reset;
	   CAPABILITIES = ;"
	::= { mcmFrPVCCntrEntry 3 }


  -- The FR SVC Counter Table

mcmFrSVCCntrTable OBJECT-TYPE
	SYNTAX  SEQUENCE OF McmFrSVCCntrEntry
	ACCESS  not-accessible
	STATUS  obsolete
	DESCRIPTION
	  "NAME = ;
	   DESC = This table has been OBSOLETED for  software \
		  releases beginning with Release 3.0. \
		  Table used to reset counters \
		  associated with the SVC;
	   HELP = ;
	   CAPABILITIES = NET_CFG, VPN_DISP;"
			::= { fr-control 4 }

mcmFrSVCCntrEntry OBJECT-TYPE
	SYNTAX  McmFrSVCCntrEntry
	ACCESS  not-accessible
	STATUS  obsolete
	DESCRIPTION
	  "NAME = ;
	   DESC = Entry int the SVC Counter table;
	   HELP = ;
	   CAPABILITIES = ;"
	INDEX   { mcmFrSVCCntrIfIndex, mcmFrSVCCntrDNA }
		::= { mcmFrSVCCntrTable 1 }

	McmFrSVCCntrEntry ::= SEQUENCE {
		mcmFrSVCCntrIfIndex 		INTEGER,
		mcmFrSVCCntrDNA 		OCTET STRING,
		mcmFrSVCCntrAction 		INTEGER
	}


mcmFrSVCCntrIfIndex	OBJECT-TYPE
	SYNTAX	INTEGER
	ACCESS	read-write
	STATUS	obsolete
	DESCRIPTION
	  "NAME = ;
	   DESC = Ifindex associated with the SVC \
		  for which the counters are to be\
	          reset;
	   HELP = ;
	   CAPABILITIES = ;"
	::= { mcmFrSVCCntrEntry 1 }

mcmFrSVCCntrDNA	OBJECT-TYPE
	SYNTAX	OCTET STRING (SIZE(3..30)) 
	ACCESS	read-write
	STATUS	obsolete
	DESCRIPTION
	  "NAME = ;
	   DESC = The DNA associated with the SVC \
		  whose counters are to be reset;
	   HELP = ;
	   CAPABILITIES = ;"
	::= { mcmFrSVCCntrEntry 2 }

mcmFrSVCCntrAction OBJECT-TYPE
	SYNTAX  INTEGER { reset(1), other(2) }
	ACCESS	write-only
	STATUS  obsolete
	DESCRIPTION
	  "NAME = ;
	   DESC = Action to take on the SVC \
	          counters (reset);
	   HELP = When set to reset, the SVC \
		  counters should be reset;
	   CAPABILITIES = ;"
	::= { mcmFrSVCCntrEntry 3 }

-- Trap Messages

mcmFrWanLinkUp TRAP-TYPE
	ENTERPRISE	micom-frame-relay
	VARIABLES	{ mcmSysAsciiTimeOfDay, mcmSysIfExtModule, mcmSysIfExtPPA }
	DESCRIPTION
	  "NAME = ;
	   DESC = FR TRAP message: indication of WAN link \
                  up.\
		  Severity Level: INFORMATIVE.;
	   HELP = The Frame Relay WAN LINK is up. \
                  Normal status Indicator.;"
	::= 1

mcmFrWanLinkDown TRAP-TYPE
	ENTERPRISE	micom-frame-relay
	VARIABLES	{ mcmSysAsciiTimeOfDay,mcmSysIfExtModule,mcmSysIfExtPPA }
	DESCRIPTION
	  "NAME = ;
	   DESC = FR TRAP message: indication of WAN link \
                  down.\
		  Severity Level: CRITICAL.;
	   HELP = Loss of Physical connection, or LMI is dropped.\
                  Please check the physical connection; the MPANL \
                  LMI status, and provisioning on Passport. If  \
                  no change, contact Sys Admin., or Field \
                  Personnel.;"
	::= 2

-- End of Trap Messages 

END
