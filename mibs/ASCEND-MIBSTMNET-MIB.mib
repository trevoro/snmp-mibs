--			Ascend mibstmnet MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBSTMNET-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibsTMNetworkProfile  OBJECT IDENTIFIER ::= { configuration 123}

	-- The mibsTMNetworkProfile table
	--
	-- This table contains parameters for the mibsTMNetworkProfile profile
	--

    mibsTMNetworkProfileTable	OBJECT-TYPE
	SYNTAX		SEQUENCE OF MibsTMNetworkProfileEntry
	ACCESS		not-accessible
	STATUS		mandatory
	DESCRIPTION	"A list of mibsTMNetworkProfile profile entries."
	::= { mibsTMNetworkProfile 1 }

    mibsTMNetworkProfileEntry	OBJECT-TYPE
	SYNTAX		MibsTMNetworkProfileEntry
	ACCESS		not-accessible
	STATUS		mandatory
	DESCRIPTION	"A mibsTMNetworkProfile entry containing objects that
			 maps to the parameters of mibsTMNetworkProfile profile."
	INDEX		{ sTMNetworkProfile-Shelf-o, sTMNetworkProfile-Slot-o, sTMNetworkProfile-Item-o }
	::= { mibsTMNetworkProfileTable 1 }

    MibsTMNetworkProfileEntry ::=
	SEQUENCE {
	    sTMNetworkProfile-Shelf-o
		INTEGER,
	    sTMNetworkProfile-Slot-o
		INTEGER,
	    sTMNetworkProfile-Item-o
		INTEGER,
	    sTMNetworkProfile-Name
		DisplayString,
	    sTMNetworkProfile-PhysicalAddress-Shelf
		INTEGER,
	    sTMNetworkProfile-PhysicalAddress-Slot
		INTEGER,
	    sTMNetworkProfile-PhysicalAddress-ItemNumber
		INTEGER,
	    sTMNetworkProfile-Enabled
		INTEGER,
	    sTMNetworkProfile-AuPointer
		INTEGER,
	    sTMNetworkProfile-Signaling
		INTEGER,
	    sTMNetworkProfile-LoopTiming
		INTEGER,
	    sTMNetworkProfile-Loopback
		INTEGER,
	    sTMNetworkProfile-ApsConfigName
		DisplayString,
	    sTMNetworkProfile-Action-o
		INTEGER
	}

    sTMNetworkProfile-Shelf-o	OBJECT-TYPE
	SYNTAX	INTEGER
	ACCESS	read-only
	STATUS	mandatory
	DESCRIPTION	""
	::= { mibsTMNetworkProfileEntry 1 }

    sTMNetworkProfile-Slot-o	OBJECT-TYPE
	SYNTAX	INTEGER
	ACCESS	read-only
	STATUS	mandatory
	DESCRIPTION	""
	::= { mibsTMNetworkProfileEntry 2 }

    sTMNetworkProfile-Item-o	OBJECT-TYPE
	SYNTAX	INTEGER
	ACCESS	read-only
	STATUS	mandatory
	DESCRIPTION	""
	::= { mibsTMNetworkProfileEntry 3 }

    sTMNetworkProfile-Name	OBJECT-TYPE
	SYNTAX	DisplayString
	ACCESS	read-write
	STATUS	mandatory
	DESCRIPTION	"Name of STM network line."
	::= { mibsTMNetworkProfileEntry 4 }

    sTMNetworkProfile-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibsTMNetworkProfileEntry 5 }

    sTMNetworkProfile-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibsTMNetworkProfileEntry 6 }

    sTMNetworkProfile-PhysicalAddress-ItemNumber	OBJECT-TYPE
	SYNTAX	INTEGER
	ACCESS	read-write
	STATUS	mandatory
	DESCRIPTION	"A number that specifies an addressable entity within the context of shelf and slot."
	::= { mibsTMNetworkProfileEntry 7 }

    sTMNetworkProfile-Enabled	OBJECT-TYPE
	SYNTAX	INTEGER {
		    no (1),
		    yes (2)
		}
	ACCESS	read-write
	STATUS	mandatory
	DESCRIPTION	"TRUE if the link is enabled, otherwise FALSE."
	::= { mibsTMNetworkProfileEntry 10 }

    sTMNetworkProfile-AuPointer	OBJECT-TYPE
	SYNTAX	INTEGER {
		    au3Pointer (2),
		    au4Pointer (3)
		}
	ACCESS	read-write
	STATUS	mandatory
	DESCRIPTION	"The AU pointer used by this STM-1 link."
	::= { mibsTMNetworkProfileEntry 11 }

    sTMNetworkProfile-Signaling	OBJECT-TYPE
	SYNTAX	INTEGER {
		    sonet (2),
		    sdh (3),
		    japan (4)
		}
	ACCESS	read-write
	STATUS	mandatory
	DESCRIPTION	"The STM signaling to use on this STM link."
	::= { mibsTMNetworkProfileEntry 14 }

    sTMNetworkProfile-LoopTiming	OBJECT-TYPE
	SYNTAX	INTEGER {
		    no (1),
		    yes (2)
		}
	ACCESS	read-write
	STATUS	mandatory
	DESCRIPTION	"TRUE if the line is to use loop timing, otherwise FALSE."
	::= { mibsTMNetworkProfileEntry 8 }

    sTMNetworkProfile-Loopback	OBJECT-TYPE
	SYNTAX	INTEGER {
		    noLoopback (1),
		    lineLoopback (2),
		    localLoopback (3)
		}
	ACCESS	read-write
	STATUS	mandatory
	DESCRIPTION	"Loopback mode"
	::= { mibsTMNetworkProfileEntry 12 }

    sTMNetworkProfile-ApsConfigName	OBJECT-TYPE
	SYNTAX	DisplayString
	ACCESS	read-write
	STATUS	mandatory
	DESCRIPTION	"APS Config Profile name, specifies APS configuration profile that defines a protection group for this line."
	::= { mibsTMNetworkProfileEntry 13 }

    sTMNetworkProfile-Action-o	OBJECT-TYPE
	SYNTAX	INTEGER {
		    noAction (1),
		    createProfile (2),
		    deleteProfile (3)
		}
	ACCESS	read-write
	STATUS	mandatory
	DESCRIPTION	""
	::= { mibsTMNetworkProfileEntry 9 }

END
