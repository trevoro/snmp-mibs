--*********************************************************************
-- Copyright: Ericsson Telecom AB 2000
-- Doc no: 102/190 55-CAA 134 74 Uen
--
-- NAME ANS-EQUIPMENT-MIB.mib
--
-- REVISION HISTORY
--
-- The revision history is found in clearcase.
-- Use the 'ct lshistory' command to view it, or
-- use the program '/vobs/tools/bin/cc_mp' program to print
-- the file with the revision information.
-- 
-- Revision: Cox R0 rev A, 96-12-12
-- Revision: ADSL R1 rev PA1, 97-1-15
--           Added an extra bit field to the alarm status on the
--           board table, 2048: boardSoftwareError
-- Revision: ADSL R1 rev PA2, 97-1-21
-- 	     Added an extra bit field to the alarm status on the
--           board table, 4096: boardRuntimeWarning
-- Revision: ADSL R1 rev PA3, 97-02-26
--	     Increased the bit field for the alarm status on the
--	     board table.
-- Revision: ADSL R1 rev PA4, 97-05-13
--           EM_CR:0136
--           "number-of" SN, subracks, and board variables and
--           table attributes deleted. New index for slot and board
--           tables. 
--           Trap variables moved to ANS-TRAP-MIB
-- Revision: ADSL R2 rev PB1, 98-04-15
--           Added RowStatus for System Node and Subrack tables.
--           Added Physical Point and Next Subrack tables.
-- PB2 98-05-14 Tomas Pettersson
--		unlocked=1, locked=2. wbas added as subrack and node type.
-- PB3 98-05-18 Tomas Pettersson
--		Usage state added in board table.
--		Oper state changed to enabled,disabled. Admin state changed
--		to unlocked,locked.
-- PB4 98-06-02 Stefan Martinsson
--		Changed ansSubrackType from read-only to read-write.
-- PB5 98-06-04 Tomas Pettersson
--		Changed ansSlotConfiguredBoardId from read-only to read-write.
-- PB6 98-06-23 Tomas Pettersson
--		Added ansSubrackAlarmStatus subrackMismatch.
--		Next subrack table changed to use subrack type as index.
-- PB7 98-09-28 Ann Lindberg
--		Added ansBoardAlarmStatus incorrect_sw_version.
-- PB8 98-11-06 Ann Lindberg
--		Added ansBoardSyncMode.
-- PB9 98-11-23 Ann Lindberg
--		Not_used valid value for ansBoardSyncMode.
-- PB10 99-01-18 Tomas Pettersson
--		 The enum set of physical point type changed from
--		 sonet(1), e1(2), t1(3) to
--		 undefined(4), sdhUni(5), sdhUniTelia(6), sonetUni(7)
--		 to be in line with ME_API.
-- PC1	99-06-18	qtxoswi	Added Net Clock Source table
-- PC2  99-08-11        qtxoswi Changed access mode for ansSystemNodeOrigin
-- PC3  99-09-13        etxanlg Added syncmode netMaster for board.
-- PC4  99-09-14        qtxoswi Restored access mode for ansSystemNodeOrigin
-- PC4  00-03-13        etxlaaa Support creation of netClockSource
-- PC5  00-04-18        teiadeg Removed in the AnsSubrackType the "ce" value   (CR 94)  
-- PC6  00-05-30        teiadeg Changed the size of ansBoardSwIdCore and the size of ansBoardSwIdApplication
--                              from (0..36) to (29).
-- PC7  00-07-24        teiadeg Restrict the possible values of AnsSystemNodeType to wbas(8)   (TR HC15207)
-- PC7  00-07-26        teiadeg Changed AnsSystemNodeType for CR95. 
-- PC8  00-10-11        teiadeg Updated ansSubrackTable and ansSlotTable and ansBoardTable for Radio Node Protection. 
-- PC9  01-05-11        teigaba Updated for MIB Clean-up. 
-- PC10 01-08-03        teigaba Modified for CBR Data Handling. 
-- PC11 01-10-15        teigaba Changed branch. 




ANS-EQUIPMENT-MIB DEFINITIONS ::= BEGIN
IMPORTS
        OBJECT-TYPE
                FROM SNMPv2-SMI
	DisplayString
		FROM RFC1213-MIB
	RowPointer, RowStatus, mlpmpR115
		FROM ANS-COMMON-MIB;


equipment		OBJECT IDENTIFIER ::= {mlpmpR115 3}
systemNode		OBJECT IDENTIFIER ::= {equipment 1}
subrack			OBJECT IDENTIFIER ::= {equipment 2}
slot			OBJECT IDENTIFIER ::= {equipment 3}
board			OBJECT IDENTIFIER ::= {equipment 4}
physicalPoint		OBJECT IDENTIFIER ::= {equipment 5}
netClockSource		OBJECT IDENTIFIER ::= {equipment 6}


AnsSubrackType ::=
        	INTEGER	{
--		unknown (1),  Not supported by ME_API, so deleted in PA4
--		ce (2),       removed in PC5 (CR 94) 
--		fim (3),
--		nu (4),
--		other (5),
--		adsl (6),
		badvalue (-1),
		concentrator (7),
--		rf-shelf (8),
		wbas (9)
		}

ProtectedBoardType ::=
                  INTEGER {
                      wbas-rn(1)
                  }

-- *****************************************************************************
--                 System Node Group
-- *****************************************************************************

-- Common System Node Variables
-- Deleted in rev PA4


-- The ANS System Node Table

ansSystemNodeTable OBJECT-TYPE 
	SYNTAX	SEQUENCE OF AnsSystemNodeEntry
	ACCESS	not-accessible
	STATUS	mandatory
	DESCRIPTION
	"Lists of all system nodes in ANx."
	::= { systemNode 3 }

ansSystemNodeEntry OBJECT-TYPE 
	SYNTAX	AnsSystemNodeEntry
	ACCESS	not-accessible
	STATUS	mandatory
	DESCRIPTION ""
	INDEX { ansSystemNodeIndex }
	::= { ansSystemNodeTable 1 }

AnsSystemNodeEntry ::= SEQUENCE {
	ansSystemNodeIndex		INTEGER,
	ansSystemNodeName		DisplayString,
	ansSystemNodeOrigin		INTEGER,
	ansSystemNodeLocation		DisplayString,
	ansSystemNodeClockSource	INTEGER,
	ansSystemNodeRowStatus		RowStatus
}

ansSystemNodeIndex OBJECT-TYPE
	SYNTAX	INTEGER
	ACCESS	read-only
	STATUS	mandatory
	DESCRIPTION
		"A unique value for the system node."
	::= { ansSystemNodeEntry 1 }

ansSystemNodeName OBJECT-TYPE
	SYNTAX	DisplayString
	ACCESS	read-write
	STATUS	mandatory
	DESCRIPTION
		"An assigned name for the system node."
	::= { ansSystemNodeEntry 2 }

ansSystemNodeOrigin OBJECT-TYPE
	SYNTAX	INTEGER{
			native(1)
		}
	ACCESS	read-write
	STATUS	mandatory
	DESCRIPTION
		"'native' indicates that the system node is managed
		by this agent."
	::= { ansSystemNodeEntry 3 }

ansSystemNodeLocation OBJECT-TYPE
	SYNTAX	DisplayString
	ACCESS	read-write
	STATUS	mandatory
	DESCRIPTION
		"An indication where the system node is located.
		This could be indicated as a row/cabinet/shelf,
		a place in a building, and/or a street address."
	::= { ansSystemNodeEntry 4 }

ansSystemNodeClockSource OBJECT-TYPE
        SYNTAX  INTEGER{
                        undefined(1),
                        net-clock-source(2)
                }
        ACCESS  read-only
        STATUS  mandatory
        DESCRIPTION
                "'net-clock-source' indicates that in the system node
                is defined the Net Master."
        ::= { ansSystemNodeEntry 5 }

ansSystemNodeRowStatus OBJECT-TYPE
	SYNTAX	RowStatus
	ACCESS	read-write
	STATUS	mandatory
	DESCRIPTION
		""
	::= { ansSystemNodeEntry 6 }


-- *****************************************************************************
--                 Subrack Group
-- *****************************************************************************

-- Common Subrack Variables

-- Deleted in rev PA4


--  Subrack Table

ansSubrackTable OBJECT-TYPE 
	SYNTAX	SEQUENCE OF AnsSubrackEntry
	ACCESS	not-accessible
	STATUS	mandatory
	DESCRIPTION "Lists of all subracks in ANx."
	::= { subrack 2 }

ansSubrackEntry OBJECT-TYPE 
	SYNTAX	AnsSubrackEntry
	ACCESS	not-accessible
	STATUS	mandatory
	DESCRIPTION ""
	INDEX   { ansSubrackSystemNodeIndex, ansSubrackIndex }
	::= { ansSubrackTable 1 }

AnsSubrackEntry ::= SEQUENCE {
	ansSubrackSystemNodeIndex	INTEGER,
	ansSubrackIndex			INTEGER,
	ansSubrackName			DisplayString,
	ansSubrackHwId			DisplayString (SIZE(46)),
	ansSubrackLocation		DisplayString,
	ansSubrackType			AnsSubrackType,
        ansSubrackProtectionState       INTEGER, 
        ansSubrackProtectionScheme      DisplayString, 
        ansSubrackNoOfSlots		INTEGER,
	ansSubrackAlarmStatus		INTEGER,
	ansSubrackRowStatus		RowStatus
}

ansSubrackSystemNodeIndex OBJECT-TYPE
	SYNTAX	INTEGER
	ACCESS	read-only
	STATUS	mandatory
	DESCRIPTION
		"A reference to the associated system node."
	::= { ansSubrackEntry 1 }

ansSubrackIndex OBJECT-TYPE
	SYNTAX	INTEGER
	ACCESS	read-only
	STATUS	mandatory
	DESCRIPTION
		"A unique value for this subrack."
	::= { ansSubrackEntry 2 }

ansSubrackName OBJECT-TYPE
	SYNTAX	DisplayString
	ACCESS	read-write
	STATUS	mandatory
	DESCRIPTION
		"An assigned name for the subrack."
	::= { ansSubrackEntry 3 }

ansSubrackHwId OBJECT-TYPE
	SYNTAX	DisplayString(SIZE(46))
	ACCESS	read-write
	STATUS	mandatory
	DESCRIPTION
		"Hardware identity string stored in PROM in
		the subrack. The ASCII string is encoded as
		follows:
		ansSubrackHwId[0-15] : 
		   Procuct number (e.g. ROJ 212 16/1),
		   [16 ASCII characters]
		ansSubrackHwId[16-22] :
		   Version (e.g. P1C/3),
		   [7 ASCII characters]
		ansSubrackHwId[23-34] :
		   Serial number (e.g. A270000141)
		   [12 ASCII characters]
		ansSubrackHwId[35-40] :
		   Vendor (e.g. ETX)
		   [6 ASCII characters]
		ansSubrackHwId[31-44] :
		   Spare (not used)
		   [4 ASCII characters]
		ansSubrackHwId[45] :
		   CR (Carrige Return)
		   [1 ASCII character]"
	::= { ansSubrackEntry 4 }

ansSubrackLocation OBJECT-TYPE
	SYNTAX	DisplayString
	ACCESS	read-write
	STATUS	mandatory
	DESCRIPTION
		"An indication where the subrack is located.
		This could be indicated as a row/cabinet/shelf,
		a place in a building, and/or a street address."
	::= { ansSubrackEntry 5 }

ansSubrackType OBJECT-TYPE
	SYNTAX	AnsSubrackType
	ACCESS	read-write
	STATUS	mandatory
	DESCRIPTION
		"Identifies subrack type."
	::= { ansSubrackEntry 6 }

ansSubrackProtectionState    OBJECT-TYPE
        SYNTAX   INTEGER {
                       not-protected(1),
                       protected(2)
                       }
        ACCESS  read-write
        STATUS  mandatory
        DESCRIPTION
                ""
        DEFVAL {1}
        ::= { ansSubrackEntry 7 }



ansSubrackProtectionScheme    OBJECT-TYPE
        SYNTAX  DisplayString 
        ACCESS  read-only
        STATUS  mandatory
        DESCRIPTION
                ""
        ::= { ansSubrackEntry 8 }


ansSubrackNoOfSlots OBJECT-TYPE
	SYNTAX	INTEGER
	ACCESS	read-only
	STATUS	mandatory
	DESCRIPTION
		"The number of slots in the subrack."
	::= { ansSubrackEntry 9 }

ansSubrackAlarmStatus OBJECT-TYPE
	SYNTAX	INTEGER(0..255)
	ACCESS	read-only
	STATUS	mandatory
	DESCRIPTION
		"Bitmap indicating the current
		alarm status of the subrack.
		The status codes are:
		  0: subrackNoDefect
		  2: subrackCommunicationLost
		  4: subrackFanFailure
		  8: subrackPowerFailure
		 16: Not used.
		 32: subrackMismatch
		 64: Not used.
		128: Not used."
	::= { ansSubrackEntry 10 }

ansSubrackRowStatus OBJECT-TYPE
	SYNTAX	RowStatus
	ACCESS	read-write
	STATUS	mandatory
	DESCRIPTION
		""
	::= { ansSubrackEntry 11 }



-- *****************************************************************************
--                 Slot Group
-- *****************************************************************************

--  Slot Table

-- Entries in this table will be created/deleted
-- by the system as a result of the creation/deletion of a subrack.
-- An empty slot will take a zero length octet string for the
-- attribute 'ansSlotInsertedBoardId'.

ansSlotTable OBJECT-TYPE 
	SYNTAX	SEQUENCE OF AnsSlotEntry
	ACCESS	not-accessible
	STATUS	mandatory
	DESCRIPTION "This table contains pre-configured 
		and and actual board data for slots in ANx."
	::= { slot 1 }

ansSlotEntry OBJECT-TYPE 
	SYNTAX	AnsSlotEntry
	ACCESS	not-accessible
	STATUS	mandatory
	DESCRIPTION ""
	INDEX {ansSlotSystemNodeIndex, ansSlotSubrackIndex, ansSlotPosition }
	::= { ansSlotTable 1 }

AnsSlotEntry ::= SEQUENCE {
	ansSlotSystemNodeIndex		INTEGER,
	ansSlotSubrackIndex		INTEGER,
	ansSlotPosition			INTEGER,
	ansSlotConfiguredBoardId	DisplayString (SIZE(0..46)),
	ansSlotInsertedBoardId		DisplayString (SIZE(0..46)),
	ansSlotManagementStatus		INTEGER,
	ansSlotFallback		        INTEGER,
	ansSlotAlarmStatus		INTEGER
}

ansSlotSystemNodeIndex OBJECT-TYPE
	SYNTAX	INTEGER
	ACCESS	read-only
	STATUS	mandatory
	DESCRIPTION
		"A reference to the associated system node."
	::= { ansSlotEntry 1 }

ansSlotSubrackIndex OBJECT-TYPE
	SYNTAX	INTEGER
	ACCESS	read-only
	STATUS	mandatory
	DESCRIPTION
		"A reference to the associated subrack"
	::= { ansSlotEntry 2 }

ansSlotPosition OBJECT-TYPE
	SYNTAX	INTEGER
	ACCESS	read-only
	STATUS	mandatory
	DESCRIPTION
		"The value of this object identifies
		the slot within the subrack." 
	::= { ansSlotEntry 3 }

ansSlotConfiguredBoardId OBJECT-TYPE
	SYNTAX	DisplayString(SIZE(0..46))
	ACCESS	read-write
	STATUS	mandatory
	DESCRIPTION
		"Hardware identity string for the board
		configured for this slot.
		The string is encoded in the same way 
		as ansSlotInsertedBoardId."
	::= { ansSlotEntry 4 }

ansSlotInsertedBoardId OBJECT-TYPE
	SYNTAX	DisplayString(SIZE(0..46))
	ACCESS	read-only
	STATUS	mandatory
	DESCRIPTION
		"This variable contains the
		identification	string of the board
		inserted in this slot. 
		The ASCII string is encoded as follows:
		ansSlotInsertedBoardId[0-15] : 
		   Procuct number (e.g. ROJ 212 16/1),
		   [16 ASCII characters]
		ansSlotInsertedBoardId[16-22] :
		   Version (e.g. P1C/3),
		   [7 ASCII characters]
		ansSlotInsertedBoardId[23-34] :
		   Serial number (e.g. A270000141)
		   [12 ASCII characters]
		ansSlotInsertedBoardId[35-40] :
		   Vendor (e.g. ETX)
		   [6 ASCII characters]
		ansSlotInsertedBoardId[31-44] :
		   Spare (not used)
		   [4 ASCII characters]
		ansSlotInsertedBoardId[45] :
		   CR (Carrige Return)
		   [1 ASCII character]"
	::= { ansSlotEntry 5 }

ansSlotManagementStatus OBJECT-TYPE
	SYNTAX	INTEGER{
			managed(1),
			unmanaged(2),	
                        unconfigEmpty(3),	
                        configEmpty(4),
                        configBoard(5)
		}
	ACCESS	read-write
	STATUS	mandatory
	DESCRIPTION
		"This attribute shows the behaviour of a slot. 
		The following values are possible:
	    managed
		The slot is of management interest.
		Inserted boards will be detected and
		events/alarms will be generated for the
		slot.
	    unmanaged
		The slot is currently not of management
		interest. No events or alarms will be
		generated for this slot. Possible boards
		inserted in the slot will not be detected
		and can not be taken into service.
		Default value of this object is 'managed'.
	    unconfigEmpty
		Unconfigured empty slot.	
            configEmpty
		Configured empty slot, that did not previously contain a 
		matching board.
	    configBoard
		Board inserted in the slot that matches the data configured for
		the slot."
	::= { ansSlotEntry 6 }

ansSlotFallback  OBJECT-TYPE
       SYNTAX   INTEGER {
                         primary(1),
                         secondary(2)
                        }
       ACCESS   read-only
       STATUS   mandatory
       DESCRIPTION   
                "This variable indicates the fallback
                 of the slot."
       ::= { ansSlotEntry 7 }

ansSlotAlarmStatus OBJECT-TYPE
	SYNTAX	INTEGER(0..255)
	ACCESS	read-only
	STATUS	mandatory
	DESCRIPTION
		"	
		This variable indicates the current
		alarm status of the slot.
		Note that the first three states represent
		normal states.
		The different states are exclusive.
		The alarm codes are:
		  0: noDefectUnconfiguredEmptySlot
		     (unconfigured empty slot)
		  1: noDefectConfiguredEmptySlot
		     (configured empty slot, that did
		      not previously contain
		      a matching board)
		  2: noDefectMatchingBoardInserted
		     (board inserted in the slot
		      that matches the data 
		      configured for the slot)
		  4: boardRemoved
		     (matching board has
		      been removed from
		      the slot)
		  8: unconfiguredBoardInserted
		     (board inserted in an
		     	unconfigured slot)
		 16: boardMismatch
		     (board inserted in a slot
		     and the board does not 
		     match the data configured
		     for the slot)
		 32: boardUnrecognized
		     (unrecognized board
		      inserted in the slot)
		 64: Not used.
		128: Not used."
	::= { ansSlotEntry 8 }


-- *****************************************************************************
--                 Board Group
-- *****************************************************************************

-- Common Board Variables

-- Deleted in rev PA4

--  Board Table
-- The board table is a dynamic table an entry is added or removed as a result 
-- of the transition to/from the slot state 'Matching board inserted'.


ansBoardTable OBJECT-TYPE 
	SYNTAX	SEQUENCE OF AnsBoardEntry
	ACCESS	not-accessible
	STATUS	mandatory
	DESCRIPTION "This table contains all known boards 
		in ANx."
	::= { board 2 }

ansBoardEntry OBJECT-TYPE 
	SYNTAX	AnsBoardEntry
	ACCESS	not-accessible
	STATUS	mandatory
	DESCRIPTION ""
	INDEX {ansBoardSystemNodeIndex, ansBoardSubrackIndex, ansBoardPosition }
	::= { ansBoardTable 1 }

AnsBoardEntry ::= SEQUENCE {
	ansBoardSystemNodeIndex	INTEGER,
	ansBoardSubrackIndex	INTEGER,
	ansBoardPosition	INTEGER,
	ansBoardType		DisplayString (SIZE(0..20)),
	ansBoardHwId		DisplayString (SIZE(46)),
	ansBoardSwIdActive	DisplayString (SIZE(29)),
	ansBoardSwIdPassive	DisplayString (SIZE(29)),
	ansBoardOperStatus	INTEGER,
	ansBoardAdminStatus	INTEGER,
	ansBoardRestart		INTEGER,
	ansBoardLedStatus	INTEGER,
	ansBoardStandbyStatus	INTEGER,
	ansBoardAlarmStatus	INTEGER,
	ansBoardUsageState	INTEGER,
	ansBoardSyncMode	INTEGER
}
ansBoardSystemNodeIndex OBJECT-TYPE
	SYNTAX	INTEGER
	ACCESS	read-only
	STATUS	mandatory
	DESCRIPTION
		"A reference to the system node the 
		board belongs to."
	::= { ansBoardEntry 1 }

ansBoardSubrackIndex OBJECT-TYPE
	SYNTAX	INTEGER
	ACCESS	read-only
	STATUS	mandatory
	DESCRIPTION
		"A reference to the subrack the circuit board
		is inserted in."
	::= { ansBoardEntry 2 }

ansBoardPosition OBJECT-TYPE
	SYNTAX	INTEGER
	ACCESS	read-only
	STATUS	mandatory
	DESCRIPTION
		"A reference to the slot within a subrack
		the circuit board is inserted in."
	::= { ansBoardEntry 3 }


ansBoardType OBJECT-TYPE
	SYNTAX	DisplayString(SIZE(0..20))
	ACCESS	read-only
	STATUS	mandatory
	DESCRIPTION
		"Type of circuit board e.g.
		ET, RN, AT."
	::= { ansBoardEntry 4 }

ansBoardHwId OBJECT-TYPE
	SYNTAX	DisplayString(SIZE(46))
	ACCESS	read-only
	STATUS	mandatory
	DESCRIPTION
		"The identification string of the board
		The ASCII string is encoded as follows:
		ansBoardHwId[0-15] : 
		   Procuct number (e.g. ROJ 212 16/1),
		   [16 ASCII characters]
		ansBoardHwId[16-22] :
		   Version (e.g. P1C/3),
		   [7 ASCII characters]
		ansBoardHwId[23-34] :
		   Serial number (e.g. A270000141)
		   [12 ASCII characters]
		ansBoardHwId[35-40] :
		   Vendor (e.g. ETX)
		   [6 ASCII characters]
		ansBoardHwId[31-44] :
		   Spare (not used)
		   [4 ASCII characters]
		ansBoardHwId[45] :
		   CR (Carrige Return)
		   [1 ASCII character]"
	::= { ansBoardEntry 5 }

ansBoardSwIdActive OBJECT-TYPE
	SYNTAX	DisplayString(SIZE(29))
	ACCESS	read-only
	STATUS	mandatory
	DESCRIPTION
	  	"Identifies the core software load module
	     	of the DP
	     	The ASCII string is encoded as follows:
             	ansBoardSwIdCore[0-21]:
		   Product Number
		   [22 ASCII characters],
	        ansBoardSwIdCore[22-28]:
	           Version
	           [7 ASCII characters]"
	::= { ansBoardEntry 6 }

ansBoardSwIdPassive OBJECT-TYPE
	SYNTAX	DisplayString(SIZE(29))
	ACCESS	read-only
	STATUS	mandatory
	DESCRIPTION
		"Identifies the application load module
		of the DP
		The ASCII string is encoded as follows:
             	ansBoardSwIdApplication[0-21]:
		   Product Number
		   [22 ASCII characters],
	        ansBoardSwIdApplication[22-28]:
	           Version
	           [7 ASCII characters]"
	::= { ansBoardEntry 7 }

ansBoardOperStatus OBJECT-TYPE
	SYNTAX	INTEGER{
			enabled(1),
			disabled(2)
		}
	ACCESS	read-only
	STATUS	mandatory
	DESCRIPTION
		""
	::= { ansBoardEntry 8 }

ansBoardAdminStatus OBJECT-TYPE
	SYNTAX	INTEGER{
			unlocked(1),
			locked(2)
		}
	ACCESS	read-write
	STATUS	mandatory
	DESCRIPTION
		""
	::= { ansBoardEntry 9 }

ansBoardRestart OBJECT-TYPE
	SYNTAX	INTEGER{
			normal(1),
			restart(2)
		}
	ACCESS	read-write
	STATUS	mandatory
	DESCRIPTION
		"Initiates a restart of the DP."
	::= { ansBoardEntry 10 }


ansBoardLedStatus OBJECT-TYPE
	SYNTAX	INTEGER{
			redOff(1),
			redOn(2),
                        none(3)
		}
	ACCESS	read-only
	STATUS	mandatory
	DESCRIPTION
		"Indicates the status of the
		board's red LED. (The green LED indicates
		that the board is powered and is asumed to
		always to be on)
		redOff : No failure has been detected.
		redOn  : Failure has been detected."
	::= { ansBoardEntry 11 }


ansBoardStandbyStatus OBJECT-TYPE
        SYNTAX  INTEGER{
                        providing-service(1),
                        cold-standby(2),
                        null(3)
                }
        ACCESS  read-only
        STATUS  mandatory
        DESCRIPTION
                "Indicates the standby status of the
                 board."
        ::= { ansBoardEntry 12 }


ansBoardAlarmStatus OBJECT-TYPE
	SYNTAX	INTEGER(0..16383)
	ACCESS	read-only
	STATUS	mandatory
	DESCRIPTION
		"A bitmap that indicates the current
		alarm status of the circuit board.
		The alarm codes are:
		   0: boardNoDefect
		   1: boardFlashMemoryWarning
		   2: boardFlashMemoryError
		   4: boardRamWarning
		   8: boardRamError
		  16: boardEEPromWarning
		  32: boardEEPromError
		  64: boardMCNWarning
		 128: boardMCNError
		 256: Not Used.
		 512: boardRuntimeError
		1024: boardStartError
		2048: boardSoftwareError
		4096: boardRuntimeWarning
		8192: boardIncorrectSwVersion"
	::= { ansBoardEntry 13 }

ansBoardUsageState OBJECT-TYPE
	SYNTAX	INTEGER{
			idle(1),
			active(2)
		}
	ACCESS	read-only
	STATUS	mandatory
	DESCRIPTION
		"Usage State"
	::= { ansBoardEntry 14 }

ansBoardSyncMode OBJECT-TYPE
	SYNTAX	INTEGER{
			master(1),
			slave(2),
			netMaster(3),
			notUsed(4)
		}
	ACCESS	read-write
	STATUS	mandatory
	DESCRIPTION
		"Clocking mode"
	::= { ansBoardEntry 15 }



-- *****************************************************************************
--                 Physical Point Group
-- *****************************************************************************

-- The ANS Physical Point Table

ansPhysicalPointTable OBJECT-TYPE
	SYNTAX	SEQUENCE OF AnsPhysicalPointEntry
	ACCESS	not-accessible
	STATUS	mandatory
	DESCRIPTION
		"This table contains all known physical 
		points in ANx."
	::= { physicalPoint 1 }

ansPhysicalPointEntry OBJECT-TYPE 
	SYNTAX	AnsPhysicalPointEntry
	ACCESS	not-accessible
	STATUS	mandatory
	DESCRIPTION ""
	INDEX {ansPhysicalPointSystemNodeIndex, ansPhysicalPointSubrackIndex,
	       ansPhysicalPointPosition, ansPhysicalPointIndex }
	::= { ansPhysicalPointTable 1 }

AnsPhysicalPointEntry ::= SEQUENCE {
	ansPhysicalPointSystemNodeIndex		INTEGER,
	ansPhysicalPointSubrackIndex		INTEGER,
	ansPhysicalPointPosition		INTEGER,
	ansPhysicalPointIndex			INTEGER,
        ansDsPhysicalPointSystemNodeIndex       INTEGER,
        ansDsPhysicalPointSubrackIndex          INTEGER,
        ansDsPhysicalPointPosition              INTEGER,
        ansDsPhysicalPointIndex                 INTEGER,
	ansPhysicalPointType			INTEGER,
	ansPhysicalPointCategory		INTEGER,
	ansPhysicalPointOperStatus		INTEGER,
	ansPhysicalPointAdminStatus		INTEGER,
	ansPhysicalPointUsageState		INTEGER
}

ansPhysicalPointSystemNodeIndex OBJECT-TYPE
	SYNTAX	INTEGER
	ACCESS	read-only
	STATUS	mandatory
	DESCRIPTION
		"A reference to the system node the 
		physical point belongs to."
	::= { ansPhysicalPointEntry 1 }

ansPhysicalPointSubrackIndex OBJECT-TYPE
	SYNTAX	INTEGER
	ACCESS	read-only
	STATUS	mandatory
	DESCRIPTION
		"A reference to the subrack the 
		physical point belongs to."
	::= { ansPhysicalPointEntry 2 }

ansPhysicalPointPosition OBJECT-TYPE
	SYNTAX	INTEGER
	ACCESS	read-only
	STATUS	mandatory
	DESCRIPTION
		"A reference to the board within a subrack
		the physical point belongs to."
	::= { ansPhysicalPointEntry 3 }

ansPhysicalPointIndex OBJECT-TYPE
	SYNTAX	INTEGER
	ACCESS	read-only
	STATUS	mandatory
	DESCRIPTION
		""
	::= { ansPhysicalPointEntry 4 }

ansDsPhysicalPointSystemNodeIndex OBJECT-TYPE
        SYNTAX  INTEGER
        ACCESS  read-write
        STATUS  mandatory
        DESCRIPTION
                "A reference to the downstream system node."
        ::= { ansPhysicalPointEntry 5 }

ansDsPhysicalPointSubrackIndex OBJECT-TYPE
        SYNTAX  INTEGER
        ACCESS  read-write
        STATUS  mandatory
        DESCRIPTION
                "A reference to the downstream subrack."
        ::= { ansPhysicalPointEntry 6 }

ansDsPhysicalPointPosition OBJECT-TYPE
        SYNTAX  INTEGER
        ACCESS  read-write
        STATUS  mandatory
        DESCRIPTION
                "A reference to the downstream board within a subrack."
        ::= { ansPhysicalPointEntry 7 }

ansDsPhysicalPointIndex OBJECT-TYPE
        SYNTAX  INTEGER
        ACCESS  read-write
        STATUS  mandatory
        DESCRIPTION
                ""
        ::= { ansPhysicalPointEntry 8 }

ansPhysicalPointType OBJECT-TYPE
	SYNTAX	INTEGER{
--			sonet(1),
--			e1(2),
--			t1(3)
			undefined(4),
			sdhUni(5),
			sdhUniTelia(6),
			sonetUni(7)
		}
	ACCESS	read-only
	STATUS	mandatory
	DESCRIPTION
		""
	::= { ansPhysicalPointEntry 9 }

ansPhysicalPointCategory OBJECT-TYPE
	SYNTAX	INTEGER{
			service(1),
			user(2),
			serviceUser(3),
			internal(4)
		}
	ACCESS	read-write
	STATUS	mandatory
	DESCRIPTION
		""
	::= { ansPhysicalPointEntry 10 }

ansPhysicalPointOperStatus OBJECT-TYPE
	SYNTAX	INTEGER{
			enabled(1),
			disabled(2)
		}
	ACCESS	read-only
	STATUS	mandatory
	DESCRIPTION
		""
	::= { ansPhysicalPointEntry 11 }

ansPhysicalPointAdminStatus OBJECT-TYPE
	SYNTAX	INTEGER{
			unlocked(1),
			locked(2)
		}
	ACCESS	read-write
	STATUS	mandatory
	DESCRIPTION
		""
	::= { ansPhysicalPointEntry 12 }

ansPhysicalPointUsageState OBJECT-TYPE
	SYNTAX	INTEGER{
			idle(1),
			active(2)
		}
	ACCESS	read-only
	STATUS	mandatory
	DESCRIPTION
		""
	::= { ansPhysicalPointEntry 13 }


-- *****************************************************************************
-- 
--			Net Clock Source Table
--
-- *****************************************************************************

netClockSourceTable OBJECT-TYPE 
	SYNTAX	SEQUENCE OF NetClockSourceEntry
	ACCESS	not-accessible
	STATUS	mandatory
	DESCRIPTION
		"Net Clock Source Table"
	::= { netClockSource 1 }

netClockSourceEntry OBJECT-TYPE
	SYNTAX	NetClockSourceEntry
	ACCESS	not-accessible
	STATUS	mandatory
	DESCRIPTION
		"This entity represents a net clock source for circuit emulation
		 synchronization."
	INDEX {netClockSourceSystemNodeIndex}
	::= { netClockSourceTable 1 }

NetClockSourceEntry ::= SEQUENCE {
	netClockSourceSystemNodeIndex	INTEGER,
	netClockSourceSubrack		INTEGER,
	netClockSourceSlot		INTEGER,
	netClockSourcePort		INTEGER,
	netClockSourceStatus		INTEGER,
	netClockSourcePriorityList	DisplayString,
	netClockSourceRevertiveMode	INTEGER,
	netClockSourceTimeToRestore	INTEGER,
	netClockSourceRowStatus	RowStatus
}

--
--	This table is an extension of the ansSystemNodeTable and uses the index
--	(ansSystemNodeIndex)
--

netClockSourceSystemNodeIndex OBJECT-TYPE
	SYNTAX	INTEGER
	ACCESS	read-only
	STATUS	mandatory
	DESCRIPTION
		"System node used for synchronization."
	::= { netClockSourceEntry 1 }

netClockSourceSubrack	OBJECT-TYPE
	SYNTAX		INTEGER
	ACCESS		read-write
	STATUS		mandatory
	DESCRIPTION
		"Subrack used for synchronization"
	::= { netClockSourceEntry 2 }

netClockSourceSlot	OBJECT-TYPE
	SYNTAX		INTEGER
	ACCESS		read-write
	STATUS		mandatory
	DESCRIPTION
		"Slot used for synchronization"
	::= { netClockSourceEntry 3 }

netClockSourcePort	OBJECT-TYPE
	SYNTAX		INTEGER
	ACCESS		read-only
	STATUS		mandatory
	DESCRIPTION
		"Port used for synchronization"
	::= { netClockSourceEntry 4 }

netClockSourceStatus	OBJECT-TYPE
	SYNTAX		INTEGER{
				active(1),
				idle(2)
				}
	ACCESS		read-only
	STATUS		mandatory
	DESCRIPTION
		"..."
	::= { netClockSourceEntry 5 }

netClockSourcePriorityList OBJECT-TYPE
        SYNTAX  DisplayString
        ACCESS  read-write
        STATUS  mandatory
        DESCRIPTION
                "Priority list used for synchronization. [Port1,Port2,Port3,Port4]"
        ::= { netClockSourceEntry 6 }

netClockSourceRevertiveMode    OBJECT-TYPE
        SYNTAX          INTEGER{
                                revertive(1),
                                not-revertive(2),
                                not-used(3)
                                }
        ACCESS          read-write
        STATUS          mandatory
        DESCRIPTION
                "Revertive Mode used for synchronization.
                 Value: revertive,not-revertive,not-used"
        ::= { netClockSourceEntry 7 }

netClockSourceTimeToRestore      OBJECT-TYPE
	SYNTAX	        INTEGER(9..900)
        ACCESS          read-write
        STATUS          mandatory
        DESCRIPTION
                "Time to restore used for synchronization 
                 (9) not_used"
        ::= { netClockSourceEntry 8 }

netClockSourceRowStatus OBJECT-TYPE
	SYNTAX	RowStatus
	ACCESS	read-write
	STATUS	mandatory
	DESCRIPTION
		""
	::= { netClockSourceEntry 9 }

END
