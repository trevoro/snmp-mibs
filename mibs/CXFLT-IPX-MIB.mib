-- Filtering and priority information for IPX router.

CXFLT-IPX-MIB DEFINITIONS ::= BEGIN
 
    IMPORTS
        OBJECT-TYPE                     
            FROM RFC-1212
                cxFltIpx               
            FROM CXProduct-SMI;

      NetNumber ::= OCTET STRING(SIZE(4))

      cxFltIpxAddrTable OBJECT-TYPE
        SYNTAX  SEQUENCE OF CxFltIpxAddrEntry
        ACCESS  not-accessible
        STATUS  mandatory
        DESCRIPTION
"Provides the filtering/forwarding information for each IPX address. Each 
entry (row) in the table corresponds to a specific IPX address. Some of 
the values in a row may be modified. If additional IPX addresses are 
required they may be added."
          ::= { cxFltIpx 1 }


      cxFltIpxAddrEntry OBJECT-TYPE
          SYNTAX  CxFltIpxAddrEntry
          ACCESS  not-accessible
          STATUS  mandatory
          DESCRIPTION
"Provides the filtering/forwarding information for a specific IPX 
address."
          INDEX   { cxFltIpxIndex }
          ::= { cxFltIpxAddrTable 1 }

      CxFltIpxAddrEntry ::=
          SEQUENCE {
              cxFltIpxIndex
                INTEGER,    
          cxFltIpxSrcAddr
                NetNumber, 
           cxFltIpxDstAddr
                NetNumber,
           cxFltIpxParameter
            INTEGER,    
           cxFltIpxRowStatus
            INTEGER
    
          }

      cxFltIpxIndex  OBJECT-TYPE
          SYNTAX  INTEGER (1..65535)
          ACCESS  read-write
          STATUS  mandatory
          DESCRIPTION 
"Identifies the number used to index entries on the IPX 
filtering/forwarding table. The number provides access to all 
filtering/forwarding information for a source IPX address,  its associated 
destination address, and filtering/forwarding parameter. 

Range of Values: 1-32

Default Value: None

Configuration Changed:  administrative"
         ::= { cxFltIpxAddrEntry 1 }
         
          cxFltIpxSrcAddr OBJECT-TYPE
          SYNTAX  NetNumber
          ACCESS  read-write
          STATUS  mandatory
          DESCRIPTION
"Determines the source IPX address (network number) used for 
filtering/forwarding. This address corresponds to a destination address in 
cxFltIpxDstAddr of this table. The object cxFltIpxParameter determines 
whether data is filtered or forwarded from the source address to the 
destination address.

This number must be entered as 8 hexadecimal characters (four octets), for 
example 0xAB12CD34. The 0x must be present in every number; it indicates 
that the number is a hex number and is not counted as one of the octets. 
The x must be lowercase; the other characters are not case sensitive. 

Default Value: None

Range of Values: 4 octets, each character ranging from 00 to FF

Configuration Changed:  administrative"
          ::= { cxFltIpxAddrEntry 2 }


      cxFltIpxDstAddr OBJECT-TYPE
          SYNTAX  NetNumber
          ACCESS  read-write
          STATUS  mandatory
          DESCRIPTION
"Determines the destination IPX address (network number). This address 
corresponds to a source address in cxFltIpxSrcAddr on this table. The 
object cxFltIpxParameter determines whether data is filtered or forwarded 
from the source address to this destination address.

The address is an IPX network number. This number must be entered as 8 
hexadecimal characters (four octets), for example 0xAB12CD34. The 0x must 
be present in every number; it indicates that the number is a hex number 
and is not counted as one of the octets. The x must be lowercase; the 
other characters are not case sensitive. 

Range of Values: 4 octets, each character ranging from 00 to FF

Default Value: None

Configuration Changed:  administrative "
          ::= { cxFltIpxAddrEntry 3 }


     cxFltIpxParameter  OBJECT-TYPE
          SYNTAX  INTEGER {
                     discard(1),
                     forward(2),
                     priority-low(3),
                     priority-high(4)
                     
                  }
          ACCESS  read-write
          STATUS  mandatory
          DESCRIPTION 
"Determines the filtering/forwarding action and the priority processing 
for data sent from a source IPX address (cxFltIpxSrcAddr) to a destination 
IPX address (cxFltIpxDstAddr). 

Options:
discard (1) 

forward (2)

priority-low (3)

priority-high (4)

Default Value: discard (1)

Configuration Changed:  administrative "
          DEFVAL { discard }        
         ::= { cxFltIpxAddrEntry 4 }

    cxFltIpxRowStatus  OBJECT-TYPE
          SYNTAX  INTEGER {
                     invalid(1),
                     valid(2) 
                  }
          ACCESS  read-write
          STATUS  mandatory
          DESCRIPTION 
"Determines the status of the objects in a table row.

Options:
invalid (1): row is flagged, after the next reset, values are disabled and 
the row is deleted from the table.

valid (2): values are enabled

Default Value: valid (2)

Configuration Changed: administrative"
        DEFVAL { valid }
         ::= { cxFltIpxAddrEntry 5 }


END
