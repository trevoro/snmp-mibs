-- *****************************************************************************
-- Unisphere-Data-RADIUS-CLIENT-MIB
--
-- Unisphere Networks Enterprise MIB
-- RADIUS Client MIB
--
-- Copyright (c) 1999 Redstone Communications, Incorporated.
-- Copyright (c) 1999, 2002 Unisphere Networks, Incorporated.
-- All Rights Reserved.
-- *****************************************************************************

Unisphere-Data-RADIUS-CLIENT-MIB DEFINITIONS ::= BEGIN

IMPORTS
    MODULE-IDENTITY, OBJECT-TYPE, Counter32, Integer32, Gauge32, IpAddress,
    TimeTicks
        FROM SNMPv2-SMI
    DisplayString, RowStatus, TruthValue
        FROM SNMPv2-TC
    MODULE-COMPLIANCE, OBJECT-GROUP
        FROM SNMPv2-CONF
    usDataMibs
        FROM Unisphere-Data-MIBs;

usdRadiusClientMIB MODULE-IDENTITY
    LAST-UPDATED "200205131754Z"  -- 13-May-02 01:54 PM EDT
    ORGANIZATION "Unisphere Networks, Inc."
    CONTACT-INFO
        "       Unisphere Networks, Inc.
        Postal: 10 Technology Park Drive
                Westford, MA  01886
                USA
        Tel:    +1 978 589 5800
        Email:  mib@UnisphereNetworks.com"
    DESCRIPTION
        "The RADIUS Client MIB for the Unisphere Networks enterprise."
    -- Revision History
    REVISION    "200205131754Z"  -- 13-May-02 01:54 PM EDT  - RX 4.0
    DESCRIPTION
        "Added objects (parameters) to indicate which RADIUS attributes should
        be included/excluded from RADIUS packets."
    REVISION    "200110161954Z"  -- 16-Oct-01 03:54 PM EDT  - RX 3.3
    DESCRIPTION
        "Added usdRadiusClientNasIpAddrUse."
    REVISION    "200109062108Z"  -- 06-Sep-01 05:08 PM EDT  - RX 3.2
    DESCRIPTION
        "Added usdRadiusClientRollover and
        usdRadiusClientCallingStationIdFormat."
    REVISION    "200103221520Z"  -- 22-Mar-01 10:20 AM EST  - RX 3.1
    DESCRIPTION
        "Added usdRadiusClientEthernetPortType,
        usdRadiusClientIncludeIpAddrInAcctStart, and
        usdRadiusClientIncludeAcctSessionIdInAccessReq."
    REVISION    "200012191640Z"  -- 19-Dec-00 11:40 AM EST  - RX 3.0
    DESCRIPTION
        "Added support for the RADIUS accounting backoff mechanism."
    REVISION    "200005051944Z"  --  5-May-00  3:44 PM EDT  - RX 2.0
    DESCRIPTION
        "Added support for client source address."
    REVISION      "9906010000Z"  --  1-Jun-99               - RX 1.1
    DESCRIPTION
        "Initial version of this MIB module, derived from IETF Internet Drafts
        of RADIUS Client MIBs for Authentication and Accounting."
    ::= { usDataMibs 19 }


-- +++++++++++++++++++++++++++++++++++++++++++++++++++++++++++++++++++++++++++++
-- Textual conventions
-- +++++++++++++++++++++++++++++++++++++++++++++++++++++++++++++++++++++++++++++
-- No textual conventions are defined in this MIB


-- +++++++++++++++++++++++++++++++++++++++++++++++++++++++++++++++++++++++++++++
-- Managed object groups
-- +++++++++++++++++++++++++++++++++++++++++++++++++++++++++++++++++++++++++++++
usdRadiusClientObjects       OBJECT IDENTIFIER ::= {usdRadiusClientMIB 1}

usdRadiusGeneralClient       OBJECT IDENTIFIER ::= { usdRadiusClientObjects 1 }
usdRadiusAuthClient          OBJECT IDENTIFIER ::= { usdRadiusClientObjects 2 }
usdRadiusAcctClient          OBJECT IDENTIFIER ::= { usdRadiusClientObjects 3 }

-- +++++++++++++++++++++++++++++++++++++++++++++++++++++++++++++++++++++++++++++
-- Managed objects for RADIUS General
-- +++++++++++++++++++++++++++++++++++++++++++++++++++++++++++++++++++++++++++++
usdRadiusClientIdentifier OBJECT-TYPE
    SYNTAX      DisplayString
    MAX-ACCESS  read-only
    STATUS      current
    DESCRIPTION
        "The NAS-Identifier of the RADIUS client."
    ::= { usdRadiusGeneralClient 1 }

usdRadiusClientAlgorithm OBJECT-TYPE
    SYNTAX      INTEGER {
                    direct(0),
                    roundRobin(1) }
    MAX-ACCESS  read-write
    STATUS      current
    DESCRIPTION
        "The algorithm used by the client when multiple
        authentication/accounting servers are configured:
            direct      Use servers in order of precedence, each time beginning
                        with the highest precedence server and proceeding to
                        lower precedence servers if the the RADIUS request
                        fails, until the request succeeds or all servers have
                        been tried.
            roundRobin  Use servers in round-robin order, each time beginning
                        with the next round-robin-ordered server and proceeding
                        cyclically through servers if the RADIUS request fails,
                        until the request succeeds or all servers have been
                        tried."
    DEFVAL    { direct }
    ::= { usdRadiusGeneralClient 2 }

usdRadiusClientSourceAddress OBJECT-TYPE
    SYNTAX      IpAddress
    MAX-ACCESS  read-write
    STATUS      current
    DESCRIPTION
        "The source address used by the RADIUS client in requests to the RADIUS
        server.  The RADIUS server returns responses from this address.  Setting
        this object to 0.0.0.0 will reset the value to its default."
    DEFVAL    { 0 }
    ::= { usdRadiusGeneralClient 3}

usdRadiusClientUdpChecksum OBJECT-TYPE
    SYNTAX      TruthValue
    MAX-ACCESS  read-write
    STATUS      current
    DESCRIPTION
        "Enables/disables the checksum calculations on RADIUS UDP packets."
    DEFVAL    { true }
    ::= { usdRadiusGeneralClient 4 }

usdRadiusClientNasIdentifier OBJECT-TYPE
    SYNTAX      DisplayString (SIZE(0..64))
    MAX-ACCESS  read-write
    STATUS      current
    DESCRIPTION
        "The identifier used by the client for the value of NAS-Identifier
        attribute (number 32) in access and accounting requests.  The default is
        to use the system name."
    DEFVAL    { "" }
    ::= { usdRadiusGeneralClient 5 }

usdRadiusClientDslPortType OBJECT-TYPE
    SYNTAX      INTEGER {
                    virtual(5),
                    sdsl(11),
                    adsl-cap(12),
                    adsl-dmt(13),
                    idsl(14),
                    xdsl(16) }
    MAX-ACCESS  read-write
    STATUS      current
    DESCRIPTION
        "The value to use in the NAS-Port-Type RADIUS Attribute (attribute
        number 61) for DSL interfaces in the RADIUS access and accounting
        messages:
            virtual    Used for Virtual interfaces.
            sdsl       Used for Symmetric DSL.
            adsl-cap   Used for Asymmetric DSL, Carrierless Amplitude Phase
                       Modulation.
            adsl-dmt   Used for Asymmetric DSL, Discrete Multi-Tone.
            idsl       Used for ISDN Digital Subscriber Line.
            xdsl       Used for Digital Subscriber Line of unknown type."
    DEFVAL    { xdsl }
    ::= { usdRadiusGeneralClient 6 }

usdRadiusClientTunnelAccounting OBJECT-TYPE
    SYNTAX      TruthValue
    MAX-ACCESS  read-write
    STATUS      current
    DESCRIPTION
        "Enables/disables the tunnel accounting feature, which causes the system
        to send tunnel and session accounting requests."
    DEFVAL    { false }
    ::= { usdRadiusGeneralClient  7 }

usdRadiusClientAcctSessionIdFormat OBJECT-TYPE
    SYNTAX      INTEGER {
                    decimal(0),
                    description(1) }
    MAX-ACCESS  read-write
    STATUS      current
    DESCRIPTION
        "The format used by the client for the Acct-Session-ID attribute
        (attribute number 44):
            decimal      Use an ASCII decimal value only in the Acct-Session-ID
                         attribute.
            description  Use an ASCII description value which includes the
                         interface type (i.e. ATM), slot, port, and circuit
                         number (VPI and VCI for ATM), and a hexidecimal value
                         in the Acct-Session-ID attribute."
    DEFVAL    { description }
    ::= { usdRadiusGeneralClient 8 }

usdRadiusClientNasPortFormat OBJECT-TYPE
    SYNTAX      INTEGER {
                    xssssppp(0),
                    ssssxppp(1) }
    MAX-ACCESS  read-write
    STATUS      current
    DESCRIPTION
        "The format used by the client for the NAS-Port attribute (attribute
        number 5):
            xssssppp    In the NAS-Port attribute (attribute 5) use format of 0
                        bit, followed by 4 bits for the slot number, 3 bits for
                        the port number, and finally, the circuit number in the
                        remaining bits.
            ssssxppp    In the NAS-Port attribute (attribute 5) use format of 4
                        bits for the slot number, followed by a 0 bit, 3 bits
                        for the port number and finally, the circuit number in
                        the remaining bits."
    DEFVAL    { ssssxppp }
    ::= { usdRadiusGeneralClient 9 }

usdRadiusClientCallingStationDelimiter OBJECT-TYPE
    SYNTAX      DisplayString (SIZE(1))
    MAX-ACCESS  read-write
    STATUS      current
    DESCRIPTION
        "The character use as for delimiting fields in the Calling-Station-ID
        attribute (attribute 31, from RFC 2865) sent by the client.  The default
        value is '#'."
    DEFVAL    { "#" }
    ::= { usdRadiusGeneralClient 10 }

usdRadiusClientEthernetPortType OBJECT-TYPE
    SYNTAX      INTEGER {
                    virtual(5),
                    ethernet(15) }
    MAX-ACCESS  read-write
    STATUS      current
    DESCRIPTION
        "The value to use in the NAS-Port-Type RADIUS Attribute (attribute
        number 61) for Ethernet interfaces in the RADIUS access and accounting
        messages:
            ethernet   Used for Ethernet interfaces.
            virtual    Used for Virtual interfaces."
    DEFVAL    { ethernet }
    ::= { usdRadiusGeneralClient 11 }

usdRadiusClientIncludeIpAddrInAcctStart OBJECT-TYPE
    SYNTAX      TruthValue
    MAX-ACCESS  read-write
    STATUS      current
    DESCRIPTION
        "Enables/disables the inclusion of the Framed-IP-Address attribute in
        the RADIUS Acct-Start packet."
    DEFVAL    { true }
    ::= { usdRadiusGeneralClient 12 }

usdRadiusClientIncludeAcctSessionIdInAccessReq OBJECT-TYPE
    SYNTAX      TruthValue
    MAX-ACCESS  read-write
    STATUS      current
    DESCRIPTION
        "Enables/disables the inclusion of the Acct-Session-ID attribute in the
        RADIUS Access-Request packet."
    DEFVAL    { true }
    ::= { usdRadiusGeneralClient 13 }

usdRadiusClientRollover OBJECT-TYPE
    SYNTAX      TruthValue
    MAX-ACCESS  read-write
    STATUS      current
    DESCRIPTION
        "Enables/disables the rollover to next server on receipt of
        access-reject."
    DEFVAL    { false }
    ::= { usdRadiusGeneralClient 14 }

usdRadiusClientCallingStationIdFormat OBJECT-TYPE
    SYNTAX      INTEGER {
                    delimited(0),
                    fixedFormat(1) }
    MAX-ACCESS  read-write
    STATUS      current
    DESCRIPTION
        "The format used by the client for the Calling-Station-ID attribute
        (attribute number 31):
            delimited   In the Calling-Station-ID attribute (attribute 31) use
                        the format '<delimiter><BAS name><delimiter>
                        <interface description><delimiter><layer 2 identifier>'.
            fixedFomat  In the Calling-Station-ID attribute (attribute 31) use
                        the format of 4 bytes for the host name (truncated if
                        needed), 2 digits of slot, 1 digit of port, 3 digits of
                        VPI, followed by 5 digits of VCI."
    DEFVAL    { delimited }
    ::= { usdRadiusGeneralClient 15 }

usdRadiusClientNasIpAddrUse OBJECT-TYPE
    SYNTAX      INTEGER {
                    normal(0),
                    tunnelClientEndpoint(1) }
    MAX-ACCESS  read-write
    STATUS      current
    DESCRIPTION
        "The value used by the client for the NAS-IP-Addr attribute (attribute
        number 4):
            normal               Use the ERX IP address value in the NAS-IP-Addr
                                 attribute (attribute 4).
            tunnelClientEndpoint Use the Tunnel Client's address value in the
                                 NAS-IP-Addr attribute (attribute 4) for tunnel
                                 users."
    DEFVAL    { normal }
    ::= { usdRadiusGeneralClient 16 }

usdRadiusClientIncludeAcctTunnelConnectionInAccessReq OBJECT-TYPE
    SYNTAX      TruthValue
    MAX-ACCESS  read-write
    STATUS      current
    DESCRIPTION
        "Enables/disables the inclusion of the Acct-Tunnel-Connection attribute
        in the RADIUS Access-Request packet."
    DEFVAL    { true }
    ::= { usdRadiusGeneralClient 17 }

usdRadiusClientIncludeCalledStationIdInAccessReq OBJECT-TYPE
    SYNTAX      TruthValue
    MAX-ACCESS  read-write
    STATUS      current
    DESCRIPTION
        "Enables/disables the inclusion of the Called-Station-ID attribute in
        the RADIUS Access-Request packet."
    DEFVAL    { true }
    ::= { usdRadiusGeneralClient 18 }

usdRadiusClientIncludeCallingStationIdInAccessReq OBJECT-TYPE
    SYNTAX      TruthValue
    MAX-ACCESS  read-write
    STATUS      current
    DESCRIPTION
        "Enables/disables the inclusion of the Calling-Station-ID attribute in
        the RADIUS Access-Request packet."
    DEFVAL    { true }
    ::= { usdRadiusGeneralClient 19 }

usdRadiusClientIncludeConnectInfoInAccessReq OBJECT-TYPE
    SYNTAX      TruthValue
    MAX-ACCESS  read-write
    STATUS      current
    DESCRIPTION
        "Enables/disables the inclusion of the Connect-Info attribute in the
        RADIUS Access-Request packet."
    DEFVAL    { true }
    ::= { usdRadiusGeneralClient 20 }

usdRadiusClientIncludeNasIdentifierInAccessReq OBJECT-TYPE
    SYNTAX      TruthValue
    MAX-ACCESS  read-write
    STATUS      current
    DESCRIPTION
        "Enables/disables the inclusion of the NAS-Identifier attribute in the
        RADIUS Access-Request packet."
    DEFVAL    { true }
    ::= { usdRadiusGeneralClient 21 }

usdRadiusClientIncludeNasPortInAccessReq OBJECT-TYPE
    SYNTAX      TruthValue
    MAX-ACCESS  read-write
    STATUS      current
    DESCRIPTION
        "Enables/disables the inclusion of the NAS-Port attribute in the RADIUS
        Access-Request packet."
    DEFVAL    { true }
    ::= { usdRadiusGeneralClient 22 }

usdRadiusClientIncludeNasPortIdInAccessReq OBJECT-TYPE
    SYNTAX      TruthValue
    MAX-ACCESS  read-write
    STATUS      current
    DESCRIPTION
        "Enables/disables the inclusion of the NAS-Port-ID attribute in the
        RADIUS Access-Request packet."
    DEFVAL    { true }
    ::= { usdRadiusGeneralClient 23 }

usdRadiusClientIncludeNasPortTypeInAccessReq OBJECT-TYPE
    SYNTAX      TruthValue
    MAX-ACCESS  read-write
    STATUS      current
    DESCRIPTION
        "Enables/disables the inclusion of the NAS-Port-Type attribute in the
        RADIUS Access-Request packet."
    DEFVAL    { true }
    ::= { usdRadiusGeneralClient 24 }

usdRadiusClientIncludePppoeDescriptionInAccessReq OBJECT-TYPE
    SYNTAX      TruthValue
    MAX-ACCESS  read-write
    STATUS      current
    DESCRIPTION
        "Enables/disables the inclusion of the PPPoE-Description (VSA) attribute
        in the RADIUS Access-Request packet."
    DEFVAL    { true }
    ::= { usdRadiusGeneralClient 25 }

usdRadiusClientIncludeTunnelClientAuthIdInAccessReq OBJECT-TYPE
    SYNTAX      TruthValue
    MAX-ACCESS  read-write
    STATUS      current
    DESCRIPTION
        "Enables/disables the inclusion of the Tunnel-Client-Auth-Id attribute
        in the RADIUS Access-Request packet."
    DEFVAL    { true }
    ::= { usdRadiusGeneralClient 26 }

usdRadiusClientIncludeTunnelClientEndpointInAccessReq OBJECT-TYPE
    SYNTAX      TruthValue
    MAX-ACCESS  read-write
    STATUS      current
    DESCRIPTION
        "Enables/disables the inclusion of the Tunnel-Client-Endpoint attribute
        in the RADIUS Access-Request packet."
    DEFVAL    { true }
    ::= { usdRadiusGeneralClient 27 }

usdRadiusClientIncludeTunnelMediumTypeInAccessReq OBJECT-TYPE
    SYNTAX      TruthValue
    MAX-ACCESS  read-write
    STATUS      current
    DESCRIPTION
        "Enables/disables the inclusion of the Tunnel-Medium attribute in the
        RADIUS Access-Request packet."
    DEFVAL    { true }
    ::= { usdRadiusGeneralClient 28 }

usdRadiusClientIncludeTunnelServerAttributesInAccessReq OBJECT-TYPE
    SYNTAX      TruthValue
    MAX-ACCESS  read-write
    STATUS      current
    DESCRIPTION
        "Enables/disables the inclusion of the Tunnel-Server attributes (Tunnel
        attributes for a PPP session terminated on the LNS) in the RADIUS
        Access-Request packet."
    DEFVAL    { false }
    ::= { usdRadiusGeneralClient 29 }

usdRadiusClientIncludeTunnelServerAuthIdInAccessReq OBJECT-TYPE
    SYNTAX      TruthValue
    MAX-ACCESS  read-write
    STATUS      current
    DESCRIPTION
        "Enables/disables the inclusion of the Tunnel-Server-Auth-Id attribute
        in the RADIUS Access-Request packet."
    DEFVAL    { true }
    ::= { usdRadiusGeneralClient 30 }

usdRadiusClientIncludeTunnelServerEndpointInAccessReq OBJECT-TYPE
    SYNTAX      TruthValue
    MAX-ACCESS  read-write
    STATUS      current
    DESCRIPTION
        "Enables/disables the inclusion of the Tunnel-Server-Endpoint attribute
        in the RADIUS Access-Request packet."
    DEFVAL    { true }
    ::= { usdRadiusGeneralClient 31 }

usdRadiusClientIncludeTunnelTypeInAccessReq OBJECT-TYPE
    SYNTAX      TruthValue
    MAX-ACCESS  read-write
    STATUS      current
    DESCRIPTION
        "Enables/disables the inclusion of the Tunnel-Type attribute in the
        RADIUS Access-Request packet."
    DEFVAL    { true }
    ::= { usdRadiusGeneralClient 32 }

usdRadiusClientIncludeAcctTunnelConnectionInAcctStart OBJECT-TYPE
    SYNTAX      TruthValue
    MAX-ACCESS  read-write
    STATUS      current
    DESCRIPTION
        "Enables/disables the inclusion of the Acct-Tunnel-Connection attribute
        in the RADIUS Accounting-Start packet."
    DEFVAL    { true }
    ::= { usdRadiusGeneralClient 33 }

usdRadiusClientIncludeCalledStationIdInAcctStart OBJECT-TYPE
    SYNTAX      TruthValue
    MAX-ACCESS  read-write
    STATUS      current
    DESCRIPTION
        "Enables/disables the inclusion of the Called-Station-ID attribute in
        the RADIUS Accounting-Start packet."
    DEFVAL    { true }
    ::= { usdRadiusGeneralClient 34 }

usdRadiusClientIncludeCallingStationIdInAcctStart OBJECT-TYPE
    SYNTAX      TruthValue
    MAX-ACCESS  read-write
    STATUS      current
    DESCRIPTION
        "Enables/disables the inclusion of the Calling-Station-ID attribute in
        the RADIUS Accounting-Start packet."
    DEFVAL    { true }
    ::= { usdRadiusGeneralClient 35 }

usdRadiusClientIncludeClassInAcctStart OBJECT-TYPE
    SYNTAX      TruthValue
    MAX-ACCESS  read-write
    STATUS      current
    DESCRIPTION
        "Enables/disables the inclusion of the Class attribute in the RADIUS
        Accounting-Start packet."
    DEFVAL    { true }
    ::= { usdRadiusGeneralClient 36 }

usdRadiusClientIncludeConnectInfoInAcctStart OBJECT-TYPE
    SYNTAX      TruthValue
    MAX-ACCESS  read-write
    STATUS      current
    DESCRIPTION
        "Enables/disables the inclusion of the Connect-Info attribute in the
        RADIUS Accounting-Start packet."
    DEFVAL    { true }
    ::= { usdRadiusGeneralClient 37 }

usdRadiusClientIncludeEgressPolicyNameInAcctStart OBJECT-TYPE
    SYNTAX      TruthValue
    MAX-ACCESS  read-write
    STATUS      current
    DESCRIPTION
        "Enables/disables the inclusion of the Egress-Policy-Name (VSA)
        attribute in the RADIUS Accounting-Start packet."
    DEFVAL    { true }
    ::= { usdRadiusGeneralClient 38 }

usdRadiusClientIncludeEventTimestampInAcctStart OBJECT-TYPE
    SYNTAX      TruthValue
    MAX-ACCESS  read-write
    STATUS      current
    DESCRIPTION
        "Enables/disables the inclusion of the Event-Timestamp attribute in the
        RADIUS Accounting-Start packet."
    DEFVAL    { true }
    ::= { usdRadiusGeneralClient 39 }

usdRadiusClientIncludeFramedCompressionInAcctStart OBJECT-TYPE
    SYNTAX      TruthValue
    MAX-ACCESS  read-write
    STATUS      current
    DESCRIPTION
        "Enables/disables the inclusion of the Framed-Compression attribute in
        the RADIUS Accounting-Start packet."
    DEFVAL    { true }
    ::= { usdRadiusGeneralClient 40 }

usdRadiusClientIncludeFramedIpNetmaskInAcctStart OBJECT-TYPE
    SYNTAX      TruthValue
    MAX-ACCESS  read-write
    STATUS      current
    DESCRIPTION
        "Enables/disables the inclusion of the Framed-IP-Netmask attribute in
        the RADIUS Accounting-Start packet."
    DEFVAL    { true }
    ::= { usdRadiusGeneralClient 41 }

usdRadiusClientIncludeIngressPolicyNameInAcctStart OBJECT-TYPE
    SYNTAX      TruthValue
    MAX-ACCESS  read-write
    STATUS      current
    DESCRIPTION
        "Enables/disables the inclusion of the Ingress-Policy-Name (VSA)
        attribute in the RADIUS Accounting-Start packet."
    DEFVAL    { true }
    ::= { usdRadiusGeneralClient 42 }

usdRadiusClientIncludeNasIdentifierInAcctStart OBJECT-TYPE
    SYNTAX      TruthValue
    MAX-ACCESS  read-write
    STATUS      current
    DESCRIPTION
        "Enables/disables the inclusion of the NAS-Identifier attribute in the
        RADIUS Accounting-Start packet."
    DEFVAL    { true }
    ::= { usdRadiusGeneralClient 43 }

usdRadiusClientIncludeNasPortInAcctStart OBJECT-TYPE
    SYNTAX      TruthValue
    MAX-ACCESS  read-write
    STATUS      current
    DESCRIPTION
        "Enables/disables the inclusion of the NAS-Port attribute in the RADIUS
        Accounting-Start packet."
    DEFVAL    { true }
    ::= { usdRadiusGeneralClient 44 }

usdRadiusClientIncludeNasPortIdInAcctStart OBJECT-TYPE
    SYNTAX      TruthValue
    MAX-ACCESS  read-write
    STATUS      current
    DESCRIPTION
        "Enables/disables the inclusion of the NAS-Port-ID attribute in the
        RADIUS Accounting-Start packet."
    DEFVAL    { true }
    ::= { usdRadiusGeneralClient 45 }

usdRadiusClientIncludeNasPortTypeInAcctStart OBJECT-TYPE
    SYNTAX      TruthValue
    MAX-ACCESS  read-write
    STATUS      current
    DESCRIPTION
        "Enables/disables the inclusion of the NAS-Port-Type attribute in the
        RADIUS Accounting-Start packet."
    DEFVAL    { true }
    ::= { usdRadiusGeneralClient 46 }

usdRadiusClientIncludePppoeDescriptionInAcctStart OBJECT-TYPE
    SYNTAX      TruthValue
    MAX-ACCESS  read-write
    STATUS      current
    DESCRIPTION
        "Enables/disables the inclusion of the PPPoE-Description (VSA) attribute
        in the RADIUS Accounting-Start packet."
    DEFVAL    { true }
    ::= { usdRadiusGeneralClient 47 }

usdRadiusClientIncludeTunnelAssignmentIdInAcctStart OBJECT-TYPE
    SYNTAX      TruthValue
    MAX-ACCESS  read-write
    STATUS      current
    DESCRIPTION
        "Enables/disables the inclusion of the Tunnel-Assignment-Id attribute in
        the RADIUS Accounting-Start packet."
    DEFVAL    { true }
    ::= { usdRadiusGeneralClient 48 }

usdRadiusClientIncludeTunnelClientAuthIdInAcctStart OBJECT-TYPE
    SYNTAX      TruthValue
    MAX-ACCESS  read-write
    STATUS      current
    DESCRIPTION
        "Enables/disables the inclusion of the Tunnel-Client-Auth-Id attribute
        in the RADIUS Accounting-Start packet."
    DEFVAL    { true }
    ::= { usdRadiusGeneralClient 49 }

usdRadiusClientIncludeTunnelClientEndpointInAcctStart OBJECT-TYPE
    SYNTAX      TruthValue
    MAX-ACCESS  read-write
    STATUS      current
    DESCRIPTION
        "Enables/disables the inclusion of the Tunnel-Client-Endpoint attribute
        in the RADIUS Accounting-Start packet."
    DEFVAL    { true }
    ::= { usdRadiusGeneralClient 50 }

usdRadiusClientIncludeTunnelMediumTypeInAcctStart OBJECT-TYPE
    SYNTAX      TruthValue
    MAX-ACCESS  read-write
    STATUS      current
    DESCRIPTION
        "Enables/disables the inclusion of the Tunnel-Medium attribute in the
        RADIUS Accounting-Start packet."
    DEFVAL    { true }
    ::= { usdRadiusGeneralClient 51 }

usdRadiusClientIncludeTunnelPreferenceInAcctStart OBJECT-TYPE
    SYNTAX      TruthValue
    MAX-ACCESS  read-write
    STATUS      current
    DESCRIPTION
        "Enables/disables the inclusion of the Tunnel-Preference attribute in
        the RADIUS Accounting-Start packet."
    DEFVAL    { true }
    ::= { usdRadiusGeneralClient 52 }

usdRadiusClientIncludeTunnelServerAttributesInAcctStart OBJECT-TYPE
    SYNTAX      TruthValue
    MAX-ACCESS  read-write
    STATUS      current
    DESCRIPTION
        "Enables/disables the inclusion of the Tunnel-Server attributes (Tunnel
        attributes for a PPP session terminated on the LNS) in the RADIUS
        Accounting-Start packet."
    DEFVAL    { false }
    ::= { usdRadiusGeneralClient 53 }

usdRadiusClientIncludeTunnelServerAuthIdInAcctStart OBJECT-TYPE
    SYNTAX      TruthValue
    MAX-ACCESS  read-write
    STATUS      current
    DESCRIPTION
        "Enables/disables the inclusion of the Tunnel-Server-Auth-Id attribute
        in the RADIUS Accounting-Start packet."
    DEFVAL    { true }
    ::= { usdRadiusGeneralClient 54 }

usdRadiusClientIncludeTunnelServerEndpointInAcctStart OBJECT-TYPE
    SYNTAX      TruthValue
    MAX-ACCESS  read-write
    STATUS      current
    DESCRIPTION
        "Enables/disables the inclusion of the Tunnel-Server-Endpoint attribute
        in the RADIUS Accounting-Start packet."
    DEFVAL    { true }
    ::= { usdRadiusGeneralClient 55 }

usdRadiusClientIncludeTunnelTypeInAcctStart OBJECT-TYPE
    SYNTAX      TruthValue
    MAX-ACCESS  read-write
    STATUS      current
    DESCRIPTION
        "Enables/disables the inclusion of the Tunnel-Type attribute in the
        RADIUS Accounting-Start packet."
    DEFVAL    { true }
    ::= { usdRadiusGeneralClient 56 }

usdRadiusClientIncludeAcctTunnelConnectionInAcctStop OBJECT-TYPE
    SYNTAX      TruthValue
    MAX-ACCESS  read-write
    STATUS      current
    DESCRIPTION
        "Enables/disables the inclusion of the Acct-Tunnel-Connection attribute
        in the RADIUS Accounting-Stop packet."
    DEFVAL    { true }
    ::= { usdRadiusGeneralClient 57 }

usdRadiusClientIncludeCalledStationIdInAcctStop OBJECT-TYPE
    SYNTAX      TruthValue
    MAX-ACCESS  read-write
    STATUS      current
    DESCRIPTION
        "Enables/disables the inclusion of the Called-Station-ID attribute in
        the RADIUS Accounting-Stop packet."
    DEFVAL    { true }
    ::= { usdRadiusGeneralClient 59 }

usdRadiusClientIncludeCallingStationIdInAcctStop OBJECT-TYPE
    SYNTAX      TruthValue
    MAX-ACCESS  read-write
    STATUS      current
    DESCRIPTION
        "Enables/disables the inclusion of the Calling-Station-ID attribute in
        the RADIUS Accounting-Stop packet."
    DEFVAL    { true }
    ::= { usdRadiusGeneralClient 60 }

usdRadiusClientIncludeClassInAcctStop OBJECT-TYPE
    SYNTAX      TruthValue
    MAX-ACCESS  read-write
    STATUS      current
    DESCRIPTION
        "Enables/disables the inclusion of the Class attribute in the RADIUS
        Accounting-Stop packet."
    DEFVAL    { true }
    ::= { usdRadiusGeneralClient 61 }

usdRadiusClientIncludeConnectInfoInAcctStop OBJECT-TYPE
    SYNTAX      TruthValue
    MAX-ACCESS  read-write
    STATUS      current
    DESCRIPTION
        "Enables/disables the inclusion of the Connect-Info attribute in the
        RADIUS Accounting-Stop packet."
    DEFVAL    { true }
    ::= { usdRadiusGeneralClient 62 }

usdRadiusClientIncludeEgressPolicyNameInAcctStop OBJECT-TYPE
    SYNTAX      TruthValue
    MAX-ACCESS  read-write
    STATUS      current
    DESCRIPTION
        "Enables/disables the inclusion of the Egress-Policy-Name (VSA)
        attribute in the RADIUS Accounting-Stop packet."
    DEFVAL    { true }
    ::= { usdRadiusGeneralClient 63 }

usdRadiusClientIncludeEventTimestampInAcctStop OBJECT-TYPE
    SYNTAX      TruthValue
    MAX-ACCESS  read-write
    STATUS      current
    DESCRIPTION
        "Enables/disables the inclusion of the Event-Timestamp attribute in the
        RADIUS Accounting-Stop packet."
    DEFVAL    { true }
    ::= { usdRadiusGeneralClient 64 }

usdRadiusClientIncludeFramedCompressionInAcctStop OBJECT-TYPE
    SYNTAX      TruthValue
    MAX-ACCESS  read-write
    STATUS      current
    DESCRIPTION
        "Enables/disables the inclusion of the Framed-Compression attribute in
        the RADIUS Accounting-Stop packet."
    DEFVAL    { true }
    ::= { usdRadiusGeneralClient 65 }

usdRadiusClientIncludeFramedIpNetmaskInAcctStop OBJECT-TYPE
    SYNTAX      TruthValue
    MAX-ACCESS  read-write
    STATUS      current
    DESCRIPTION
        "Enables/disables the inclusion of the Framed-IP-Netmask attribute in
        the RADIUS Accounting-Stop packet."
    DEFVAL    { true }
    ::= { usdRadiusGeneralClient 66 }

usdRadiusClientIncludeIngressPolicyNameInAcctStop OBJECT-TYPE
    SYNTAX      TruthValue
    MAX-ACCESS  read-write
    STATUS      current
    DESCRIPTION
        "Enables/disables the inclusion of the Ingress-Policy-Name (VSA)
        attribute in the RADIUS Accounting-Stop packet."
    DEFVAL    { true }
    ::= { usdRadiusGeneralClient 67 }

usdRadiusClientIncludeInputGigawordsInAcctStop OBJECT-TYPE
    SYNTAX      TruthValue
    MAX-ACCESS  read-write
    STATUS      current
    DESCRIPTION
        "Enables/disables the inclusion of the Input-Gigawords attribute in the
        RADIUS Accounting-Stop packet."
    DEFVAL    { true }
    ::= { usdRadiusGeneralClient 68 }

usdRadiusClientIncludeNasIdentifierInAcctStop OBJECT-TYPE
    SYNTAX      TruthValue
    MAX-ACCESS  read-write
    STATUS      current
    DESCRIPTION
        "Enables/disables the inclusion of the NAS-Identifier attribute in the
        RADIUS Accounting-Stop packet."
    DEFVAL    { true }
    ::= { usdRadiusGeneralClient 69 }

usdRadiusClientIncludeNasPortInAcctStop OBJECT-TYPE
    SYNTAX      TruthValue
    MAX-ACCESS  read-write
    STATUS      current
    DESCRIPTION
        "Enables/disables the inclusion of the NAS-Port attribute in the RADIUS
        Accounting-Stop packet."
    DEFVAL    { true }
    ::= { usdRadiusGeneralClient 70 }

usdRadiusClientIncludeNasPortIdInAcctStop OBJECT-TYPE
    SYNTAX      TruthValue
    MAX-ACCESS  read-write
    STATUS      current
    DESCRIPTION
        "Enables/disables the inclusion of the NAS-Port-ID attribute in the
        RADIUS Accounting-Stop packet."
    DEFVAL    { true }
    ::= { usdRadiusGeneralClient 71 }

usdRadiusClientIncludeNasPortTypeInAcctStop OBJECT-TYPE
    SYNTAX      TruthValue
    MAX-ACCESS  read-write
    STATUS      current
    DESCRIPTION
        "Enables/disables the inclusion of the NAS-Port-Type attribute in the
        RADIUS Accounting-Stop packet."
    DEFVAL    { true }
    ::= { usdRadiusGeneralClient 72 }

usdRadiusClientIncludeOutputGigawordsInAcctStop OBJECT-TYPE
    SYNTAX      TruthValue
    MAX-ACCESS  read-write
    STATUS      current
    DESCRIPTION
        "Enables/disables the inclusion of the Output-Gigawords attribute in the
        RADIUS Accounting-Stop packet."
    DEFVAL    { true }
    ::= { usdRadiusGeneralClient 73 }

usdRadiusClientIncludePppoeDescriptionInAcctStop OBJECT-TYPE
    SYNTAX      TruthValue
    MAX-ACCESS  read-write
    STATUS      current
    DESCRIPTION
        "Enables/disables the inclusion of the PPPoE-Description (VSA) attribute
        in the RADIUS Accounting-Stop packet."
    DEFVAL    { true }
    ::= { usdRadiusGeneralClient 74 }

usdRadiusClientIncludeTunnelAssignmentIdInAcctStop OBJECT-TYPE
    SYNTAX      TruthValue
    MAX-ACCESS  read-write
    STATUS      current
    DESCRIPTION
        "Enables/disables the inclusion of the Tunnel-Assignment-Id attribute in
        the RADIUS Accounting-Stop packet."
    DEFVAL    { true }
    ::= { usdRadiusGeneralClient 75 }

usdRadiusClientIncludeTunnelClientAuthIdInAcctStop OBJECT-TYPE
    SYNTAX      TruthValue
    MAX-ACCESS  read-write
    STATUS      current
    DESCRIPTION
        "Enables/disables the inclusion of the Tunnel-Client-Auth-Id attribute
        in the RADIUS Accounting-Stop packet."
    DEFVAL    { true }
    ::= { usdRadiusGeneralClient 76 }

usdRadiusClientIncludeTunnelClientEndpointInAcctStop OBJECT-TYPE
    SYNTAX      TruthValue
    MAX-ACCESS  read-write
    STATUS      current
    DESCRIPTION
        "Enables/disables the inclusion of the Tunnel-Client-Endpoint attribute
        in the RADIUS Accounting-Stop packet."
    DEFVAL    { true }
    ::= { usdRadiusGeneralClient 77 }

usdRadiusClientIncludeTunnelMediumTypeInAcctStop OBJECT-TYPE
    SYNTAX      TruthValue
    MAX-ACCESS  read-write
    STATUS      current
    DESCRIPTION
        "Enables/disables the inclusion of the Tunnel-Medium attribute in the
        RADIUS Accounting-Stop packet."
    DEFVAL    { true }
    ::= { usdRadiusGeneralClient 78 }

usdRadiusClientIncludeTunnelPreferenceInAcctStop OBJECT-TYPE
    SYNTAX      TruthValue
    MAX-ACCESS  read-write
    STATUS      current
    DESCRIPTION
        "Enables/disables the inclusion of the Tunnel-Preference attribute in
        the RADIUS Accounting-Stop packet."
    DEFVAL    { true }
    ::= { usdRadiusGeneralClient 79 }

usdRadiusClientIncludeTunnelServerAttributesInAcctStop OBJECT-TYPE
    SYNTAX      TruthValue
    MAX-ACCESS  read-write
    STATUS      current
    DESCRIPTION
        "Enables/disables the inclusion of the Tunnel-Server attributes (Tunnel
        attributes for a PPP session terminated on the LNS) in the RADIUS
        Accounting-Stop packet."
    DEFVAL    { false }
    ::= { usdRadiusGeneralClient 80 }

usdRadiusClientIncludeTunnelServerAuthIdInAcctStop OBJECT-TYPE
    SYNTAX      TruthValue
    MAX-ACCESS  read-write
    STATUS      current
    DESCRIPTION
        "Enables/disables the inclusion of the Tunnel-Server-Auth-Id attribute
        in the RADIUS Accounting-Stop packet."
    DEFVAL    { true }
    ::= { usdRadiusGeneralClient 81 }

usdRadiusClientIncludeTunnelServerEndpointInAcctStop OBJECT-TYPE
    SYNTAX      TruthValue
    MAX-ACCESS  read-write
    STATUS      current
    DESCRIPTION
        "Enables/disables the inclusion of the Tunnel-Server-Endpoint attribute
        in the RADIUS Accounting-Stop packet."
    DEFVAL    { true }
    ::= { usdRadiusGeneralClient 82 }

usdRadiusClientIncludeTunnelTypeInAcctStop OBJECT-TYPE
    SYNTAX      TruthValue
    MAX-ACCESS  read-write
    STATUS      current
    DESCRIPTION
        "Enables/disables the inclusion of the Tunnel-Type attribute in the
        RADIUS Accounting-Stop packet."
    DEFVAL    { true }
    ::= { usdRadiusGeneralClient 83 }

usdRadiusClientIncludeInputGigapktsInAcctStop OBJECT-TYPE
    SYNTAX      TruthValue
    MAX-ACCESS  read-write
    STATUS      current
    DESCRIPTION
        "Enables/disables the inclusion of the Input-Gigapkts attribute in the
        RADIUS Accounting-Stop packet."
    DEFVAL    { true }
    ::= { usdRadiusGeneralClient 84 }

usdRadiusClientIncludeOutputGigapktsInAcctStop OBJECT-TYPE
    SYNTAX      TruthValue
    MAX-ACCESS  read-write
    STATUS      current
    DESCRIPTION
        "Enables/disables the inclusion of the Output-Gigapkts attribute in the
        RADIUS Accounting-Stop packet."
    DEFVAL    { true }
    ::= { usdRadiusGeneralClient 85 }

usdRadiusClientIgnoreFramedIpNetmask OBJECT-TYPE
    SYNTAX      TruthValue
    MAX-ACCESS  read-write
    STATUS      current
    DESCRIPTION
        "Enables/disables ignoring the Framed-IP-Netmask attribute in the
        RADIUS Access-Accept packet."
    DEFVAL    { true }
    ::= { usdRadiusGeneralClient 86 }


-- +++++++++++++++++++++++++++++++++++++++++++++++++++++++++++++++++++++++++++++
-- Managed objects for RADIUS Authentication
-- +++++++++++++++++++++++++++++++++++++++++++++++++++++++++++++++++++++++++++++
usdRadiusAuthClientInvalidServerAddresses OBJECT-TYPE
    SYNTAX      Counter32
    MAX-ACCESS  read-only
    STATUS      current
    DESCRIPTION
        "The number of RADIUS Access-Response packets received from unknown
        addresses."
    ::= { usdRadiusAuthClient 1 }

--
-- Statistics for RADIUS authentication servers
--
usdRadiusAuthClientServerTable OBJECT-TYPE
    SYNTAX      SEQUENCE OF UsdRadiusAuthClientServerEntry
    MAX-ACCESS  not-accessible
    STATUS      current
    DESCRIPTION
        "The (conceptual) table listing the RADIUS authentication servers with
        which the client shares a secret."
    ::= { usdRadiusAuthClient 2 }

usdRadiusAuthClientServerEntry OBJECT-TYPE
    SYNTAX      UsdRadiusAuthClientServerEntry
    MAX-ACCESS  not-accessible
    STATUS      current
    DESCRIPTION
        "An entry (conceptual row) representing a RADIUS authentication server
        with which the client shares a secret."
    INDEX     { usdRadiusAuthClientServerAddress }
    ::= { usdRadiusAuthClientServerTable 1 }

UsdRadiusAuthClientServerEntry ::= SEQUENCE {
    usdRadiusAuthClientServerAddress            IpAddress,
    usdRadiusAuthClientServerPortNumber         Integer32,
    usdRadiusAuthClientRoundTripTime            TimeTicks,
    usdRadiusAuthClientAccessRequests           Counter32,
    usdRadiusAuthClientAccessRetransmissions    Counter32,
    usdRadiusAuthClientAccessAccepts            Counter32,
    usdRadiusAuthClientAccessRejects            Counter32,
    usdRadiusAuthClientAccessChallenges         Counter32,
    usdRadiusAuthClientMalformedAccessResponses Counter32,
    usdRadiusAuthClientBadAuthenticators        Counter32,
    usdRadiusAuthClientPendingRequests          Gauge32,
    usdRadiusAuthClientTimeouts                 Counter32,
    usdRadiusAuthClientUnknownTypes             Counter32,
    usdRadiusAuthClientPacketsDropped           Counter32 }

usdRadiusAuthClientServerAddress OBJECT-TYPE
    SYNTAX      IpAddress
    MAX-ACCESS  not-accessible
    STATUS      current
    DESCRIPTION
        "The IP address of the RADIUS authentication server referred to in this
        table entry.  A value of 0.0.0.0 indicates this entry is not in use."
    ::= { usdRadiusAuthClientServerEntry 1 }

usdRadiusAuthClientServerPortNumber  OBJECT-TYPE
    SYNTAX      Integer32
    MAX-ACCESS  read-only
    STATUS      current
    DESCRIPTION
        "The UDP port the client is using to send requests to this server."
    ::= { usdRadiusAuthClientServerEntry 2 }

usdRadiusAuthClientRoundTripTime  OBJECT-TYPE
    SYNTAX      TimeTicks
    MAX-ACCESS  read-only
    STATUS      current
    DESCRIPTION
        "The time interval (in hundredths of seconds) between the most recent
        Access-Reply/Access-Challenge and the Access-Request that matched it
        from this RADIUS authentication server."
    ::= { usdRadiusAuthClientServerEntry 3 }


--
-- Request/Response statistics
--
-- TotalIncomingPackets = Accepts + Rejects + Challenges + UnknownTypes
--
-- TotalIncomingPackets - MalformedResponses - BadAuthenticators -
-- UnknownTypes - PacketsDropped = Successfully received
--
-- AccessRequests + PendingRequests + ClientTimeouts = Successfully Received
--
usdRadiusAuthClientAccessRequests OBJECT-TYPE
    SYNTAX      Counter32
    MAX-ACCESS  read-only
    STATUS      current
    DESCRIPTION
        "The number of RADIUS Access-Request packets sent to this server.  This
        does not include retransmissions."
    ::= { usdRadiusAuthClientServerEntry 4 }

usdRadiusAuthClientAccessRetransmissions OBJECT-TYPE
    SYNTAX      Counter32
    MAX-ACCESS  read-only
    STATUS      current
    DESCRIPTION
        "The number of RADIUS Access-Request packets retransmitted to this
        RADIUS authentication server."
    ::= { usdRadiusAuthClientServerEntry 5 }

usdRadiusAuthClientAccessAccepts OBJECT-TYPE
    SYNTAX      Counter32
    MAX-ACCESS  read-only
    STATUS      current
    DESCRIPTION
        "The number of RADIUS Access-Accept packets (valid or invalid) received
        from this server."
    ::= { usdRadiusAuthClientServerEntry 6 }

usdRadiusAuthClientAccessRejects OBJECT-TYPE
    SYNTAX      Counter32
    MAX-ACCESS  read-only
    STATUS      current
    DESCRIPTION
        "The number of RADIUS Access-Reject packets (valid or invalid) received
        from this server."
    ::= { usdRadiusAuthClientServerEntry  7 }

usdRadiusAuthClientAccessChallenges OBJECT-TYPE
    SYNTAX      Counter32
    MAX-ACCESS  read-only
    STATUS      current
    DESCRIPTION
        "The number of RADIUS Access-Challenge packets (valid or invalid)
        received from this server."
    ::= { usdRadiusAuthClientServerEntry 8 }


--
-- "Access-Response" includes an Access-Accept, Access-Challenge
-- or Access-Reject
--
usdRadiusAuthClientMalformedAccessResponses OBJECT-TYPE
    SYNTAX      Counter32
    MAX-ACCESS  read-only
    STATUS      current
    DESCRIPTION
        "The number of malformed RADIUS Access-Response packets received from
        this server.  Malformed packets include packets with an invalid length.
        Bad authenticators or signature attributes or unknown types are not
        included as malformed access responses."
    ::= { usdRadiusAuthClientServerEntry 9 }

usdRadiusAuthClientBadAuthenticators OBJECT-TYPE
    SYNTAX      Counter32
    MAX-ACCESS  read-only
    STATUS      current
    DESCRIPTION
        "The number of RADIUS Access-Response packets containing invalid
        authenticators or signature attributes received from this server."
    ::= { usdRadiusAuthClientServerEntry 10 }

usdRadiusAuthClientPendingRequests OBJECT-TYPE
    SYNTAX      Gauge32
    MAX-ACCESS  read-only
    STATUS      current
    DESCRIPTION
        "The number of RADIUS Access-Request packets destined for this server
        that have not yet timed out or received a response.  This variable is
        incremented when an Access-Request is sent and decremented due to
        receipt of an Access-Accept, Access-Reject or Access-Challenge, a timeout
        or retransmission."
    ::= { usdRadiusAuthClientServerEntry 11 }

usdRadiusAuthClientTimeouts OBJECT-TYPE
    SYNTAX      Counter32
    MAX-ACCESS  read-only
    STATUS      current
    DESCRIPTION
        "The number of authentication timeouts to this server.  After a timeout
        the client may retry to the same server, send to a different server, or
        give up.  A retry to the same server is counted as a retransmit as well
        as a timeout.  A send to a different server is counted as a Request as
        well as a timeout."
    ::= { usdRadiusAuthClientServerEntry  12 }

usdRadiusAuthClientUnknownTypes OBJECT-TYPE
    SYNTAX      Counter32
    MAX-ACCESS  read-only
    STATUS      current
    DESCRIPTION
        "The number of RADIUS packets of unknown type which were received from
        this server on the authentication port."
    ::= { usdRadiusAuthClientServerEntry  13 }

usdRadiusAuthClientPacketsDropped OBJECT-TYPE
    SYNTAX      Counter32
    MAX-ACCESS  read-only
    STATUS      current
    DESCRIPTION
        "The number of RADIUS packets of which were received from this server on
        the authentication port and dropped for some other reason."
    ::= { usdRadiusAuthClientServerEntry  14 }


--
-- Configuration of RADIUS authentication servers
--
usdRadiusAuthClientCfgServerTable  OBJECT-TYPE
    SYNTAX      SEQUENCE OF UsdRadiusAuthClientCfgServerEntry
    MAX-ACCESS  not-accessible
    STATUS      current
    DESCRIPTION
        "The (conceptual) table listing the RADIUS authentication servers with
        which the client shares a secret."
    ::= { usdRadiusAuthClient 3 }

usdRadiusAuthClientCfgServerEntry  OBJECT-TYPE
    SYNTAX      UsdRadiusAuthClientCfgServerEntry
    MAX-ACCESS  not-accessible
    STATUS      current
    DESCRIPTION
        "An entry (conceptual row) representing a RADIUS authentication server
        with which the client shares a secret."
    INDEX     { usdRadiusAuthClientCfgServerAddress }
    ::= { usdRadiusAuthClientCfgServerTable 1 }

UsdRadiusAuthClientCfgServerEntry ::= SEQUENCE {
    usdRadiusAuthClientCfgServerAddress         IpAddress,
    usdRadiusAuthClientCfgServerPortNumber      Integer32,
    usdRadiusAuthClientCfgKey                   DisplayString,
    usdRadiusAuthClientCfgTimeoutInterval       Integer32,
    usdRadiusAuthClientCfgRetries               Integer32,
    usdRadiusAuthClientCfgMaxPendingRequests    Integer32,
    usdRadiusAuthClientCfgRowStatus             RowStatus,
    usdRadiusAuthClientCfgPrecedence            Integer32,
    usdRadiusAuthClientCfgDeadTime              Integer32 }

usdRadiusAuthClientCfgServerAddress OBJECT-TYPE
    SYNTAX      IpAddress
    MAX-ACCESS  not-accessible
    STATUS      current
    DESCRIPTION
        "The IP address of the RADIUS authentication server referred to in this
        table entry."
    ::= { usdRadiusAuthClientCfgServerEntry 1 }

usdRadiusAuthClientCfgServerPortNumber  OBJECT-TYPE
    SYNTAX      Integer32 (1..65535)
    MAX-ACCESS  read-create
    STATUS      current
    DESCRIPTION
        "The UDP port the client is using to send requests to this server."
    DEFVAL    { 1812 }
    ::= { usdRadiusAuthClientCfgServerEntry 2 }

usdRadiusAuthClientCfgKey  OBJECT-TYPE
    SYNTAX      DisplayString (SIZE(0..32))
    MAX-ACCESS  read-create
    STATUS      current
    DESCRIPTION
        "The secret (RADIUS authenticator) used by the client during exchanges
        with this authentication server.  The default is a zero-length string,
        indicating no authenticator is used."
    DEFVAL    { ''H }
    ::= { usdRadiusAuthClientCfgServerEntry 3 }

usdRadiusAuthClientCfgTimeoutInterval  OBJECT-TYPE
    SYNTAX      Integer32 (3..30)
    UNITS       "seconds"
    MAX-ACCESS  read-create
    STATUS      current
    DESCRIPTION
        "The interval between retransmissions of a request to this
        authentication server."
    DEFVAL    { 3 }
    ::= { usdRadiusAuthClientCfgServerEntry 4 }

usdRadiusAuthClientCfgRetries  OBJECT-TYPE
    SYNTAX      Integer32 (0..16)
    MAX-ACCESS  read-create
    STATUS      current
    DESCRIPTION
        "The maximum number of times to resend a request to this authentication
        server (in addition to the original request), before resorting to the
        server specified in the next entry."
    DEFVAL    { 3 }
    ::= { usdRadiusAuthClientCfgServerEntry 5 }

usdRadiusAuthClientCfgMaxPendingRequests  OBJECT-TYPE
    SYNTAX      Integer32 (10..4000)
    MAX-ACCESS  read-create
    STATUS      current
    DESCRIPTION
        "The maximum number of outstanding requests this server can support."
    DEFVAL    { 255 }
    ::= { usdRadiusAuthClientCfgServerEntry 6 }

usdRadiusAuthClientCfgRowStatus  OBJECT-TYPE
    SYNTAX      RowStatus
    MAX-ACCESS  read-create
    STATUS      current
    DESCRIPTION
        "Supports 'createAndGo' and 'destroy' only."
    ::= { usdRadiusAuthClientCfgServerEntry 7 }

usdRadiusAuthClientCfgPrecedence  OBJECT-TYPE
    SYNTAX      Integer32 (0..2147483647)
    MAX-ACCESS  read-only
    STATUS      current
    DESCRIPTION
        "Relative precedence of this server with respect to other servers
        configured in this table.  Lower values correspond to higher precedence.
        Precedence is assigned by the device, in order of entry creation, from
        higher to lower precedence."
    ::= { usdRadiusAuthClientCfgServerEntry 8 }

usdRadiusAuthClientCfgDeadTime  OBJECT-TYPE
    SYNTAX      Integer32 (0..30)
    UNITS       "minutes"
    MAX-ACCESS  read-create
    STATUS      current
    DESCRIPTION
        "The period of time, in minutes, to ignore this server after a request
        to the server times out (thereby avoiding additional request timeouts
        for this period, if the server failure persists)."
    DEFVAL    { 5 }
    ::= { usdRadiusAuthClientCfgServerEntry 9 }


-- +++++++++++++++++++++++++++++++++++++++++++++++++++++++++++++++++++++++++++++
-- Managed objects for RADIUS Accounting
-- +++++++++++++++++++++++++++++++++++++++++++++++++++++++++++++++++++++++++++++
usdRadiusAcctClientInvalidServerAddresses OBJECT-TYPE
    SYNTAX      Counter32
    MAX-ACCESS  read-only
    STATUS      current
    DESCRIPTION
        "The number of RADIUS Accounting-Response packets received from unknown
        addresses."
    ::= { usdRadiusAcctClient 1 }

--
-- Statistics for RADIUS accounting servers
--
usdRadiusAcctClientServerTable OBJECT-TYPE
    SYNTAX      SEQUENCE OF UsdRadiusAcctClientServerEntry
    MAX-ACCESS  not-accessible
    STATUS      current
    DESCRIPTION
        "The (conceptual) table listing the RADIUS accounting servers with which
        the client shares a secret."
    ::= { usdRadiusAcctClient 2 }

usdRadiusAcctClientServerEntry OBJECT-TYPE
    SYNTAX      UsdRadiusAcctClientServerEntry
    MAX-ACCESS  not-accessible
    STATUS      current
    DESCRIPTION
        "An entry (conceptual row) representing a RADIUS accounting server with
        which the client shares a secret."
    INDEX     { usdRadiusAcctClientServerAddress }
    ::= { usdRadiusAcctClientServerTable 1 }

UsdRadiusAcctClientServerEntry ::= SEQUENCE {
    usdRadiusAcctClientServerAddress        IpAddress,
    usdRadiusAcctClientServerPortNumber     Integer32,
    usdRadiusAcctClientRoundTripTime        TimeTicks,
    usdRadiusAcctClientRequests             Counter32,
    usdRadiusAcctClientRetransmissions      Counter32,
    usdRadiusAcctClientResponses            Counter32,
    usdRadiusAcctClientMalformedResponses   Counter32,
    usdRadiusAcctClientBadAuthenticators    Counter32,
    usdRadiusAcctClientPendingRequests      Gauge32,
    usdRadiusAcctClientTimeouts             Counter32,
    usdRadiusAcctClientUnknownTypes         Counter32,
    usdRadiusAcctClientPacketsDropped       Counter32 }

usdRadiusAcctClientServerAddress OBJECT-TYPE
    SYNTAX      IpAddress
    MAX-ACCESS  not-accessible
    STATUS      current
    DESCRIPTION
        "The IP address of the RADIUS accounting server referred to in this
        table entry.  A value of 0.0.0.0 indicates this entry is not in use."
    ::= { usdRadiusAcctClientServerEntry 1 }

usdRadiusAcctClientServerPortNumber  OBJECT-TYPE
    SYNTAX      Integer32
    MAX-ACCESS  read-only
    STATUS      current
    DESCRIPTION
        "The UDP port the client is using to send requests to this server."
    ::= { usdRadiusAcctClientServerEntry 2 }

usdRadiusAcctClientRoundTripTime  OBJECT-TYPE
    SYNTAX      TimeTicks
    MAX-ACCESS  read-only
    STATUS      current
    DESCRIPTION
        "The time interval between the most recent Accounting-Response and the
        Accounting-Request that matched it from this RADIUS accounting server."
    ::= { usdRadiusAcctClientServerEntry 3 }


--
-- Request/Response statistics
--
-- Requests = Responses + PendingRequests + ClientTimeouts
--
-- Responses - MalformedResponses - BadAuthenticators -
-- UnknownTypes - PacketsDropped = Successfully received
--
usdRadiusAcctClientRequests OBJECT-TYPE
    SYNTAX      Counter32
    MAX-ACCESS  read-only
    STATUS      current
    DESCRIPTION
        "The number of RADIUS Accounting-Request packets sent.  This does not
        include retransmissions."
    ::= { usdRadiusAcctClientServerEntry 4 }

usdRadiusAcctClientRetransmissions OBJECT-TYPE
    SYNTAX      Counter32
    MAX-ACCESS  read-only
    STATUS      current
    DESCRIPTION
        "The number of RADIUS Accounting-Request packets retransmitted to this
        RADIUS accounting server.  Retransmissions include retries where the
        Identifier and Acct-Delay have been updated, as well as those in which
        they remain the same."
    ::= { usdRadiusAcctClientServerEntry 5 }

usdRadiusAcctClientResponses OBJECT-TYPE
    SYNTAX      Counter32
    MAX-ACCESS  read-only
    STATUS      current
    DESCRIPTION
        "The number of RADIUS packets received on the accounting port from this
        server."
    ::= { usdRadiusAcctClientServerEntry 6 }

usdRadiusAcctClientMalformedResponses OBJECT-TYPE
    SYNTAX      Counter32
    MAX-ACCESS  read-only
    STATUS      current
    DESCRIPTION
        "The number of malformed RADIUS Accounting-Response packets received
        from this server.  Malformed packets include packets with an invalid
        length.  Bad authenticators and unknown types are not included as
        malformed accounting responses."
    ::= { usdRadiusAcctClientServerEntry 7 }

usdRadiusAcctClientBadAuthenticators OBJECT-TYPE
    SYNTAX      Counter32
    MAX-ACCESS  read-only
    STATUS      current
    DESCRIPTION
        "The number of RADIUS Accounting-Response packets which contained
        invalid authenticators received from this server."
    ::= { usdRadiusAcctClientServerEntry 8 }

usdRadiusAcctClientPendingRequests OBJECT-TYPE
    SYNTAX      Gauge32
    MAX-ACCESS  read-only
    STATUS      current
    DESCRIPTION
        "The number of RADIUS Accounting-Request packets sent to this server
        that have not yet timed out or received a response.  This variable is
        incremented when an Accounting-Request is sent and decremented due to
        receipt of an Accounting-Response, a timeout or a retransmission."
    ::= { usdRadiusAcctClientServerEntry 9 }

usdRadiusAcctClientTimeouts OBJECT-TYPE
    SYNTAX      Counter32
    MAX-ACCESS  read-only
    STATUS      current
    DESCRIPTION
        "The number of accounting timeouts to this server.  After a timeout the
        client may retry to the same server, send to a different server, or give
        up.  A retry to the same server is counted as a retransmit as well as a
        timeout.  A send to a different server is counted as an
        Accounting-Request as well as a timeout."
    ::= { usdRadiusAcctClientServerEntry  10 }

usdRadiusAcctClientUnknownTypes OBJECT-TYPE
    SYNTAX      Counter32
    MAX-ACCESS  read-only
    STATUS      current
    DESCRIPTION
        "The number of RADIUS packets of unknown type which were received from
        this server on the accounting port."
    ::= { usdRadiusAcctClientServerEntry  11 }

usdRadiusAcctClientPacketsDropped OBJECT-TYPE
    SYNTAX      Counter32
    MAX-ACCESS  read-only
    STATUS      current
    DESCRIPTION
        "The number of RADIUS packets which were received from this server on
        the accounting port and dropped for some other reason."
    ::= { usdRadiusAcctClientServerEntry  12 }


--
-- Configuration of RADIUS accounting servers
--
usdRadiusAcctClientCfgServerTable  OBJECT-TYPE
    SYNTAX      SEQUENCE OF UsdRadiusAcctClientCfgServerEntry
    MAX-ACCESS  not-accessible
    STATUS      current
    DESCRIPTION
        "The (conceptual) table listing the RADIUS accounting servers with which
        the client shares a secret."
    ::= { usdRadiusAcctClient 3 }

usdRadiusAcctClientCfgServerEntry  OBJECT-TYPE
    SYNTAX      UsdRadiusAcctClientCfgServerEntry
    MAX-ACCESS  not-accessible
    STATUS      current
    DESCRIPTION
        "An entry (conceptual row) representing a RADIUS accounting server with
        which the client shares a secret."
    INDEX     { usdRadiusAcctClientCfgServerAddress }
    ::= { usdRadiusAcctClientCfgServerTable 1 }

UsdRadiusAcctClientCfgServerEntry ::= SEQUENCE {
    usdRadiusAcctClientCfgServerAddress         IpAddress,
    usdRadiusAcctClientCfgServerPortNumber      Integer32,
    usdRadiusAcctClientCfgKey                   DisplayString,
    usdRadiusAcctClientCfgTimeoutInterval       Integer32,
    usdRadiusAcctClientCfgRetries               Integer32,
    usdRadiusAcctClientCfgMaxPendingRequests    Integer32,
    usdRadiusAcctClientCfgRowStatus             RowStatus,
    usdRadiusAcctClientCfgPrecedence            Integer32,
    usdRadiusAcctClientCfgDeadTime              Integer32 }

usdRadiusAcctClientCfgServerAddress  OBJECT-TYPE
    SYNTAX      IpAddress
    MAX-ACCESS  not-accessible
    STATUS      current
    DESCRIPTION
        "The IP address of the RADIUS accounting server referred to in this
        table entry."
    ::= { usdRadiusAcctClientCfgServerEntry 1 }

usdRadiusAcctClientCfgServerPortNumber  OBJECT-TYPE
    SYNTAX      Integer32 (1..65535)
    MAX-ACCESS  read-create
    STATUS      current
    DESCRIPTION
        "The UDP port the client is using to send requests to this server."
    DEFVAL    { 1813 }
    ::= { usdRadiusAcctClientCfgServerEntry 2 }

usdRadiusAcctClientCfgKey  OBJECT-TYPE
    SYNTAX      DisplayString (SIZE(0..32))
    MAX-ACCESS  read-create
    STATUS      current
    DESCRIPTION
        "The secret (RADIUS authenticator) used by the client during exchanges
        with this accounting server.  The default is a zero-length string,
        indicating no authenticator is used."
    DEFVAL    { ''H }
    ::= { usdRadiusAcctClientCfgServerEntry 3 }

usdRadiusAcctClientCfgTimeoutInterval  OBJECT-TYPE
    SYNTAX      Integer32 (3..30)
    UNITS       "seconds"
    MAX-ACCESS  read-create
    STATUS      current
    DESCRIPTION
        "The interval between retransmissions of a request to this accounting
        server."
    DEFVAL    { 3 }
    ::= { usdRadiusAcctClientCfgServerEntry 4 }

usdRadiusAcctClientCfgRetries  OBJECT-TYPE
    SYNTAX      Integer32 (0..16)
    MAX-ACCESS  read-create
    STATUS      current
    DESCRIPTION
        "The maximum number of times to resend a request to this accounting
        server (in addition to the original request), before resorting to the
        server specified in the next entry."
    DEFVAL    { 3 }
    ::= { usdRadiusAcctClientCfgServerEntry 5 }

usdRadiusAcctClientCfgMaxPendingRequests  OBJECT-TYPE
    SYNTAX      Integer32 (10..4000)
    MAX-ACCESS  read-create
    STATUS      current
    DESCRIPTION
        "The maximum number of outstanding requests this server can support."
    DEFVAL    { 255 }
    ::= { usdRadiusAcctClientCfgServerEntry 6 }

usdRadiusAcctClientCfgRowStatus  OBJECT-TYPE
    SYNTAX      RowStatus
    MAX-ACCESS  read-create
    STATUS      current
    DESCRIPTION
        "Supports 'createAndGo' and 'destroy' only."
    ::= { usdRadiusAcctClientCfgServerEntry 7 }

usdRadiusAcctClientCfgPrecedence  OBJECT-TYPE
    SYNTAX      Integer32 (0..2147483647)
    MAX-ACCESS  read-only
    STATUS      current
    DESCRIPTION
        "Relative precedence of this server with respect to other servers
        configured in this table.  Lower values correspond to higher precedence.
        Precedence is assigned by the device, in order of entry creation, from
        higher to lower precedence."
    ::= { usdRadiusAcctClientCfgServerEntry 8 }

usdRadiusAcctClientCfgDeadTime  OBJECT-TYPE
    SYNTAX      Integer32 (0..30)
    UNITS       "minutes"
    MAX-ACCESS  read-create
    STATUS      current
    DESCRIPTION
        "The period of time, in minutes, to ignore this server after a request
        to the server times out (thereby avoiding additional request timeouts
        for this period, if the server failure persists)."
    DEFVAL    { 5 }
    ::= { usdRadiusAcctClientCfgServerEntry 9 }


-- +++++++++++++++++++++++++++++++++++++++++++++++++++++++++++++++++++++++++++++
-- Notification control objects
-- +++++++++++++++++++++++++++++++++++++++++++++++++++++++++++++++++++++++++++++
-- No notifications are defined in this MIB.  Placeholder follows.
-- usdRadiusClientTrapControl      OBJECT IDENTIFIER ::= { usdRadiusClientMIB 2 }

-- +++++++++++++++++++++++++++++++++++++++++++++++++++++++++++++++++++++++++++++
-- Notifications
-- +++++++++++++++++++++++++++++++++++++++++++++++++++++++++++++++++++++++++++++
-- No notifications are defined in this MIB.  Placeholders follow.
-- The following two OBJECT IDENTIFIERS are used to define SNMPv2
-- Notifications that are easily translated into SNMPv1 Traps.
-- usdRadiusClientTraps           OBJECT IDENTIFIER ::= { usdRadiusClientMIB 3 }
-- usdRadiusClientTrapPrefix      OBJECT IDENTIFIER ::= { usdRadiusClientTraps 0 }


-- +++++++++++++++++++++++++++++++++++++++++++++++++++++++++++++++++++++++++++++
-- Conformance information
-- +++++++++++++++++++++++++++++++++++++++++++++++++++++++++++++++++++++++++++++
usdRadiusClientMIBConformance
             OBJECT IDENTIFIER ::= { usdRadiusClientMIB 2 }
usdRadiusClientMIBCompliances
             OBJECT IDENTIFIER ::= { usdRadiusClientMIBConformance 1 }
usdRadiusClientMIBGroups
             OBJECT IDENTIFIER ::= { usdRadiusClientMIBConformance 2 }

--
-- compliance statements
--
usdRadiusAuthClientCompliance MODULE-COMPLIANCE
    STATUS      obsolete
    DESCRIPTION
        "Obsolete compliance statement for authentication clients implementing
        the Unisphere RADIUS Client MIB authentication functionality.  This
        statement became obsolete when the usdRadiusClientSourceAddress object
        was added."
    MODULE  -- this module
        MANDATORY-GROUPS {
            usdRadiusGeneralClientGroup,
            usdRadiusAuthClientGroup }
    ::= { usdRadiusClientMIBCompliances 1 }                            -- RX 1.1

usdRadiusAcctClientCompliance MODULE-COMPLIANCE
    STATUS      obsolete
    DESCRIPTION
        "Obsolete compliance statement for accounting clients implementing the
        Unisphere RADIUS Client MIB accounting functionality.  This statement
        became obsolete when the usdRadiusClientSourceAddress object was added."
    MODULE  -- this module
        MANDATORY-GROUPS {
            usdRadiusGeneralClientGroup,
            usdRadiusAcctClientGroup }
    ::= { usdRadiusClientMIBCompliances 2 }                            -- RX 1.1

usdRadiusAuthClientCompliance2 MODULE-COMPLIANCE
    STATUS      obsolete
    DESCRIPTION
        "Obsolete compliance statement for authentication clients implementing
        the Unisphere RADIUS Client MIB authentication functionality.  This
        statement became obsolete when new objects were added."
    MODULE  -- this module
        MANDATORY-GROUPS {
            usdRadiusGeneralClientGroup2,
            usdRadiusAuthClientGroup }
    ::= { usdRadiusClientMIBCompliances 3 }                            -- RX 2.0

usdRadiusAcctClientCompliance2 MODULE-COMPLIANCE
    STATUS      obsolete
    DESCRIPTION
        "Obsolete compliance statement for accounting clients implementing the
        Unisphere RADIUS Client MIB accounting functionality.  This statement
        became obsolete when new objects were added."
    MODULE  -- this module
        MANDATORY-GROUPS {
            usdRadiusGeneralClientGroup2,
            usdRadiusAcctClientGroup }
    ::= { usdRadiusClientMIBCompliances 4 }                            -- RX 2.0

usdRadiusClientCompliance MODULE-COMPLIANCE
    STATUS      obsolete
    DESCRIPTION
        "Obsolete compliance statement for authentication clients implementing
        the Unisphere RADIUS Client MIB authentication functionality.  This
        statement became obsolete when new B-RAS objects were added."
    MODULE  -- this module
        MANDATORY-GROUPS {
            usdRadiusBasicClientGroup }
        GROUP       usdRadiusAuthClientGroup
        DESCRIPTION
            "This group is mandatory only for those router switch modules that
            implement authentication support."
        GROUP       usdRadiusAcctClientGroup
        DESCRIPTION
            "This group is mandatory only for those router switch modules that
            implement accounting support."
        GROUP       usdRadiusBrasClientGroup
        DESCRIPTION
            "This group is mandatory only for those router switch modules that
            implement B-RAS support."
        GROUP       usdRadiusTunnelClientGroup
        DESCRIPTION
            "This group is mandatory only for those router switch modules that
            implement tunneling support."
    ::= { usdRadiusClientMIBCompliances 5 }                            -- RX 3.0

usdRadiusClientCompliance2 MODULE-COMPLIANCE
    STATUS      obsolete
    DESCRIPTION
        "Obsolete compliance statement for authentication clients implementing
        the Unisphere RADIUS Client MIB authentication functionality.  This
        statement became obsolete when new objects were added."
    MODULE  -- this module
        MANDATORY-GROUPS {
            usdRadiusBasicClientGroup }
        GROUP       usdRadiusAuthClientGroup
        DESCRIPTION
            "This group is mandatory only for those router switch modules that
            implement authentication support."
        GROUP       usdRadiusAcctClientGroup
        DESCRIPTION
            "This group is mandatory only for those router switch modules that
            implement accounting support."
        GROUP       usdRadiusBrasClientGroup2
        DESCRIPTION
            "This group is mandatory only for those router switch modules that
            implement B-RAS support."
        GROUP       usdRadiusTunnelClientGroup
        DESCRIPTION
            "This group is mandatory only for those router switch modules that
            implement tunneling support."
    ::= { usdRadiusClientMIBCompliances 6 }                            -- RX 3.1

usdRadiusClientCompliance3 MODULE-COMPLIANCE
    STATUS      obsolete
    DESCRIPTION
        "Obsolete compliance statement for authentication clients implementing
        the Unisphere RADIUS Client MIB authentication functionality.  This
        statement became obsolete when the usdRadiusClientNasIpAddrUse object
        was added."
    MODULE  -- this module
        MANDATORY-GROUPS {
            usdRadiusBasicClientGroup2 }
        GROUP       usdRadiusAuthClientGroup
        DESCRIPTION
            "This group is mandatory only for those router switch modules that
            implement authentication support."
        GROUP       usdRadiusAcctClientGroup
        DESCRIPTION
            "This group is mandatory only for those router switch modules that
            implement accounting support."
        GROUP       usdRadiusBrasClientGroup3
        DESCRIPTION
            "This group is mandatory only for those router switch modules that
            implement B-RAS support."
        GROUP       usdRadiusTunnelClientGroup
        DESCRIPTION
            "This group is mandatory only for those router switch modules that
            implement tunneling support."
    ::= { usdRadiusClientMIBCompliances 7 }                            -- RX 3.2

usdRadiusClientCompliance4 MODULE-COMPLIANCE
    STATUS      obsolete
    DESCRIPTION
        "Obsolete compliance statement for authentication clients implementing
        the Unisphere RADIUS Client MIB authentication functionality.  This
        statement became obsolete when objects were added to indicate which
        RADIUS attributes should be included or excluded from RADIUS packets."
    MODULE  -- this module
        MANDATORY-GROUPS {
            usdRadiusBasicClientGroup2 }
        GROUP       usdRadiusAuthClientGroup
        DESCRIPTION
            "This group is mandatory only for those router switch modules that
            implement authentication support."
        GROUP       usdRadiusAcctClientGroup
        DESCRIPTION
            "This group is mandatory only for those router switch modules that
            implement accounting support."
        GROUP       usdRadiusBrasClientGroup4
        DESCRIPTION
            "This group is mandatory only for those router switch modules that
            implement B-RAS support."
        GROUP       usdRadiusTunnelClientGroup
        DESCRIPTION
            "This group is mandatory only for those router switch modules that
            implement tunneling support."
    ::= { usdRadiusClientMIBCompliances 8 }                            -- RX 3.3

usdRadiusClientCompliance5 MODULE-COMPLIANCE
    STATUS      current
    DESCRIPTION
        "The compliance statement for authentication clients implementing the
        Unisphere RADIUS Client MIB authentication functionality."
    MODULE  -- this module
        MANDATORY-GROUPS {
            usdRadiusBasicClientGroup2 }
        GROUP       usdRadiusAuthClientGroup
        DESCRIPTION
            "This group is mandatory only for those router switch modules that
            implement authentication support."
        GROUP       usdRadiusAcctClientGroup
        DESCRIPTION
            "This group is mandatory only for those router switch modules that
            implement accounting support."
        GROUP       usdRadiusBrasClientGroup5
        DESCRIPTION
            "This group is mandatory only for those router switch modules that
            implement B-RAS support."
        GROUP       usdRadiusTunnelClientGroup
        DESCRIPTION
            "This group is mandatory only for those router switch modules that
            implement tunneling support."
    ::= { usdRadiusClientMIBCompliances 9 }                            -- RX 4.0


--
-- units of conformance
--
usdRadiusGeneralClientGroup OBJECT-GROUP
    OBJECTS {
        usdRadiusClientIdentifier,
        usdRadiusClientAlgorithm }
    STATUS      obsolete
    DESCRIPTION
        "Obsolete basic collection of objects providing management of RADIUS
        Clients.  This group became obsolete when usdRadiusClientSourceAddress
        was added."
    ::= { usdRadiusClientMIBGroups 1 }

usdRadiusAuthClientGroup OBJECT-GROUP
    OBJECTS {
        usdRadiusAuthClientInvalidServerAddresses,

        usdRadiusAuthClientServerPortNumber,
        usdRadiusAuthClientRoundTripTime,
        usdRadiusAuthClientAccessRequests,
        usdRadiusAuthClientAccessRetransmissions,
        usdRadiusAuthClientAccessAccepts,
        usdRadiusAuthClientAccessRejects,
        usdRadiusAuthClientAccessChallenges,
        usdRadiusAuthClientMalformedAccessResponses,
        usdRadiusAuthClientBadAuthenticators,
        usdRadiusAuthClientPendingRequests,
        usdRadiusAuthClientTimeouts,
        usdRadiusAuthClientUnknownTypes,
        usdRadiusAuthClientPacketsDropped,

        usdRadiusAuthClientCfgServerPortNumber,
        usdRadiusAuthClientCfgKey,
        usdRadiusAuthClientCfgTimeoutInterval,
        usdRadiusAuthClientCfgRetries,
        usdRadiusAuthClientCfgMaxPendingRequests,
        usdRadiusAuthClientCfgRowStatus,
        usdRadiusAuthClientCfgPrecedence,
        usdRadiusAuthClientCfgDeadTime }
    STATUS      current
    DESCRIPTION
        "The basic collection of objects providing management of
        RADIUS Authentication Clients."
    ::= { usdRadiusClientMIBGroups 2 }

usdRadiusAcctClientGroup OBJECT-GROUP
    OBJECTS {
        usdRadiusAcctClientInvalidServerAddresses,

        usdRadiusAcctClientServerPortNumber,
        usdRadiusAcctClientRoundTripTime,
        usdRadiusAcctClientRequests,
        usdRadiusAcctClientRetransmissions,
        usdRadiusAcctClientResponses,
        usdRadiusAcctClientMalformedResponses,
        usdRadiusAcctClientBadAuthenticators,
        usdRadiusAcctClientPendingRequests,
        usdRadiusAcctClientTimeouts,
        usdRadiusAcctClientUnknownTypes,
        usdRadiusAcctClientPacketsDropped,

        usdRadiusAcctClientCfgServerPortNumber,
        usdRadiusAcctClientCfgKey,
        usdRadiusAcctClientCfgTimeoutInterval,
        usdRadiusAcctClientCfgRetries,
        usdRadiusAcctClientCfgMaxPendingRequests,
        usdRadiusAcctClientCfgRowStatus,
        usdRadiusAcctClientCfgPrecedence,
        usdRadiusAcctClientCfgDeadTime }
    STATUS      current
    DESCRIPTION
        "The basic collection of objects providing management of RADIUS
        Accounting Clients."
    ::= { usdRadiusClientMIBGroups 3 }

usdRadiusGeneralClientGroup2 OBJECT-GROUP
    OBJECTS {
        usdRadiusClientIdentifier,
        usdRadiusClientAlgorithm,
        usdRadiusClientSourceAddress }
    STATUS      obsolete
    DESCRIPTION
        "Obsolete basic collection of objects providing management of RADIUS
        Clients.  This group became obsolete when new objects were added."
    ::= { usdRadiusClientMIBGroups 4 }

usdRadiusBasicClientGroup OBJECT-GROUP
    OBJECTS {
        usdRadiusClientIdentifier,
        usdRadiusClientAlgorithm,
        usdRadiusClientSourceAddress,
        usdRadiusClientUdpChecksum,
        usdRadiusClientNasIdentifier }
    STATUS      obsolete
    DESCRIPTION
        "Obsolete collection of objects providing basic management of RADIUS
        Clients.  This group became obsolete when the usdRadiusClientRollover
        object was added."
    ::= { usdRadiusClientMIBGroups 5 }

usdRadiusBrasClientGroup OBJECT-GROUP
    OBJECTS {
        usdRadiusClientDslPortType,
        usdRadiusClientAcctSessionIdFormat,
        usdRadiusClientNasPortFormat,
        usdRadiusClientCallingStationDelimiter }
    STATUS      obsolete
    DESCRIPTION
        "Obsolete collection of objects providing management of general B-RAS
        functions for RADIUS Clients.  This group became obsolete when new
        objects were added."
    ::= { usdRadiusClientMIBGroups 6 }

usdRadiusTunnelClientGroup OBJECT-GROUP
    OBJECTS {
        usdRadiusClientTunnelAccounting }
    STATUS      current
    DESCRIPTION
        "An object providing management of tunneling functions for RADIUS
        Clients."
    ::= { usdRadiusClientMIBGroups 7 }

usdRadiusBrasClientGroup2 OBJECT-GROUP
    OBJECTS {
        usdRadiusClientDslPortType,
        usdRadiusClientAcctSessionIdFormat,
        usdRadiusClientNasPortFormat,
        usdRadiusClientCallingStationDelimiter,
        usdRadiusClientEthernetPortType,
        usdRadiusClientIncludeIpAddrInAcctStart,
        usdRadiusClientIncludeAcctSessionIdInAccessReq }
    STATUS      obsolete
    DESCRIPTION
        "Obsolete collection of objects providing management of general B-RAS
        functions for RADIUS Clients.  This group became obsolete when the
        usdRadiusClientCallingStationIdFormat object was added."
    ::= { usdRadiusClientMIBGroups 8 }

usdRadiusBasicClientGroup2 OBJECT-GROUP
    OBJECTS {
        usdRadiusClientIdentifier,
        usdRadiusClientAlgorithm,
        usdRadiusClientSourceAddress,
        usdRadiusClientUdpChecksum,
        usdRadiusClientNasIdentifier,
        usdRadiusClientRollover }
    STATUS      current
    DESCRIPTION
        "A collection of objects providing basic management of RADIUS Clients."
    ::= { usdRadiusClientMIBGroups 9 }

usdRadiusBrasClientGroup3 OBJECT-GROUP
    OBJECTS {
        usdRadiusClientDslPortType,
        usdRadiusClientAcctSessionIdFormat,
        usdRadiusClientNasPortFormat,
        usdRadiusClientCallingStationDelimiter,
        usdRadiusClientEthernetPortType,
        usdRadiusClientIncludeIpAddrInAcctStart,
        usdRadiusClientIncludeAcctSessionIdInAccessReq,
        usdRadiusClientCallingStationIdFormat }
    STATUS      obsolete
    DESCRIPTION
        "Obsolete collection of objects providing management of general B-RAS
        functions for RADIUS Clients.  This group became obsolete when the
        usdRadiusClientNasIpAddrUse object was added."
    ::= { usdRadiusClientMIBGroups 10 }

usdRadiusBrasClientGroup4 OBJECT-GROUP
    OBJECTS {
        usdRadiusClientDslPortType,
        usdRadiusClientAcctSessionIdFormat,
        usdRadiusClientNasPortFormat,
        usdRadiusClientCallingStationDelimiter,
        usdRadiusClientEthernetPortType,
        usdRadiusClientIncludeIpAddrInAcctStart,
        usdRadiusClientIncludeAcctSessionIdInAccessReq,
        usdRadiusClientCallingStationIdFormat,
        usdRadiusClientNasIpAddrUse }
    STATUS      obsolete
    DESCRIPTION
        "Obsolete collection of objects providing management of general B-RAS
        functions for RADIUS Clients.  This group became obsolete when objects
        were added to indicate which RADIUS attributes should be included or
        excluded from RADIUS packets."
    ::= { usdRadiusClientMIBGroups 11 }

usdRadiusBrasClientGroup5 OBJECT-GROUP
    OBJECTS {
        usdRadiusClientDslPortType,
        usdRadiusClientAcctSessionIdFormat,
        usdRadiusClientNasPortFormat,
        usdRadiusClientCallingStationDelimiter,
        usdRadiusClientEthernetPortType,
        usdRadiusClientIncludeIpAddrInAcctStart,
        usdRadiusClientIncludeAcctSessionIdInAccessReq,
        usdRadiusClientCallingStationIdFormat,
        usdRadiusClientNasIpAddrUse,
        usdRadiusClientIncludeAcctTunnelConnectionInAccessReq,
        usdRadiusClientIncludeCalledStationIdInAccessReq,
        usdRadiusClientIncludeCallingStationIdInAccessReq,
        usdRadiusClientIncludeConnectInfoInAccessReq,
        usdRadiusClientIncludeNasIdentifierInAccessReq,
        usdRadiusClientIncludeNasPortInAccessReq,
        usdRadiusClientIncludeNasPortIdInAccessReq,
        usdRadiusClientIncludeNasPortTypeInAccessReq,
        usdRadiusClientIncludePppoeDescriptionInAccessReq,
        usdRadiusClientIncludeTunnelClientAuthIdInAccessReq,
        usdRadiusClientIncludeTunnelClientEndpointInAccessReq,
        usdRadiusClientIncludeTunnelMediumTypeInAccessReq,
        usdRadiusClientIncludeTunnelServerAttributesInAccessReq,
        usdRadiusClientIncludeTunnelServerAuthIdInAccessReq,
        usdRadiusClientIncludeTunnelServerEndpointInAccessReq,
        usdRadiusClientIncludeTunnelTypeInAccessReq,
        usdRadiusClientIncludeAcctTunnelConnectionInAcctStart,
        usdRadiusClientIncludeCalledStationIdInAcctStart,
        usdRadiusClientIncludeCallingStationIdInAcctStart,
        usdRadiusClientIncludeClassInAcctStart,
        usdRadiusClientIncludeConnectInfoInAcctStart,
        usdRadiusClientIncludeEgressPolicyNameInAcctStart,
        usdRadiusClientIncludeEventTimestampInAcctStart,
        usdRadiusClientIncludeFramedCompressionInAcctStart,
        usdRadiusClientIncludeFramedIpNetmaskInAcctStart,
        usdRadiusClientIncludeIngressPolicyNameInAcctStart,
        usdRadiusClientIncludeNasIdentifierInAcctStart,
        usdRadiusClientIncludeNasPortInAcctStart,
        usdRadiusClientIncludeNasPortIdInAcctStart,
        usdRadiusClientIncludeNasPortTypeInAcctStart,
        usdRadiusClientIncludePppoeDescriptionInAcctStart,
        usdRadiusClientIncludeTunnelAssignmentIdInAcctStart,
        usdRadiusClientIncludeTunnelClientAuthIdInAcctStart,
        usdRadiusClientIncludeTunnelClientEndpointInAcctStart,
        usdRadiusClientIncludeTunnelMediumTypeInAcctStart,
        usdRadiusClientIncludeTunnelPreferenceInAcctStart,
        usdRadiusClientIncludeTunnelServerAttributesInAcctStart,
        usdRadiusClientIncludeTunnelServerAuthIdInAcctStart,
        usdRadiusClientIncludeTunnelServerEndpointInAcctStart,
        usdRadiusClientIncludeTunnelTypeInAcctStart,
        usdRadiusClientIncludeAcctTunnelConnectionInAcctStop,
        usdRadiusClientIncludeCalledStationIdInAcctStop,
        usdRadiusClientIncludeCallingStationIdInAcctStop,
        usdRadiusClientIncludeClassInAcctStop,
        usdRadiusClientIncludeConnectInfoInAcctStop,
        usdRadiusClientIncludeEgressPolicyNameInAcctStop,
        usdRadiusClientIncludeEventTimestampInAcctStop,
        usdRadiusClientIncludeFramedCompressionInAcctStop,
        usdRadiusClientIncludeFramedIpNetmaskInAcctStop,
        usdRadiusClientIncludeIngressPolicyNameInAcctStop,
        usdRadiusClientIncludeInputGigawordsInAcctStop,
        usdRadiusClientIncludeNasIdentifierInAcctStop,
        usdRadiusClientIncludeNasPortInAcctStop,
        usdRadiusClientIncludeNasPortIdInAcctStop,
        usdRadiusClientIncludeNasPortTypeInAcctStop,
        usdRadiusClientIncludeOutputGigawordsInAcctStop,
        usdRadiusClientIncludePppoeDescriptionInAcctStop,
        usdRadiusClientIncludeTunnelAssignmentIdInAcctStop,
        usdRadiusClientIncludeTunnelClientAuthIdInAcctStop,
        usdRadiusClientIncludeTunnelClientEndpointInAcctStop,
        usdRadiusClientIncludeTunnelMediumTypeInAcctStop,
        usdRadiusClientIncludeTunnelPreferenceInAcctStop,
        usdRadiusClientIncludeTunnelServerAttributesInAcctStop,
        usdRadiusClientIncludeTunnelServerAuthIdInAcctStop,
        usdRadiusClientIncludeTunnelServerEndpointInAcctStop,
        usdRadiusClientIncludeTunnelTypeInAcctStop,
        usdRadiusClientIncludeInputGigapktsInAcctStop,
        usdRadiusClientIncludeOutputGigapktsInAcctStop,
        usdRadiusClientIgnoreFramedIpNetmask }
    STATUS      current
    DESCRIPTION
        "A collection of objects providing management of general B-RAS functions
        for RADIUS Clients."
    ::= { usdRadiusClientMIBGroups 12 }

END
