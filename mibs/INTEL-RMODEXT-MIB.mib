INTEL-RMODEXT-MIB DEFINITIONS ::= BEGIN

-- Copyright (C) 1997 Intel Corporation. All rights reserved.
--
-- Router specific hardware extension MIB, 18-09-1997
--
-- Change History:
-- 97-09-18 Initial version
--

IMPORTS
   modulesext           FROM INTEL-GEN-MIB
   OBJECT-TYPE          FROM RFC-1212;

   rmodext              OBJECT IDENTIFIER     ::= { modulesext 1 }
   rmodextGeneral       OBJECT IDENTIFIER     ::= { rmodext 1 }

rmodextGModuleTable OBJECT-TYPE
    SYNTAX SEQUENCE OF RmodextGModuleEntry
    ACCESS not-accessible
    STATUS mandatory
    DESCRIPTION "General extensions that applies to all hardware revisions."
    ::= { rmodextGeneral 1 }

rmodextGModuleEntry OBJECT-TYPE
    SYNTAX RmodextGModuleEntry
    ACCESS not-accessible
    STATUS mandatory
    DESCRIPTION ""
    INDEX { rmodextGModuleChassisIndex, rmodextGModuleIndex }
    ::= { rmodextGModuleTable 1 }

RmodextGModuleEntry ::= SEQUENCE {
                        rmodextGModuleChassisIndex
                           INTEGER,
                        rmodextGModuleIndex
                           INTEGER,
                        rmodextGModuleHwEncryption
                           INTEGER,
                        rmodextGModuleSwEncryption
                           INTEGER,
                        rmodextGModuleSwState
                           INTEGER,
                        rmodextGModuleRamFree
                           INTEGER,
                        rmodextGModuleSwVersion
                           OCTET STRING,
                        rmodextGModulePbaNo
                           OCTET STRING,
                        rmodextGModuleBootSectionVersion
                           OCTET STRING,
                        rmodextGModuleMulti1
                           OCTET STRING,
                        rmodextGModuleMulti2
                           OCTET STRING
                        }

rmodextGModuleChassisIndex OBJECT-TYPE
    SYNTAX INTEGER
    ACCESS read-only
    STATUS mandatory
    DESCRIPTION "Chassis number in stack that contains the module.
                 Same as moduleChassisIndex in INTEL-GEN-MIB."
    ::= { rmodextGModuleEntry 1 }

rmodextGModuleIndex OBJECT-TYPE
    SYNTAX INTEGER
    ACCESS read-only
    STATUS mandatory
    DESCRIPTION "Module number in the chassis.
                 Same as moduleIndex in INTEL-GEN-MIB."
    ::= { rmodextGModuleEntry 2 }

rmodextGModuleHwEncryption OBJECT-TYPE
    SYNTAX INTEGER { disabled(1), enabled(2) }
    ACCESS read-only
    STATUS mandatory
    DESCRIPTION "Encryption support
                 disabled: Hardware does not support encryption
                 enabled: Hardware does not support encryption"
    ::= { rmodextGModuleEntry 3 }

rmodextGModuleSwEncryption OBJECT-TYPE
    SYNTAX INTEGER { disabled(1), enabled(2) }
    ACCESS read-only
    STATUS mandatory
    DESCRIPTION "Encryption support
                 disabled: Software does not support encryption
                 enabled: Software does not support encryption"
    ::= { rmodextGModuleEntry 4 }

rmodextGModuleSwState OBJECT-TYPE
    SYNTAX INTEGER { testing(1), noError(2), error(3) }
    ACCESS read-only
    STATUS mandatory
    DESCRIPTION "Router status after cold reset"
    ::= { rmodextGModuleEntry 5 }

rmodextGModuleRamFree OBJECT-TYPE
    SYNTAX INTEGER
    ACCESS read-only
    STATUS mandatory
    DESCRIPTION "Number of kilobytes free in RAM"
    ::= { rmodextGModuleEntry 6 }

rmodextGModuleSwVersion OBJECT-TYPE
    SYNTAX OCTET STRING
    ACCESS read-only
    STATUS mandatory
    DESCRIPTION "Router software version number"
    ::= { rmodextGModuleEntry 7 }

rmodextGModulePbaNo OBJECT-TYPE
    SYNTAX OCTET STRING
    ACCESS read-only
    STATUS mandatory
    DESCRIPTION "PBA number"
    ::= { rmodextGModuleEntry 8 }

rmodextGModuleBootSectionVersion OBJECT-TYPE
    SYNTAX OCTET STRING
    ACCESS read-only
    STATUS mandatory
    DESCRIPTION "Boot PROM version number"
    ::= { rmodextGModuleEntry 9 }

rmodextGModuleMulti1 OBJECT-TYPE
    SYNTAX OCTET STRING (SIZE(250))
    ACCESS read-only
    STATUS mandatory
    DESCRIPTION "Multiple information object 1:
                 - MaxMpLinks (2 bytes)
                 - CompressionType (1 byte): sw(2), hw(3)
                 - Max Compression Rate in kbps (4 bytes)
                 (all values are returned in big-endian format)"
    ::= { rmodextGModuleEntry 10 }

rmodextGModuleMulti2 OBJECT-TYPE
    SYNTAX OCTET STRING (SIZE(250))
    ACCESS read-only
    STATUS mandatory
    DESCRIPTION "Multiple information object 2:
                   Currently empty"
    ::= { rmodextGModuleEntry 11 }

END
