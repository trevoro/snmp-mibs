Nortel-Magellan-Passport-StandardTextualConventionsMIB
DEFINITIONS ::= BEGIN

IMPORTS

      Gauge, Counter, IpAddress, TimeTicks
   FROM RFC1155-SMI

      passportMIBs
   FROM Nortel-Magellan-Passport-UsefulDefinitionsMIB;

--   LAST-UPDATED   "9603010000Z"
--   ORGANIZATION   "Nortel"
--   CONTACT-INFO   "
--         Nortel Magellan Network Management
--
--         Postal: P.O. Box 5080, Station F
--                 Ottawa, Ontario
--                 Canada  K2C 3T1
--
--         Email:  nm_plm@nt.com"
--   DESCRIPTION 
--    "The MIB module providing the Nortel Magellan Passport supported
--     Standard Textual Conventions. This module is provided for your
--     convenience: rather than compiling all of the standard MIBs whose
--     Textual Conventions have been adopted by Magellan Passport, you may
--     compile this MIB instead. "

standardTextualConventionsMIB OBJECT IDENTIFIER ::= { passportMIBs 6 }

-- PassportCounter64 is mapped to Counter to be V1 compatible.

PassportCounter64  ::= Counter

-- SNMPv2 types are redefined here for consistency across
-- the two versions of the MIB Modules:
--
-- If using a SNMPv2 compatible compiler the following lines should
-- be commented out or the compiler will generate error(s) and will
-- not load the MIB.

Gauge32            ::= Gauge
Counter32          ::= Counter
Unsigned32         ::= Gauge
Integer32          ::= INTEGER
NsapAddress        ::= OCTET STRING (SIZE (1 | 4..21 ))

-- This is an SNMPv1 equivalent of SNMPv2-TC. For descriptions of the
-- following textual conventions please see rfc 1903.

DisplayString    ::= OCTET STRING -- (SIZE (0..255))
PhysAddress      ::= OCTET STRING
MacAddress       ::= OCTET STRING (SIZE (6))
TruthValue       ::= INTEGER { true(1), false(2) }
TestAndIncr      ::= INTEGER (0..2147483647)
AutonomousType   ::= OBJECT IDENTIFIER
VariablePointer  ::= OBJECT IDENTIFIER
RowPointer       ::= OBJECT IDENTIFIER
RowStatus        ::= INTEGER {
                     active(1),
                     notInService(2),
                     notReady(3),
                     createAndGo(4),
                     createAndWait(5),
                     destroy(6) }
TimeStamp        ::= TimeTicks
TimeInterval     ::= INTEGER (0..2147483647)
DateAndTime      ::= OCTET STRING (SIZE (8 | 11))
TAddress ::= OCTET STRING (SIZE (1..255))
StorageType ::= INTEGER {
                     other(1),       -- eh?
                     volatile(2),    -- e.g., in RAM
                     nonVolatile(3), -- e.g., in NVRAM
                     permanent(4),   -- e.g., partially in ROM             
                     readOnly(5)     -- e.g., completely in ROM 
                     }


--
-- Standard Conventions:
--

-- from rfc1573: Evolution of the Interfaces Group of MIB-II

   IANAifType ::= INTEGER {
                   other(1),          -- none of the following
                   regular1822(2),
                   hdh1822(3),
                   ddnX25(4),
                   rfc877x25(5),
                   ethernetCsmacd(6),
                   iso88023Csmacd(7),
                   iso88024TokenBus(8),
                   iso88025TokenRing(9),
                   iso88026Man(10),
                   starLan(11),
                   proteon10Mbit(12),
                   proteon80Mbit(13),
                   hyperchannel(14),
                   fddi(15),
                   lapb(16),
                   sdlc(17),
                   ds1(18),           -- DS1/E1 (RFC 1406)
                   e1(19),            -- obsolete
                   basicISDN(20),
                   primaryISDN(21),
                   propPointToPointSerial(22), -- proprietary serial
                   ppp(23),
                   softwareLoopback(24),
                   eon(25),            -- CLNP over IP (RFC 1070)
                   ethernet3Mbit(26),
                   nsip(27),           -- XNS over IP
                   slip(28),           -- generic SLIP
                   ultra(29),          -- ULTRA technologies
                   ds3(30),            -- T-3
                   sip(31),            -- SMDS
                   frameRelay(32),    -- DTE only
                   rs232(33),
                   para(34),           -- parallel-port
                   arcnet(35),         -- arcnet
                   arcnetPlus(36),     -- arcnet plus
                   atm(37),            -- ATM cells
                   miox25(38),
                   sonet(39),          -- SONET or SDH
                   x25ple(40),
                   iso88022llc(41),
                   localTalk(42),
                   smdsDxi(43),
                   frameRelayService(44),  -- Frame relay DCE
                   v35(45),
                   hssi(46),
                   hippi(47),
                   modem(48),          -- Generic modem
                   aal5(49),           -- AAL5 over ATM
                   sonetPath(50),
                   sonetVT(51),
                   smdsIcip(52),       -- SMDS InterCarrier Interface
                   propVirtual(53),    -- proprietary virtual/internal
                   propMultiplexor(54) -- proprietary multiplexing
               }

   -- OwnerString has the same semantics as used in RFC 1271

   --OwnerString ::= OCTET STRING (SIZE(0..255))



   -- InterfaceIndex contains the semantics of ifIndex and
   -- should be used for any objects defined on other mib
   -- modules that need these semantics.

   InterfaceIndex ::= Integer32

-- from rfc1512: FDDI Management Information Base

          FddiTimeNano ::= INTEGER (0..2147483647)
          -- This data type specifies 1 nanosecond units as
          -- an integer value.
          --
          -- NOTE: The encoding is normal integer representation, not
          -- two's complement.  Since this type is used for variables
          -- which are encoded as TimerTwosComplement in the ANSI
          -- specification, two operations need to be performed on such
          -- variables to convert from ANSI form to SNMP form:
          --
          -- 1) Convert from two's complement to normal integer
          --    representation
          -- 2) Multiply by 80 to convert from 80 nsec to 1 nsec units
          --
          -- No resolution is lost.  Moreover, the objects for which
          -- this data type is used effectively do not lose any range
          -- due to the lower maximum value since they do not require
          -- the full range.
          --
          -- Example: If fddimibMACTReq had a value of 8 ms, it would
          -- be stored in ANSI TimerTwosComplement format as 0xFFFE7960
          -- [8 ms is 100000 in 80 nsec units, which is then converted
          -- to two's complement] but be reported as 8000000 in SNMP
          -- since it is encoded here as FddiTimeNano.


          FddiTimeMilli ::= INTEGER (0..2147483647)
          -- This data type is used for some FDDI timers. It specifies
          -- time in 1 millisecond units, in normal integer
          -- representation.

          FddiResourceId ::= INTEGER (0..65535)
          -- This data type is used to refer to an instance of a  MAC,
          -- PORT, or PATH Resource ID.  Indexing begins
          -- at 1.  Zero is used to indicate the absence of a resource.

          FddiSMTStationIdType ::= OCTET STRING (SIZE (8))
          -- The unique identifier for the FDDI station.  This is a
          -- string of 8 octets, represented as X' yy yy xx xx xx xx
          -- xx xx' with the low order 6 octet (xx) from a unique IEEE
          -- assigned address.  The high order two bits of the IEEE
          -- address, the group address bit and the administration bit
          -- (Universal/Local) bit should both be zero.  The first two
          -- octets, the yy octets, are implementor-defined.
           --
          -- The representation of the address portion of the station id
          -- is in the IEEE (ANSI/IEEE P802.1A) canonical notation for
          -- 48 bit addresses.  The canonical form is a 6-octet string
          -- where the first octet contains the first 8 bits of the
          -- address, with the I/G(Individual/Group) address bit as the
          -- least significant bit and the  U/L (Universal/Local) bit
          -- as the next more significant bit, and so on.  Note that
          -- addresses in the ANSI FDDI standard SMT frames are
          -- represented in FDDI MAC order.

          FddiMACLongAddressType ::= OCTET STRING (SIZE (6))
          -- The representation of long MAC addresses as management
          -- values is in the IEEE (ANSI/IEEE P802.1A) canonical
          -- notation for 48 bit addresses.  The canonical form is a
          -- 6-octet string where the first octet contains the first 8
          -- bits of the address, with the I/G (Individual/Group)
          -- address bit as the least significant bit and the  U/L
          -- (Universal/Local) bit as the next more significant bit,
          -- and so on.  Note that the addresses in the SMT frames are
          -- represented in FDDI MAC order.


-- from rfc1493: Definitions of Managed Objects for Bridges

          BridgeId ::= OCTET STRING (SIZE (8))   -- the
                                                 -- Bridge-Identifier
                                                 -- as used in the
                                                 -- Spanning Tree
          -- Protocol to uniquely identify a bridge.  Its first two
          -- octets (in network byte order) contain a priority
          -- value and its last 6 octets contain the MAC address
          -- used to refer to a bridge in a unique fashion
          -- (typically, the numerically smallest MAC address
          -- of all ports on the bridge).
          -- Several objects in this MIB module represent values of
          -- timers used by the Spanning Tree Protocol.  In this
          -- MIB, these timers have values in units of hundreths of
          -- a second (i.e. 1/100 secs).
          -- These timers, when stored in a Spanning Tree Protocol's
          -- BPDU, are in units of 1/256 seconds.  Note, however,
          -- that 802.1D-1990 specifies a settable granularity of
          -- no more than 1 second for these timers.  To avoid
          -- ambiguity, a data type is defined here as a textual
          -- convention and all representation of these timers
          -- in this MIB module are defined using this data type.  An
          -- algorithm is also defined for converting between the
          -- different units, to ensure a timer's value is not
          -- distorted by multiple conversions.
          -- The data type is:

          Timeout ::= INTEGER -- a STP timer in units of 1/100 seconds

          -- To convert a Timeout value into a value in units of
          -- 1/256 seconds, the following algorithm should be used:
          --
          --      b  = floor( (n * 256) / 100)
          --
          -- where:
          --      floor   =  quotient [ignore remainder]
          --      n is the value in 1/100 second units
          --      b is the value in 1/256 second units
          --
          -- To convert the value from 1/256 second units back to
          -- 1/100 seconds, the following algorithm should be used:
          --
          --      n = ceiling( (b * 100) / 256)
          --
          -- where:
          --      ceiling =  quotient [if remainder is 0], or
          --                 quotient + 1 [if remainder is non-zero]
          --      n is the value in 1/100 second units
          --      b is the value in 1/256 second units
          --
          -- Note: it is important that the arithmetic operations are
          -- done in the order specified (i.e., multiply first, divide
          -- second).


-- from rfc1315: Management Information Base for Frame Relay DTEs

     DLCI ::= INTEGER        -- 0..DLCINumber
     --
     --      the range of a Data Link Connection Identifier
     --


-- from rfc1253: OSPF Version 2 Management Information Base

             AreaID ::= IpAddress
     --  The Area ID, in OSPF, has the same format as an IP Address,
     --  but has the function of defining a summarization point for
     --  Link State Advertisements

             RouterID ::= IpAddress
     --  The Router ID, in OSPF, has the same format as an IP Address,
     --  but identifies the router independent of its IP Address.

             Metric    ::= INTEGER (1..'FFFF'h)
             BigMetric ::= INTEGER (1..'FFFFFF'h)
     --  The OSPF Metric is defined as an unsigned value in the range

             Status ::= INTEGER { enabled (1), disabled (2) }
     --  Status Values

             Validation ::= INTEGER { valid (1), invalid (2) }
     --  Row Creation/Deletion Values

             PositiveInteger ::= INTEGER (1..2147483647)
             HelloRange      ::= INTEGER (1..'FFFF'h)
             UpToMaxAge      ::= INTEGER (1..3600)
     --  Time Durations measured in seconds

             DesignatedRouterPriority ::= INTEGER (0..'FF'h)
     --  Potential Priorities for the Designated Router Election

             TOSType ::= INTEGER (0..31)
     --  Type of Service is defined as a mapping to the IP Type of
     --  Service Flags as defined in the Router Requirements
     --  Document:
     --
     --      D => Low Delay          R => Reliable Route
     --      T => High Bandwidth

     --  D T R   TOS      D T R   TOS
     --  0 0 0 =>  0      0 0 1 =>  4
     --  0 1 0 =>  8      0 1 1 => 12
     --  1 0 0 => 16      1 0 1 => 20
     --  1 1 0 => 24      1 1 1 => 28

     --  The remaining values are left for future definition.


-- from rfc1382: SNMP MIB Extension for the X.25 Packet Layer

          X121Address ::= OCTET STRING (SIZE(0..17))
           -- 0 to 17 bytes in length containing the ASCII
           -- characters [0-9], each octet contains one digit
           -- of the address.


--
-- Version and Compliance statements
--
 
 
-- Object-Group Statement:
 
--    OBJECTS   { }
--    STATUS    current
--    DESCRIPTION
--       "A list of all current accessible leaf objects."
 
standardTextualConventionsGroup OBJECT IDENTIFIER ::= { standardTextualConventionsMIB 1 }
standardTextualConventionsGroupBC OBJECT IDENTIFIER ::= { standardTextualConventionsGroup 3 }
standardTextualConventionsGroupBC02 OBJECT IDENTIFIER ::= { standardTextualConventionsGroupBC 2 }
standardTextualConventionsGroupBC02A OBJECT IDENTIFIER ::= { standardTextualConventionsGroupBC02 2 }

 
-- Agent-Capabilities Statement:
 
--    PRODUCT-RELEASE "Passport Release 3.2 Standard Textual Conventions."
--    STATUS          current
--    DESCRIPTION
--       "Standard Textual Conventions MIB: MIB Version BC02A."
--    SUPPORTS        Nortel-Magellan-Passport-StandardTextualConventionsMIB
--    INCLUDES        { standardTextualConventionsGroupBC02A }
 
standardTextualConventionsCapabilities OBJECT IDENTIFIER ::= { standardTextualConventionsMIB 3 }
standardTextualConventionsCapabilitiesBC OBJECT IDENTIFIER ::= { standardTextualConventionsCapabilities 3 }
standardTextualConventionsCapabilitiesBC02 OBJECT IDENTIFIER ::= { standardTextualConventionsCapabilitiesBC 2 }
standardTextualConventionsCapabilitiesBC02A OBJECT IDENTIFIER ::= { standardTextualConventionsCapabilitiesBC02 2 }


END
