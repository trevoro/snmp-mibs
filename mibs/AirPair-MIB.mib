-- File Name : AirPair-MIB_18.0.0.mib
-- Version   : 18.0.0
-- Date      : July 25, 2006
-- Author    : DragonWave Inc.
--
-- $Log: AirPair-MIB_18.0.3.v1.mib $
-- Revision 1.1  2006/11/03 22:28:26Z  ssayeed
-- Initial revision
-- Revision 1.12  2006/11/03 21:35:37Z  ssayeed
-- Revision 1.1  2006/09/18 18:50:40Z  ssayeed
-- Initial revision
-- Revision 1.2  2006/09/08 18:43:32Z  ssayeed
-- v3 trap host entry made read only
-- Revision 1.1  2006/08/31 19:12:46Z  ssayeed
-- Initial revision
-- Revision 1.13  2006/08/29 20:55:26Z  jxu
-- Excessive cable loss change.
-- Revision 1.12  2006/07/26 18:30:38Z  ssayeed
-- mib file was updated to be same as 4.3.1 releases
-- Revision 1.11  2006/07/26 18:03:28Z  aanantha
-- Revision 1.10  2006/07/25 19:01:53Z  aanantha
-- Revision 1.9  2006/07/25 18:59:25Z  aanantha
-- Added new radio bands in 'frequencyType' object. Also made some of the apLinkAnalysis objects as 'OBSOLETE'.
-- Revision 1.8  2006/07/13 16:12:32Z  aguhanathan
-- to add radius related mib
-- Revision 1.7  2006/07/13 14:51:39Z  ssayeed
-- v3 trap host table added
-- Revision 1.6  2006/06/30 20:51:47Z  jxu
-- some stuff.
-- Revision 1.5  2006/06/16 13:08:58Z  aguhanathan
-- cableloss threshold not supported
-- Revision 1.4  2006/06/13 20:12:50Z  ssayeed
-- mdmAmplitudeImbalance is defined back to string
-- Revision 1.3  2006/06/13 18:53:51Z  aanantha
-- Taken care of -1 value for 0 Mbps in Mib file.
-- Revision 1.2  2006/06/13 17:15:03Z  ssayeed
-- syntax error fixed
-- Revision 1.1  2006/06/12 20:25:09Z  ssayeed
-- Initial revision
-- Revision 1.2  2006/06/09 13:21:38Z  aguhanathan
-- to add cable loss threshold, bw utilization
-- Revision 1.1  2006/06/07 14:39:38Z  aanantha
-- Initial revision
-- Revision 1.4  2006/04/11 13:27:15Z  aguhanathan
-- to add radioserialNumMisMatch trap
-- Revision 1.3  2006/04/10 15:12:44Z  jxu
-- change wording and add primary radio faulty trap.
-- Revision 1.1  2006/03/01 20:24:32Z  kadeney
-- Initial revision
-- Revision 1.3  2006/02/23 16:01:07Z  aguhanathan
-- for aam, radio redundancy
-- Revision 1.2  2006/01/06 16:10:45Z  aanantha
-- Support for new frequency file related alarms and traps. New radio bands , airpair types(airpari65, airpair150), SDR_0.
-- Revision 1.1  2005/11/01 21:28:30Z  bkay
-- Initial revision
-- Revision 1.6  2005/10/17 13:54:56Z  jxu
-- Add more mib nodes.
-- Revision 1.5  2005/10/07 13:19:34Z  jxu
-- More nodes.
-- Revision 1.4  2005/10/05 19:33:04Z  pliu
-- radio firmware upgrade.
-- Revision 1.3  2005/10/05 18:53:15Z  jxu
-- New objects for RLS.
-- Revision 1.2  2005/09/26 22:52:54Z  rtharmalingam
-- Added log configs and the modem frame in/out counts
-- Revision 1.1  2005/09/21 20:31:52Z  jxu
-- Initial revision
-- Revision 1.2  2005/06/05 21:21:11Z  jxu
-- Added ranges for some object.
-- Revision 1.1  2005/06/01 19:08:56Z  jxu
-- Initial revision
-- Revision 1.1  2005/05/18 20:29:09Z  bkay
-- Initial revision
--
--


AirPair-MIB	DEFINITIONS ::= BEGIN
         IMPORTS
                  Counter, Gauge,TimeTicks, IpAddress
                      FROM RFC1155-SMI
 				  snmp
			          FROM SNMPv2-MIB                      
                  OBJECT-TYPE,
                  ifIndex
                          FROM RFC-1212;

	PhysAddress ::= 		OCTET STRING

	DisplayString ::= OCTET STRING

-- Important!! For HP OpenView, the following OID definition for ISO must be commented out,
-- otherwise it won't compile. HP openView has already defined ISO.
 
--      iso   OBJECT IDENTIFIER  ::=  { 1 }

	org	OBJECT IDENTIFIER
		::=  {  iso  3  }

	dod	OBJECT IDENTIFIER
		::=  {  org  6  }

	internet	OBJECT IDENTIFIER
		::=  {  dod  1  }

	private	OBJECT IDENTIFIER
		::=  {  internet  4  }

	enterprises	OBJECT IDENTIFIER
		::=  {  private  1  }

	dragonwave	OBJECT IDENTIFIER
		::=  {  enterprises  7262  }

	airPair	OBJECT IDENTIFIER
		::=  {  dragonwave  1  }

	
--
-- AIR PAIR TOP LEVEL OBJECTS
--
        
	apResetSystem	OBJECT-TYPE	
		SYNTAX			INTEGER  ( 0 .. 1  ) 
		ACCESS			write-only
		STATUS			mandatory
		DESCRIPTION		"Writing '1' to this object resets the NIC, Modem, and radio."
		::=  {  airPair  1  }

	apSaveMIB	OBJECT-TYPE	
		SYNTAX			INTEGER  { save ( 1 )  }
		ACCESS			write-only
		STATUS			mandatory
		DESCRIPTION		"Writing '1' to this object save all MIB values. Note: If the AirPair type is 
                                        'airpair120' or 'airpair170' and the radio band doesn't match the AirPair type,
                                         Mib can't be saved."
                                         
		::=  {  airPair  2  }


	apAdminStatus	OBJECT-TYPE	
		SYNTAX			INTEGER  { up ( 1 ) , down ( 2 ) , testing ( 3 ) } 
		ACCESS			read-write
		STATUS			mandatory  
		DESCRIPTION		"NOT IMPLEMENTED
		
						 The desired state of the system. 'testing' and 'down' indicates that no user 
					     packet data can be passed.'down' disables the transmitter, while 'testing' 
					     does not.'up' enables the transmitter."
		DEFVAL 			{ up }
		::=  {  airPair  3  }

	apOperStatus	OBJECT-TYPE	
		SYNTAX			INTEGER  { up ( 1 ) , down ( 2 ) , testing ( 3 ) } 
		ACCESS			read-only
		STATUS			mandatory
		DESCRIPTION		"The current operational state of the system. 
						Testing indicates that no operational packets can be passed."
		::=  {  airPair  4  }

	apAirInterfaceEncryption	OBJECT-TYPE	
		SYNTAX			INTEGER  { disabled ( 1 ) , enabled ( 2 ) } 
		ACCESS			read-only
		STATUS			mandatory 
		DESCRIPTION		"OBSOLETE. This enables encryption on the air interface. "
		DEFVAL			{ disabled }
		::=  {  airPair  5  }

	apMibVersionNumber	OBJECT-TYPE	
		SYNTAX			DisplayString
		ACCESS			read-only
		STATUS			mandatory
		DESCRIPTION		"The version number of the MIB."
		::=  {  airPair  6  }

	apType	OBJECT-TYPE	
		SYNTAX			INTEGER  { airPair50 ( 1 ) , airPair100 ( 2 ) , airPairOC3 ( 3 ) , airPairFLEX ( 4 ), airPair120 ( 5 ),  airPair170 ( 6 ),  airPair200 ( 7 ), airpair150 ( 8 ), airpair65 ( 9 ), airpair40 ( 10 )  } 
		ACCESS			read-only
		STATUS			mandatory  
		DESCRIPTION		"Indicates the specific type of system this is."
		::=  {  airPair  7  } 
		
	apSpeed	OBJECT-TYPE	
		SYNTAX			INTEGER  {flex-0Mbps ( -1 ),  flex-10Mbps ( 1 ) , flex-20Mbps  ( 2 ) ,  flex-30Mbps ( 3 ) , flex-40Mbps ( 4 )
						  , flex-50Mbps ( 5 ) ,  flex-60Mbps  ( 6 ) ,  flex-70Mbps ( 7 )
						  , flex-80Mbps ( 8 ) ,  flex-90Mbps  ( 9 ) ,  flex-100Mbps ( 10 )
                                                  ,flex-110Mbps ( 11 ) , flex-120Mbps ( 12 ) , flex-130Mbps ( 13 )
                                                  ,flex-140Mbps ( 14 ) , flex-150Mbps ( 15 ) , flex-160Mbps ( 16 )
                                                  ,flex-170Mbps ( 17 ) , flex-180Mbps ( 18 ) , flex-190Mbps ( 19 )
                                                  ,flex-200Mbps ( 20 )  } 
		ACCESS			read-write
		STATUS			mandatory  
		DESCRIPTION		"Changes the working speed of the Airpair. 
                                         Writes are only valid if system is a FLEX. Due to backwards compatibility issue, 0 value should
					be treated as 0 Mbps."
		::=  {  airPair  8  }

	apMaxSpeed	OBJECT-TYPE	
		SYNTAX			INTEGER  {flex-0Mbps ( -1 ) , flex-10Mbps ( 1 ) , flex-20Mbps  ( 2 ) ,  flex-30Mbps ( 3 ) , flex-40Mbps ( 4 )
						  , flex-50Mbps ( 5 ) ,  flex-60Mbps  ( 6 ) ,   flex-70Mbps ( 7 )
						  , flex-80Mbps ( 8 ) ,  flex-90Mbps  ( 9 ) ,  flex-100Mbps ( 10 )
                                                  ,flex-110Mbps ( 11 ) , flex-120Mbps ( 12 ) , flex-130Mbps ( 13 )
                                                  ,flex-140Mbps ( 14 ) , flex-150Mbps ( 15 ) , flex-160Mbps ( 16 )
                                                  ,flex-170Mbps ( 17 ) , flex-180Mbps ( 18 ) , flex-190Mbps ( 19 )
                                                  ,flex-200Mbps ( 20 )  } 
		ACCESS			read-only
		STATUS			mandatory  
		DESCRIPTION		"Indicates the maximum speed that this system can operate at. Due to backwards compatibility issue, 0 value should
					be treated as 0 Mbps."
		::=  {  airPair  9  }

	apKey	OBJECT-TYPE	
		SYNTAX			DisplayString
		ACCESS			write-only
		STATUS			mandatory
		DESCRIPTION		"Enter your AirPairFLEX key here along with the maximum speed for 
						 that key to upgrade the FLEX system.
						 
						 Format: [speed] [key]
						 Example: 50 abc123"
		::=  {  airPair  10  }

	apAuthentication	OBJECT IDENTIFIER
		::=  {  airPair  11  }

	apNetworkInterfaceCard	OBJECT IDENTIFIER
		::=  {  airPair  12  }

	apIntermediateFrequencyCard	OBJECT IDENTIFIER
		::=  {  airPair  13  }

	apFrequencies	OBJECT IDENTIFIER
		::=  {  airPair  14  }

	apModem	OBJECT IDENTIFIER
		::=  {  airPair  15  }

	apRadio	OBJECT IDENTIFIER
		::=  {  airPair  16  }

	apCalendar	OBJECT IDENTIFIER
		::=  {  airPair  17  }

	apLeds	OBJECT IDENTIFIER
		::=  {  airPair  18  }

	apSystemAlarms	OBJECT IDENTIFIER
		::=  {  airPair  19  } 

	apSnmpTraps	OBJECT IDENTIFIER
		::=  {  airPair  20  }

	apSnmpManagers	OBJECT IDENTIFIER
		::=  {  airPair  21  }

	apLinkAnalysis	OBJECT IDENTIFIER
		::=  {  airPair  22  }

        apCoS	OBJECT IDENTIFIER
		::=  {  airPair  23  }
        	
        apManagementSessions	OBJECT IDENTIFIER
		::=  {  airPair  24  }
 
        apInstall	OBJECT IDENTIFIER
		::=  {  airPair  25  } 

	httpSecure	OBJECT IDENTIFIER
		::=   {  airPair  27  }
    
        gigaEQos   OBJECT IDENTIFIER
		::=  {  airPair  28  } 
 
        rapidLinkShutdown   OBJECT IDENTIFIER
		::=  {  airPair  29  } 

        sntp OBJECT IDENTIFIER
		::=  {  airPair  30  }
             
        apLogs OBJECT IDENTIFIER
		::=  {  airPair  31  }

	  radius OBJECT IDENTIFIER
		::=  {  airPair  32  }


--
--  NESTED OBJECTS BELOW:
--
  
  
--
-- AIRPAIR PEER NODE AUTHENTICATION INFORMATION
--

	uniquePeerAuthenticationKey	OBJECT-TYPE	
		SYNTAX			DisplayString ( SIZE ( 0 .. 34  ) ) 
		ACCESS			read-write
		STATUS			mandatory 
		DESCRIPTION		"The serial number of the peer node that this node will communicate with. 
						 This is only used when authentication mode is set to unique."
		::=  {  apAuthentication  1  }

	peerDetectedSerialNumber	OBJECT-TYPE	
		SYNTAX			DisplayString
		ACCESS			read-only
		STATUS			mandatory
		DESCRIPTION		"The serial number of the peer node that the system is presently communicating 
					     with. This is only used when authentication is set to unique."
		::=  {  apAuthentication  2  }

	authenticationMode	OBJECT-TYPE	
		SYNTAX			INTEGER  { none ( 1 ) , unique ( 2 ) , group ( 3 ) } 
		ACCESS			read-write
		STATUS			mandatory  
		DESCRIPTION		"This sets the authentication mode for the system.If configured for unique 
					     authentication, an AIRPAIR node only exchanges user traffic with one other 
					     AIRPAIR node. The serial number is used in this case.
					     
					     If configured for group authentication, an AIRPAIR node exchanges user 
					     traffic with another AIRPAIR node of the same group and uses the 
					     authentication keys."
		DEFVAL			{ none }
		::=  {  apAuthentication  3  }

	authenticationFailureAction	OBJECT-TYPE	
		SYNTAX			INTEGER  { blockTraffic ( 1 ) , passTraffic ( 2 ) } 
		ACCESS			read-write
		STATUS			mandatory 
		DESCRIPTION		"This sets the authentication failure action for the system. 
		
						 Block traffic will block all user traffic including remote 
						 management access.  Pass traffic will allow all user traffic
						 to be sent and recieved"
		DEFVAL			{ blockTraffic }                             
		::=  {  apAuthentication  4  }

	peerAuthenticationStatus	OBJECT-TYPE	
		SYNTAX			INTEGER  { authenticated ( 1 ) , notAuthenticated ( 2 ) , explicitAuthenticationFailure ( 3 ) } 
		ACCESS			read-only
		STATUS			mandatory
		DESCRIPTION		"Specifies the current authentication status of the system.
		
						 Authenticated means authentication is on and the system
						 has been authenticated, notAuthenticated means authentication
						 is off or the system has not communicated yet with the other node,
						 explicit authentication failure means authentication is on and 
						 authentication has failed"
		::=  {  apAuthentication  5  }

--
-- NETWORK CARD INFORMATION
--

	networkInterfaceDesc	OBJECT-TYPE	
		SYNTAX			DisplayString
		ACCESS			read-only
		STATUS			mandatory
		DESCRIPTION		"A textual string containing information about the modem. 
						 Includes the manufacturer, product name, software 
						 version, and hardware version of the modem card."
		::=  {  apNetworkInterfaceCard  1  }
		
	ipAddress	OBJECT-TYPE	
		SYNTAX			IpAddress
		ACCESS			read-only
		STATUS			mandatory
		DESCRIPTION		"The IP Address of the network interface card."
		::=  {  apNetworkInterfaceCard  2  }

	subnetMask	OBJECT-TYPE	
		SYNTAX			IpAddress
		ACCESS			read-only
		STATUS			mandatory
		DESCRIPTION		"The subnet mask for the network interface card."
		::=  {  apNetworkInterfaceCard  3  }

	defaultGateway	OBJECT-TYPE	
		SYNTAX			IpAddress
		ACCESS			read-only
		STATUS			mandatory
		DESCRIPTION		"The default gateway for the network interface card"
		::=  {  apNetworkInterfaceCard  4  }

	autoNegotiationSetup	OBJECT-TYPE	
		SYNTAX			INTEGER  { off ( 1 ) , on ( 2 ) } 
		ACCESS			read-write
		STATUS			mandatory
		DESCRIPTION		"Turns auto-negotiation on or off. Turning off results in 
						 the interface defaulting to 100BaseT, Full Duplex. "
		DEFVAL			{ on }
		::=  {  apNetworkInterfaceCard  5  }

	negotiatedLinkParameters	OBJECT-TYPE	
		SYNTAX			INTEGER  { x100BaseTFullDublex ( 1 ) , x100BaseTHalfDublex ( 2 ) , x1000BaseTFullDublex ( 3 ) , x1000BaseTHalfDublex ( 4 ), notKnown ( 5 ),  x10BaseTFullDublex ( 6 ), x10BaseTHalfDublex ( 7 ), linkNotUp ( 8 ) } 
		ACCESS			read-only
		STATUS			mandatory
		DESCRIPTION		"Displays the Interface card current operating negotiated 
						 parameters."
		::=  {  apNetworkInterfaceCard  6  }

	minimumNegotiableLinkParameters	OBJECT-TYPE	
		SYNTAX			INTEGER  { x100BaseTFullDublex ( 1 ) , x100BaseTHalfDublex ( 2 ) , x1000BaseTFullDublex ( 3 ) , x1000BaseTHalfDublex ( 4 ) } 
		ACCESS			read-only
		STATUS			mandatory
		DESCRIPTION		"Displays the minimum negotiable parameter set for the enet 
						 interface."
		::=  {  apNetworkInterfaceCard  7  }

	serialNumber	OBJECT-TYPE	
		SYNTAX			DisplayString
		ACCESS			read-only
		STATUS			mandatory
		DESCRIPTION		"The Serial number of the network interface card."
		::=  {  apNetworkInterfaceCard  8  }

	snmpSetRequests	OBJECT-TYPE	
		SYNTAX			INTEGER  { disabled ( 1 ) , enabled ( 2 ) } 
		ACCESS			read-only
		STATUS			mandatory
		DESCRIPTION		"Indicates whether SNMP SET requests are allowed."
		DEFVAL			{ disabled }
		::=  {  apNetworkInterfaceCard  9  }

	httpAccessMode	OBJECT-TYPE	
		SYNTAX			INTEGER  { disabled ( 1 ) , enabled ( 2 ) } 
		ACCESS			read-write
		STATUS			mandatory
		DESCRIPTION		"NOT IMPLEMENTED
		
						 Indicates whether HTTP access is allowed."
		DEFVAL			{ disabled }
		::=  {  apNetworkInterfaceCard  10  }

	telnetAccessMode	OBJECT-TYPE	
		SYNTAX			INTEGER  { disabled ( 1 ) , enabled ( 2 ) } 
		ACCESS			read-write
		STATUS			mandatory
		DESCRIPTION		"Indicates whether Telnet access is allowed."
		DEFVAL			{ enabled }
		::=  {  apNetworkInterfaceCard  11  }

	dnsServer	OBJECT-TYPE	
		SYNTAX			IpAddress
		ACCESS			read-write
		STATUS			mandatory
		DESCRIPTION		"NOT IMPLEMENTED
		
						 Indicates the DNS for the system."
		::=  {  apNetworkInterfaceCard  12  }

	vlanTagging	OBJECT-TYPE	
		SYNTAX			INTEGER  { disabled ( 1 ) , enabled ( 2 ) } 
		ACCESS			read-write
		STATUS			mandatory
		DESCRIPTION		"Indicates whether VLAN tagging is enabled."
		DEFVAL			{ disabled }
		::=  {  apNetworkInterfaceCard  13  }

	vlanTag	OBJECT-TYPE	
		SYNTAX			DisplayString  ( SIZE ( 8 ) )
		ACCESS			read-write
		STATUS			mandatory
		DESCRIPTION		"The first two bytes are set to 0x8100. The two byte 
						 control tag is set by the user."
		DEFVAL			{ "81000000" }
		::=  {  apNetworkInterfaceCard  14  }

--
-- NETWORK STATISTICS
--
	nicStatistics	OBJECT IDENTIFIER
		::=  {  apNetworkInterfaceCard  15  }
   
	
        nicFramesIn	OBJECT-TYPE	
		SYNTAX			Counter
		ACCESS			read-only
		STATUS			mandatory
		DESCRIPTION		"The current count of NIC frames received."
		::=  {  nicStatistics  1  }

	nicFramesOut	OBJECT-TYPE	
		SYNTAX			Counter
		ACCESS			read-only
		STATUS			mandatory
		DESCRIPTION		"The current count of NIC frames sent."
		::=  {  nicStatistics  2  }

	nicFramesInError	OBJECT-TYPE	
		SYNTAX			Counter
		ACCESS			read-only
		STATUS			mandatory
		DESCRIPTION		"The current count of NIC frames received in error."
		::=  {  nicStatistics  3  }

	nicUndersizedFramesIn	OBJECT-TYPE	
		SYNTAX			Counter
		ACCESS			read-only
		STATUS			mandatory
		DESCRIPTION		"The current count of undersized NIC frames received."
		::=  {  nicStatistics  4  }

	nicOversizedFramesIn	OBJECT-TYPE	
		SYNTAX			Counter
		ACCESS			read-only
		STATUS			mandatory
		DESCRIPTION		"The current count of oversized NIC frames received."
		::=  {  nicStatistics  5  }

	nicFramesInQueue1Discarded	OBJECT-TYPE	
		SYNTAX			Counter
		ACCESS			read-only
		STATUS			mandatory
		DESCRIPTION		"The current count of NIC frames received in queue 2 that  
						 were discarded, but due to an error. One possible reason  
						 is lack of buffer space."
		::=  {  nicStatistics  6  }

	nicFramesInQueue2Discarded	OBJECT-TYPE	
		SYNTAX			Counter
		ACCESS			read-only
		STATUS			mandatory
		DESCRIPTION		"The current count of NIC frames received in queue 2 that 
						 were discarded, but due to an error. One possible reason  
						 is lack of buffer space."
		::=  {  nicStatistics  7  }

	nicFramesInQueue1	OBJECT-TYPE	
		SYNTAX			Counter
		ACCESS			read-only
		STATUS			mandatory
		DESCRIPTION		"The current count of NIC frames passed through queue 1."
		::=  {  nicStatistics  8  }
	
	nicFramesInQueue2	OBJECT-TYPE	
		SYNTAX			Counter
		ACCESS			read-only
		STATUS			mandatory
		DESCRIPTION		"The current count of NIC frames passed through queue 2."
		::=  {  nicStatistics  9  }
   
	nicFramesInQueue3	OBJECT-TYPE	
		SYNTAX			Counter
		ACCESS			read-only
		STATUS			mandatory
		DESCRIPTION		"The current count of NIC frames passed through queue 3."
		::=  {  nicStatistics  10  }
   
	nicFramesInQueue4	OBJECT-TYPE	
		SYNTAX			Counter
		ACCESS			read-only
		STATUS			mandatory
		DESCRIPTION		"The current count of NIC frames passed through queue 4."
		::=  {  nicStatistics  11  }
   
	nicFramesInQueue3Discarded	OBJECT-TYPE	
		SYNTAX			Counter
		ACCESS			read-only
		STATUS			mandatory
		DESCRIPTION		"The current count of NIC frames received in queue 3 that 
						 were discarded, but due to an error. One possible reason  
						 is lack of buffer space."
		::=  {  nicStatistics  12  }

	nicFramesInQueue4Discarded	OBJECT-TYPE	
		SYNTAX			Counter
		ACCESS			read-only
		STATUS			mandatory
		DESCRIPTION		"The current count of NIC frames received in queue 4 that 
						 were discarded, but due to an error. One possible reason  
						 is lack of buffer space."
		::=  {  nicStatistics  13  }


	maxFrameSize	                OBJECT-TYPE	
		SYNTAX			INTEGER  ( 1600..9600 ) 
		ACCESS			read-write
		STATUS			mandatory
		DESCRIPTION		"The default maximum frame size is 1600 bytes. The settable 
                                         maximum frame size must be a multiple of 128. If the chosen
                                         maximum frame size is not a multiple of 128, its closest 
                                         number which is a multiple of 128 is actually used. The 
                                         settable lowest maximum frame size is 1664, and the settable
                                         highest maximum frame size is 9600. If the chosen maximum 
                                         frame size is out of this range, the default maximum frame 
                                         size of 1600 is used. "
		DEFVAL			{ 1600 }
		::=  {  apNetworkInterfaceCard  16  }


	pauseFrameEnable	        OBJECT-TYPE	
		SYNTAX			INTEGER  { disabled ( 1 ) , enabled ( 2 ) } 
		ACCESS			read-write
		STATUS			mandatory
		DESCRIPTION		"When PAUSE is enabled, pause frames can be generated by the 
                                         system and the pause frames will flow toward the link partner 
                                         on the network. When PAUSE is enabled, 
                                         Qos is disabled automatically.  When PAUSE is not enabled,
                                         no pause frames will be generated by the system. " 
		DEFVAL			{ disabled }
		::=  {  apNetworkInterfaceCard  17  }

       opticalTransmitterState	        OBJECT-TYPE	
		SYNTAX			INTEGER  { off ( 1 ) , on ( 2 ) } 
		ACCESS			read-write
		STATUS			mandatory
		DESCRIPTION		"When it is on, optical transmitter is enabled. Otherwise
                                        optical transmitter is disabled."
		DEFVAL			{ off }
		::=  {  apNetworkInterfaceCard 18 }


	intermediateFrequencyDesc	OBJECT-TYPE	
		SYNTAX			DisplayString
		ACCESS			read-only
		STATUS			mandatory
		DESCRIPTION		"A textual string containing information about the modem. 
						 Includes the manufacturer, product name, software 
						 version, and hardware version of the modem card."
		::=  {  apIntermediateFrequencyCard  1  }

	ifTxSynthesizerLock	OBJECT-TYPE	
		SYNTAX			INTEGER  { unlocked ( 1 ) , locked ( 2 ) } 
		ACCESS			read-only
		STATUS			mandatory
		DESCRIPTION		"Indicates if the transmit synthesizer is locked."
		::=  {  apIntermediateFrequencyCard  2  }

	ifRxSynthesizerLock	OBJECT-TYPE	
		SYNTAX			INTEGER  { unlocked ( 1 ) , locked ( 2 ) } 
		ACCESS			read-only
		STATUS			mandatory
		DESCRIPTION		"Indicates if the receive synthesizer is locked."
		::=  {  apIntermediateFrequencyCard  3  }

	
--
-- FREQENCY INFORMATION
--
	frequencyType	OBJECT-TYPE	
		SYNTAX			INTEGER  { freqNone ( 1 ),fcc18a ( 2 ),fcc18b ( 3 ),fcc18c ( 4 ),
						   ic18a ( 5 ),ic18b ( 6 ),ic18c ( 7 ),fcc23a ( 8 ),fcc23b ( 9 ),fcc23c ( 10 ),
						   fcc23d ( 11 ),ic23a ( 12 ),ic23b ( 13 ),fcc28a ( 14 ),fcc28b ( 15 ),
						   china23 ( 16 ) , un24 (17) , etsi23a-28 ( 18 ), etsi23a-56 ( 19 ), etsi26b-28 ( 20 ),
 						   etsi26b-56 ( 21 ),aus23b-50 ( 22 ),aus23b-28 ( 23 ), dems24-20 ( 24 ), dems24-40 ( 25 ), un24-etsi ( 26 ),
				               	etsi18d-27-5 ( 27 ), aus18-27-5 ( 28 ), etsi18d-55 ( 29 ), aus18-55 ( 30 ),
						   itu23c-28 ( 31 ), nz23c-56 ( 32 ), etsi18c-27-5 ( 33 ),  etsi18c-55 (34),
						   fcc11a-40 ( 35 ), ic11a-40 (36),  fcc11a-30 ( 37),    ic11a-30 ( 38 ), etsi26d-28 ( 39 ),
					           etsi26d-56 ( 40 ), uk23a-56 ( 41 ), ic18c-50 ( 42 ), etsi11a-40 ( 43 ), etsi13a-14 ( 44 ), 
						   etsi13a-28 ( 45 ), nz13a-14 ( 46 ), nz13a-28 ( 47 ), aus13a-28 ( 48 ), france18d-27-5 ( 49 ),
						   france18c-27-5 ( 50 ), ic15-40 ( 51 ), itu15-28 ( 52 ), mex15b-28 ( 53 ), nz15-28 ( 54 ),
						   aus15-28 ( 55 ), etsi15-28 ( 56 ), mex15a-28 ( 57 ), etsi15-14 ( 58 ), aus15-14 ( 59 ), nz15-14 ( 60 ),
						   mex15b-14 ( 61 ), lmds28a1x-50(62), lmds28a1x-25 (63),fcc23c-40(64), fcc23d-40(65) }
										
		ACCESS			read-write
		STATUS			mandatory
		DESCRIPTION		"The radio frequency standard used in the system.
		
						 Frequency bands are divided into sub bands.
						 
						 ie FCC 23 Ghz Band is comprised of fcc23a, fcc23b, fcc23c and 
						 fcc23d which make up the entire FCC23 band"
		DEFVAL			{ freqNone }
		::=  {  apFrequencies  1  }


	freqGroupSelected	OBJECT-TYPE	
		SYNTAX			INTEGER  { txLow ( 1 ) , txHigh ( 2 ) , go ( 3 ) , return ( 4 ) } 
		ACCESS			read-write
		STATUS			mandatory
		DESCRIPTION		"The frequency group selected for the system.
		
						 The frequency subbands are divided into frequency groups txHigh
						 and txLow.  An AIRPAIR system must have one node configured to
						 txLow and the other node configure to txHigh"
		::=  {  apFrequencies  2  }

	txHighFreqTable	OBJECT-TYPE
		SYNTAX		SEQUENCE  OF  TxHighFreqEntry
		ACCESS		not-accessible
		STATUS		mandatory
		DESCRIPTION	"A table of txHigh frequency settings for the system"
		::=  { apFrequencies  3 }

	txHighFreqEntry	OBJECT-TYPE
		SYNTAX		TxHighFreqEntry
		ACCESS		not-accessible
		STATUS		mandatory
		DESCRIPTION	"A txHighFrequency entry containing all the frequency values"      
		INDEX		{  txHighFreqIndex  }
		::=  { txHighFreqTable 1 }

	TxHighFreqEntry  ::=  SEQUENCE {
		txHighFreqIndex  INTEGER,
		txHighFreqChannelIndex  DisplayString,
		txHighFreqTransmitIfFrequency  INTEGER,
		txHighFreqReceiveIfFrequency  INTEGER,
		txHighFreqTransmitRfFrequency  INTEGER,
		txHighFreqReceiveRfFrequency  INTEGER,
		txHighFreqAvailable  INTEGER,
		txHighFreqSelected  INTEGER
		}


	txHighFreqIndex	OBJECT-TYPE	
		SYNTAX			INTEGER  
		ACCESS			read-only
		STATUS			mandatory
		DESCRIPTION		"A unique value for each frequency channel. "
		::=  {  txHighFreqEntry  1  }


	txHighFreqChannelIndex	OBJECT-TYPE	
		SYNTAX			DisplayString
		ACCESS			read-only
		STATUS			mandatory
		DESCRIPTION		"The channel index for the frequency."
		::=  {  txHighFreqEntry  2  }


	txHighFreqTransmitIfFrequency	OBJECT-TYPE	
		SYNTAX			INTEGER   
		ACCESS			read-only
		STATUS			mandatory
		DESCRIPTION		"The IF TX frequency in MHz."
		::=  {  txHighFreqEntry  3  }


	txHighFreqReceiveIfFrequency	OBJECT-TYPE	
		SYNTAX			INTEGER   
		ACCESS			read-only
		STATUS			mandatory
		DESCRIPTION		"The IF RX frequency in MHz."
		::=  {  txHighFreqEntry  4  }


	txHighFreqTransmitRfFrequency	OBJECT-TYPE	
		SYNTAX			INTEGER   
		ACCESS			read-only
		STATUS			mandatory
		DESCRIPTION		"The RF TX frequency in MHz."
		::=  {  txHighFreqEntry  5  }


	txHighFreqReceiveRfFrequency	OBJECT-TYPE	
		SYNTAX			INTEGER   
		ACCESS			read-only
		STATUS			mandatory
		DESCRIPTION		"The RF RX frequency in MHz."
		::=  {  txHighFreqEntry  6  }


	txHighFreqAvailable	OBJECT-TYPE	
		SYNTAX			INTEGER  { notAvailable ( 1 ) , available ( 2 ) } 
		ACCESS			read-write
		STATUS			mandatory
		DESCRIPTION		"Specifies whether the frequency channel can be used."  
		DEFVAL			{ notAvailable }
		::=  {  txHighFreqEntry  7  }


	txHighFreqSelected	OBJECT-TYPE	
		SYNTAX			INTEGER  { active ( 1 ) , notActive ( 2 ) } 
		ACCESS			read-write
		STATUS			mandatory
		DESCRIPTION		"Specifies the operating frequency channel for the modem.
		
						 ***Only 1 index may be selected in a 1 modem system." 
		DEFVAL 			{ notActive }
		::=  {  txHighFreqEntry  8  }

	txLowFreqTable	OBJECT-TYPE
		SYNTAX		SEQUENCE  OF  TxLowFreqEntry
		ACCESS		not-accessible
		STATUS		mandatory
		DESCRIPTION	"A table of txLow frequency settings for the system"
		::=  { apFrequencies  4 }

	txLowFreqEntry	OBJECT-TYPE
		SYNTAX		TxLowFreqEntry
		ACCESS		not-accessible
		STATUS		mandatory
		DESCRIPTION	"A txLowFrequeny entry containing the frequency values
					 for a specific index"
		INDEX		{  txLowFreqIndex  }
		::=  { txLowFreqTable 1 }

	TxLowFreqEntry  ::=  SEQUENCE {
		txLowFreqIndex  INTEGER,
		txLowFreqChannelIndex  DisplayString,
		txLowFreqTransmitIfFrequency  INTEGER,
		txLowFreqReceiveIfFrequency  INTEGER,
		txLowFreqTransmitRfFrequency  INTEGER,
		txLowFreqReceiveRfFrequency  INTEGER,
		txLowFreqAvailable  INTEGER,
		txLowFreqSelected  INTEGER
		}


	txLowFreqIndex	OBJECT-TYPE	
		SYNTAX			INTEGER   
		ACCESS			read-only
		STATUS			mandatory
		DESCRIPTION		"A unique value for each frequency channel. "
		::=  {  txLowFreqEntry  1  }


	txLowFreqChannelIndex	OBJECT-TYPE	
		SYNTAX			DisplayString
		ACCESS			read-only
		STATUS			mandatory
		DESCRIPTION		"The channel index for the frequency. "
		::=  {  txLowFreqEntry  2  }


	txLowFreqTransmitIfFrequency	OBJECT-TYPE	
		SYNTAX			INTEGER   
		ACCESS			read-only
		STATUS			mandatory
		DESCRIPTION		"The IF TX frequency in MHz."
		::=  {  txLowFreqEntry  3  }


	txLowFreqReceiveIfFrequency	OBJECT-TYPE	
		SYNTAX			INTEGER   
		ACCESS			read-only
		STATUS			mandatory
		DESCRIPTION		"The IF RX frequency in MHz."
		::=  {  txLowFreqEntry  4  }


	txLowFreqTransmitRfFrequency	OBJECT-TYPE	
		SYNTAX			INTEGER   
		ACCESS			read-only
		STATUS			mandatory
		DESCRIPTION		"The RF TX frequency in MHz."
		::=  {  txLowFreqEntry  5  }


	txLowFreqReceiveRfFrequency	OBJECT-TYPE	
		SYNTAX			INTEGER   
		ACCESS			read-only
		STATUS			mandatory
		DESCRIPTION		"The RF RX frequency in MHz."
		::=  {  txLowFreqEntry  6  }


	txLowFreqAvailable	OBJECT-TYPE	
		SYNTAX			INTEGER  { notAvailable ( 1 ) , available ( 2 ) } 
		ACCESS			read-write
		STATUS			mandatory
		DESCRIPTION		"Specifies whether the frequency channel can be used. "   
		DEFVAL			{ notAvailable }
		::=  {  txLowFreqEntry  7  }


	txLowFreqSelected	OBJECT-TYPE	
		SYNTAX			INTEGER  { active ( 1 ) , notActive ( 2 ) } 
		ACCESS			read-write
		STATUS			mandatory
		DESCRIPTION		"Specifies the operating frequency channel for the modem.
		
						 ***Only 1 index may be selected in a 1 modem system. "
		DEFVAL			{ notActive }
		::=  {  txLowFreqEntry  8  }
 
 	goFreqTable	OBJECT-TYPE
		SYNTAX		SEQUENCE  OF  GoFreqEntry
		ACCESS		not-accessible
		STATUS		mandatory
		DESCRIPTION	"A table of go frequency settings for the system"
		::=  { apFrequencies  5 }

	goFreqEntry	OBJECT-TYPE
		SYNTAX		GoFreqEntry
		ACCESS		not-accessible
		STATUS		mandatory
		DESCRIPTION	"A goFrequency entry containing all the frequency values"      
		INDEX		{  goFreqIndex  }
		::=  { goFreqTable 1 }

	GoFreqEntry  ::=  SEQUENCE {
		goFreqIndex  INTEGER,
		goFreqChannelIndex  DisplayString,
		goFreqTransmitIfFrequency  INTEGER,
		goFreqReceiveIfFrequency  INTEGER,
		goFreqTransmitRfFrequency  INTEGER,
		goFreqReceiveRfFrequency  INTEGER,
		goFreqAvailable  INTEGER,
		goFreqSelected  INTEGER
		}


	goFreqIndex	OBJECT-TYPE	
		SYNTAX			INTEGER  
		ACCESS			read-only
		STATUS			mandatory
		DESCRIPTION		"A unique value for each frequency channel. "
		::=  {  goFreqEntry  1  }


	goFreqChannelIndex	OBJECT-TYPE	
		SYNTAX			DisplayString
		ACCESS			read-only
		STATUS			mandatory
		DESCRIPTION		"The channel index for the frequency."
		::=  {  goFreqEntry  2  }


	goFreqTransmitIfFrequency	OBJECT-TYPE	
		SYNTAX			INTEGER   
		ACCESS			read-only
		STATUS			mandatory
		DESCRIPTION		"The IF TX frequency in MHz."
		::=  {  goFreqEntry  3  }


	goFreqReceiveIfFrequency	OBJECT-TYPE	
		SYNTAX			INTEGER   
		ACCESS			read-only
		STATUS			mandatory
		DESCRIPTION		"The IF RX frequency in MHz."
		::=  {  goFreqEntry  4  }


	goFreqTransmitRfFrequency	OBJECT-TYPE	
		SYNTAX			INTEGER   
		ACCESS			read-only
		STATUS			mandatory
		DESCRIPTION		"The RF TX frequency in MHz."
		::=  {  goFreqEntry  5  }


	goFreqReceiveRfFrequency	OBJECT-TYPE	
		SYNTAX			INTEGER   
		ACCESS			read-only
		STATUS			mandatory
		DESCRIPTION		"The RF RX frequency in MHz."
		::=  {  goFreqEntry  6  }


	goFreqAvailable	OBJECT-TYPE	
		SYNTAX			INTEGER  { notAvailable ( 1 ) , available ( 2 ) } 
		ACCESS			read-only
		STATUS			mandatory
		DESCRIPTION		"Specifies whether the frequency channel can be used."  
		DEFVAL			{ notAvailable }
		::=  {  goFreqEntry  7  }


	goFreqSelected	OBJECT-TYPE	
		SYNTAX			INTEGER  { active ( 1 ) , notActive ( 2 ) } 
		ACCESS			read-write
		STATUS			mandatory
		DESCRIPTION		"Specifies the operating frequency channel for the modem.
		
						 ***Only 1 index may be selected in a 1 modem system." 
		DEFVAL 			{ notActive }
		::=  {  goFreqEntry  8  }

 	returnFreqTable	OBJECT-TYPE
		SYNTAX		SEQUENCE  OF  ReturnFreqEntry
		ACCESS		not-accessible
		STATUS		mandatory
		DESCRIPTION	"A table of return frequency settings for the system"
		::=  { apFrequencies  6 }

	returnFreqEntry	OBJECT-TYPE
		SYNTAX		ReturnFreqEntry
		ACCESS		not-accessible
		STATUS		mandatory
		DESCRIPTION	"A returnFrequency entry containing all the frequency values"      
		INDEX		{  returnFreqIndex  }
		::=  { returnFreqTable 1 }

	ReturnFreqEntry  ::=  SEQUENCE {
		returnFreqIndex  INTEGER,
		returnFreqChannelIndex  DisplayString,
		returnFreqTransmitIfFrequency  INTEGER,
		returnFreqReceiveIfFrequency  INTEGER,
		returnFreqTransmitRfFrequency  INTEGER,
		returnFreqReceiveRfFrequency  INTEGER,
		returnFreqAvailable  INTEGER,
		returnFreqSelected  INTEGER
		}


	returnFreqIndex	OBJECT-TYPE	
		SYNTAX			INTEGER  
		ACCESS			read-only
		STATUS			mandatory
		DESCRIPTION		"A unique value for each frequency channel. "
		::=  {  returnFreqEntry  1  }


	returnFreqChannelIndex	OBJECT-TYPE	
		SYNTAX			DisplayString
		ACCESS			read-only
		STATUS			mandatory
		DESCRIPTION		"The channel index for the frequency."
		::=  {  returnFreqEntry  2  }


	returnFreqTransmitIfFrequency	OBJECT-TYPE	
		SYNTAX			INTEGER   
		ACCESS			read-only
		STATUS			mandatory
		DESCRIPTION		"The IF TX frequency in MHz."
		::=  {  returnFreqEntry  3  }


	returnFreqReceiveIfFrequency	OBJECT-TYPE	
		SYNTAX			INTEGER   
		ACCESS			read-only
		STATUS			mandatory
		DESCRIPTION		"The IF RX frequency in MHz."
		::=  {  returnFreqEntry  4  }


	returnFreqTransmitRfFrequency	OBJECT-TYPE	
		SYNTAX			INTEGER   
		ACCESS			read-only
		STATUS			mandatory
		DESCRIPTION		"The RF TX frequency in MHz."
		::=  {  returnFreqEntry  5  }


	returnFreqReceiveRfFrequency	OBJECT-TYPE	
		SYNTAX			INTEGER   
		ACCESS			read-only
		STATUS			mandatory
		DESCRIPTION		"The RF RX frequency in MHz."
		::=  {  returnFreqEntry  6  }


	returnFreqAvailable	OBJECT-TYPE	
		SYNTAX			INTEGER  { notAvailable ( 1 ) , available ( 2 ) } 
		ACCESS			read-only
		STATUS			mandatory
		DESCRIPTION		"Specifies whether the frequency channel can be used."  
		DEFVAL			{ notAvailable }
		::=  {  returnFreqEntry  7  }


	returnFreqSelected	OBJECT-TYPE	
		SYNTAX			INTEGER  { active ( 1 ) , notActive ( 2 ) } 
		ACCESS			read-write
		STATUS			mandatory
		DESCRIPTION		"Specifies the operating frequency channel for the modem.
		
						 ***Only 1 index may be selected in a 1 modem system." 
		DEFVAL 			{ notActive }
		::=  {  returnFreqEntry  8  }


 	unlicensedTxFreqTable	OBJECT-TYPE
		SYNTAX		SEQUENCE  OF  UnlicensedTxFreqEntry
		ACCESS		not-accessible
		STATUS		mandatory
		DESCRIPTION	"OBSOLETE. A table of unlicensed Tx frequency settings for the system"
		::=  { apFrequencies  7 }

	unlicensedTxFreqEntry	OBJECT-TYPE
		SYNTAX		UnlicensedTxFreqEntry
		ACCESS		not-accessible
		STATUS		mandatory
		DESCRIPTION	"A unlicensed Tx entry containing all the frequency values"      
		INDEX		{  unlicensedTxFreqIndex  }
		::=  { unlicensedTxFreqTable 1 }

	UnlicensedTxFreqEntry  ::=  SEQUENCE {
		unlicensedTxFreqIndex  INTEGER,
		unlicensedTxFreqChannelIndex  DisplayString,
		unlicensedTxIfFrequency  INTEGER,
		unlicensedTxRfFrequency  INTEGER,
		setUnlicensedTxFrequency  INTEGER
		}


	unlicensedTxFreqIndex	OBJECT-TYPE	
		SYNTAX			INTEGER  
		ACCESS			read-only
		STATUS			mandatory
		DESCRIPTION		"A unique value for each frequency channel. "
		::=  {  unlicensedTxFreqEntry  1  }


	unlicensedTxFreqChannelIndex	OBJECT-TYPE	
		SYNTAX			DisplayString
		ACCESS			read-only
		STATUS			mandatory
		DESCRIPTION		"The channel index for the frequency."
		::=  {  unlicensedTxFreqEntry  2  }


	unlicensedTxIfFrequency	OBJECT-TYPE	
		SYNTAX			INTEGER   
		ACCESS			read-only
		STATUS			mandatory
		DESCRIPTION		"The IF TX frequency in MHz."
		::=  {  unlicensedTxFreqEntry  3  }

	unlicensedTxRfFrequency	OBJECT-TYPE	
		SYNTAX			INTEGER   
		ACCESS			read-only
		STATUS			mandatory
		DESCRIPTION		"The RF TX frequency in MHz."
		::=  {  unlicensedTxFreqEntry  4  }
		
	setUnlicensedTxFrequency	OBJECT-TYPE	
		SYNTAX			INTEGER { set ( 1 ) }  
		ACCESS			read-write
		STATUS			mandatory
		DESCRIPTION		"To set the TX frequencies in the progrmmed frequency."
		::=  {  unlicensedTxFreqEntry  5  }   
		
		
 	unlicensedRxFreqTable	OBJECT-TYPE
		SYNTAX		SEQUENCE  OF  UnlicensedRxFreqEntry
		ACCESS		not-accessible
		STATUS		mandatory
		DESCRIPTION	"OBSOLETE. A table of unlicensed Rx frequency settings for the system"
		::=  { apFrequencies  8 }

	unlicensedRxFreqEntry	OBJECT-TYPE
		SYNTAX		UnlicensedRxFreqEntry
		ACCESS		not-accessible
		STATUS		mandatory
		DESCRIPTION	"A unlicensed Rx entry containing all the frequency values"      
		INDEX		{  unlicensedRxFreqIndex  }
		::=  { unlicensedRxFreqTable 1 }

	UnlicensedRxFreqEntry  ::=  SEQUENCE {
		unlicensedRxFreqIndex  INTEGER,
		unlicensedRxFreqChannelIndex  DisplayString,
		unlicensedRxIfFrequency  INTEGER,
		unlicensedRxRfFrequency  INTEGER,
		setUnlicensedRxFrequency  INTEGER
		}


	unlicensedRxFreqIndex	OBJECT-TYPE	
		SYNTAX			INTEGER  
		ACCESS			read-only
		STATUS			mandatory
		DESCRIPTION		"A unique value for each frequency channel. "
		::=  {  unlicensedRxFreqEntry  1  }


	unlicensedRxFreqChannelIndex	OBJECT-TYPE	
		SYNTAX			DisplayString
		ACCESS			read-only
		STATUS			mandatory
		DESCRIPTION		"The channel index for the frequency."
		::=  {  unlicensedRxFreqEntry  2  }


	unlicensedRxIfFrequency	OBJECT-TYPE	
		SYNTAX			INTEGER   
		ACCESS			read-only
		STATUS			mandatory
		DESCRIPTION		"The IF Rx frequency in MHz."
		::=  {  unlicensedRxFreqEntry  3  }

	unlicensedRxRfFrequency	OBJECT-TYPE	
		SYNTAX			INTEGER   
		ACCESS			read-only
		STATUS			mandatory
		DESCRIPTION		"The RF Rx frequency in MHz."
		::=  {  unlicensedRxFreqEntry  4  }
		
	setUnlicensedRxFrequency	OBJECT-TYPE	
		SYNTAX			INTEGER { set ( 1 ) }
		ACCESS			read-write
		STATUS			mandatory
		DESCRIPTION		"To set the Rx frequencies in the progrmmed frequency."
		::=  {  unlicensedRxFreqEntry  5  } 

	programmedFrequency	OBJECT IDENTIFIER
		::=  {  apFrequencies  9  }  
		
	programmedFrequencyChannel	OBJECT-TYPE	
		SYNTAX			DisplayString  
		ACCESS			read-only
		STATUS			mandatory
		DESCRIPTION		"The channel that has been programmed into the system."
		::=  {  programmedFrequency  1  }		

	programmedFrequencyTxIf	OBJECT-TYPE	
		SYNTAX			INTEGER   
		ACCESS			read-only
		STATUS			mandatory
		DESCRIPTION		"The programmed IF TX frequency in MHz."
		::=  {  programmedFrequency  2  }


	programmedFrequencyRxIf	OBJECT-TYPE	
		SYNTAX			INTEGER   
		ACCESS			read-only
		STATUS			mandatory
		DESCRIPTION		"The programmed IF RX frequency in MHz."
		::=  {  programmedFrequency  3  }


	programmedFrequencyTxRf	OBJECT-TYPE	
		SYNTAX			INTEGER   
		ACCESS			read-only
		STATUS			mandatory
		DESCRIPTION		"The programmed RF TX frequency in MHz."
		::=  {  programmedFrequency  4  }


	programmedFrequencyRxRf	OBJECT-TYPE	
		SYNTAX			INTEGER   
		ACCESS			read-only
		STATUS			mandatory
		DESCRIPTION		"The RF RX frequency in MHz."
		::=  {  programmedFrequency  5  }


--
-- FREQUENCY FILE INFO
--

	apFrequencyFile OBJECT IDENTIFIER
		::=  { apFrequencies  10  }


        frequencyFileOption  OBJECT-TYPE	
		SYNTAX			INTEGER   { on ( 1 ) , off ( 2 ) } 
		ACCESS			read-only
		STATUS			mandatory
		DESCRIPTION		"Option which tells whether frequency file is being used for system settings."
		::=  {  apFrequencyFile 1  }
        
       

--
-- MODEM CARD INFORMATION
--
  
	mdmDesc	OBJECT-TYPE	
		SYNTAX			DisplayString
		ACCESS			read-only
		STATUS			mandatory
		DESCRIPTION		"A textual string containing information about the modem. 
						 Includes the manufacturer, product name, software 
						 version, and hardware version of the modem card."
		::=  {  apModem  1  }

	mdmModulationType	OBJECT-TYPE	
		SYNTAX			INTEGER  { qpsk ( 1 ) , qam ( 2 ) , qam16 ( 3 ) , qam32 ( 4 ) , qam64 ( 5 ) , qam128 ( 6 ) , qam256 ( 7 ) , x8psk ( 8 ) } 
		ACCESS			read-only
		STATUS			mandatory
		DESCRIPTION		"The modulation type of the modem, distinguished according 
						 to the physical/link protocol."
		::=  {  apModem  2  }

	mdmCurrentRxSpeed	OBJECT-TYPE	
		SYNTAX			DisplayString
		ACCESS			read-only
		STATUS			mandatory
		DESCRIPTION		"An estimate of the modem's current Rx bandwidth in bits per 
						 second."
		::=  {  apModem  3  }

	mdmCurrentTxSpeed	OBJECT-TYPE	
		SYNTAX			DisplayString
		ACCESS			read-only
		STATUS			mandatory
		DESCRIPTION		"An estimate of the modem's current Tx bandwidth in bits per 
						 second."
		::=  {  apModem  4  }

	mdmAdminStatus	OBJECT-TYPE	
		SYNTAX			INTEGER  { up ( 1 ) , down ( 2 ) , testing ( 3 ) } 
		ACCESS			read-write
		STATUS			mandatory
		DESCRIPTION		"NOT IMPLEMENTED
		
						 The desired state of the modem card. 'testing' and 'down' 
						 indicates that no user  packet data can be passed."
		::=  {  apModem  5  }

	mdmOperStatus	OBJECT-TYPE	
		SYNTAX			INTEGER  { up ( 1 ) , down ( 2 ) , testing ( 3 ) } 
		ACCESS			read-only
		STATUS			mandatory
		DESCRIPTION		"The current operational state of the interface. Testing 
						 indicates that no operational packets can be passed."
		::=  {  apModem  6  }

	mdmLastChange	OBJECT-TYPE	
		SYNTAX			TimeTicks
		ACCESS			read-only
		STATUS			mandatory
		DESCRIPTION		"The value of sysUpTime at the time the modem entered its 
						 current operational state. If the current state was 
						 entered prior to the last re-initialization of the local 
						 network management subsystem, then this object contains 
						 a zero value."
		::=  {  apModem  7  }

	mdmBer	OBJECT-TYPE	
		SYNTAX			DisplayString
		ACCESS			read-only
		STATUS			mandatory
		DESCRIPTION		"An estimation of the current uncorrected BER.  Uncorrected BER is the bit error rate as measured before frame error correction."
		::=  {  apModem  8  }

	mdmEbToNoiseRatio	OBJECT-TYPE	
		SYNTAX			DisplayString
		ACCESS			read-only
		STATUS			mandatory
		DESCRIPTION		"The ratio of the modem Estimated Energy per information bit to Noise power spectral density"
		::=  {  apModem  9  }

	mdmRSL	OBJECT-TYPE	
		SYNTAX			DisplayString
		ACCESS			read-only
		STATUS			mandatory
		DESCRIPTION		"NOT USED. DEPRECATED. Use radioRSL object in radio folder. The Received Signal Level at the demodulator. Indicates the power of the receive level in -dBm."
		::=  {  apModem  10  }

	mdmEqualizerStress	OBJECT-TYPE	
		SYNTAX			DisplayString
		ACCESS			read-only
		STATUS			mandatory
		DESCRIPTION		"Indicates the average magnitude of all the equalizer taps to provide a measure of how hard the equalizer is working."
		::=  {  apModem  11  }

	mdmReset	OBJECT-TYPE	
		SYNTAX			INTEGER ( 0 .. 1  )
		ACCESS			read-write
		STATUS			mandatory
		DESCRIPTION		"Writing 1 to this object causes the modem card to be reset. 
						 All other values are not recognized. This variable always 
						 reads back as 0. mdmOperStatus should be polled by the 
						 user after this object is written to, to verify that the 
						 modem card has been reset. "
		::=  {  apModem  12  }

	mdmSlopeEqualizerStress	OBJECT-TYPE	
		SYNTAX			DisplayString
		ACCESS			read-only
		STATUS			mandatory
		DESCRIPTION		"A floating point number indicating how much the received 
					  	 signal has been spectrally sloped."
		::=  {  apModem  13  }

	mdmPhaseImbalance	OBJECT-TYPE	
		SYNTAX			DisplayString
		ACCESS			read-only
		STATUS			mandatory
		DESCRIPTION		"Reports the I/Q phase correction applied by demodulator 
						 ASSP correction loops."
		::=  {  apModem  14  }


	mdmAmplitudeImbalance	OBJECT-TYPE	
		SYNTAX			DisplayString
		ACCESS			read-only
		STATUS			mandatory
		DESCRIPTION		"Reports the I/Q amplitude correction applied by demodulator 
						 ASSP correction loops."
		::=  {  apModem  15 }
		
	mdmCurrentRxSpeedInt	OBJECT-TYPE	
		SYNTAX			INTEGER
		ACCESS			read-only
		STATUS			mandatory
		DESCRIPTION		"Integer version of 'mdmCurrentRxSpeed' object. Divide by '10000' to get the 
					actual value. Mainly provided to facilitate plotting of values. An estimate of the modem's current Rx bandwidth in bits per 
						 second. "
		::=  {  apModem  18  }
		
		
	mdmCurrentTxSpeedInt	OBJECT-TYPE	
		SYNTAX			INTEGER
		ACCESS			read-only
		STATUS			mandatory
		DESCRIPTION		"Integer version of 'mdmCurrentTxSpeed' object. Divide by '10000' to get the 
					actual value. Mainly provided to facilitate plotting of values. An estimate of the modem's current Tx bandwidth in bits per 
						 second."
		::=  {  apModem  19  }
		
		
    	mdmBerInt	OBJECT-TYPE	
		SYNTAX			INTEGER
		ACCESS			read-only
		STATUS			mandatory
		DESCRIPTION		"Integer version of 'mdmBer' object.Divide by 1e+8 to get the actual value. Any value less than 1e-8 will
						  be truncated to 0.Mainly provided to facilitate plotting of values.
						 An estimation of the current uncorrected BER. 
						 Uncorrected BER is the bit error rate as measured before frame error correction."
		::=  {  apModem  20  }
		
	mdmEbToNoiseRatioInt	OBJECT-TYPE	
		SYNTAX			INTEGER
		ACCESS			read-only
		STATUS			mandatory
		DESCRIPTION		"Integer version of 'mdmEbToNoiseRatio' object. Divide by '10' to get the 
					actual value. Mainly provided to facilitate plotting of values. The ratio of the modem Estimated 
						 Energy per information bit to Noise power spectral density. "
		::=  {  apModem  21  }
		
		
	mdmSlopeEqualizerStressInt	OBJECT-TYPE	
		SYNTAX			INTEGER
		ACCESS			read-only
		STATUS			mandatory
		DESCRIPTION		"Integer version of 'mdmSlopeEqualizerStress' object. Divide by '100' to get the 
					actual value. Mainly provided to facilitate plotting of values.A floating point number indicating how much the received 
					  	 signal has been spectrally sloped."
		::=  {  apModem  22  }
		
	mdmPhaseImbalanceInt	OBJECT-TYPE	
		SYNTAX			INTEGER
		ACCESS			read-only
		STATUS			mandatory
		DESCRIPTION		"Integer version of 'mdmPhaseImbalance' object. Divide by '100' to get the 
					actual value. Mainly provided to facilitate plotting of values.Reports the I/Q phase correction applied by demodulator 
						 ASSP correction loops."
		::=  {  apModem  23  }
		
	mdmAmplitudeImbalanceInt	OBJECT-TYPE	
		SYNTAX			INTEGER
		ACCESS			read-only
		STATUS			mandatory
		DESCRIPTION		"Integer version of 'mdmAmplitudeImbalance' object. Divide by '100' to get the 
					actual value. Mainly provided to facilitate plotting of values. Reports the I/Q amplitude correction applied by demodulator 
						 ASSP correction loops."
		::=  {  apModem  24 }
		
--
-- MODEM CARD STATISTICS
--
	mdmStatistics	OBJECT IDENTIFIER
		::=  {  apModem  16  }
		
	aamStatus     OBJECT-TYPE	
		SYNTAX			INTEGER  { disabled ( 1 ) , enabled ( 2 ) } 
		ACCESS			read-write
		STATUS			mandatory
		DESCRIPTION		"Indicates whether Automatic Adaptive Modulation(AAM) is enabled."
		DEFVAL			{ disabled }
		::=  {  apModem  17  }	


	mdmFramesOut	  OBJECT-TYPE	
		SYNTAX			Counter
		ACCESS			read-only
		STATUS			mandatory
		DESCRIPTION		"The current count of Modem frames sent."
		::=  {  mdmStatistics 1  }

	mdmFramesBlocksIn	  OBJECT-TYPE	
		SYNTAX			Counter
		ACCESS			read-only
		STATUS			mandatory
		DESCRIPTION		"The current count of Modem blocks received."
		::=  {  mdmStatistics 2  }

	mdmFramesBlocksInError	  OBJECT-TYPE	
		SYNTAX			Counter
		ACCESS			read-only
		STATUS			mandatory
		DESCRIPTION		"The current count of Modem blocks received in error."
		::=  {  mdmStatistics 3  }

	mdmFramesIn	  OBJECT-TYPE	
		SYNTAX			Counter
		ACCESS			read-only
		STATUS			mandatory
		DESCRIPTION		"The current count of Modem frames received."
		::=  {  mdmStatistics 4  }

	mdmFramesInError	OBJECT-TYPE	
		SYNTAX			Counter
		ACCESS			read-only
		STATUS			mandatory
		DESCRIPTION		"The current count of Modem frames received in error."
		::=  {  mdmStatistics 5  }

	mdmQueueFramesDiscarded	OBJECT-TYPE	
		SYNTAX			Counter
		ACCESS			read-only
		STATUS			mandatory
		DESCRIPTION		"The current count of Modem frames in the queue that were discarded."
		::=  {  mdmStatistics 6  }

 	mdmBWUtilization	OBJECT-TYPE	
		SYNTAX			INTEGER
		ACCESS			read-only
		STATUS			mandatory
		DESCRIPTION		"The carried load over link capacity."
		::=  {  mdmStatistics 7  }

	mdmIngressDataRate	OBJECT-TYPE	
		SYNTAX			INTEGER
		ACCESS			read-only
		STATUS			mandatory
		DESCRIPTION		"The data rate coming into the ethernet port.
					 The data rate you see is multiplied by 100. e.g. A display
                                                 of 1530 is actually 15.30 Mpbs"
		::=  {  mdmStatistics 8  }

	mdmEgressDataRate	OBJECT-TYPE	
		SYNTAX			INTEGER
		ACCESS			read-only
		STATUS			mandatory
		DESCRIPTION		"The data rate going out of the ethernet port.
					 The data rate you see is multiplied by 100. e.g. A display
                                                 of 1530 is actually 15.30 Mpbs."
		::=  {  mdmStatistics 9  }



--
-- RADIO INFORMATION
--

	radioDesc	OBJECT-TYPE	
		SYNTAX			DisplayString
		ACCESS			read-only
		STATUS			mandatory
		DESCRIPTION		"A textual string containing information about the radio. 
						 Includes the manufacturer, product name, software version, 
						 serial number, and hardware version of the radio."
		::=  {  apRadio  1  }

	radioPhysAddr	OBJECT-TYPE	
		SYNTAX			INTEGER
		ACCESS			read-only
		STATUS			mandatory
		DESCRIPTION		"The physical address used to distinguish it from other 
						 radios."
		::=  {  apRadio  2  }

	radioAdminStatus	OBJECT-TYPE	
		SYNTAX			INTEGER  { up ( 1 ) , down ( 2 ) , testing ( 3 ), firmwareUpgrade( 4) } 
		ACCESS			read-write
		STATUS			mandatory
		DESCRIPTION		"OBSOLETE. The desired state of the radio. The radio only transmits 
						 when in the up state i.e. the transmitter is muted when 
						 in the down, testing state or firmware upgrade state." 
		DEFVAL 			{ up }
		::=  {  apRadio  3  }

	radioOperStatus	OBJECT-TYPE	
		SYNTAX			INTEGER  { up ( 1 ) , down ( 2 ) , testing ( 3 ) } 
		ACCESS			read-only
		STATUS			mandatory
		DESCRIPTION		"The current operational state of the interface. Testing 
						 indicates that no operational packets can be passed. Testing
						 also indicates that a firmware upgrade may be in progress"
		::=  {  apRadio  4  }

	radioLastChanged	OBJECT-TYPE	
		SYNTAX			TimeTicks
		ACCESS			read-only
		STATUS			mandatory
		DESCRIPTION		"The value of sysUpTime at the time the radio entered 
						 its current operational state. If the current state was 
						 entered prior to the last re-initialization of the local 
						 network management subsystem, then this object contains 
						 a zero value."
		::=  {  apRadio  5  }

	radioRSL	OBJECT-TYPE	
		SYNTAX			INTEGER
		ACCESS			read-only
		STATUS			mandatory
		DESCRIPTION		"The Received Signal Level indicates the power of the receive level in dBm. The number is divided by 10. e.g. -432 is actually -43.2dBm."
		::=  {  apRadio  6  }

	radioTxGain	OBJECT-TYPE	
		SYNTAX			INTEGER  ( 20 .. 40  ) 
		ACCESS			read-write
		STATUS			mandatory
		DESCRIPTION		"The gain of the radio in the transmit chain. Indicates 
						 the gain in dB."
		DEFVAL 			{ 30 }
		::=  {  apRadio  7  }

	radioRxGain	OBJECT-TYPE	
		SYNTAX			INTEGER  ( 20 .. 40  ) 
		ACCESS			read-write
		STATUS			mandatory
		DESCRIPTION		"The gain of the radio in the receive chain. Indicates 
						 the gain in dB. "
		DEFVAL 			{ 30 }
		::=  {  apRadio  8  }

	radioVoltageSupply	OBJECT-TYPE	
		SYNTAX			INTEGER
		ACCESS			read-only
		STATUS			mandatory
		DESCRIPTION		"The voltage level of the supply to the radio."
		::=  {  apRadio  9  }

	radioReset	OBJECT-TYPE	
		SYNTAX			INTEGER ( 0 .. 1  )
		ACCESS			read-write
		STATUS			mandatory
		DESCRIPTION		"Writing 1 to this object causes the radio to be reset. 
						 All other values are not recognized. This variable 
						 always reads back as 0. radioOperStatus should be polled 
						 by the user after this object is written to, to verify 
						 that the radio card has been reset."
		::=  {  apRadio  10  }

	transmitPowerDbm	OBJECT-TYPE	
		SYNTAX			INTEGER 
		ACCESS			read-write
		STATUS			mandatory
		DESCRIPTION		"This defines the transmit level of the radio.
                                                 If ATPC is enabled, you can't change the transmit power.

                                                 The power you see is divided by 10. e.g. A display
                                                 of 133 is actually 13.3 dBm.
                                                 
                                                 If the radio is operational and not muted, it is the 
                                                 current transmitting power.
                                                 
                                                 If the radio is operational and muted, it is the 
                                                 programmed transmitting power, and will transmit at 
                                                 this level when the radio is un-muted.
                                                 						 
                                                 If the radio is not operational it is the programmed 
                                                 transmitting power, and will transmit at this level 
                                                 when the radio is operational and not muted.
						 
                                                 If the radio does not have transmit calibration tables 
                                                 programmed into its EEPROM, this transmit power level 
                                                 cannot be used as it is not possible to accurately 
                                                 calculate the actual transmit level. In this case this 
                                                 object will return -99." 
		DEFVAL  		{ 0 }
		::=  {  apRadio  11  }
		
	programmedAntennaDiameter	OBJECT-TYPE	
		SYNTAX			INTEGER  { antenna12 ( 1 ) , antenna24 ( 2 ) , antenna36 ( 3 ) }
		ACCESS			read-write
		STATUS			mandatory
		DESCRIPTION		"This defines the diameter of the antenna used by the system represented in inches."
		DEFVAL  		{ 0 }
		::=  {  apRadio  12  }
		

	powerOption	                OBJECT-TYPE	
		SYNTAX			INTEGER  { normal ( 1 ) , highPower ( 2 ) }
		ACCESS			read-write
		STATUS			mandatory
		DESCRIPTION		"This indicates the power option of the radio: normal or high power."
		DEFVAL  		{ 0 }
		::=  {  apRadio  13  }

        atpcStatus     OBJECT-TYPE	
		SYNTAX			INTEGER  { disabled ( 1 ) , enabled ( 2 ) } 
		ACCESS			read-write
		STATUS			mandatory
		DESCRIPTION		"Indicates whether Automatic Transmit Power Control (ATPC) is enabled."
		DEFVAL			{ disabled }
		::=  {  apRadio  14 }


	atpcRslThreshold	        OBJECT-TYPE  	
		SYNTAX			INTEGER ( -800 .. -300 )  
		ACCESS			read-only
		STATUS			mandatory
		DESCRIPTION		"This defines the atpc rsl threshold."
		DEFVAL  		{ -530 }
		::=  {  apRadio  15  }

	atpcFadeStep	OBJECT-TYPE	
		SYNTAX			INTEGER ( 1 .. 50 ) 
		ACCESS			read-only
		STATUS			mandatory
		DESCRIPTION		"This defines atpc fade step size."
		DEFVAL  		{ 50 }
		::=  {  apRadio  16  }

	atpcRslHysteresis		OBJECT-TYPE 	
		SYNTAX			INTEGER ( 1 .. 15 ) 
		ACCESS			read-only
		STATUS			mandatory
		DESCRIPTION		"This defines the rsl hysteresis. "
		DEFVAL  		{ 5 }
		::=  {  apRadio  17  }

	atpcMaximumChange		OBJECT-TYPE 	
		SYNTAX			INTEGER ( 1 .. 50 )
		ACCESS			read-only
		STATUS			mandatory
		DESCRIPTION		"This defines the maximum allowed atpc change."
		DEFVAL  		{ 200 }
		::=  {  apRadio  18  }
		
	redundancyStatus			OBJECT-TYPE 	
		SYNTAX			INTEGER  { disabled ( 1 ) , enabled ( 2 ) } 
		ACCESS			read-write
		STATUS			mandatory
		DESCRIPTION			"Indicates whether radio redundancy is enabled or not.
						It can be turned on only when there is valid primary and 
						secondary serial number in flash"
		DEFVAL  		{ disabled }
		::=  {  apRadio  19  }	

	redundancyMode	OBJECT-TYPE 	
		SYNTAX			INTEGER  { dcdp ( 1 ) , scsp ( 2 ) }
		ACCESS			read-write
		STATUS			mandatory
		DESCRIPTION			"Radio installtion type 
						dcdp - different channel or differenr polarzation,
						scsp - same channel and same polarization"
		DEFVAL  		{ 1 }
		::=  {  apRadio  20  }

	redundancyCurrentSerialNum		OBJECT-TYPE	
		SYNTAX			DisplayString
		ACCESS			read-only
		STATUS			mandatory
		DESCRIPTION		"Display active radio's serial number" 
		::=  {  apRadio  21  }

	redundancySecondarySerialNum	OBJECT-TYPE	
		SYNTAX			DisplayString
		ACCESS			read-write
		STATUS			mandatory
		DESCRIPTION		"Display the secondary radio's serial number in flash" 
		::=  {  apRadio  22  }

	redundancyPrimarySerialNum		OBJECT-TYPE	
		SYNTAX			DisplayString
		ACCESS			read-write
		STATUS			mandatory
		DESCRIPTION		"Display the primary radio's serial number in flash" 
		::=  {  apRadio  23  }
	
	radioRSLUnsignedInt	OBJECT-TYPE	
		SYNTAX			INTEGER
		ACCESS			read-only
		STATUS			mandatory
		DESCRIPTION		"The Received Signal Level indicates the power of the receive level in dBm. The number is divided by 10. e.g. -432 is actually -43.2dBm.
						Object provided mainly to accomodate plotting of negative RSL values which is not supported in some EMS (Ex: CastleRock). 
						Please use 'radioRSL' object if your EMS supports plotting of -ve integer."
		::=  {  apRadio  24  }

	radioTemperature	OBJECT-TYPE	
		SYNTAX			INTEGER
		ACCESS			read-only
		STATUS			mandatory
		DESCRIPTION		"The Radio temperature in degree Centigrade. The actual temperature is got by dividing the number by 10. e.g. -432 is actually -43.2 degree centigrade."
						
		::=  {  apRadio  25  }

		
		
	date	OBJECT-TYPE	
		SYNTAX			DisplayString
		ACCESS			read-only
		STATUS			mandatory
		DESCRIPTION		"A string in the format as follows:		
                                                XX/YY/ZZ 
                                                Where XX = day of month (range 01 to  31)	 
                                                YY = month of year(range 01 to 12)	 
                                                ZZ = year (range 01 - 99)"
		::=  {  apCalendar  1  }

	time	OBJECT-TYPE	
		SYNTAX			DisplayString
		ACCESS			read-only
		STATUS			mandatory
		DESCRIPTION		"A string in the format as follows:
                                                 aa:bb:cc:dd
                                                 Where aa = hour of day ( range 00 to 23 )	 
                                                       bb = minute of hour ( range 00 to 59 )	 
                                                       cc = second of minute( range 00 to 59 )	 
                                                       dd = hundredths of second (range 00 to 99)"
		::=  {  apCalendar  2  }

--
-- LED FOLDER
--
	
        powerLed	OBJECT-TYPE	
		SYNTAX			INTEGER  { off ( 1 ) , on ( 2 ) } 
		ACCESS			read-only
		STATUS			mandatory
		DESCRIPTION		"Indicates the status of the power led."
		::=  {  apLeds  1  }

	linkStatusOrSpeedLed	OBJECT-TYPE	
		SYNTAX			INTEGER  { off ( 1 ) , on ( 2 ), fastBlink1000BaseT ( 3 ), 
                                                   solidOn100BaseT ( 4 ), slowBlink10BaseT ( 5),
                                                   fastBlink1000BaseSX (6) } 
		ACCESS			read-only
		STATUS			mandatory
		DESCRIPTION		"Indicates the status of Ethernet link for release 3 or earlier hardware platforms.
                                         Indicates the speed of the Ethernet link for release 4 or later platforms.
                                         The values fastBlink1000BaseT, solidOn100BaseT, and slowBlink10BaseT are applicable only to release 4 hardware platforms."
		::=  {  apLeds  2  }

	trafficLed	OBJECT-TYPE	
		SYNTAX			INTEGER  { off ( 1 ) , on ( 2 ) } 
		ACCESS			read-only
		STATUS			mandatory
		DESCRIPTION		"Indicates the presence of Ethernet traffic. It represents transmit and receive traffic on the ethernet interface."
		::=  {  apLeds  3  }

	duplexModeOrLinkTypeLed	OBJECT-TYPE	
		SYNTAX			INTEGER  { off ( 1 ) , on ( 2 ), copperInterfaceLedOff ( 3 ),      
                                                   opticalInterfaceOpticalTransmitterOffLedSlowBlink( 4 ),
                                                   opticalInterfaceLedOn (5) } 
		ACCESS			read-only
		STATUS			mandatory
		DESCRIPTION		"For release 3 or earlier hardward platforms, 
                                         indicates whether the Ethernet link is working in full duplex mode, 1 means 
                                         off and 2 means on. The values of 3, 4, and 5 do not apply. 
                                         For release 4 hardware platforms or later, off (1) and on (2) does not apply.
                                         In this case, 3 means copper interface led is off, 4 means optical interface 
                                         optical transmitter Off led is slowly blinking, and 5 means optical
                                         interface led is on. "
		::=  {  apLeds  4  }

	rfOnLed	OBJECT-TYPE	
		SYNTAX			INTEGER  { off ( 1 ) , on ( 2 ) } 
		ACCESS			read-only
		STATUS			mandatory
		DESCRIPTION		"Indicates whether the radio is transmitting or not"
		::=  {  apLeds  5  }

	modemSyncLed	OBJECT-TYPE	
		SYNTAX			INTEGER  { off ( 1 ) , on ( 2 ) } 
		ACCESS			read-only
		STATUS			mandatory
		DESCRIPTION		"Indicates that the modem is synchronized to another AirPair"
		::=  {  apLeds  6  }

	systemTroubleLed	OBJECT-TYPE	
		SYNTAX			INTEGER  { off ( 1 ) , on ( 2 ) } 
		ACCESS			read-only
		STATUS			mandatory
		DESCRIPTION		"Indicates the status of the system trouble LED. 
                                         The Trouble LED will be on if on of the following 
                                         conditions exist:						 
                                                 i)Communication with the radio has failed.
                                                 ii) The PLDRO has lost lock on the Radio
                                                 iii) The synthesizers are not locked on the IF Card.
                                                 						 
                                                 The alarm group should be checked"
		::=  {  apLeds  7  }

	multiSegmentLed	OBJECT-TYPE	
		SYNTAX			INTEGER  { off ( 1 ) , on ( 2 )  } 
		ACCESS			read-only
		STATUS			mandatory
		DESCRIPTION		"NOT IMPLEMENTED
		
						 Indicates the value loaded to the multi-segment LED. 
					 	 Used for antenna alignment. Value is read as a 
					 	 percentage. "
		::=  {  apLeds  8  }
		
	
	fanAlarmLed	OBJECT-TYPE	
		SYNTAX			INTEGER  { off ( 1 ) , on ( 2 )  } 
		ACCESS			read-only
		STATUS			mandatory
		DESCRIPTION	    "Indicates whether the fan alarm led is off or not.If any one of the fan stops working, this led will be turned on.
						This alarm is applicable for split IDU/ODU modems only."
					 
		::=  {  apLeds  9  }

--
-- ALARM FOLDER
--
	
        clearAlarmCounters	OBJECT-TYPE	
		SYNTAX			INTEGER  { nicCounters ( 1 ) , modemCounters ( 2 ) , radioCounters ( 3 ) , ifCounters ( 4 ) , allCounters ( 5 ), otherCounters (6) } 
		ACCESS			write-only
		STATUS			mandatory
		DESCRIPTION		"Clears the alarm counters for the specified group"
		::=  {  apSystemAlarms  1  }	
    
        networkInterfaceCardAlarms	OBJECT IDENTIFIER
		::=  {  apSystemAlarms  2  } 

        modemAlarms	OBJECT IDENTIFIER
		::=  {  apSystemAlarms  3  } 

        radioAlarms	OBJECT IDENTIFIER
		::=  {  apSystemAlarms  4  } 
                                                          
        intermediateFrequencyCardAlarms	OBJECT IDENTIFIER
		::=  {  apSystemAlarms  5  } 

        otherAlarms	OBJECT IDENTIFIER
		::=  {  apSystemAlarms  6  } 

        frequencyFileAlarms OBJECT IDENTIFIER
		::=  {  apSystemAlarms  7  } 


--
-- FREQUENCY FILE ALARMS
--
	frequencyFileInvalid	OBJECT-TYPE	
		SYNTAX			INTEGER  { off ( 1 ) , on ( 2 ) } 
		ACCESS			read-only
		STATUS			mandatory
        	DESCRIPTION		"Executing frequency file is valid or not"
		::=  {  frequencyFileAlarms 1  }

	frequencyFileInvalidCount	OBJECT-TYPE	
		SYNTAX			Counter
		ACCESS			read-only
		STATUS			mandatory
        	DESCRIPTION		"Indicates the time (in secs) since this alarm exist."
		::=  {  frequencyFileAlarms 2  }

	optionalParaNotEntered	OBJECT-TYPE	
		SYNTAX			INTEGER  { off ( 1 ) , on ( 2 ) } 
		ACCESS			read-only
		STATUS			mandatory
        	DESCRIPTION		"Executing frequency file doesn't contain all the  parameters needed for optimum performance of the system."
		::=  {  frequencyFileAlarms 3  }

	optionalParaNotEnteredCount	OBJECT-TYPE	
		SYNTAX			Counter
		ACCESS			read-only
		STATUS			mandatory
        	DESCRIPTION		"Indicates the time (in secs) since this alarm exist."
		::=  {  frequencyFileAlarms 4  }

	progRadioBandNotFound	OBJECT-TYPE	
		SYNTAX			INTEGER  { off ( 1 ) , on ( 2 ) } 
		ACCESS			read-only
		STATUS			mandatory
        	DESCRIPTION		"Executing frequency file doesn't contain radio band info that is programmed in the system."
		::=  {  frequencyFileAlarms 5  }

	progRadioBandNotFoundCount	OBJECT-TYPE	
		SYNTAX			Counter
		ACCESS			read-only
		STATUS			mandatory
        	DESCRIPTION		"Indicates the time (in secs) since this alarm exist."
		::=  {  frequencyFileAlarms 6 }


    
--
-- NETWORK INTERFACE ALARMS 
--	
        
	explicitAuthenticationFailure	OBJECT-TYPE	
		SYNTAX			INTEGER  { off ( 1 ) , on ( 2 ) } 
		ACCESS			read-only
		STATUS			mandatory
        	DESCRIPTION		"Authentication of the peer AirPair node has failed. The severity is critical, the probable cause is an incorrect authentication configuration on AirPair faulty cable between the modem and radio, and recommended course of action is to check both ends of the link."
		::=  {  networkInterfaceCardAlarms  1  }

	explicitAuthenticationFailureCount	OBJECT-TYPE	
		SYNTAX			Counter
		ACCESS			read-only
		STATUS			mandatory
		DESCRIPTION		"Indicates the number of times explicit authentication has failed."
		::=  {  networkInterfaceCardAlarms  2  }

	autoNegotiationDuplexMismatch	OBJECT-TYPE	
		SYNTAX			INTEGER  { off ( 1 ) , on ( 2 ) } 
		ACCESS			read-only
		STATUS			mandatory
        	DESCRIPTION		"NOT USED. DEPRECATED.  The AirPair ethernet interface has a mismatch in duplex. The severity is major, the probable cause is an incorrect configuration of the switch or router connected to AirPair, or the AirPair autonegotion settings. The recommended course of action is to check the connection."
		::=  {  networkInterfaceCardAlarms  3  }

	autoNegotiationDuplexMismatchCount	OBJECT-TYPE	
		SYNTAX			Counter
		ACCESS			read-only
		STATUS			mandatory
		DESCRIPTION		"NOT USED. DEPRECATED. Indicates the number of times auto negotiation has failed."
		::=  {  networkInterfaceCardAlarms  4  }
                
	droppedEnetFramesThresholdExceeded	OBJECT-TYPE	
		SYNTAX			INTEGER  { off ( 1 ) , on ( 2 ) } 
		ACCESS			read-only
		STATUS			mandatory
		DESCRIPTION		"The threshold for number of frames dropped has been exceeded. The threshold and the number of seconds that it must exceed this threshold are programmed by the user."
		::=  {  networkInterfaceCardAlarms  5  }
                
	droppedEnetFramesThresholdParameters	OBJECT-TYPE	
		SYNTAX			DisplayString  ( SIZE ( 0 .. 24  ) ) 
		ACCESS			read-write
		STATUS			mandatory
		DESCRIPTION		"A read-write string: The threshold, in percent, and the number of seconds that it must exceed this threshold are programmed by the user. An example of the format of the string is as follows: '70 10'. The first parameter is the percentage of frames that are dropped, the second is the time in seconds that the threshold must be exceeded. The single quote marks i.e. ' ' are not used in the command."
		::=  {  networkInterfaceCardAlarms  6  }

	droppedEnetFramesThresholdCount	OBJECT-TYPE	
		SYNTAX			Counter
		ACCESS			read-only
		STATUS			mandatory
		DESCRIPTION		"Indicates the approximate time, in seconds, that this alarm has been in the active state"
		::=  {  networkInterfaceCardAlarms  7  }
	
        bandwidthUtilizationThresholdExceeded	OBJECT-TYPE	
		SYNTAX			INTEGER  { off ( 1 ) , on ( 2 ) } 
		ACCESS			read-only
		STATUS			mandatory
		DESCRIPTION		"The threshold for the percentage of available bandwidth has been exceeded. The threshold and the number of seconds that it must exceed this threshold are programmed by the user."
		::=  {  networkInterfaceCardAlarms  8  }
                
	bandwidthUtilizationThresholdParameters	OBJECT-TYPE	
		SYNTAX			DisplayString  ( SIZE ( 0 .. 24  ) ) 
		ACCESS			read-write
		STATUS			mandatory
		DESCRIPTION		"A read-write string: The percentage of available bandwidth threshold and the number of seconds that it must exceed this threshold are programmed by the user. An example of the format of the string is as follows: '70 10'. The first parameter is the threshold point in percent, the number of seconds that the threshold must be exceeded. The single quote marks i.e. ' ' are not used in the command."
		::=  {  networkInterfaceCardAlarms  9  }

	bandwidthUtilizationThresholdCount	OBJECT-TYPE	
		SYNTAX			Counter
		ACCESS			read-only
		STATUS			mandatory
		DESCRIPTION		"Indicates the approximate time, in seconds, that this alarm has been in the active state"
		::=  {  networkInterfaceCardAlarms  10  }

        rlsMismatch	OBJECT-TYPE	
		SYNTAX			INTEGER  { off ( 1 ) , on ( 2 ) } 
		ACCESS			read-only
		STATUS			mandatory
		DESCRIPTION		"RLS configurations on the pair of systems are mismatched."
		::=  {  networkInterfaceCardAlarms  11  }
 
	rlsMismatchCount	OBJECT-TYPE	
		SYNTAX			Counter
		ACCESS			read-only
		STATUS			mandatory
		DESCRIPTION		"Indicates the approximate time, in seconds, that this alarm has been in the active state"
		::=  {  networkInterfaceCardAlarms  12  }


        rLSShutdownActivated	OBJECT-TYPE	
		SYNTAX			INTEGER  { off ( 1 ) , on ( 2 ) } 
		ACCESS			read-only
		STATUS			mandatory
		DESCRIPTION		"RLS shutdown is activated."
		::=  {  networkInterfaceCardAlarms  13  }
 
	rLSShutdownActivatedCount	OBJECT-TYPE	
		SYNTAX			Counter
		ACCESS			read-only
		STATUS			mandatory
		DESCRIPTION		"Indicates the approximate time, in seconds, that this alarm has been in the active state"
		::=  {  networkInterfaceCardAlarms  14  }
                
    ethernetLinkDown  OBJECT-TYPE	
		SYNTAX			INTEGER  { off ( 1 ) , on ( 2 ) } 
		ACCESS			read-only
		STATUS			mandatory
		DESCRIPTION		"Indicates whether the Ethernet link is down or not. The severity is major, the probable cause is an incorrect configuration of the switch or router connected to AirPair. The recommended course of action is to check the connection."
		::=  {  networkInterfaceCardAlarms  15  }
 
	ethernetLinkDownActivatedCount	OBJECT-TYPE	
		SYNTAX			Counter
		ACCESS			read-only
		STATUS			mandatory
		DESCRIPTION		"Indicates the approximate time, in seconds, that this alarm has been in the active state"
		::=  {  networkInterfaceCardAlarms  16  }
      

--
-- MODEM ALARMS
--

	modemLossOfSignalLockFromDemodulator	OBJECT-TYPE	
		SYNTAX			INTEGER  { off ( 1 ) , on ( 2 ) } 
		ACCESS			read-only
		STATUS			mandatory
        	DESCRIPTION		"Loss of signal lock from the demodulator. The severity is critical, the probable cause is lost synchronization with the far end, and recommended course of action is to check the operational state of both ends of the link."
		::=  {  modemAlarms  1  }

	modemLossOfSignalLockFromDemodulatorCount	OBJECT-TYPE	
		SYNTAX			Counter
		ACCESS			read-only
		STATUS			mandatory
		DESCRIPTION		"Indicates the approximate number of seconds that this alarm has been active."
		::=  {  modemAlarms  2  }

	modemUncorrectedBerThresholdExceeded	OBJECT-TYPE	
		SYNTAX			INTEGER  { off ( 1 ) , on ( 2 ) } 
		ACCESS			read-only
		STATUS			mandatory
        	DESCRIPTION		"The uncorrected BER threshold has been exceeded. The severity is major, the probable cause is physical interference in the air link or misalignment of the radios or severe weather conditions, and recommended course of action is to check the line of site between the air pair nodes."
		::=  {  modemAlarms  3  }

	modemUncorrectedBerThresholdParameters	OBJECT-TYPE	
		SYNTAX			DisplayString  ( SIZE ( 0 .. 24  ) ) 
		ACCESS			read-write
		STATUS			mandatory
		DESCRIPTION		"A read-write string: The threshold, in exponential format, and the number of seconds in exponential format that the uncorrected BER must exceed this threshold are programmed by the user. An example of the format of the string is as follows: '1.2e-4 1.1e-1'. The first parameter is uncorrected BER threshold point, the second is the time in seconds that the threshold must be exceeded. In this example the threshold is set to 1.2 bits every 1000 and the time is set to 0.11 of a second. The single quote marks i.e. ' ' are not used in the command. Uncorrected BER is the bit error rate as measured before frame error correction."
		::=  {  modemAlarms  4  }
	
        modemUncorrectedBerThresholdExceededCount	OBJECT-TYPE	
		SYNTAX			Counter
		ACCESS			read-only
		STATUS			mandatory
		DESCRIPTION		"Indicates the approximate number of seconds that this alarm has been active."
		::=  {  modemAlarms  5  }

	modemModulatorPllLockFailure	OBJECT-TYPE	
		SYNTAX			INTEGER  { off ( 1 ) , on ( 2 ) } 
		ACCESS			read-only
		STATUS			mandatory
        	DESCRIPTION		"Modulator PLL failure. The severity is critical, the probable cause a faulty modem card within AirPair, and recommended course of action is to replace the modem unit."
		::=  {  modemAlarms  6  }

	modemModulatorPllLockFailureCount	OBJECT-TYPE	
		SYNTAX			Counter
		ACCESS			read-only
		STATUS			mandatory
		DESCRIPTION		"Indicates the approximate number of seconds that this alarm has been active."
		::=  {  modemAlarms  7  }

	modemModulatorLossOfSyncBytes	OBJECT-TYPE	
		SYNTAX			INTEGER  { off ( 1 ) , on ( 2 ) } 
		ACCESS			read-only
		STATUS			mandatory
        	DESCRIPTION		"Loss of sync bytes at the input of the modulator. The severity is critical, the probable cause is physical interference in the air link, and recommended course of action is to check the line of site between the air pair nodes."
		::=  {  modemAlarms  8  }  
		
	modemModulatorLossOfSyncBytesCount	OBJECT-TYPE	
		SYNTAX			Counter
		ACCESS			read-only
		STATUS			mandatory
		DESCRIPTION		"Indicates the approximate number of seconds that this alarm has been active."
		::=  {  modemAlarms  9  }     
		
	modemModulatorInputFifoError	OBJECT-TYPE	
		SYNTAX			INTEGER  { off ( 1 ) , on ( 2 ) } 
		ACCESS			read-only
		STATUS			mandatory
        	DESCRIPTION		"Overrun or underrun of the FIFO contained inside the modulator. The severity is critical, the probable cause is electrical interference, and recommended course of action is to reset the modem unit, or relpace the modem unit."
		::=  {  modemAlarms  10  }

	modemModulatorInputFifoErrorCount	OBJECT-TYPE	
		SYNTAX			Counter
		ACCESS			read-only
		STATUS			mandatory
		DESCRIPTION		"Indicates the approximate number of seconds that this alarm has been active."
		::=  {  modemAlarms  11  }

	modemModulatorInputDataError	OBJECT-TYPE	
		SYNTAX			INTEGER  { off ( 1 ) , on ( 2 ) } 
		ACCESS			read-only
		STATUS			mandatory
        	DESCRIPTION		"All ones or all zeroes at the input of the modulator. The severity is critical, the probable cause is electrical interference, and recommended course of action is to reset the modem unit, or replace the modem unit"
		::=  {  modemAlarms  12  }

	modemModulatorInputDataErrorCount	OBJECT-TYPE	
		SYNTAX			Counter
		ACCESS			read-only
		STATUS			mandatory
		DESCRIPTION		"Indicates the approximate number of seconds that this alarm has been active."
		::=  {  modemAlarms  13  }


	modemSnrBelowThreshold	OBJECT-TYPE	
		SYNTAX			INTEGER  { off ( 1 ) , on ( 2 ) } 
		ACCESS			read-only
		STATUS			mandatory
        	DESCRIPTION		"The demodulator SNR performance worse than programmed levels. The severity is major, the probable cause is physical interference in the air link path or misalignment of the radios or severe weather conditions, and recommended course of action is to check the line of site between the air pair nodes."
		::=  {  modemAlarms  14  }

	modemSnrAlarmThresholdParameter	OBJECT-TYPE	
		SYNTAX			INTEGER
		ACCESS			read-write
		STATUS			mandatory
		DESCRIPTION		"The demodulator SNR threshold level which triggers the modemSnrBelowThreshold alarm. A number in the range 10 to 25. The proper setting depends on the operational parameters of the system e.g. QPSK, QAM16, QAM32 and the expected link budget."
		::=  {  modemAlarms  15  }

	modemSnrBelowThresholdCount	OBJECT-TYPE	
		SYNTAX			Counter 
		ACCESS			read-only
		STATUS			mandatory
		DESCRIPTION		"Indicates the approximate number of seconds that this alarm has been active."
		::=  {  modemAlarms  16  }

	modemCardMismatchedHardwareFirmware	OBJECT-TYPE	
		SYNTAX			INTEGER  { off ( 1 ) , on ( 2 ) } 
		ACCESS			read-only
		STATUS			mandatory
        	DESCRIPTION		"The modem card has firmware that is incompatible with the hardware. The card will not operate properly."
		::=  {  modemAlarms  17  }

	modemCardMismatchedHardwareFirmwareCount OBJECT-TYPE	
		SYNTAX			Counter 
		ACCESS			read-only
		STATUS			mandatory
		DESCRIPTION		"Indicates the approximate number of seconds that this alarm has been active."
		::=  {  modemAlarms  18  }
                
    modemAAMConfigMismatch		OBJECT-TYPE	
		SYNTAX			INTEGER  { off ( 1 ) , on ( 2 ) }  
		ACCESS			read-only
		STATUS			mandatory
		DESCRIPTION		"In the near end Automatic Adaptive Modulation(AAM) feature set to on and in peer it is set to off"
		::=  {  modemAlarms  19  }

	modemAAMConfigMismatchCount	OBJECT-TYPE	
		SYNTAX			Counter 
		ACCESS			read-only
		STATUS			mandatory
		DESCRIPTION		"Indicates the approximate number of seconds AAMConfigMismatch alarm has been active."
		::=  {  modemAlarms  20  }

	modemAAMQpskActive		OBJECT-TYPE	
		SYNTAX			INTEGER  { off ( 1 ) , on ( 2 ) }  
		ACCESS			read-only
		STATUS			mandatory
		DESCRIPTION		"Indicates aam is active and system running on QPSK modulation"
		::=  {  modemAlarms  21  }

	modemAAMQpskActiveCount	OBJECT-TYPE	
		SYNTAX			Counter
		ACCESS			read-only
		STATUS			mandatory
		DESCRIPTION		"Indicates the approximate number of seconds AAMQpskActive alarm has been active."
		::=  {  modemAlarms  22  }
            

--
-- RADIO ALARMS
--
	
        radioPLDROLostLock	OBJECT-TYPE	
		SYNTAX			INTEGER  { off ( 1 ) , on ( 2 ) } 
		ACCESS			read-only
		STATUS			mandatory
        	DESCRIPTION		"The PLDRO/LO has lost lock on the radio. The severity is critical, the probable cause a faulty radio unit within AirPair, and recommended course of action is to replace the radio unit."
		::=  {  radioAlarms  1  }

	radioPLDROLostLockCount	OBJECT-TYPE	
		SYNTAX			Counter
		ACCESS			read-only
		STATUS			mandatory
		DESCRIPTION		"Indicates the approximate number of seconds that this alarm has been active."
		::=  {  radioAlarms  2  }


	radioLostCommunication	OBJECT-TYPE	
		SYNTAX			INTEGER  { off ( 1 ) , on ( 2 ) } 
		ACCESS			read-only
		STATUS			mandatory
       	        DESCRIPTION		"RS232 communication lost between AIRPAIR and the radio. The severity is critical, the probable cause is a faulty cable between the modem and radio, and recommended course of action is to check the connection."
		
                ::=  {  radioAlarms  3  }
     
     
	radioLostCommunicationCount	OBJECT-TYPE	
		SYNTAX			Counter
		ACCESS			read-only
		STATUS			mandatory
		DESCRIPTION		"Indicates the approximate number of seconds that this alarm has been active."
		::=  {  radioAlarms  4  }


	radioMismatch	OBJECT-TYPE	
		SYNTAX			INTEGER  { off ( 1 ) , on ( 2 ) } 
		ACCESS			read-only
		STATUS			mandatory
        	DESCRIPTION		"The radio connected to the AIRPAIR modem does not match the frequency programmed into the modem unit. The severity is major, the probable cause is an incorrectly programmed modem or an incorrect radio type connected to the modem, and recommended course of action is to check the modem frequency settings and radio hardware version number or serial number."
		::=  {  radioAlarms  5  }

	radioMismatchCount	OBJECT-TYPE	
		SYNTAX			Counter
		ACCESS			read-only
		STATUS			mandatory
		DESCRIPTION		"Indicates the approximate number of seconds that this alarm has been active."
		::=  {  radioAlarms  6  }
 
 	radioPowerAmp	OBJECT-TYPE	
		SYNTAX			INTEGER  { off ( 1 ) , on ( 2 ) } 
		ACCESS			read-only
		STATUS			mandatory
        	DESCRIPTION		"The power amplifier on the radio is not operating within normal operating specifications. The severity is critical, the probable cause a faulty radio unit within AirPair, and recommended course of action is to replace the radio unit."
		::=  {  radioAlarms  7  }

	radioPowerAmpCount	OBJECT-TYPE	
		SYNTAX			Counter
		ACCESS			read-only
		STATUS			mandatory
		DESCRIPTION		"Indicates the approximate number of seconds that this alarm has been active."
		::=  {  radioAlarms  8  }
 

	radioRslBelowThreshold	OBJECT-TYPE	
		SYNTAX			INTEGER  { off ( 1 ) , on ( 2 ) } 
		ACCESS			read-only
		STATUS			mandatory
        	DESCRIPTION		"The minimum radio receive signal level threshold has been crossed. The severity is major, the probable cause is physical interference in the air link path or misalignment of the radios or severe weather conditions, and recommended course of action is to check the line of site between the air pair nodes."
		::=  {  radioAlarms  9  }

	radioRslBelowThresholdParameters	OBJECT-TYPE	
		SYNTAX			DisplayString  ( SIZE ( 0 .. 24  ) ) 
		ACCESS			read-write
		STATUS			mandatory
		DESCRIPTION		"A read-write string: The threshold in dBm  and the number of seconds threshold are programmed by the user. An example of the format of the string is as follows: '-75 10'. The first parameter power level in dBm, the second is the time in seconds that the threshold must be exceeded. In this example the threshold -75 dBm and the time is set to 10 seconds. The single quote marks i.e. ' ' are not used in the command."
		::=  {  radioAlarms  10  }

	radioRslBelowThresholdCount	OBJECT-TYPE	
		SYNTAX			Counter 
		ACCESS			read-only
		STATUS			mandatory
		DESCRIPTION		"Indicates the approximate number of seconds that this alarm has been active."
		::=  {  radioAlarms  11  }
                
	radioHighPowerOptionM1	        OBJECT-TYPE	
		SYNTAX			INTEGER  { off ( 1 ) , on ( 2 ) }                 
		ACCESS			read-only
		STATUS			mandatory
		DESCRIPTION		"This applies to High Power Radios only. Indicates Power Amp Alarm (M1)."
		::=  {  radioAlarms  12  }

	radioHighPowerOptionM1Count	OBJECT-TYPE	
		SYNTAX			Counter  
		ACCESS			read-only
		STATUS			mandatory
		DESCRIPTION		"This applies to High Power Radios only. Indicates the number of seconds that Power Amp Alarm (M1) has been active."
		::=  {  radioAlarms  13  }

	radioHighPowerOptionM2	        OBJECT-TYPE	
       	        SYNTAX			INTEGER  { off ( 1 ) , on ( 2 ) }
 		ACCESS			read-only
		STATUS			mandatory
		DESCRIPTION		"This applies to High Power Radios only. Indicates Power Amp Alarm (M2)."
		::=  {  radioAlarms  14  }

	radioHighPowerOptionM2Count	OBJECT-TYPE	
		SYNTAX			Counter  
		ACCESS			read-only
		STATUS			mandatory
		DESCRIPTION		"This applies to High Power Radios only. Indicates the number of seconds that Power Amp Alarm (M2) has been active."
		::=  {  radioAlarms  15  }

	radioHighPowerTxDetector	OBJECT-TYPE	
       	        SYNTAX			INTEGER  { off ( 1 ) , on ( 2 ) }
       		ACCESS			read-only
		STATUS			mandatory
		DESCRIPTION		"This applies to High Power Radios only. Indicates minimum power threshold has not been surpassed."
		::=  {  radioAlarms  16  }

	radioHighPowerTxDetectorCount	OBJECT-TYPE	
		SYNTAX			Counter  
		ACCESS			read-only
		STATUS			mandatory
		DESCRIPTION		"This applies to High Power Radios only. Indicates the number of seconds that radioHighPowerTxDetector alarm has been active."
		::=  {  radioAlarms  17  }

        atpcConfigMismatch	        OBJECT-TYPE	
		SYNTAX			INTEGER  { off ( 1 ) , on ( 2 ) } 
		ACCESS			read-only
		STATUS			mandatory
        	DESCRIPTION		"The pair of the systems don't have same ATPC configurations. On
                                         one side ATPC is enabled, but on the other side ATPC is not 
                                         enabled. "
		::=  {  radioAlarms 18  }


    atpcConfigMismatchCount	        OBJECT-TYPE	
		SYNTAX			Counter  
		ACCESS			read-only
		STATUS			mandatory
		DESCRIPTION		"Indicates how long atpc configurations are mismatched on the
                                         two systems."
		::=  {  radioAlarms  19  }
		
	redundancySecondaryActive	        OBJECT-TYPE	
		SYNTAX			INTEGER  { off ( 1 ) , on ( 2 ) } 
		ACCESS			read-only
		STATUS			mandatory
        	DESCRIPTION		"Radio redundancy on, secondary radio is active "
		::=  {  radioAlarms 20  }


    redundancySecondaryActiveCount	        OBJECT-TYPE	
		SYNTAX			Counter  
		ACCESS			read-only
		STATUS			mandatory
		DESCRIPTION		"Indicates how long secondary radio is active."
		::=  {  radioAlarms  21  }

	redundancySerialNumMismatch	        OBJECT-TYPE	
		SYNTAX			INTEGER  { off ( 1 ) , on ( 2 ) } 
		ACCESS			read-only
		STATUS			mandatory
        	DESCRIPTION		"Radio serial number programmed in flash and radio doesn't match "
		::=  {  radioAlarms 22  }


       redundancySerialNumMismatchCount	        OBJECT-TYPE	
		SYNTAX			Counter  
		ACCESS			read-only
		STATUS			mandatory
		DESCRIPTION		"Indicates how long redundancyserailNumMismatch alarm is active."
		::=  {  radioAlarms  23  }
	

       excessiveCableLossChange	        OBJECT-TYPE	
		SYNTAX			INTEGER  { off ( 1 ) , on ( 2 ) } 
		ACCESS			read-only
		STATUS			mandatory
        	DESCRIPTION		"Cable loss change exceeds the threshold"
		::=  {  radioAlarms 24  }


       excessiveCableLossChangeCount	OBJECT-TYPE	
		SYNTAX			Counter  
		ACCESS			read-only
		STATUS			mandatory
		DESCRIPTION		"Indicates how long Cable loss change has exceeded the threshold"
		::=  {  radioAlarms  25  }

       excessiveRxCableLoss	        OBJECT-TYPE	
		SYNTAX			INTEGER  { off ( 1 ) , on ( 2 ) } 
		ACCESS			read-only
		STATUS			mandatory
        	DESCRIPTION		"Rx gain can not be adjusted to desired value"
		::=  {  radioAlarms 26  }


       excessiveRxCableLossCount	OBJECT-TYPE	
		SYNTAX			Counter  
		ACCESS			read-only
		STATUS			mandatory
		DESCRIPTION		"Indicates how long rx gain can not be adjusted to desired value"
		::=  {  radioAlarms  27  }


--
-- IF CARD ALARMS
--

	ifTxSynthesizerUnlocked	OBJECT-TYPE	
		SYNTAX			INTEGER  { off ( 1 ) , on ( 2 ) } 
		ACCESS			read-only
		STATUS			mandatory
        	DESCRIPTION		"The IF card within the modem unit has a Transmit Synthesizer which is not locked and as a result will not transmit. The severity is critical, the probable cause an incorrectly programmed frequency setting in the modem or a faulty IF card, and recommended course of action is to check frequency setting in the modem or to replace the modem unit."
		::=  {  intermediateFrequencyCardAlarms  1  }

	ifTxSynthesizerUnlockedCount	OBJECT-TYPE	
		SYNTAX			Counter
		ACCESS			read-only
		STATUS			mandatory
		DESCRIPTION		"Indicates the approximate number of seconds that this alarm has been active."
		::=  {  intermediateFrequencyCardAlarms  2  }

	ifRxSynthesizerUnlocked	OBJECT-TYPE	
		SYNTAX			INTEGER  { off ( 1 ) , on ( 2 ) } 
		ACCESS			read-only
		STATUS			mandatory
        	DESCRIPTION		"The IF card within the modem unit has a Receive Synthesizer which is not locked. The severity is critical, the probable cause an incorrectly programmed frequency setting in the modem or a faulty IF card, and recommended course of action is to check frequency setting in the modem or to replace the modem unit."
		::=  {  intermediateFrequencyCardAlarms  3  }

	ifRxSynthesizerUnlockedCount	OBJECT-TYPE	
		SYNTAX			Counter
		ACCESS			read-only
		STATUS			mandatory
		DESCRIPTION		"Indicates the approximate number of seconds that this alarm has been active."
		::=  {  intermediateFrequencyCardAlarms  4  }

--
-- Other ALARMS
--
	rxCableLossExcessive	OBJECT-TYPE	
		SYNTAX			INTEGER  { off ( 1 ) , on ( 2 ) } 
		ACCESS			read-only
		STATUS			mandatory
        	DESCRIPTION		"The Rx cable loss exceeds limit.
		
						Valid only when the installation type is IDU-ODU split"
		::=  {  otherAlarms  1  }

	rxCableLossExcessiveCount	OBJECT-TYPE	
		SYNTAX			Counter
		ACCESS			read-only
		STATUS			mandatory
		DESCRIPTION		"Indicates the approximate number of seconds that this alarm has been active.
						
						Valid only when the installation type is IDU-ODU split"
		::=  {  otherAlarms  2  }

	txCableLossExcessive	OBJECT-TYPE	
		SYNTAX			INTEGER  { off ( 1 ) , on ( 2 ) } 
		ACCESS			read-only
		STATUS			mandatory
        	DESCRIPTION		"The Tx cable loss exceeds limit.
        	
        					Valid only when the installation type is IDU-ODU split"
		::=  {  otherAlarms  3  }

	txCableLossExcessiveCount	OBJECT-TYPE	
		SYNTAX			Counter
		ACCESS			read-only
		STATUS			mandatory
		DESCRIPTION		"Indicates the approximate number of seconds that this alarm has been active.
		
						Valid only when the installation type is IDU-ODU split"
		::=  {  otherAlarms  4  }

	fan1Failed	OBJECT-TYPE	
		SYNTAX			INTEGER  { off ( 1 ) , on ( 2 ) } 
		ACCESS			read-only
		STATUS			mandatory
        	DESCRIPTION		"The fan 1 failed.
		
						Valid only when the installation type is IDU-ODU split"
		::=  {  otherAlarms  5  }

	fan1FailedCount	OBJECT-TYPE	
		SYNTAX			Counter
		ACCESS			read-only
		STATUS			mandatory
		DESCRIPTION		"Indicates the approximate number of seconds that this alarm has been active.
		
						Valid only when the installation type is IDU-ODU split"
		::=  {  otherAlarms  6  }
		
	fan2Failed	OBJECT-TYPE	
		SYNTAX			INTEGER  { off ( 1 ) , on ( 2 ) } 
		ACCESS			read-only
		STATUS			mandatory
        	DESCRIPTION		"The fan 2 failed.

						Valid only when the installation type is IDU-ODU split"
		::=  {  otherAlarms  7  }

	fan2FailedCount	OBJECT-TYPE	
		SYNTAX			Counter
		ACCESS			read-only
		STATUS			mandatory
		DESCRIPTION		"Indicates the approximate number of seconds that this alarm has been active.
		
						Valid only when the installation type is IDU-ODU split"
		::=  {  otherAlarms  8  }


        reserved	                OBJECT-TYPE	
		SYNTAX			INTEGER  { off ( 1 ) , on ( 2 ) } 
		ACCESS			read-only
		STATUS			mandatory
        	DESCRIPTION		"To be filled. "
		::=  {  otherAlarms  9  }


	reservedAlarmCount	        OBJECT-TYPE	
		SYNTAX			Counter
		ACCESS			read-only
		STATUS			mandatory
		DESCRIPTION		"To be filled."
		::=  {  otherAlarms  10  }


        sntpServerUnavailableAlarm       OBJECT-TYPE	
		SYNTAX			INTEGER  { off ( 1 ) , on ( 2 ) } 
		ACCESS			read-only
		STATUS			mandatory
        	DESCRIPTION		"All of the SNTP servers are not available. "
		::=  {  otherAlarms  11  }


	sntpServerUnavailableAlarmCount       OBJECT-TYPE	
		SYNTAX			Counter
		ACCESS			read-only
		STATUS			mandatory
		DESCRIPTION		"Indicates how long in seconds all of the SNTP servers are not available."
		::=  {  otherAlarms  12  }


--
-- TRAP INFORMATION HOSTS, ENABLE/DISABLE
--	
	snmpTrapHostTable	OBJECT-TYPE
		SYNTAX		SEQUENCE  OF  SnmpTrapHostEntry
		ACCESS		not-accessible
		STATUS		mandatory
		DESCRIPTION	"Table containing SNMP trap host entries."
		::=  { apSnmpTraps  1 }

	snmpTrapHostEntry	OBJECT-TYPE
		SYNTAX		SnmpTrapHostEntry
		ACCESS		not-accessible
		STATUS		mandatory
		DESCRIPTION	"The snmp trap host entry containing all the trap host information"
		INDEX		{  snmpTrapHostIndex  }
		::=  { snmpTrapHostTable 1 }

	SnmpTrapHostEntry  ::=  SEQUENCE {
		snmpTrapHostIndex  INTEGER,
		snmpTrapHostMode  INTEGER,
		snmpTrapHostIpAddress  IpAddress,
		snmpTrapHostDomainName  DisplayString,
		snmpTrapHostCommunityName  DisplayString,
		snmpTrapHostActivated  INTEGER
		}


	snmpTrapHostIndex	OBJECT-TYPE	
		SYNTAX			INTEGER
		ACCESS			read-only
		STATUS			mandatory
		DESCRIPTION		"A unique value for each trap host. "
		::=  {  snmpTrapHostEntry  1  }


	snmpTrapHostMode	OBJECT-TYPE	
		SYNTAX			INTEGER  { static ( 1 ) , dns ( 2 ) } 
		ACCESS			read-only
		STATUS			mandatory
		DESCRIPTION		"Indicates how the snmp trap host is obtained for the system."   
		DEFVAL			{ static }
		::=  {  snmpTrapHostEntry  2  }


	snmpTrapHostIpAddress	OBJECT-TYPE	
		SYNTAX			IpAddress
		ACCESS			read-only
		STATUS			mandatory
		DESCRIPTION		"Indicates snmp trap host IP address. "
		::=  {  snmpTrapHostEntry  3  }


	snmpTrapHostDomainName	OBJECT-TYPE	
		SYNTAX			DisplayString  ( SIZE ( 0 .. 24  ) ) 
		ACCESS			read-only
		STATUS			mandatory
		DESCRIPTION		"NOT IMPLEMENTED. Indicates snmp trap host name that is used when DNS is used. "
		::=  {  snmpTrapHostEntry  4  }


	snmpTrapHostCommunityName	OBJECT-TYPE	
		SYNTAX			DisplayString  ( SIZE ( 0 .. 24  ) ) 
		ACCESS			read-only
		STATUS			mandatory
		DESCRIPTION		"The community string name used in Traps."
		::=  {  snmpTrapHostEntry  5  }


	snmpTrapHostActivated	OBJECT-TYPE	
		SYNTAX			INTEGER  { notActive ( 1 ) , active ( 2 ) } 
		ACCESS			read-only
		STATUS			mandatory
		DESCRIPTION		"Specifies whether traps are to be sent to this specific host or not"      
		DEFVAL 			{ notActive }
		::=  {  snmpTrapHostEntry  6  }

	coldStartTrap	OBJECT-TYPE	
		SYNTAX			INTEGER  { disabled ( 1 ) , enabled ( 2 ) } 
		ACCESS			read-write
		STATUS			mandatory
		DESCRIPTION		"Specifies whether this trap is to be sent or not"  
		DEFVAL  		{ disabled }
		::=  {  apSnmpTraps  2  }

	linkDownTrap	OBJECT-TYPE	
		SYNTAX			INTEGER  { disabled ( 1 ) , enabled ( 2 ) } 
		ACCESS			read-write
		STATUS			mandatory
		DESCRIPTION		"Specifies whether this trap is to be sent or not"  
		DEFVAL  		{ disabled }
		::=  {  apSnmpTraps  3  }

	linkUpTrap	OBJECT-TYPE	
		SYNTAX			INTEGER  { disabled ( 1 ) , enabled ( 2 ) } 
		ACCESS			read-write
		STATUS			mandatory
		DESCRIPTION		"Specifies whether this trap is to be sent or not"  
		DEFVAL  		{ disabled }
		::=  {  apSnmpTraps  4  }

	explicitAuthenticationFailureTrap	OBJECT-TYPE	
		SYNTAX			INTEGER  { disabled ( 1 ) , enabled ( 2 ) } 
		ACCESS			read-write
		STATUS			mandatory
		DESCRIPTION		"Specifies whether this trap is to be sent or not"  
		DEFVAL  		{ disabled }
		::=  {  apSnmpTraps  5  }

	autoNegotiationDuplexMismatchTrap	OBJECT-TYPE	
		SYNTAX			INTEGER  { disabled ( 1 ) , enabled ( 2 ) } 
		ACCESS			read-write
		STATUS			mandatory
		DESCRIPTION		"Specifies whether this trap is to be sent or not"  
		DEFVAL  		{ disabled }
		::=  {  apSnmpTraps  6  }

	modemLossOfSignalLockFromDemodulatorTrap	OBJECT-TYPE	
		SYNTAX			INTEGER  { disabled ( 1 ) , enabled ( 2 ) } 
		ACCESS			read-write
		STATUS			mandatory
		DESCRIPTION		"Specifies whether this trap is to be sent or not"  
		DEFVAL  		{ disabled }
		::=  {  apSnmpTraps  7  }

	modemUncorrectedBerThresholdExceededTrap	OBJECT-TYPE	
		SYNTAX			INTEGER  { disabled ( 1 ) , enabled ( 2 ) } 
		ACCESS			read-write
		STATUS			mandatory
		DESCRIPTION		"Specifies whether this trap is to be sent or not"  
		DEFVAL  		{ disabled }
		::=  {  apSnmpTraps  8  }

	modemModulatorPllLockFailureTrap	OBJECT-TYPE	
		SYNTAX			INTEGER  { disabled ( 1 ) , enabled ( 2 ) } 
		ACCESS			read-write
		STATUS			mandatory
		DESCRIPTION		"Description"
		::=  {  apSnmpTraps  9  }

	modemModulatorLossOfSyncBytesTrap	OBJECT-TYPE	
		SYNTAX			INTEGER  { disabled ( 1 ) , enabled ( 2 ) } 
		ACCESS			read-write
		STATUS			mandatory
		DESCRIPTION		"Specifies whether this trap is to be sent or not"  
		DEFVAL  		{ disabled }
		::=  {  apSnmpTraps  10  }

	modemModulatorInputFifoErrorTrap	OBJECT-TYPE	
		SYNTAX			INTEGER  { disabled ( 1 ) , enabled ( 2 ) } 
		ACCESS			read-write
		STATUS			mandatory
		DESCRIPTION		"Specifies whether this trap is to be sent or not"  
		DEFVAL  		{ disabled }
		::=  {  apSnmpTraps  11  }

	modemModulatorInputDataErrorTrap	OBJECT-TYPE	
		SYNTAX			INTEGER  { disabled ( 1 ) , enabled ( 2 ) } 
		ACCESS			read-write
		STATUS			mandatory
		DESCRIPTION		"Specifies whether this trap is to be sent or not"  
		DEFVAL  		{ disabled }
		::=  {  apSnmpTraps  12  }
	
	modemSnrBelowThresholdTrap	OBJECT-TYPE	
		SYNTAX			INTEGER  { disabled ( 1 ) , enabled ( 2 ) } 
		ACCESS			read-write
		STATUS			mandatory
		DESCRIPTION		"Specifies whether this trap is to be sent or not"  
		DEFVAL  		{ disabled }
		::=  {  apSnmpTraps  13  }

	radioPLDROLostLockTrap	OBJECT-TYPE	
		SYNTAX			INTEGER  { disabled ( 1 ) , enabled ( 2 ) } 
		ACCESS			read-write
		STATUS			mandatory
		DESCRIPTION		"Specifies whether this trap is to be sent or not"  
		DEFVAL  		{ disabled }
		::=  {  apSnmpTraps  14  }

	radioLostCommunicationTrap	OBJECT-TYPE	
		SYNTAX			INTEGER  { disabled ( 1 ) , enabled ( 2 ) } 
		ACCESS			read-write
		STATUS			mandatory
		DESCRIPTION		"Specifies whether this trap is to be sent or not"  
		DEFVAL  		{ disabled }
		::=  {  apSnmpTraps  15  }

	radioMismatchTrap	OBJECT-TYPE	
		SYNTAX			INTEGER  { disabled ( 1 ) , enabled ( 2 ) } 
		ACCESS			read-write
		STATUS			mandatory
		DESCRIPTION		"Specifies whether this trap is to be sent or not"  
		DEFVAL  		{ disabled }
		::=  {  apSnmpTraps  16  }

	radioPowerAmpTrap	OBJECT-TYPE	
		SYNTAX			INTEGER  { disabled ( 1 ) , enabled ( 2 ) } 
		ACCESS			read-write
		STATUS			mandatory
		DESCRIPTION		"Specifies whether this trap is to be sent or not"  
		DEFVAL  		{ disabled }
		::=  {  apSnmpTraps  17  }
		
	ifTxSynthesizerUnlockedTrap	OBJECT-TYPE	
		SYNTAX			INTEGER  { disabled ( 1 ) , enabled ( 2 ) } 
		ACCESS			read-write
		STATUS			mandatory
		DESCRIPTION		"Specifies whether this trap is to be sent or not"  
		DEFVAL  		{ disabled }
		::=  {  apSnmpTraps  18  }

	ifRxSynthesizerUnlockedTrap	OBJECT-TYPE	
		SYNTAX			INTEGER  { disabled ( 1 ) , enabled ( 2 ) } 
		ACCESS			read-write
		STATUS			mandatory
		DESCRIPTION		"Specifies whether this trap is to be sent or not"  
		DEFVAL  		{ disabled }
		::=  {  apSnmpTraps  19  }


	ttyManagementSessionCommencedTrap	OBJECT-TYPE	
		SYNTAX			INTEGER  { disabled ( 1 ) , enabled ( 2 ) } 
		ACCESS			read-write
		STATUS			mandatory
		DESCRIPTION		"Specifies whether this trap is to be sent or not"  
		DEFVAL  		{ disabled }
		::=  {  apSnmpTraps  20  }

	ttyManagementSessionTerminatedTrap	OBJECT-TYPE	
		SYNTAX			INTEGER  { disabled ( 1 ) , enabled ( 2 ) } 
		ACCESS			read-write
		STATUS			mandatory
		DESCRIPTION		"Specifies whether this trap is to be sent or not"  
		DEFVAL  		{ disabled }
		::=  {  apSnmpTraps  21  }

                
	rslThresholdExceedTrap	OBJECT-TYPE	
		SYNTAX			INTEGER  { disabled ( 1 ) , enabled ( 2 ) } 
		ACCESS			read-write
		STATUS			mandatory
		DESCRIPTION		"Enables or disables the trap. This trap, if enabled, will be sent when the radio receive signal level threshold is exceeded. If enabled, the system will send this trap to all trap hosts programmed in the system by the user."  
		DEFVAL  		{ disabled }
		::=  {  apSnmpTraps  22  }
	
        droppedFramesThresholdExceedTrap	OBJECT-TYPE	
		SYNTAX			INTEGER  { disabled ( 1 ) , enabled ( 2 ) } 
		ACCESS			read-write
		STATUS			mandatory
		DESCRIPTION		"Enables or disables the trap. This trap, if enabled, will be sent when the dropped ethernet frames threshold is exceeded. If enabled, the system will send this trap to all trap hosts programmed in the system by the user."  
		DEFVAL  		{ disabled }
		::=  {  apSnmpTraps  23  }
                
	bandwidthUtilizationThresholdExceedTrap	OBJECT-TYPE	
		SYNTAX			INTEGER  { disabled ( 1 ) , enabled ( 2 ) } 
		ACCESS			read-write
		STATUS			mandatory
		DESCRIPTION		"Enables or disables the trap. This trap, if enabled, will be sent when the ethernet bandwidth utilization threshold is exceeded. If enabled, the system will send this trap to all trap hosts programmed in the system by the user."  
		DEFVAL  		{ disabled }
		::=  {  apSnmpTraps  24  }
                
	ifRxCableLossExceedTrap	OBJECT-TYPE	
		SYNTAX			INTEGER  { disabled ( 1 ) , enabled ( 2 ) } 
		ACCESS			read-write
		STATUS			mandatory
		DESCRIPTION		"Enables or disables the trap. This trap, if enabled, will be sent when the ethernet bandwidth utilization threshold is exceeded. If enabled, the system will send this trap to all trap hosts programmed in the system by the user.
						Valid only when the installation type is IDU-ODU split"  
		DEFVAL  		{ disabled }
		::=  {  apSnmpTraps  25  }
                
	ifTxCableLossExceedTrap	OBJECT-TYPE	
		SYNTAX			INTEGER  { disabled ( 1 ) , enabled ( 2 ) } 
		ACCESS			read-write
		STATUS			mandatory
		DESCRIPTION		"Enables or disables the trap. This trap, if enabled, will be sent when the ethernet bandwidth utilization threshold is exceeded. If enabled, the system will send this trap to all trap hosts programmed in the system by the user.
						Valid only when the installation type is IDU-ODU split"  
		DEFVAL  		{ disabled }
		::=  {  apSnmpTraps  26  }

	fan1FailedTrap	OBJECT-TYPE	
		SYNTAX			INTEGER  { disabled ( 1 ) , enabled ( 2 ) } 
		ACCESS			read-write
		STATUS			mandatory
		DESCRIPTION		"Enables or disables the trap. This trap, if enabled, will be sent when the ethernet bandwidth utilization threshold is exceeded. If enabled, the system will send this trap to all trap hosts programmed in the system by the user.
						Valid only when the installation type is IDU-ODU split"  
		DEFVAL  		{ disabled }
		::=  {  apSnmpTraps  27  }  
		
	fan2FailedTrap	OBJECT-TYPE	
		SYNTAX			INTEGER  { disabled ( 1 ) , enabled ( 2 ) } 
		ACCESS			read-write
		STATUS			mandatory
		DESCRIPTION		"Enables or disables the trap. This trap, if enabled, will be sent when the ethernet bandwidth utilization threshold is exceeded. If enabled, the system will send this trap to all trap hosts programmed in the system by the user.
						Valid only when the installation type is IDU-ODU split"  
		DEFVAL  		{ disabled }
		::=  {  apSnmpTraps  28  }

	mdmCardHardwareFirmwareMismatchTrap	OBJECT-TYPE	
		SYNTAX			INTEGER  { disabled ( 1 ) , enabled ( 2 ) } 
		ACCESS			read-write
		STATUS			mandatory
		DESCRIPTION		"Enables or disables the trap. "  
		DEFVAL  		{ disabled }
		::=  {  apSnmpTraps  29  }

        atpcConfigMismatchTrap	        OBJECT-TYPE	
		SYNTAX			INTEGER  { disabled ( 1 ) , enabled ( 2 ) } 
		ACCESS			read-write
		STATUS			mandatory
		DESCRIPTION		"Enables or disables the trap. "  
		DEFVAL  		{ disabled }
		::=  {  apSnmpTraps  30  }

        hiPowerOptionM1Trap	        OBJECT-TYPE	
		SYNTAX			INTEGER  { disabled ( 1 ) , enabled ( 2 ) } 
		ACCESS			read-write
		STATUS			mandatory
		DESCRIPTION		"Enables or disables the trap. "  
		DEFVAL  		{ disabled }
		::=  {  apSnmpTraps  31  }


        hiPowerOptionM2Trap	        OBJECT-TYPE	
		SYNTAX			INTEGER  { disabled ( 1 ) , enabled ( 2 ) } 
		ACCESS			read-write
		STATUS			mandatory
		DESCRIPTION		"Enables or disables the trap. "  
		DEFVAL  		{ disabled }
		::=  {  apSnmpTraps  32  }

        hiPowerTxDetectorTrap	        OBJECT-TYPE	
		SYNTAX			INTEGER  { disabled ( 1 ) , enabled ( 2 ) } 
		ACCESS			read-write
		STATUS			mandatory
		DESCRIPTION		"Enables or disables the trap. "  
		DEFVAL  		{ disabled }
		::=  {  apSnmpTraps  33  }

       sntpServersUnreachableTrap        OBJECT-TYPE	
		SYNTAX			INTEGER  { disabled ( 1 ) , enabled ( 2 ) } 
		ACCESS			read-write
		STATUS			mandatory
		DESCRIPTION		"Enables or disables the trap. "  
		DEFVAL  		{ disabled }
		::=  {  apSnmpTraps  34  }


      rlsMismatchTrap                   OBJECT-TYPE	
		SYNTAX		        INTEGER  { disabled ( 1 ) , enabled ( 2 ) } 
		ACCESS			read-write
		STATUS			mandatory
		DESCRIPTION		"Enables or disables the trap. "  
		DEFVAL  		{ disabled }
		::=  {  apSnmpTraps  35  }


      rLSShutdownActivatedTrap          OBJECT-TYPE	
		SYNTAX			INTEGER  { disabled ( 1 ) , enabled ( 2 ) } 
		ACCESS			read-write
		STATUS			mandatory
		DESCRIPTION		"Enables or disables the trap. "  
		DEFVAL  		{ disabled }
		::=  {  apSnmpTraps  36  }
--
-- FREQUENCY FILE RELATED TRAPS
--
      frequencyFileInvalidTrap	        OBJECT-TYPE	
		SYNTAX			INTEGER  { disabled ( 1 ) , enabled ( 2 ) } 
		ACCESS			read-write
		STATUS			mandatory
		DESCRIPTION		"Enables or disables the trap. "  
		DEFVAL  		{ disabled }
		::=  {  apSnmpTraps  37  }


     optionalParaNotEntTrap	        OBJECT-TYPE	
		SYNTAX			INTEGER  { disabled ( 1 ) , enabled ( 2 ) } 
		ACCESS			read-write
		STATUS			mandatory
		DESCRIPTION		"Enables or disables the trap. "  
		DEFVAL  		{ disabled }
		::=  {  apSnmpTraps  38  }


     progRadioBandNotFoundTrap	        OBJECT-TYPE	
		SYNTAX			INTEGER  { disabled ( 1 ) , enabled ( 2 ) } 
		ACCESS			read-write
		STATUS			mandatory
		DESCRIPTION		"Enables or disables the trap. "  
		DEFVAL  		{ disabled }
		::=  {  apSnmpTraps  39  }
--
-- RADIO REDUNDANCY RELATED TRAPS
--
    radioRedundancySwitchOverSuccessTrap          OBJECT-TYPE	
		SYNTAX			INTEGER  { disabled ( 1 ) , enabled ( 2 ) } 
		ACCESS			read-write
		STATUS			mandatory
		DESCRIPTION		"Enables or disables the trap. "  
		DEFVAL  		{ disabled }
		::=  {  apSnmpTraps  40  }

	radioRedundancySwitchOverFailedTrap          OBJECT-TYPE	
		SYNTAX			INTEGER  { disabled ( 1 ) , enabled ( 2 ) } 
		ACCESS			read-write
		STATUS			mandatory
		DESCRIPTION		"Enables or disables the trap. "  
		DEFVAL  		{ disabled }
		::=  {  apSnmpTraps  41  }

	radioRedundancyNoAtpcSupportTrap          OBJECT-TYPE	
		SYNTAX			INTEGER  { disabled ( 1 ) , enabled ( 2 ) } 
		ACCESS			read-write
		STATUS			mandatory
		DESCRIPTION		"Enables or disables the trap. "  
		DEFVAL  		{ disabled }
		::=  {  apSnmpTraps  42  }

	radioRedundancyInvalidRadioFirmwareTrap          OBJECT-TYPE	
		SYNTAX			INTEGER  { disabled ( 1 ) , enabled ( 2 ) } 
		ACCESS			read-write
		STATUS			mandatory
		DESCRIPTION		"Enables or disables the trap. "  
		DEFVAL  		{ disabled }
		::=  {  apSnmpTraps  43  }

	radioRedundancySwitchByLocalEndTrap          OBJECT-TYPE	
		SYNTAX			INTEGER  { disabled ( 1 ) , enabled ( 2 ) } 
		ACCESS			read-write
		STATUS			mandatory
		DESCRIPTION		"Enables or disables the trap. "  
		DEFVAL  		{ disabled }
		::=  {  apSnmpTraps  44  }

	radioRedundancySwitchByPeerTrap          OBJECT-TYPE	
		SYNTAX			INTEGER  { disabled ( 1 ) , enabled ( 2 ) } 
		ACCESS			read-write
		STATUS			mandatory
		DESCRIPTION		"Enables or disables the trap. "  
		DEFVAL  		{ disabled }
		::=  {  apSnmpTraps  45  }
--
-- Automatic Adaptive Modulation(AAM) RELATED TRAPS
--
	aamConfigMismatchTrap          OBJECT-TYPE	
		SYNTAX			INTEGER  { disabled ( 1 ) , enabled ( 2 ) } 
		ACCESS			read-write
		STATUS			mandatory
		DESCRIPTION		"Enables or disables the aamConfigMismatch trap. "  
		DEFVAL  		{ disabled }
		::=  {  apSnmpTraps  46  }

	aamQpskActiveTrap          OBJECT-TYPE	
		SYNTAX			INTEGER  { disabled ( 1 ) , enabled ( 2 ) } 
		ACCESS			read-write
		STATUS			mandatory
		DESCRIPTION		"Enables or disables the aamQpskActive trap. "  
		DEFVAL  		{ disabled }
		::=  {  apSnmpTraps  47  }

	primaryRadioFaultyTrap  	OBJECT-TYPE	
		SYNTAX			INTEGER  { disabled ( 1 ) , enabled ( 2 ) } 
		ACCESS			read-write
		STATUS			mandatory
		DESCRIPTION		"Enables or disables the primaryRadioFaulty  trap. "  
		DEFVAL  		{ disabled }
		::=  {  apSnmpTraps  48  }

	radioSerialNumberMismatchTrap          OBJECT-TYPE	
		SYNTAX			INTEGER  { disabled ( 1 ) , enabled ( 2 ) } 
		ACCESS			read-write
		STATUS			mandatory
		DESCRIPTION		"Enables or disables the radioSerialNumberMismatch trap. "  
		DEFVAL  		{ disabled }
		::=  {  apSnmpTraps  49  } 

--
-- SNMP V3 TRAP HOST TABLE
--

	snmpV3TrapHostsTable	OBJECT-TYPE
		SYNTAX		SEQUENCE  OF  SnmpV3TrapHostsEntry
		ACCESS		not-accessible
		STATUS		mandatory
		DESCRIPTION	"Table containing snmp V3 trap host entries"
		::=  { apSnmpTraps  50 }

	snmpV3TrapHostsEntry	OBJECT-TYPE
		SYNTAX		SnmpV3TrapHostsEntry
		ACCESS		not-accessible
		STATUS		mandatory
		DESCRIPTION	"Contains the snmp v3 trap host information"
		INDEX		{  snmpV3TrapHostsIndex  }
		::=  { snmpV3TrapHostsTable 1 }

	SnmpV3TrapHostsEntry  ::=  SEQUENCE {
		snmpV3TrapHostsIndex  INTEGER,
		snmpV3TrapHostIpAddress  IpAddress,
		snmpV3TrapHostUserName  DisplayString,
		snmpV3TrapHostAuthProtocol  INTEGER,
		snmpV3TrapHostAuthPassword  DisplayString,
		snmpV3TrapHostPrivProtocol  INTEGER,
		snmpV3TrapHostPrivPassword  DisplayString,		
		snmpV3TrapHostActivated  INTEGER
		}
		
	snmpV3TrapHostsIndex	OBJECT-TYPE	
		SYNTAX			INTEGER
		ACCESS			read-only
		STATUS			mandatory
		DESCRIPTION		"A unique value for each v3 trap host."
		::=  {  snmpV3TrapHostsEntry  1  }

	snmpV3TrapHostIpAddress	OBJECT-TYPE	
		SYNTAX			IpAddress
		ACCESS			read-only
		STATUS			mandatory
		DESCRIPTION		"Indicates snmp trap host IP address. "
		::=  {  snmpV3TrapHostsEntry  2  }

	snmpV3TrapHostUserName	OBJECT-TYPE	
		SYNTAX			DisplayString  ( SIZE ( 0 .. 24  ) ) 
		ACCESS			read-only
		STATUS			mandatory
		DESCRIPTION		"The user name of the v3 trap host."
		::=  {  snmpV3TrapHostsEntry  3  }


	snmpV3TrapHostAuthProtocol 	OBJECT-TYPE	
		SYNTAX			INTEGER  { noAuth ( 1 ) , md5 ( 2 ), sha(3) } 
		ACCESS			read-only
		STATUS			mandatory
		DESCRIPTION		"The authentication alogorithm used by the v3 trap host."
		::=  {  snmpV3TrapHostsEntry  4  }

	snmpV3TrapHostAuthPassword	OBJECT-TYPE	
		SYNTAX			DisplayString  ( SIZE ( 0 .. 24  ) ) 
		ACCESS			read-only
		STATUS			mandatory
		DESCRIPTION		"The authentication password of the v3 trap host."
		::=  {  snmpV3TrapHostsEntry  5  }
	
	snmpV3TrapHostPrivProtocol 	OBJECT-TYPE	
		SYNTAX			INTEGER  { noPriv ( 1 ) , des ( 2 ) } 
		ACCESS			read-only
		STATUS			mandatory
		DESCRIPTION		"The privacy encryiption alogorithm used by the v3 trap host."
		::=  {  snmpV3TrapHostsEntry  6  }

	snmpV3TrapHostPrivPassword	OBJECT-TYPE	
		SYNTAX			DisplayString  ( SIZE ( 0 .. 24  ) ) 
		ACCESS			read-only
		STATUS			mandatory
		DESCRIPTION		"The privacy password of the v3 trap host."
		::=  {  snmpV3TrapHostsEntry  7  }

	snmpV3TrapHostActivated	OBJECT-TYPE	
		SYNTAX			INTEGER  { notActive ( 1 ) , active ( 2 ) } 
		ACCESS			read-only
		STATUS			mandatory
		DESCRIPTION		"Specifies whether a specific v3 trap host is allowed to access the system" 
		DEFVAL			{ notActive }
		::=  {  snmpV3TrapHostsEntry  8  }


	excessiveCblLossChangeTrap          OBJECT-TYPE	
		SYNTAX			INTEGER  { disabled ( 1 ) , enabled ( 2 ) } 
		ACCESS			read-write
		STATUS			mandatory
		DESCRIPTION		"Enables or disables the excessiveCblLossChange trap. "  
		DEFVAL  		{ disabled }
		::=  {  apSnmpTraps  51  } 

--
-- SNMP MANAGERS
--


	snmpUserAccess	OBJECT-TYPE	
		SYNTAX			INTEGER  { managers ( 1 ) , any ( 2 ) } 
		ACCESS			read-only
		STATUS			mandatory
		DESCRIPTION		"Specifies the user access to the system.If access is set to managers then only managers with there ip addresses set in snmpManagersTable will be able to gain snmp access to the system.  If access is set to any then any manager will be able to gain snmp access to the system"
		::=  {  apSnmpManagers  1  }

	snmpManagerAnyCommunityName	OBJECT-TYPE	
		SYNTAX			DisplayString  ( SIZE ( 0 .. 24  ) ) 
		ACCESS			read-only
		STATUS			mandatory
		DESCRIPTION		"The community string name used by the 'any' manager."
		::=  {  apSnmpManagers  2  }

	snmpManagersTable	OBJECT-TYPE
		SYNTAX		SEQUENCE  OF  SnmpManagersEntry
		ACCESS		not-accessible
		STATUS		mandatory
		DESCRIPTION	"Table containing snmp manager entries"
		::=  { apSnmpManagers  3 }

	snmpManagersEntry	OBJECT-TYPE
		SYNTAX		SnmpManagersEntry
		ACCESS		not-accessible
		STATUS		mandatory
		DESCRIPTION	"Contains the snmp manager information"
		INDEX		{  snmpManagersIndex  }
		::=  { snmpManagersTable 1 }

	SnmpManagersEntry  ::=  SEQUENCE {
		snmpManagersIndex  INTEGER,
		snmpManagerIpAddress  IpAddress,
		snmpManagerCommunityName  DisplayString,
		snmpManagerActivated  INTEGER
		}
		
	snmpManagersIndex	OBJECT-TYPE	
		SYNTAX			INTEGER
		ACCESS			read-only
		STATUS			mandatory
		DESCRIPTION		"A unique value for each manager."
		::=  {  snmpManagersEntry  1  }


	snmpManagerIpAddress	OBJECT-TYPE	
		SYNTAX			IpAddress
		ACCESS			read-only
		STATUS			mandatory
		DESCRIPTION		"The IP address of the Manager."
		::=  {  snmpManagersEntry  2  }


	snmpManagerCommunityName	OBJECT-TYPE	
		SYNTAX			DisplayString  ( SIZE ( 0 .. 24  ) ) 
		ACCESS			read-only
		STATUS			mandatory
		DESCRIPTION		"The community string name used by the manager."
		::=  {  snmpManagersEntry  3  }


	snmpManagerActivated	OBJECT-TYPE	
		SYNTAX			INTEGER  { notActive ( 1 ) , active ( 2 ) } 
		ACCESS			read-only
		STATUS			mandatory
		DESCRIPTION		"Specifies whether a specific manager is allowed to access the system" 
		DEFVAL			{ notActive }
		::=  {  snmpManagersEntry  4  }
	snmpV3ManagersTable	OBJECT-TYPE
		SYNTAX		SEQUENCE  OF  SnmpV3ManagersEntry
		ACCESS		not-accessible
		STATUS		mandatory
		DESCRIPTION	"Table containing snmp V3 manager entries"
		::=  { apSnmpManagers  4 }

	snmpV3ManagersEntry	OBJECT-TYPE
		SYNTAX		SnmpV3ManagersEntry
		ACCESS		not-accessible
		STATUS		mandatory
		DESCRIPTION	"Contains the snmp v3 manager information"
		INDEX		{  snmpV3ManagersIndex  }
		::=  { snmpV3ManagersTable 1 }

	SnmpV3ManagersEntry  ::=  SEQUENCE {
		snmpV3ManagersIndex  INTEGER,
		snmpV3ManagerUserName  DisplayString,
		snmpV3ManagerAuthProtocol  INTEGER,
		snmpV3ManagerAuthPassword  DisplayString,
		snmpV3ManagerPrivProtocol  INTEGER,
		snmpV3ManagerPrivPassword  DisplayString,		
		snmpV3ManagerActivated  INTEGER
		}
		
	snmpV3ManagersIndex	OBJECT-TYPE	
		SYNTAX			INTEGER
		ACCESS			read-only
		STATUS			mandatory
		DESCRIPTION		"A unique value for each v3 manager."
		::=  {  snmpV3ManagersEntry  1  }


	snmpV3ManagerUserName	OBJECT-TYPE	
		SYNTAX			DisplayString  ( SIZE ( 0 .. 24  ) ) 
		ACCESS			read-only
		STATUS			mandatory
		DESCRIPTION		"The user name of the v3 Manager."
		::=  {  snmpV3ManagersEntry  2  }


	snmpV3ManagerAuthProtocol 	OBJECT-TYPE	
		SYNTAX			INTEGER  { noAuth ( 1 ) , md5 ( 2 ), sha(3) } 
		ACCESS			read-only
		STATUS			mandatory
		DESCRIPTION		"The authentication alogorithm used by the v3 manager."
		::=  {  snmpV3ManagersEntry  3  }

	snmpV3ManagerAuthPassword	OBJECT-TYPE	
		SYNTAX			DisplayString  ( SIZE ( 0 .. 24  ) ) 
		ACCESS			read-only
		STATUS			mandatory
		DESCRIPTION		"The authentication password of the v3 Manager."
		::=  {  snmpV3ManagersEntry  4  }
	
	snmpV3ManagerPrivProtocol 	OBJECT-TYPE	
		SYNTAX			INTEGER  { noPriv ( 1 ) , des ( 2 ) } 
		ACCESS			read-only
		STATUS			mandatory
		DESCRIPTION		"The privacy encryiption alogorithm used by the v3 manager."
		::=  {  snmpV3ManagersEntry  5  }

	snmpV3ManagerPrivPassword	OBJECT-TYPE	
		SYNTAX			DisplayString  ( SIZE ( 0 .. 24  ) ) 
		ACCESS			read-only
		STATUS			mandatory
		DESCRIPTION		"The privacy password of the v3 Manager."
		::=  {  snmpV3ManagersEntry  6  }

	snmpV3ManagerActivated	OBJECT-TYPE	
		SYNTAX			INTEGER  { notActive ( 1 ) , active ( 2 ) } 
		ACCESS			read-only
		STATUS			mandatory
		DESCRIPTION		"Specifies whether a specific v3 manager is allowed to access the system" 
		DEFVAL			{ notActive }
		::=  {  snmpV3ManagersEntry  7  }


--
-- LINK ANALYSIS OBJECTS
--
	
        units	OBJECT-TYPE	
		SYNTAX			DisplayString
		ACCESS			read-only
		STATUS			mandatory
		DESCRIPTION		"OBSOLETE. The units of measurement used in the link analysis."
		::=  {  apLinkAnalysis  1  }

	distanceInputMethod	OBJECT-TYPE	
		SYNTAX			INTEGER  { direct ( 1 ) , latLongCoord ( 2 ) } 
		ACCESS			read-only
		STATUS			mandatory
		DESCRIPTION		"OBSOLETE. The input method used that determines whether distance between nodes coordinates were used for system calculations."
		::=  {  apLinkAnalysis  2  }

	distanceBetweenNodes	OBJECT-TYPE	
		SYNTAX			DisplayString
		ACCESS			read-only
		STATUS			mandatory
		DESCRIPTION		"OBSOLETE. The distance between nodes, in either meters, or feet, depending on the the Units used. This object will be 0 if Longitude and Latitude are used."
		::=  {  apLinkAnalysis  3  }

	latitudeThisNode	OBJECT-TYPE	
		SYNTAX			DisplayString
		ACCESS			read-only
		STATUS			mandatory
		DESCRIPTION		"OBSOLETE.The latitude of this node.This object will be 0 if  DistanceBetweenNodes is used."
		::=  {  apLinkAnalysis  4  }

	longitudeThisNode	OBJECT-TYPE	
		SYNTAX			DisplayString
		ACCESS			read-only
		STATUS			mandatory
		DESCRIPTION		"OBSOLETE. The longitude of this node.This object will be 0 if  DistanceBetweenNodes is used."
		::=  {  apLinkAnalysis  5  }

	latitudePeerNode	OBJECT-TYPE	
		SYNTAX			DisplayString
		ACCESS			read-only
		STATUS			mandatory
		DESCRIPTION		"OBSOLETE. The latitude of the peer node.This object will be 0 if  DistanceBetweenNodes is used."
		::=  {  apLinkAnalysis  6  }

	longitudePeerNode	OBJECT-TYPE	
		SYNTAX			DisplayString
		ACCESS			read-only
		STATUS			mandatory
		DESCRIPTION		"OBSOLETE. The longitude of the peer node.This object will be 0 if  DistanceBetweenNodes is used."
		::=  {  apLinkAnalysis  7  }
	
	linkAnalysisFrequencyBand	OBJECT-TYPE	
		SYNTAX			DisplayString
		ACCESS			read-only
		STATUS			mandatory
		DESCRIPTION		"OBSOLETE. The frequency band that this system was set up for"
		::=  {  apLinkAnalysis  8  }

	availabilityPercentage	OBJECT-TYPE	
		SYNTAX			DisplayString 
		ACCESS			read-only
		STATUS			mandatory
		DESCRIPTION		"OBSOLETE. The required availability of the link. A value of 95999 is 95.000%"
		::=  {  apLinkAnalysis  9  }

	polarization	OBJECT-TYPE	
		SYNTAX			INTEGER  { horizontal ( 1 ) , vertical ( 2 ) } 
		ACCESS			read-only
		STATUS			mandatory
		DESCRIPTION		"OBSOLETE. The polarization of the node."
		::=  {  apLinkAnalysis  10  }

	linkAnalysisAirPairType	OBJECT-TYPE	
		SYNTAX			INTEGER  { airPair50 ( 1 ) , airPair100 ( 2 ) } 
		ACCESS			read-only
		STATUS			mandatory
		DESCRIPTION		"OBSOLETE. The AirPair type that this system was set up as"
		::=  {  apLinkAnalysis  11  }

	rainRegion	OBJECT-TYPE	
		SYNTAX			DisplayString
		ACCESS			read-only
		STATUS			mandatory
		DESCRIPTION		"OBSOLETE. The rain region of the site."
		::=  {  apLinkAnalysis  12  }

	antennaDiameter	OBJECT-TYPE	
		SYNTAX			DisplayString
		ACCESS			read-only
		STATUS			mandatory
		DESCRIPTION		"OBSOLETE. The diameter of the antenna, in inches or centimeters."
		::=  {  apLinkAnalysis  13  }

	transmitPowerBackoff	OBJECT-TYPE	
		SYNTAX			INTEGER
		ACCESS			read-only
		STATUS			mandatory
		DESCRIPTION		"OBSOLETE. The transmitter back off power."
		::=  {  apLinkAnalysis  14  }

--
-- COS OBJECTS
--

	
        dot1pFiltering	OBJECT-TYPE	
		SYNTAX			INTEGER  { disabled ( 1 ) , enabled ( 2 ) }
		ACCESS			read-write
		STATUS			mandatory
		DESCRIPTION		"Sets DotP1 filtering on/off."
		::=  {  apCoS  1  }

	dot1pValue0QueueAssignment	OBJECT-TYPE	
		SYNTAX			INTEGER  { one ( 1 ) , two ( 2 ) }
		ACCESS			read-write
		STATUS			mandatory
		DESCRIPTION		"Queue assignment for DotP1 value 0."
		::=  {  apCoS  2  }		

	dot1pValue1QueueAssignment	OBJECT-TYPE	
		SYNTAX			INTEGER  { one ( 1 ) , two ( 2 ) }
		ACCESS			read-write
		STATUS			mandatory
		DESCRIPTION		"Queue assignment for DotP1 value 1."
		::=  {  apCoS  3  } 
				
	dot1pValue2QueueAssignment	OBJECT-TYPE	
		SYNTAX			INTEGER  { one ( 1 ) , two ( 2 ) }
		ACCESS			read-write
		STATUS			mandatory
		DESCRIPTION		"Queue assignment for DotP1 value 2."
		::=  {  apCoS  4  } 
				
	dot1pValue3QueueAssignment	OBJECT-TYPE	
		SYNTAX			INTEGER  { one ( 1 ) , two ( 2 ) }
		ACCESS			read-write
		STATUS			mandatory
		DESCRIPTION		"Queue assignment for DotP1 value 3."
		::=  {  apCoS  5  } 
				
	dot1pValue4QueueAssignment	OBJECT-TYPE	
		SYNTAX			INTEGER  { one ( 1 ) , two ( 2 ) }
		ACCESS			read-write
		STATUS			mandatory
		DESCRIPTION		"Queue assignment for DotP1 value 4."
		::=  {  apCoS  6  } 
				
	dot1pValue5QueueAssignment	OBJECT-TYPE	
		SYNTAX			INTEGER  { one ( 1 ) , two ( 2 ) }
		ACCESS			read-write
		STATUS			mandatory
		DESCRIPTION		"Queue assignment for DotP1 value 5."
		::=  {  apCoS  7  } 
				
	dot1pValue6QueueAssignment	OBJECT-TYPE	
		SYNTAX			INTEGER  { one ( 1 ) , two ( 2 ) }
		ACCESS			read-write
		STATUS			mandatory
		DESCRIPTION		"Queue assignment for DotP1 value 6."
		::=  {  apCoS  8  } 
				
	dot1pValue7QueueAssignment	OBJECT-TYPE	
		SYNTAX			INTEGER  { one ( 1 ) , two ( 2 ) }
		ACCESS			read-write
		STATUS			mandatory
		DESCRIPTION		"Queue assignment for DotP1 value 7."
		::=  {  apCoS  9  } 
				
	cosQueueWidth	OBJECT-TYPE	
		SYNTAX			INTEGER
		ACCESS			read-write
		STATUS			mandatory
		DESCRIPTION		"The class of service queue width.  Enter a value from 1 to 16 to define the priority queues size."
		::=  {  apCoS  10  } 


--
-- User Login information       
-- 
	
        
        ttySessionUser1	OBJECT IDENTIFIER
		::=  {  apManagementSessions 1  }
                
                ttySessionUser1Name		OBJECT-TYPE	
		        SYNTAX			DisplayString  ( SIZE ( 0 .. 32  ) ) 
		        ACCESS			read-only
		        STATUS			mandatory
		        DESCRIPTION		"The username of a management session using Telnet or HTTP. The session state variable must be checked to determine if the management session is currently in progress."
		        ::=  {  ttySessionUser1  1  }

	
	        ttySessionUser1ConnectionType		OBJECT-TYPE	
		        SYNTAX			INTEGER  { informationNotAvailable ( 1 ) , serialPort ( 2 ) , tenBaseT ( 3 ) , inband ( 4 )  } 
		        ACCESS			read-only
		        STATUS			mandatory
		        DESCRIPTION		"The physical port used to log in to the system. The serial port is always local to the equipment. The 10BaseT connector may be local, or remote, depending on if the configuration of network management port. The inband connection is the port carrying customer traffic."
		        ::=  {  ttySessionUser1  2  }
        
	        ttySessionUser1State		OBJECT-TYPE	
		        SYNTAX			INTEGER  { informationNotAvailable ( 1 ) , sessionTerminated ( 2 ) , sessionInProgress ( 3 ) } 
		        ACCESS			read-only
		        STATUS			mandatory
		        DESCRIPTION		"The state of the session. The session is inProgress if the user is currently logged into the system. The session is terminated if the user has logged out of the system."
		        ::=  {  ttySessionUser1  3  }
        
        ttySessionUser2	OBJECT IDENTIFIER
		::=  {  apManagementSessions 2  }
                
                ttySessionUser2Name		OBJECT-TYPE	
		        SYNTAX			DisplayString  ( SIZE ( 0 .. 32  ) ) 
		        ACCESS			read-only
		        STATUS			mandatory
		        DESCRIPTION		"The username of a person currently logged in to the system using Telnet or HTTP. This can be in-band or the side 10BT channel, if supported on this system."
		        ::=  {  ttySessionUser2  1  }

	
	        ttySessionUser2ConnectionType		OBJECT-TYPE	
		        SYNTAX			INTEGER  { informationNotAvailable ( 1 ) , serialPort ( 2 ) , tenBaseT ( 3 ) , inband ( 4 )  } 
		        ACCESS			read-only
		        STATUS			mandatory
		        DESCRIPTION		"The physical port used to log in to the system. The serial port is always local to the equipment. The 10BaseT connector may be local, or remote, depending on if the configuration of network management port. The inband connection is the port carrying customer traffic."
		        ::=  {  ttySessionUser2  2  }

	        ttySessionUser2State		OBJECT-TYPE	
		        SYNTAX			INTEGER  { informationNotAvailable ( 1 ) , sessionTerminated ( 2 ) , sessionInProgress ( 3 ) } 
		        ACCESS			read-only
		        STATUS			mandatory
		        DESCRIPTION		"The state of the session. The session is inProgress if the user is currently logged into the system. The session is terminated if the user has logged out of the system."
		        ::=  {  ttySessionUser2  3  }

        ttySessionUser3	OBJECT IDENTIFIER
		::=  {  apManagementSessions 3  }
                
                ttySessionUser3Name		OBJECT-TYPE	
		        SYNTAX			DisplayString  ( SIZE ( 0 .. 32  ) ) 
		        ACCESS			read-only
		        STATUS			mandatory
		        DESCRIPTION		"The username of a person currently logged in to the system using Telnet or HTTP. This can be in-band or the side 10BT channel, if supported on this system."
		        ::=  {  ttySessionUser3  1  }

	
	        ttySessionUser3ConnectionType		OBJECT-TYPE	
		        SYNTAX			INTEGER  { informationNotAvailable ( 1 ) , serialPort ( 2 ) , tenBaseT ( 3 ) , inband ( 4 )  } 
		        ACCESS			read-only
		        STATUS			mandatory
		        DESCRIPTION		"The physical port used to log in to the system. The serial port is always local to the equipment. The 10BaseT connector may be local, or remote, depending on if the configuration of network management port. The inband connection is the port carrying customer traffic."
		        ::=  {  ttySessionUser3  2  }


	        ttySessionUser3State		OBJECT-TYPE	
		        SYNTAX			INTEGER  { informationNotAvailable ( 1 ) , sessionTerminated ( 2 ) , sessionInProgress ( 3 ) } 
		        ACCESS			read-only
		        STATUS			mandatory
		        DESCRIPTION		"The state of the session. The session is inProgress if the user is currently logged into the system. The session is terminated if the user has logged out of the system."
		        ::=  {  ttySessionUser3  3  }

        ttySessionUser4	OBJECT IDENTIFIER
		::=  {  apManagementSessions 4  }
                
                ttySessionUser4Name		OBJECT-TYPE	
		        SYNTAX			DisplayString  ( SIZE ( 0 .. 32  ) ) 
		        ACCESS			read-only
		        STATUS			mandatory
		        DESCRIPTION		"The username of a person currently logged in to the system using Telnet or HTTP. This can be in-band or the side 10BT channel, if supported on this system."
		        ::=  {  ttySessionUser4  1  }

	
	        ttySessionUser4ConnectionType		OBJECT-TYPE	
		        SYNTAX			INTEGER  { informationNotAvailable ( 1 ) , serialPort ( 2 ) , tenBaseT ( 3 ) , inband ( 4 )  } 
		        ACCESS			read-only
		        STATUS			mandatory
		        DESCRIPTION		"The physical port used to log in to the system. The serial port is always local to the equipment. The 10BaseT connector may be local, or remote, depending on if the configuration of network management port. The inband connection is the port carrying customer traffic."
		        ::=  {  ttySessionUser4  2  }

	        ttySessionUser4State		OBJECT-TYPE	
		        SYNTAX			INTEGER  { informationNotAvailable ( 1 ) , sessionTerminated ( 2 ) , sessionInProgress ( 3 ) } 
		        ACCESS			read-only
		        STATUS			mandatory
		        DESCRIPTION		"The state of the session. The session is inProgress if the user is currently logged into the system. The session is terminated if the user has logged out of the system."
		        ::=  {  ttySessionUser4  3  }

        ttySessionUser5	OBJECT IDENTIFIER
		::=  {  apManagementSessions 5  }
                
                ttySessionUser5Name		OBJECT-TYPE	
		        SYNTAX			DisplayString  ( SIZE ( 0 .. 32  ) ) 
		        ACCESS			read-only
		        STATUS			mandatory
		        DESCRIPTION		"The username of a person currently logged in to the system using Telnet or HTTP. This can be in-band or the side 10BT channel, if supported on this system."
		        ::=  {  ttySessionUser5  1  }

	
	        ttySessionUser5ConnectionType		OBJECT-TYPE	
		        SYNTAX			INTEGER  { informationNotAvailable ( 1 ) , serialPort ( 2 ) , tenBaseT ( 3 ) , inband ( 4 )  } 
		        ACCESS			read-only
		        STATUS			mandatory
		        DESCRIPTION		"The physical port used to log in to the system. The serial port is always local to the equipment. The 10BaseT connector may be local, or remote, depending on if the configuration of network management port. The inband connection is the port carrying customer traffic."
		        ::=  {  ttySessionUser5  2  }


	        ttySessionUser5State		OBJECT-TYPE	
		        SYNTAX			INTEGER  { informationNotAvailable ( 1 ) , sessionTerminated ( 2 ) , sessionInProgress ( 3 ) } 
		        ACCESS			read-only
		        STATUS			mandatory
		        DESCRIPTION		"The state of the session. The session is inProgress if the user is currently logged into the system. The session is terminated if the user has logged out of the system."
		        ::=  {  ttySessionUser5  3  }
        
        ttySessionUser6	OBJECT IDENTIFIER
		::=  {  apManagementSessions 6  }
                
                ttySessionUser6Name		OBJECT-TYPE	
		        SYNTAX			DisplayString  ( SIZE ( 0 .. 32  ) ) 
		        ACCESS			read-only
		        STATUS			mandatory
		        DESCRIPTION		"The username of a person currently logged in to the system using Telnet or HTTP. This can be in-band or the side 10BT channel, if supported on this system."
		        ::=  {  ttySessionUser6  1  }

	
	        ttySessionUser6ConnectionType		OBJECT-TYPE	
		        SYNTAX			INTEGER  { informationNotAvailable ( 1 ) , serialPort ( 2 ) , tenBaseT ( 3 ) , inband ( 4 )  } 
		        ACCESS			read-only
		        STATUS			mandatory
		        DESCRIPTION		"The physical port used to log in to the system. The serial port is always local to the equipment. The 10BaseT connector may be local, or remote, depending on if the configuration of network management port. The inband connection is the port carrying customer traffic."
		        ::=  {  ttySessionUser6  2  }


	        ttySessionUser6State		OBJECT-TYPE	
		        SYNTAX			INTEGER  { informationNotAvailable ( 1 ) , sessionTerminated ( 2 ) , sessionInProgress ( 3 ) } 
		        ACCESS			read-only
		        STATUS			mandatory
		        DESCRIPTION		"The state of the session. The session is inProgress if the user is currently logged into the system. The session is terminated if the user has logged out of the system."
		        ::=  {  ttySessionUser6  3  }
          

        sessionUserInterformation               OBJECT IDENTIFIER
		::=  {  apManagementSessions 7  }
                
                ttySessionUserName		OBJECT-TYPE	
		        SYNTAX			DisplayString  ( SIZE ( 0 .. 32  ) ) 
		        ACCESS			read-only
		        STATUS			mandatory
		        DESCRIPTION		"NOT IMPLEMENTED. Object type placeholder for username string for SNMP traps. The username of a person currently logged in to the system using Telnet or HTTP. This can be in-band or the side 10BT channel, if supported on this system."
		        ::=  {  sessionUserInterformation  1  }

	
	        ttySessionUserConnectionType		OBJECT-TYPE	
		        SYNTAX			INTEGER  { informationNotAvailable ( 1 ) , serialPort ( 2 ) , tenBaseT ( 3 ) , inband ( 4 )  } 
		        ACCESS			read-only
		        STATUS			mandatory
		        DESCRIPTION		"NOT IMPLEMENTED. Object type placeholder for connection type for SNMP traps. The physical port used to log in to the system. The serial port is always local to the equipment. The 10BaseT connector may be local, or remote, depending on if the configuration of network management port. The inband connection is the port carrying customer traffic."
		        ::=  {  sessionUserInterformation  2  }

--
-- AP Install group
--        
	apInstallationType	OBJECT-TYPE	
		SYNTAX			INTEGER { odu ( 1 ), odu-idu ( 2 )}
		ACCESS			read-only
		STATUS			mandatory
		DESCRIPTION		"The AirPair installation type.
						 
						 All ODU or IDU-ODU split"
		::=  {  apInstall  1  }

	apRxCableLoss	OBJECT-TYPE	
		SYNTAX			DisplayString  ( SIZE ( 0 .. 100  ) )
		ACCESS			read-only
		STATUS			mandatory
		DESCRIPTION		"Rx cable loss.
						 
						 Valid only when the installation type is IDU-ODU split"
		::=  {  apInstall  2  }

	apTxCableLoss	OBJECT-TYPE	
		SYNTAX			DisplayString  ( SIZE ( 0 .. 100  ) )
		ACCESS			read-only
		STATUS			mandatory
		DESCRIPTION		"Tx cable loss.
						 
						 Valid only when the installation type is IDU-ODU split"
		::=  {  apInstall  3  }


	apFan1Status	OBJECT-TYPE	
		SYNTAX			INTEGER {  off( 1 ), running ( 2 ), not-installed( 3), failed( 4) }
		ACCESS			read-only
		STATUS			mandatory
		DESCRIPTION		"The fan 1 status.
		
						Valid only when the installation type is IDU-ODU split"
		::=  {  apInstall  4  }

	apFan2Status	OBJECT-TYPE	
		SYNTAX			INTEGER {  off( 1 ), running ( 2 ), not-installed( 3), failed( 4) }
		ACCESS			read-only
		STATUS			mandatory
		DESCRIPTION		"The fan 2 status.
		
						Valid only when the installation type is IDU-ODU split"
		::=  {  apInstall  5 }
		
	apFanTestMode	OBJECT-TYPE	
		SYNTAX			INTEGER {  off( 1 ), on ( 2 ) }
		ACCESS			read-write
		STATUS			mandatory
		DESCRIPTION		"This operation turns on or off fan test mode.
						Fan test mode forces all fans in the system to on.
		
						Valid only when the installation type is IDU-ODU split"
		::=  {  apInstall  6 }

	apCableLossChange	OBJECT-TYPE	
		SYNTAX			DisplayString  ( SIZE ( 0 .. 100  ) )
		ACCESS			read-only
		STATUS			mandatory
		DESCRIPTION		"Cable loss change. Valid only when the installation type 
                                         is IDU-ODU split"
		::=  {  apInstall  7 }

--
-- HTTPS group
--        
	httpSecureCertificateStatus OBJECT-TYPE	
		SYNTAX			DisplayString  ( SIZE ( 0 .. 100  ) )
		ACCESS			read-only
		STATUS			mandatory
		DESCRIPTION		"Returns the HTTPS certificate status"						 
		::=  {  httpSecure  1  }


	httpSecureAccessForAdminUsers	OBJECT-TYPE	
		SYNTAX			INTEGER {  off( 1 ), on ( 2 ) }
		ACCESS			read-write
		STATUS			mandatory
		DESCRIPTION		"the HTTPS access requirement for Admin user group."
		::=  {  httpSecure  2  }

	httpSecureAccessForNocUsers	OBJECT-TYPE	
		SYNTAX			INTEGER {  off( 1 ), on ( 2 ) }
		ACCESS			read-write
		STATUS			mandatory
		DESCRIPTION		"the HTTPS access requirement for Noc user group."
		::=  {  httpSecure  3  }

	httpSecureAccessForSuperUsers	OBJECT-TYPE	
		SYNTAX			INTEGER {  off( 1 ), on ( 2 ) }
		ACCESS			read-write
		STATUS			mandatory
		DESCRIPTION		"the HTTPS access requirement for Super user group."
		::=  {  httpSecure  4  }

--
-- Giga Ethernet Qos
--
	qosEnable     OBJECT-TYPE	
		SYNTAX			INTEGER  { disabled ( 1 ) , enabled ( 2 ) } 
		ACCESS			read-write
		STATUS			mandatory
		DESCRIPTION		"Indicates whether gigabit Ethernet QOS is enabled."
		DEFVAL			{ disabled }
		::=  {  gigaEQos  1 }

--
-- 802.1p priorities assignment.
--

       dot1pValue0To7VsQueueMapping      OBJECT-TYPE	
		SYNTAX			 DisplayString ( SIZE ( 15 .. 32 ) ) 
		ACCESS			 read-write
		STATUS			 mandatory 
		DESCRIPTION		 "User queue assignments for Dot1P values 0 to 7.
                                         Dot1P value 0 is lowest priority and Dot1P value 7
                                         is highest priority. We have 4 user queues. Their corresponding 
                                         queue numbers are 1,2, 3, and 4, from lowest priority to highest 
                                         priority. The dot1p value to queue number mapping queue 
                                         numbers mustbe in an increasing order. 
                                         E.g. 1 1 2 2 3 3 4 4 is a valid mapping. 1 2 3 4 2 4 3 1 is NOT."
		::=  {  gigaEQos 2  }

   

--
-- Queue operation mode
--
	queueOperationMode	        OBJECT-TYPE	
		SYNTAX		        INTEGER  { disabled  ( 1 ), enabled ( 2 ) } 
		ACCESS			read-write
		STATUS			mandatory  
		DESCRIPTION		"This sets the user queue operation mode. (a) In expedite mode,
                                        User Queue 4 has 100% of CIR. User Queue 4 will be serviced 
                                        until it  is empty. (b) In non expedite mode, the sum of all CIRs 
                                        must be equal to 100%. Higher priority queues
                                        will be serviced first until the queues are emptied or
                                        the defined CIRs are reached."
		DEFVAL			{ 1 }
		::=  {  gigaEQos  3  }

--
-- user queues configuration.
--

        userQueue1To4CIRs	        OBJECT-TYPE
		SYNTAX			DisplayString ( SIZE ( 0 .. 32 ) ) 
		ACCESS			read-write
		STATUS			mandatory 
		DESCRIPTION		"Committeed Information Rate (CIR) assignments for user queues
                                         1 to 4. CIR is the percentage of maximum bandwidth for user 
                                         traffic. (a) In queue operation expedite mode, User Queue 1 has 
                                         100% of CIR. But CIRs can still be assigned for other queues. 
                                         This is because if there is not much traffic for queue 1, CIRs 
                                         of other queues can still be observed. However, the sum of
                                         CIRs for queues 2 to 4 should not be greater than 100%.  (b) In 
                                         queue operation priority mode, the sum of CIRs of user queues 1 
                                         to 4 must not be greater than 100%. In cosideration of Qos can be
                                         disabled, or less than 4 user queues can be used, the only condition
                                         to check if CIRs are vaild is that CIRs of used queues must not 
                                         be greater than 100%. Example1: 25 25 25 25. Example2: 25 50 25 0. 
                                         In example 2, the CIR of queue 1 is 25%, the CIR of queue 2 is 50%, 
                                         and CIR of queue 3 is 25%, and CIR of queue 4 is 0."

		::=  {  gigaEQos  4  }


        userQueue1To4PBS	        OBJECT-TYPE
		SYNTAX			DisplayString ( SIZE ( 0 .. 32 ) ) 
		ACCESS			read-write
		STATUS			mandatory 
		DESCRIPTION		"Peak Burst Size (PBS) for user queues 1 to 4. PBS is the percentage 
                                         of total user queue packet buffer size. The sum of PBS's of all 4
                                         user queues must not exceed 100%. Example1: 25 25 25 25. 
                                         Example 2: 75 25 0 0. In example 2, PBS for queue 1 is 75%, for queue 2
                                         is 25%, and for queue 3 and 4 is 0%."

		::=  {  gigaEQos  5  }


	defaultQosValue	                OBJECT-TYPE	
		SYNTAX		        INTEGER  (0 .. 7) 
		ACCESS			read-write
		STATUS			mandatory  
		DESCRIPTION		"Default Qos value is the assigned 802.1p value for the ethernet 
                                         frames that don't have dot1p tagged."
		DEFVAL			{ 0 }
		::=  {  gigaEQos  6  }


--
-- rapidLinkShutdown
--

	rlsEnable     OBJECT-TYPE	
		SYNTAX			INTEGER  { disabled ( 1 ) , enabled ( 2 ) } 
		ACCESS			read-write
		STATUS			mandatory
		DESCRIPTION		"The Rapid Link Shutdown feature: enabled or disabled.
                                         Changing this option requires a system reset."
		DEFVAL			{ disabled }
		::=  {  rapidLinkShutdown  1 }

	automaticLinkReestablish     OBJECT-TYPE	
		SYNTAX			INTEGER  { disabled ( 1 ) , enabled ( 2 ) } 
		ACCESS			read-write
		STATUS			mandatory
		DESCRIPTION		"If this feature is enabled, the link will be automatically reestablihedl 
                                         If this feature is disabled, the user must explicitly use the manualReestablish object
                                         to bring the link back up"
		DEFVAL			{ disabled }
		::=  {  rapidLinkShutdown  2 }


	manualLinkReestablish     OBJECT-TYPE	
		SYNTAX			INTEGER  { disabled ( 1 ) , enabled ( 2 ) } 
		ACCESS			read-write
		STATUS			mandatory
		DESCRIPTION		"This object is writeable ONLY if automaticLinkReestablish is set to disabled.
                                         The user explicitly brings the link back up by setting this object to enabled. 
                                         The user explicitly brings the link down by setting this object to disabled. 
                                         to bring the link back up"
		DEFVAL			{ disabled }
		::=  {  rapidLinkShutdown  3 }


	hysterisisErredFramesPerMilliSecond        
                                        OBJECT-TYPE	
		SYNTAX		        INTEGER   
		ACCESS			read-write
		STATUS			mandatory  
		DESCRIPTION		"The link will be automatically shut down when this number of erred
                                         modem frames threshold is exceeded during the time set in the 
                                         hysterisisErredMilliSeconds object.
                                         **NOTE: You must SET the writeRlsMonitorParametersToSystem object
                                                 to write this paramater to RAM. If you write and immediately
                                                 read this object, the previous value will be displayed.
                                                 You should SET all parameters in this folder first, and then write
                                                 to a '1' to the writeRlsMonitorParametersToSystem object.
                                                 You must also save the MIB via the writing the apSaveMIB object,
                                                 and then reset the system."
		DEFVAL			{ 0 }
		::=  {  rapidLinkShutdown  4  }
  
	hysterisisErredMilliSeconds        
                                        OBJECT-TYPE	
		SYNTAX		        INTEGER   
		ACCESS			read-write
		STATUS			mandatory  
		DESCRIPTION		"The time to determine a link that has excessive errors.
                                         The link will be automatically shut down when this number of milliseconds
                                         experiences the number of erred frames specified in the 
                                         hysterisisErredFramesPerMilliSecond object.
                                         **NOTE: You must SET the writeRlsMonitorParametersToSystem object
                                                 to write this paramater to RAM. If you write and immediately
                                                 read this object, the previous value will be displayed.
                                                 You should SET all parameters in this folder first, and then write
                                                 to a '1' to the writeRlsMonitorParametersToSystem object.
                                                 You must also save the MIB via the writing the apSaveMIB object,
                                                 and then reset the system."
		
                DEFVAL			{ 0 }
		::=  {  rapidLinkShutdown  5  }
  

	hysterisisUnerredFramesPerMilliSecond        
                                        OBJECT-TYPE	
		SYNTAX		        INTEGER   
		ACCESS			read-write
		STATUS			mandatory  
		DESCRIPTION		"The link will be automatically brought back up when the number of erred
                                         modem frames is less than this value ( only if automaticLinkReestablish 
                                         is set to enabled). 
                                         This threshold value cannot be crossed for the duration of time specified in the  
                                         hysterisisUnerredMilliSeconds object.
                                         **NOTE: You must SET the writeRlsMonitorParametersToSystem object
                                                 to write this paramater to RAM. If you write and immediately
                                                 read this object, the previous value will be displayed.
                                                 You should SET all parameters in this folder first, and then write
                                                 to a '1' to the writeRlsMonitorParametersToSystem object.
                                                 You must also save the MIB via the writing the apSaveMIB object,
                                                 and then reset the system."

		DEFVAL			{ 0 }
		::=  {  rapidLinkShutdown  6  }
  
	hysterisisUnerredMilliSeconds        
                                        OBJECT-TYPE	
		SYNTAX		        INTEGER   
		ACCESS			read-write
		STATUS			mandatory  
		DESCRIPTION		"The time block to use to determine if the link is error free enough to 
                                         warrant it to automatically reestablish itself ( only if automaticLinkReestablish 
                                         is set to enabled).
                                         The link will be brought back up automatically when this number of milliseconds
                                         experiences less the number of acceptable erred frames specified in the 
                                         hysterisisUnerredFramesPerMilliSecond object.
                                         **NOTE: You must SET the writeRlsMonitorParametersToSystem object
                                                 to write this paramater to RAM. If you write and immediately
                                                 read this object, the previous value will be displayed.
                                                 You should SET all parameters in this folder first, and then write
                                                 to a '1' to the writeRlsMonitorParametersToSystem object.
                                                 You must also save the MIB via the writing the apSaveMIB object,
                                                 and then reset the system."

		DEFVAL			{ 0 }
		::=  {  rapidLinkShutdown  7  }
  
	writeRlsMonitorParametersToSystem        
                                        OBJECT-TYPE	
		SYNTAX		        INTEGER   
		ACCESS			read-write
		STATUS			mandatory  
		DESCRIPTION		"This writes the following parameters to RAM:
                                         hysterisisErredFramesPerMilliSecond,
                                         hysterisisErredMilliSeconds,
                                         hysterisisUnerredFramesPerMilliSecond,
                                         hysterisisUnerredMilliSeconds.
                                         Reading this object returns '1'."
		DEFVAL			{ 0 }
		::=  {  rapidLinkShutdown  8  }


        rlsAdvancedAlgorithm	        OBJECT-TYPE	
		SYNTAX			INTEGER  { off ( 1 ) , on ( 2 ) } 
		ACCESS			read-write
		STATUS			mandatory
		DESCRIPTION		"When it is on RLS advanced algorithm is used, otherwise
                                         RLS advanced algorithm is not used."
		DEFVAL			{ off }
		::=  {  rapidLinkShutdown 9  }

 	rlsSampleTimeInMilliSeconds        
                                        OBJECT-TYPE	
		SYNTAX		        INTEGER   
		ACCESS			read-write
		STATUS			mandatory  
		DESCRIPTION		""

		DEFVAL			{ 0 }
		::=  {  rapidLinkShutdown  10  }

--
-- sntp
--

	sntpEnable	                OBJECT-TYPE	
		SYNTAX			INTEGER  { disabled ( 1 ) , enabled ( 2 ) } 
		ACCESS			read-write
		STATUS			mandatory
		DESCRIPTION		"Indicates whether SNTP feature is enabled."
		DEFVAL			{ enabled }
		::=  {  sntp  1 }

	sntpOffset	                OBJECT-TYPE	
-- This value is 10 times the actual value.
		SYNTAX			INTEGER  ( -140 .. 140  ) 
		ACCESS			read-write
		STATUS			mandatory
		DESCRIPTION		"System time offset from GMT."
		DEFVAL 			{ -40 }
		::=  {  sntp  2  }


	sntpServerTable	        OBJECT-TYPE
		SYNTAX		SEQUENCE OF SntpServerEntry
		ACCESS		not-accessible
		STATUS		mandatory
		DESCRIPTION	"Table containing sntp server entries"
		::=  { sntp  3 }

	sntpServerEntry	        OBJECT-TYPE
		SYNTAX		SntpServerEntry
		ACCESS		not-accessible
		STATUS		mandatory
		DESCRIPTION	"Contains the sntp server information"
		INDEX		{  sntpServerIndex  }
		::=  { sntpServerTable 1 }

	SntpServerEntry  ::=  SEQUENCE {
		sntpServerIndex       INTEGER,
		sntpServerIpAddress   IpAddress,
		sntpServerStatus      INTEGER,
		sntpServerStratum     INTEGER
		}
		
	sntpServerIndex    	        OBJECT-TYPE	
		SYNTAX			INTEGER
		ACCESS			read-only
		STATUS			mandatory
		DESCRIPTION		"A unique value for each server."
		::=  {  sntpServerEntry  1  }


	sntpServerIpAddress	        OBJECT-TYPE	
		SYNTAX			IpAddress
		ACCESS			read-write
		STATUS			mandatory
		DESCRIPTION		"The IP address of the server."
		::=  {  sntpServerEntry  2  }


	sntpServerStatus	        OBJECT-TYPE	
		SYNTAX			INTEGER  { good (1) , failed (2) } 
		ACCESS			read-only
		STATUS			mandatory
		DESCRIPTION		"The status of the sntp server."
		::=  {  sntpServerEntry  3  }


	sntpServerStratum	OBJECT-TYPE	
		SYNTAX			INTEGER   
		ACCESS			read-only
		STATUS			mandatory
		DESCRIPTION		"Specifies the stratum of a server, 0 for failed server" 
		::=  {  sntpServerEntry  4  }
                
--
-- logs
--

	eventLogEnable	                OBJECT-TYPE	
		SYNTAX			INTEGER  { disabled ( 1 ) , enabled ( 2 ) } 
		ACCESS			read-write
		STATUS			mandatory
		DESCRIPTION		"Indicates whether event log is enabled."
		DEFVAL			{ enabled }
		::=  {  apLogs  1 }
                
        perfmLogEnable	                OBJECT-TYPE	
		SYNTAX			INTEGER  { disabled ( 1 ) , enabled ( 2 ) } 
		ACCESS			read-write
		STATUS			mandatory
		DESCRIPTION		"Indicates whether performance log is enabled."
		DEFVAL			{ enabled }
		::=  {  apLogs  2 }

        perfmLogInterval	        OBJECT-TYPE	
		SYNTAX			DisplayString  ( SIZE ( 0 .. 10  ) ) 
		ACCESS			read-write
		STATUS			mandatory
		DESCRIPTION		"Performance statistics are logged periodically by this interval."
		::=  {  apLogs  3 }

--
-- radius
--
	superUserAuthentication	                OBJECT-TYPE	
		SYNTAX			INTEGER  { on ( 1 ) , off( 2 ) } 
		ACCESS			read-write
		STATUS			mandatory
		DESCRIPTION		" The set strict mode on or off"
		DEFVAL			{ off }
		::=  {  radius 1 }

	serverTimeOut	                OBJECT-TYPE	
		SYNTAX			INTEGER
		ACCESS			read-only
		STATUS			mandatory
		DESCRIPTION		" Timeout period for authentication requests"
		DEFVAL			{ 0 }
		::=  {  radius 2 }


	serverDeadTime	                OBJECT-TYPE	
		SYNTAX			INTEGER 
		ACCESS			read-only
		STATUS			mandatory
		DESCRIPTION		" Time to declare an unresponsive server 'dead'"
		DEFVAL			{ 0 }
		::=  {  radius 3 }

 	serverReTransmit		                OBJECT-TYPE	
		SYNTAX			INTEGER  { strict ( 1 ) , notstrict ( 2 ) } 
		ACCESS			read-only
		STATUS			mandatory
		DESCRIPTION		" Maximum number of retransmits to an unresponsive server"
		DEFVAL			{ enabled }
		::=  {  radius 4 }



	radiusServerTable	        OBJECT-TYPE
		SYNTAX		SEQUENCE OF RadiusServerEntry
		ACCESS		not-accessible
		STATUS		mandatory
		DESCRIPTION	"Table containing radius server entries"
		::=  { radius 5 }

	radiusServerEntry	        OBJECT-TYPE
		SYNTAX		RadiusServerEntry
		ACCESS		not-accessible
		STATUS		mandatory
		DESCRIPTION	"Contains the sntp server information"
		INDEX		{  radiusServerIndex }
		::=  { radiusServerTable 1 }

	RadiusServerEntry::=  SEQUENCE {
		radiusServerIndex       INTEGER,
		cfgdHostIpAddress       IpAddress,
		activeHostIpAddress     IpAddress
		}
		
	radiusServerIndex    	        OBJECT-TYPE	
		SYNTAX			INTEGER
		ACCESS			read-only
		STATUS			mandatory
		DESCRIPTION		"A unique value for each server."
		::=  {  radiusServerEntry 1  }


	cfgdHostIpAddress	        OBJECT-TYPE	
		SYNTAX			IpAddress
		ACCESS			read-write
		STATUS			mandatory
		DESCRIPTION		"The IP address of the configured radius server."
		::=  {  radiusServerEntry 2  }


	activeHostIpAddress	        OBJECT-TYPE	
		SYNTAX			IpAddress
		ACCESS			read-only
		STATUS			mandatory
		DESCRIPTION		"The IP address of the active radius server."
		::=  {  radiusServerEntry 3  }





--
-- TRAP DEFINITIONS
--                   		

	coldStart	TRAP-TYPE
        	ENTERPRISE  snmp  
        	DESCRIPTION		
                        "A coldStart trap signifies that the sending protocol entity is reinitializing itself such that the agent's configuration or the protocol entity implementation may be altered."
        ::= 0

-- for generic traps real trap value of linkDwon is 2.
	linkDown	TRAP-TYPE
        	ENTERPRISE  snmp  
                VARIABLES {ifIndex}
        	DESCRIPTION		
        	        "A linkDown trap signifies that the sending protocol entity recognizes a failure in one of the communication links represented in the agent's configuration."
        ::= 1

-- for generic traps real trap value of linkup is 3.

	linkUp	TRAP-TYPE
        	ENTERPRISE  snmp  
                VARIABLES {ifIndex}
        	DESCRIPTION		 
        		"A linkUp trap signifies that the sending protocol entity recognizes that one of the communication links represented in the agent's configuration has come up."		 
        ::= 2


        explicitAuthenticationFailureV1Trap	TRAP-TYPE
        	ENTERPRISE  apSnmpTraps  
        	DESCRIPTION		"Authentication of the peer AirPair node has failed. The severity is critical, the probable cause is an incorrect authentication configuration on AirPair faulty cable between the modem and radio, and recommended course of action is to check both ends of the link."
        ::= 3

	autoNegotiationDuplexMismatchV1Trap	TRAP-TYPE
        	ENTERPRISE  apSnmpTraps
        	DESCRIPTION		"The AirPair ethernet interface has a mismatch in duplex. The severity is major, the probable cause is an incorrect configuration of the switch or router connected to AirPair, or the AirPair autonegotion settings. The recommended course of action is to check the connection."
        ::= 4

	modemLossOfSignalLockFromDemodulatorV1Trap	TRAP-TYPE
        	ENTERPRISE  apSnmpTraps
        	DESCRIPTION		"Loss of signal lock from the demodulator. The severity is critical, the probable cause is lost synchronization with the far end, and recommended course of action is to check the operational state of both ends of the link."
        ::= 5

	modemUncorrectedBerThresholdExceededV1Trap	TRAP-TYPE
        	ENTERPRISE  apSnmpTraps
        	DESCRIPTION		"The uncorrected BER threshold has been exceeded. The severity is major, the probable cause is physical interference in the air link or misalignment of the radios or severe weather conditions, and recommended course of action is to check the line of site between the air pair nodes."
        ::= 6

	modemModulatorPllLockFailureV1Trap	TRAP-TYPE
        	ENTERPRISE  apSnmpTraps
        	DESCRIPTION		"Modulator PLL failure. The severity is critical, the probable cause a faulty modem card within AirPair, and recommended course of action is to replace the modem unit."
        ::= 7

	modemModulatorLossOfSyncBytesV1Trap	TRAP-TYPE
        	ENTERPRISE  apSnmpTraps
        	DESCRIPTION		"Loss of sync bytes at the input of the modulator. The severity is critical, the probable cause is physical interference in the air link, and recommended course of action is to check the line of site between the air pair nodes."
        ::= 8

	modemModulatorInputFifoErrorV1Trap	TRAP-TYPE
        	ENTERPRISE  apSnmpTraps
        	DESCRIPTION		"Overrun or underrun of the FIFO contained inside the modulator. The severity is critical, the probable cause is electrical interference, and recommended course of action is to reset the modem unit, or relpace the modem unit."
        ::= 9

	modemModulatorInputDataErrorV1Trap	TRAP-TYPE
        	ENTERPRISE  apSnmpTraps
        	DESCRIPTION		"All ones or all zeroes at the input of the modulator. The severity is critical, the probable cause is electrical interference, and recommended course of action is to reset the modem unit, or replace the modem unit"
        ::= 10

	modemSnrBelowThresholdV1Trap	TRAP-TYPE
        	ENTERPRISE  apSnmpTraps
        	DESCRIPTION		"The demodulator SNR performance worse than programmed levels. The severity is major, the probable cause is physical interference in the air link path or misalignment of the radios or severe weather conditions, and recommended course of action is to check the line of site between the air pair nodes."
        ::= 11

	radioPLDROLostLockV1Trap	TRAP-TYPE
        	ENTERPRISE  apSnmpTraps
        	DESCRIPTION		"The PLDRO/LO has lost lock on the radio. The severity is critical, the probable cause a faulty radio unit within AirPair, and recommended course of action is to replace the radio unit."
        ::= 12


	radioLostCommunicationV1Trap	TRAP-TYPE
        	ENTERPRISE  apSnmpTraps
       	        DESCRIPTION		"RS232 communication lost between AIRPAIR and the radio. The severity is critical, the probable cause is a faulty cable between the modem and radio, and recommended course of action is to check the connection."
        ::= 13

	radioMismatchV1Trap	TRAP-TYPE
        	ENTERPRISE  apSnmpTraps
        	DESCRIPTION		"The radio connected to the AIRPAIR modem does not match the frequency programmed into the modem unit. The severity is major, the probable cause is an incorrectly programmed modem or an incorrect radio type connected to the modem, and recommended course of action is to check the modem frequency settings and radio hardware version number or serial number."
        ::= 14

	radioPowerAmpV1Trap	TRAP-TYPE
        	ENTERPRISE  apSnmpTraps
        	DESCRIPTION		"The power amplifier on the radio is not operating within normal operating specifications. The severity is critical, the probable cause a faulty radio unit within AirPair, and recommended course of action is to replace the radio unit."
        ::= 15

	ifTxSynthUnlockedV1Trap	TRAP-TYPE
        	ENTERPRISE  apSnmpTraps
        	DESCRIPTION		"The IF card within the modem unit has a Transmit Synthesizer which is not locked and as a result will not transmit. The severity is critical, the probable cause an incorrectly programmed frequency setting in the modem or a faulty IF card, and recommended course of action is to check frequency setting in the modem or to replace the modem unit."
        ::= 16

	ifRxSynthUnlockedV1Trap	TRAP-TYPE
        	ENTERPRISE  apSnmpTraps
        	DESCRIPTION		"The IF card within the modem unit has a Receive Synthesizer which is not locked. The severity is critical, the probable cause an incorrectly programmed frequency setting in the modem or a faulty IF card, and recommended course of action is to check frequency setting in the modem or to replace the modem unit."
        ::= 17

	
        ttySessionCommencedV1Trap	TRAP-TYPE
        	ENTERPRISE  apSnmpTraps
		VARIABLES   { ttySessionUserName,
			      ttySessionUserConnectionType }
        	
                DESCRIPTION		"A person has successfully gained access to the ascii management port (telnet, local management port, or HTTP). The username is included in the Trap."
        ::= 18

	ttySessionTerminatedV1Trap	TRAP-TYPE
        	ENTERPRISE  apSnmpTraps
		VARIABLES   { ttySessionUserName,
			      ttySessionUserConnectionType }
        	DESCRIPTION		"A person has logged out of an ascii management port (telnet, local management port, or HTTP). The username is included in the Trap."
        ::= 19


        rslBelowThresholdV1Trap	        TRAP-TYPE
        	ENTERPRISE  apSnmpTraps
        	DESCRIPTION     "The RSL has been detected below its minimum threshold."
        ::= 20
	
        droppedFramesThresholdExceededV1Trap	TRAP-TYPE
        	ENTERPRISE  apSnmpTraps
        	DESCRIPTION     "The ethernet dropped frames threshold has been detected above its threshold value."
        ::= 21
        
        bwUtilizationThresholdExceededV1Trap	TRAP-TYPE
        	ENTERPRISE  apSnmpTraps
        	DESCRIPTION     "The ethernet bandwidth threshold has been detected above its threshold value."
        ::= 22
        
        explicitAuthFailureClearedV1Trap	TRAP-TYPE
        	ENTERPRISE  apSnmpTraps
        	DESCRIPTION		"The condition has cleared. The peer node is now authenticated."
        ::= 23

 		
	autoNegDuplexMismatchClearedV1Trap	TRAP-TYPE
        	ENTERPRISE  apSnmpTraps
        	DESCRIPTION		"The condition has cleared. The Ethernet connection is not experiencing auto-negotiation duplex mismatch."
        ::= 24

	lossOfSyncSigFromDemoClearedV1Trap	TRAP-TYPE
        	ENTERPRISE  apSnmpTraps
        	DESCRIPTION		"The condition has cleared. The demodulator is synchronized."
        ::= 25
                
	uncorrectedBerThresExceededClearedV1Trap	TRAP-TYPE
        	ENTERPRISE  apSnmpTraps
        	DESCRIPTION		"The condition has cleared. The demodulator uncorrected BER is now below its minimum threshold value."
        ::= 26
                
	modemModPLLFailureClearedV1Trap	TRAP-TYPE
        	ENTERPRISE  apSnmpTraps
        	DESCRIPTION		"The condition has cleared. The modem PLL is not failing."
        ::= 27
                
	modemModLossOfSyncBytesClearedV1Trap	TRAP-TYPE
        	ENTERPRISE  apSnmpTraps
        	DESCRIPTION		"The condition has cleared. The modem is not experiencing loss of synch bytes."
        ::= 28
                
	modemModInputFifoOverUnderClearedV1Trap	TRAP-TYPE
        	ENTERPRISE  apSnmpTraps
        	DESCRIPTION		"The condition has cleared. The modem is not experiencing input FIFO over/under runs."
        ::= 29
                
	modemModInputDataInacClearedV1Trap	TRAP-TYPE
        	ENTERPRISE  apSnmpTraps
        	DESCRIPTION		"The condition has cleared. The modem is not experiencing data inactivity."
        ::= 30
                
	snrBelowThresholdClearedV1Trap	TRAP-TYPE
        	ENTERPRISE  apSnmpTraps
        	DESCRIPTION		"The condition has cleared. SNR is now above its minimum threshold value."
        ::= 31
                
	radioPLDROLostLockClearedV1Trap	TRAP-TYPE
        	ENTERPRISE  apSnmpTraps
        	DESCRIPTION		"The condition has cleared. The radio PLDRO/LO lost lock condition has cleared."
        ::= 32
        
        
        radioLostCommunicationClearedV1Trap	TRAP-TYPE
        	ENTERPRISE  apSnmpTraps
        	DESCRIPTION     "The condition has cleared. RS232 communication has been re-establisted between AIRPAIR and the radio."
        ::= 33

        
        radioMismatchClearedV1Trap	TRAP-TYPE
        	ENTERPRISE  apSnmpTraps
        	DESCRIPTION     "The condtion has cleared. The radio matches the programmed parameters in the modem."
        ::= 34

        radioPowerAmpClearedV1Trap	TRAP-TYPE
        	ENTERPRISE  apSnmpTraps
        	DESCRIPTION     "The condtion has cleared. The radio Power Amp is not in the failed state."
        ::= 35
        
        ifTxSynthUnlockedClearedV1Trap	TRAP-TYPE
        	ENTERPRISE  apSnmpTraps
        	DESCRIPTION     "The condtion has cleared. The IF stage transmit synthesizer is now locked."
        ::= 36
        
        ifRxSynthUnlockedClearedV1Trap	TRAP-TYPE
        	ENTERPRISE  apSnmpTraps
        	DESCRIPTION     "The condtion has cleared. The IF stage receive synthesizer is now locked."
        ::= 37
        
        

        rslBelowThresholdClearedV1Trap        TRAP-TYPE
        	ENTERPRISE  apSnmpTraps
        	DESCRIPTION     "The condition has cleared. RSL is now above its minimum threshold."
        ::= 38



        droppedFramesThresholdExceededClearedV1Trap        TRAP-TYPE
        	ENTERPRISE  apSnmpTraps
        	DESCRIPTION     "The condition has cleared.The ethernet dropped frames threshold is now below its threshold value."
        ::= 39
        

        bwUtilizationThresholdExceededClearedV1Trap        TRAP-TYPE
        	ENTERPRISE  apSnmpTraps
        	DESCRIPTION     "The condition has cleared. The ethernet bandwidth threshold is now below its threshold value."
        ::= 40
        
       rxIfCableLossExceededV1Trap        TRAP-TYPE
        	ENTERPRISE  apSnmpTraps
        	DESCRIPTION     "The Rx cable loss has exceeded limit.
        	
        	This trap is only valid when the AirPair installation type is IDU-ODU split"
        ::= 41
        
     rxIfCableLossExceededClearedV1Trap        TRAP-TYPE
        	ENTERPRISE  apSnmpTraps
        	DESCRIPTION     "The condition has cleared. The Rx cable loss is now within limit.
        	
        	This trap is only valid when the AirPair installation type is IDU-ODU split"
        ::= 42
        

     txIfCableLossExceededV1Trap        TRAP-TYPE
        	ENTERPRISE  apSnmpTraps
        	DESCRIPTION     "The Tx cable loss has exceeded limit.
        	
        	This trap is only valid when the AirPair installation type is IDU-ODU split"
        ::= 43
        
     txIfCableLossExceededClearedV1Trap        TRAP-TYPE
        	ENTERPRISE  apSnmpTraps
        	DESCRIPTION     "The condition has cleared. The Tx cable loss is now within limit.
        	
        	This trap is only valid when the AirPair installation type is IDU-ODU split"
        ::= 44    
        
     fan1FailedV1Trap        TRAP-TYPE
        	ENTERPRISE  apSnmpTraps
        	DESCRIPTION     "The Fan1 has failed.
        	
        	This trap is only valid when the AirPair installation type is IDU-ODU split"
        ::= 45
        
     fan1FailedClearedV1Trap        TRAP-TYPE
        	ENTERPRISE  apSnmpTraps
        	DESCRIPTION     "The condition has cleared. The fan1 is running normally.
        	
        	This trap is only valid when the AirPair installation type is IDU-ODU split"
        ::= 46
        
     fan2FailedV1Trap        TRAP-TYPE
        	ENTERPRISE  apSnmpTraps
        	DESCRIPTION     "The Fan2 has failed.
        	
        	This trap is only valid when the AirPair installation type is IDU-ODU split"
        ::= 47
        
     fan2FailedClearedV1Trap        TRAP-TYPE
        	ENTERPRISE  apSnmpTraps
        	DESCRIPTION     "The condition has cleared. The fan2 is running normally.
        	
        	This trap is only valid when the AirPair installation type is IDU-ODU split"
        ::= 48


     modemCardMismatchedHardwareFirmwareV1Trap  TRAP-TYPE
        	ENTERPRISE  apSnmpTraps
        	DESCRIPTION     "The modem card has firmware that is incompatible with the hardware. The card will not operate properly."
        ::= 49
        
     modemCardMismatchedHardwareFirmwareClearedV1Trap   TRAP-TYPE
        	ENTERPRISE  apSnmpTraps
        	DESCRIPTION     "The condition has cleared. The modem card does not have incompatible firmware with the hardware."
        ::= 50



     atpcConfigMismatchV1Trap      TRAP-TYPE
        	ENTERPRISE         apSnmpTraps
        	DESCRIPTION        "ATPC configuration mismatch in the Airpair systems. ATPC is 
                                    enabled at one system, but ATPC is not enabled at the other
                                    system. "
        ::= 51

     atpcConfigMismatchClearedV1Trap        TRAP-TYPE
        	ENTERPRISE         apSnmpTraps
        	DESCRIPTION        "ATPC configuration mismatch in the Airpair systems is cleared. 
        	        	    Both systems enabled ATPC."
        ::= 52


    radioHiPwrOptM1V1Trap         TRAP-TYPE
        	ENTERPRISE         apSnmpTraps
        	DESCRIPTION        "When hi-power radio is used, hi-power gate M1 drain current 
                                    is out of lower or upper limits."
        ::= 53

    radioHiPwrOptM1ClearedV1Trap     TRAP-TYPE
        	ENTERPRISE            apSnmpTraps
        	DESCRIPTION           "When hi-power radio is used, hi-power gate M1 drain current 
                                       is between lower and upper limits."
        ::= 54

    radioHiPwrOptM2V1Trap          TRAP-TYPE
        	ENTERPRISE         apSnmpTraps
        	DESCRIPTION        "When hi-power radio is used, hi-power gate M2 drain current 
                                    is out of lower or upper limits."
        ::= 55

    radioHiPwrOptM2ClearedV1Trap     TRAP-TYPE
        	ENTERPRISE            apSnmpTraps
        	DESCRIPTION           "When hi-power radio is used, hi-power gate M2 drain current 
                                       is between lower and upper limits."
        ::= 56
                
    radioHiPwrTxDetectorV1Trap       TRAP-TYPE
        	ENTERPRISE           apSnmpTraps
        	DESCRIPTION          "When hi-power radio is used, hi-power tx detector dBm value 
                                      is smaller than limit."
        ::= 57

    radioHiPwrTxDetectorClearedV1Trap     TRAP-TYPE
        	ENTERPRISE                apSnmpTraps
        	DESCRIPTION               "When hi-power radio is used, hi-power tx detector dBm 
                                           value is not smaller than limit."
        ::= 58

    sntpServersUnreachableV1Trap       TRAP-TYPE
        	ENTERPRISE           apSnmpTraps
        	DESCRIPTION          "Can't reach any of the sntp servers"
        ::= 59

    sntpServersUnreachableClearedV1Trap     TRAP-TYPE
        	ENTERPRISE                apSnmpTraps
        	DESCRIPTION               "At least one of SNTP servers is reachable"
        ::= 60

    rlsMismatchV1Trap       TRAP-TYPE
        	ENTERPRISE                apSnmpTraps
        	DESCRIPTION               "RLS mismatch"
        ::= 61

    rlsMismatchClearedV1Trap              TRAP-TYPE
        	ENTERPRISE                apSnmpTraps
        	DESCRIPTION               "RLS mismatch cleared"
        ::= 62

    rLSShutdownActivatedv1Trap            TRAP-TYPE
        	ENTERPRISE                apSnmpTraps
        	DESCRIPTION               "RLS shutdown is activated"
        ::= 63

    rLSShutdownActivatedClearedV1Trap              TRAP-TYPE
        	ENTERPRISE                apSnmpTraps
        	DESCRIPTION               "RLS shutdown is not activated"
        ::= 64
       
       
       
    --
-- FREQUENCY FILE RELATED TRAPS
--
   frequencyFileInvalidV1Trap	        TRAP-TYPE
		ENTERPRISE              apSnmpTraps
        	DESCRIPTION             "When the executing frequency file is invalid, 
					this trap is generated."
        ::= 65



   optionalParaNotEntFreqFileV1Trap	        TRAP-TYPE
		ENTERPRISE                apSnmpTraps
        	DESCRIPTION               "when the optional parameters are not entered in frequency file,
                                           and the system boots up, this trap is generated."
        ::= 66



   progRadioBandNotFoundFreqFileV1Trap	        TRAP-TYPE
		ENTERPRISE                apSnmpTraps
        	DESCRIPTION               "when the executing frequency file doesn't contain the info related to programmed
                                            radio band, this trap is generated."
        ::= 67

   redundancySwitchOverSuccessTrap					TRAP-TYPE				
		ENTERPRISE                apSnmpTraps
        	DESCRIPTION               "Redundancy radio switch over success"
        ::= 68

    redundancySwitchOverFailedTrap					TRAP-TYPE				
		ENTERPRISE                apSnmpTraps
        	DESCRIPTION               "Redundancy radio switch over failed"
        ::= 69

    radioNoAtpcSupportTrap					TRAP-TYPE				
		ENTERPRISE                apSnmpTraps
        	DESCRIPTION               "Radio does not support atpc"
        ::= 70

    radioNoAtpcSupportClearedTrap					TRAP-TYPE				
		ENTERPRISE                apSnmpTraps
        	DESCRIPTION               "Radio does not support atpc cleared"
        ::= 71			
     			 		
    radioFirmwareMismatchTrap					TRAP-TYPE				
		ENTERPRISE                apSnmpTraps
        	DESCRIPTION               "Radio firmware on radio and on modem card mismatch"
        ::= 72	

    radioFirmwareMismatchClearedTrap        			TRAP-TYPE				
		ENTERPRISE                apSnmpTraps
        	DESCRIPTION               "Radio firmware mismatch cleared"
        ::= 73	

    redundancySwitchInitByLocalend					TRAP-TYPE				
		ENTERPRISE                apSnmpTraps
        	DESCRIPTION               "Radio switch initiated by local end"
        ::= 74	
				
    redundancySwitchInitByPeer					TRAP-TYPE				
		ENTERPRISE                apSnmpTraps
        	DESCRIPTION               "Radio switch initiated by peer"
        ::= 75

    aamConfigMisMatch					TRAP-TYPE				
		ENTERPRISE                apSnmpTraps
        	DESCRIPTION               "Adaptive modulation configuration mismatch"
        ::= 76	

    aamConfigMisMatchClear					TRAP-TYPE				
		ENTERPRISE                apSnmpTraps
        	DESCRIPTION               "Adaptive modulation configuration mismatch cleared"
        ::= 77	

    aamQpskActive					TRAP-TYPE				
		ENTERPRISE                apSnmpTraps
        	DESCRIPTION               "Adaptive modulation on and system running on QPSK modulation"
        ::= 78	

    aamQpskActiveCleared					TRAP-TYPE				
		ENTERPRISE                apSnmpTraps
        	DESCRIPTION               "Adaptive modulation on  system running on higher modulation"
        ::= 79		

    primaryRadioFaultyTrap					TRAP-TYPE				
		ENTERPRISE                apSnmpTraps
        	DESCRIPTION               "Primary radio is faulty"
        ::= 80	

    primaryRadioFaultyClearedTrap					TRAP-TYPE				
		ENTERPRISE                apSnmpTraps
        	DESCRIPTION               "primary radio is not faulty anymore"
        ::= 81	

    radioSerialNumberMismatchTrap					TRAP-TYPE				
		ENTERPRISE                apSnmpTraps
        	DESCRIPTION               "Redundancy, Radio Serial number mismatch."
        ::= 82	

    radioSerialNumberMismatchTrapClearedTrap					TRAP-TYPE				
		ENTERPRISE                apSnmpTraps
        	DESCRIPTION               "Redundancy, Radio Serial number mismatch cleared."
        ::= 83

    excessiveCableLossChangeTrap	  TRAP-TYPE				
		ENTERPRISE                apSnmpTraps
        	DESCRIPTION               "Excessive transmit cable loss change."
        ::= 84	

    excessiveCableLossChangeClearedTrap					TRAP-TYPE				
		ENTERPRISE                apSnmpTraps
        	DESCRIPTION               "Excessive transmit cable loss change cleared."
        ::= 85

   
END
