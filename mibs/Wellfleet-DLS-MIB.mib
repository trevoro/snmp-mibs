Wellfleet-DLS-MIB DEFINITIONS ::= BEGIN

-- Created by mdl2asn version 3.1
-- Creation date: Wed Aug 30 16:39:40 EDT 1995


    IMPORTS

      IpAddress, Counter, Gauge
        FROM RFC1155-SMI
      OBJECT-TYPE
        FROM RFC-1212
      DisplayString
        FROM RFC1213-MIB
      wfDlsGroup
        FROM Wellfleet-COMMON-MIB;


    wfDls		OBJECT IDENTIFIER ::= { wfDlsGroup 1 }

    wfDlsDelete OBJECT-TYPE
        SYNTAX	INTEGER {
    		    created(1),
    		    deleted(2)
    		}
        ACCESS	read-write
        STATUS	mandatory
        DESCRIPTION
                "Create/Delete parameter. Default is created. Users perform an SNMP SET
                operation on this object in order to create/delete DLSw"
        DEFVAL	{ created }
        ::= { wfDls 1 }

    wfDlsDisable OBJECT-TYPE
        SYNTAX	INTEGER {
    		    enabled(1),
    		    disabled(2)
    		}
        ACCESS	read-write
        STATUS	mandatory
        DESCRIPTION
                "Enable/Disable parameter. Default is enabled. Users perform an SNMP SET
                operation on this object in order to enable/disable DLSw"
        DEFVAL	{ enabled }
        ::= { wfDls 2 }

    wfDlsState OBJECT-TYPE
        SYNTAX	INTEGER {
    		    up(1),
    		    down(2),
    		    init(3),
    		    notpresent(4)
    		}
        ACCESS	read-only
        STATUS	mandatory
        DESCRIPTION
                "The current state of DLSw"
        DEFVAL	{ down }
        ::= { wfDls 3 }

    wfDlsTcpWindowSize OBJECT-TYPE
        SYNTAX	INTEGER(5000..64000)
        ACCESS	read-write
        STATUS	mandatory
        DESCRIPTION
                "The size in bytes of the windows used for the DLSw TCP connections"
        DEFVAL	{ 8000 }
        ::= { wfDls 4 }

    wfDlsVirtualRing OBJECT-TYPE
        SYNTAX	INTEGER
        ACCESS	read-write
        STATUS	mandatory
        DESCRIPTION
                "The virtual ring number for the TCP/IP cloud. Valid values (1-4095)"
        ::= { wfDls 5 }

    wfDlsInternalLanId OBJECT-TYPE
        SYNTAX	INTEGER
        ACCESS	read-write
        STATUS	mandatory
        DESCRIPTION
                "The source routing internal lan id. Valid Values (1-4095)"
        ::= { wfDls 6 }

    wfDlsBridgeId OBJECT-TYPE
        SYNTAX	INTEGER
        ACCESS	read-write
        STATUS	mandatory
        DESCRIPTION
                "The source routing base bridge number.  Valid Values (1-15)"
        ::= { wfDls 7 }

    wfDlsMaxSlotSessions OBJECT-TYPE
        SYNTAX	INTEGER(1..10000)
        ACCESS	read-write
        STATUS	mandatory
        DESCRIPTION
                "The maximum number of LLC2 sessions to support per slot"
        DEFVAL	{ 200 }
        ::= { wfDls 8 }

    wfDlsTotalCircuits OBJECT-TYPE
        SYNTAX	Counter
        ACCESS	read-only
        STATUS	mandatory
        DESCRIPTION
                "A current count of the total number of DLSw circuits established"
        ::= { wfDls 9 }

    wfDlsVirtualRingMtu OBJECT-TYPE
        SYNTAX	INTEGER(1..16383)
        ACCESS	read-write
        STATUS	mandatory
        DESCRIPTION
                "The MTU to use in explorers generated by this DLSw. It should reflect
                the minimum MTU size of the entire network including the remote LANs.
                Valid values (> 0)"
        DEFVAL	{ 1500 }
        ::= { wfDls 10 }

    wfDlsMacAgeTime OBJECT-TYPE
        SYNTAX	Gauge(0..4294967295)
        ACCESS	read-write
        STATUS	mandatory
        DESCRIPTION
                "The time in seconds before inactive MAC addresses will be aged out of
                the cache. Valid values (> 20)"
        DEFVAL	{ 300 }
        ::= { wfDls 11 }

    wfDlsNbAgeTime OBJECT-TYPE
        SYNTAX	Gauge(21..4294967295)
        ACCESS	read-write
        STATUS	mandatory
        DESCRIPTION
                "The time in seconds before inactive NetBIOS names will be aged out of the
                cache. Valid values (> 20)"
        DEFVAL	{ 300 }
        ::= { wfDls 12 }

    wfDlsUnconfPeerReject OBJECT-TYPE
        SYNTAX	INTEGER {
    		    accepted(1),
    		    rejected(2)
    		}
        ACCESS	read-write
        STATUS	mandatory
        DESCRIPTION
                "Allow establishment of TCP connections from peers not in the Peer Table"
        DEFVAL	{ accepted }
        ::= { wfDls 13 }

    wfDlsDebugLevel1 OBJECT-TYPE
        SYNTAX	Gauge
        ACCESS	read-write
        STATUS	mandatory
        DESCRIPTION
                "First Level debug flag.  Cannot be configured with Site Manager.
                When this flag is set to Zero, no debug messages will be logged.
                Each bit of this flag represents certain functionality in DLSw.
                When this bit is set, all level2 elements that are part of this
                functionality that have their bits set will be allowed to log debug
                messages."
        DEFVAL	{ 4294967295 }
        ::= { wfDls 14 }

    wfDlsDebugLevel2 OBJECT-TYPE
        SYNTAX	Gauge
        ACCESS	read-write
        STATUS	mandatory
        DESCRIPTION
                "Second Level debug flag.  Cannot be configured with Site Manager.
                When this flag is set to Zero, no debug messages will be logged.
                Each bit of this flag represents a sub-functional element.  When this
                bit is set, all debug messages in this element will be logged, as long
                as the related level1 functionality is set."
        DEFVAL	{ 0 }
        ::= { wfDls 15 }

    wfDlsWanKeepaliveTime OBJECT-TYPE
        SYNTAX	INTEGER(0..2147483647)
        ACCESS	read-write
        STATUS	mandatory
        DESCRIPTION
                "Keepalive packets will be sent into inactive, established TCP connections
                after this time interval (in seconds).  A time of zero disables this
                keepalive feature."
        DEFVAL	{ 60 }
        ::= { wfDls 16 }

    wfDlsPPriDisable OBJECT-TYPE
        SYNTAX	INTEGER {
    		    enabled(1),
    		    disabled(2)
    		}
        ACCESS	read-write
        STATUS	mandatory
        DESCRIPTION
                "Protocol Prioritization Enable/Disable parameter. Default is disabled.
                Users perform an SNMP SET operation to enable/disable this feature."
        DEFVAL	{ disabled }
        ::= { wfDls 17 }

    wfDlsPPriDefaultNumQueues OBJECT-TYPE
        SYNTAX	INTEGER(1..10)
        ACCESS	read-write
        STATUS	mandatory
        DESCRIPTION
                "DLSw Prioritization Default number of Queues. The number of queues to be
                created when establishing a Peer connection if none have been previously
                defined.  The default is two queues: queue number 0 and 1."
        DEFVAL	{ 2 }
        ::= { wfDls 18 }

    wfDlsPPriDefaultQBandwidth OBJECT-TYPE
        SYNTAX	OCTET STRING
        ACCESS	read-write
        STATUS	mandatory
        DESCRIPTION
                "DLSw Prioritization Default Queues Bandwidth. The bandwidth for
                each default queue.  Default of: 60% queue 0, 40% queue 1 via site manager."
        ::= { wfDls 19 }

    wfDlsPPriUnconfPeerDisable OBJECT-TYPE
        SYNTAX	INTEGER {
    		    enable(1),
    		    disable(2)
    		}
        ACCESS	read-write
        STATUS	mandatory
        DESCRIPTION
                "DLSw Prioritization enabled/disabled for peers not in Peer Table."
        DEFVAL	{ disable }
        ::= { wfDls 20 }

    wfDlsPPriUnconfPeerMaxQBuf OBJECT-TYPE
        SYNTAX	INTEGER {
    		    default(50)
    		}
        ACCESS	read-write
        STATUS	mandatory
        DESCRIPTION
                "DLSw Prioritization enabled/disabled for peers not in Peer Table."
        DEFVAL	{ default }
        ::= { wfDls 21 }

    wfDlsPPriUnconfPeerMaxQSize OBJECT-TYPE
        SYNTAX	INTEGER {
    		    default(16000)
    		}
        ACCESS	read-write
        STATUS	mandatory
        DESCRIPTION
                "DLSw Prioritization enabled/disabled for peers not in Peer Table."
        DEFVAL	{ default }
        ::= { wfDls 22 }

    wfDlsPkgMaxSize OBJECT-TYPE
        SYNTAX	INTEGER(0..2147483647)
        ACCESS	read-write
        STATUS	mandatory
        DESCRIPTION
                "Maximum size of frame to sended over the WAN. Used when packaging
                multiple DLS frames into a single TCP frame. The value specified must
                be smaller than the wfDlsTcpWindowSize and  should be no greater
                than the MTU for the WAN minus the size of the TCP/IP/MAC headers."
        DEFVAL	{ 1532 }
        ::= { wfDls 23 }

    wfDlsPkgTO OBJECT-TYPE
        SYNTAX	INTEGER(0..2147483647)
        ACCESS	read-write
        STATUS	mandatory
        DESCRIPTION
                "DLSw packaging Time-out. Number of msec to delay a package before sending
                to TCP.  This value should be based on the WAN speed wfDlsPkgWinPercent
                (defined below).  This value should be no greater than the amount of time
                it takes to send the number of outstanding bytes before packaging begins:
                          number bytes / (number bytes per msec)
                Default of 10 msec.  "
        DEFVAL	{ 10 }
        ::= { wfDls 24 }

    wfDlsPkgWinPercent OBJECT-TYPE
        SYNTAX	INTEGER(0..100)
        ACCESS	read-write
        STATUS	mandatory
        DESCRIPTION
                "DLSw Packaging threshold. What percent of the DLS TCP window must be
                outstanding inorder to delay the sending of a package being built.
                Default: 20% of TCP window.
                Range: 0 - 100, with 0 meaning no delay."
        DEFVAL	{ 20 }
        ::= { wfDls 25 }

    wfDlsMultislotBcasts OBJECT-TYPE
        SYNTAX  INTEGER {
                    enabled(1),
                    disabled(2)
                }
        ACCESS  read-write
        STATUS  mandatory
        DESCRIPTION
                "Allow broadcasts inbound from the WAN to be broadcast
                to all active DLSw slots."
        DEFVAL  { enabled }
        ::= { wfDls 26 }

    wfDlsInitialPacingWindow OBJECT-TYPE
        SYNTAX  INTEGER(5..100)
        ACCESS  read-write
        STATUS  mandatory
        DESCRIPTION
                "Initial pacing window to be advertised in Capabilities
                Exchange messages.  Adaptive pacing will begin with this
                value and use the state of the network to find the
                proper pacing window size."
        DEFVAL  { 5 }
        ::= { wfDls 27 }

    wfDlsRfc OBJECT-TYPE
        SYNTAX  INTEGER {
                    rfc1434(1),
                    rfc1795(2),
		    v20unicast(3),
		    rfc2166(4)
                }
        ACCESS  read-write
        STATUS  mandatory
        DESCRIPTION
                "DLSw RFC mode selection.
		 - RFC1434 is the original implementation
		 - RFC1795 provides improved interoperability and flow control
		 - v20_unicast supports Canureach Exploring via unicast UDP
		   frames and provides single TCP connections
		 - RFC2166 additionally supports Multicast Canureach Exploring"
        DEFVAL  { rfc1434 }
        ::= { wfDls 28 }

    wfDlsNetbiosSessionAliveFilter OBJECT-TYPE
        SYNTAX  INTEGER {
                    enabled(1),
                    disabled(2)
                }
        ACCESS  read-write
        STATUS  mandatory
        DESCRIPTION
                "Netbios session alive filter."
        DEFVAL  { disabled }
        ::= { wfDls 29 }

    wfDlsWanKeepaliveRetryTimer OBJECT-TYPE
        SYNTAX	INTEGER(0..600)
        ACCESS	read-write
        STATUS	mandatory
        DESCRIPTION
                "KEEPALIVE retransmit timeout period, in seconds.  This is
                the interval at which unacknowledged KEEPALIVE messages will
                be retransmitted.  If the Idle Timer is set to zero, this
                timer ignored.  If the Idle Timer is non-zero and this timer
                IS zero, no KEEPALIVEs are sent and the session is terminated
                upon expiration of the Idle Timer."
        DEFVAL	{ 60 }
        ::= { wfDls 30 }

    wfDlsWanKeepaliveRetries OBJECT-TYPE
        SYNTAX	INTEGER(0..99)
        ACCESS	read-write
        STATUS	mandatory
        DESCRIPTION
		"Number of unacknowledged KEEPALIVE messages retransmitted
                before the TCP session is terminated.  If this count is set
                to zero, only one KEEPALIVE message will be sent."
        DEFVAL	{ 4 }
        ::= { wfDls 31 }

    wfDlsSnaFallbackAttempts OBJECT-TYPE
        SYNTAX  INTEGER(0..2147483647)
        ACCESS  read-write
        STATUS  mandatory
        DESCRIPTION
                "Number of times CANUREACH_ex will be sent (for
                 SNA based connections) before attempting
                 to fall back. Used for peers configured as
                 wfDlsPeerTransportType = unknown to attempt
                 connecting via RFC 1795."
        DEFVAL  { 5 }
        ::= { wfDls 32 }

    wfDlsNetbiosFallbackTime OBJECT-TYPE
        SYNTAX  INTEGER(0..2147483647)
        ACCESS  read-write
        STATUS  mandatory
        DESCRIPTION
                "Amount of time in sec before falling back to RFC 1795
		for the peers configured with wfDlsPeerTransportType = unknown,
		if NETBIOS_NQ does not get answered."
        DEFVAL  { 180 }
        ::= { wfDls 33 }

    wfDlsTcpInactTime OBJECT-TYPE
        SYNTAX  INTEGER(0..2147483647)
        ACCESS  read-write
        STATUS  mandatory
        DESCRIPTION
                "Amount of time in sec after the last active DLSw circuit
		has terminated or there was no data transfered over TCP
		pipe, before bringing down TCP connection. Used in conjunction
		with wfDlsTcpInactMethod."
        DEFVAL  { 300 }
        ::= { wfDls 34 }

    wfDlsTcpInactMethod OBJECT-TYPE
        SYNTAX  INTEGER {
		    never (1),
                    circuits(2),
                    data(3)
                }
        ACCESS  read-write
        STATUS  mandatory
        DESCRIPTION
	        "Determines when tcp connections may be brought down. Could
        	be due to no DLS circuits on a peer, no data passing over the
        	TCP link, or leave the TCP connection up.
		Used in conjunction with wfDlsTcpInactTime."
        DEFVAL  { circuits }
        ::= { wfDls 35 }

    wfDlsMslotDLCBcasts OBJECT-TYPE
        SYNTAX  INTEGER {
                    enabled(1),
                    disabled(2)
                }
        ACCESS  read-write
        STATUS  mandatory
        DESCRIPTION
                "Allow broadcast messages inbound from the DLC to be
                  sent to all active DLSw slots."
        DEFVAL  { enabled }
        ::= { wfDls 36 }

    wfDlsRsvpSupport OBJECT-TYPE
        SYNTAX  INTEGER {
                    enabled(1),
                    disabled(2)
                }
        ACCESS  read-write
        STATUS  mandatory
        DESCRIPTION
                "Enables/Disables use of RSVP by DLSw"
        DEFVAL  { disabled }
        ::= { wfDls 37 }

    wfDlsOutBandwidth OBJECT-TYPE
        SYNTAX  INTEGER(0..2147483647)
        ACCESS  read-write
        STATUS  mandatory
        DESCRIPTION
                "Bandwidth amount for the outgoing DLSw traffic,
		 to use in RSVP reservations for unconfigured peers"
        DEFVAL  { 0 }
        ::= { wfDls 38 }

    wfDlsOutBurstSize OBJECT-TYPE
        SYNTAX  INTEGER(0..2147483647)
        ACCESS  read-write
        STATUS  mandatory
        DESCRIPTION
                "Burst Size amount for the outgoing DLSw traffic,
		 to use in RSVP reservations for unconfigured peers"
        DEFVAL  { 0 }
        ::= { wfDls 39 }

    wfDlsInBandwidth OBJECT-TYPE
        SYNTAX  INTEGER(0..2147483647)
        ACCESS  read-write
        STATUS  mandatory
        DESCRIPTION
                "Bandwidth amount for the incoming DLSw traffic,
		 to use in RSVP reservations for unconfigured peers"
        DEFVAL  { 0 }
        ::= { wfDls 40 }

    wfDlsInBurstSize OBJECT-TYPE
        SYNTAX  INTEGER(0..2147483647)
        ACCESS  read-write
        STATUS  mandatory
        DESCRIPTION
                "Burst Size amount for the incoming DLSw traffic,
		 to use in RSVP reservations for unconfigured peers"
        DEFVAL  { 0 }
        ::= { wfDls 41 }

    wfDlsNonPeakOutBandwidth OBJECT-TYPE
        SYNTAX  INTEGER(0..2147483647)
        ACCESS  read-write
        STATUS  mandatory
        DESCRIPTION
                "Bandwidth amount for the outgoing DLSw traffic,
		 to use in RSVP reservations for unconfigured peers
		 during non-peak hours"
        DEFVAL  { 0 }
        ::= { wfDls 42 }

    wfDlsNonPeakOutBurstSize OBJECT-TYPE
        SYNTAX  INTEGER(0..2147483647)
        ACCESS  read-write
        STATUS  mandatory
        DESCRIPTION
                "Burst Size amount for the outgoing DLSw traffic,
		 to use in RSVP reservations for unconfigured peers
		 during non-peak hours"
        DEFVAL  { 0 }
        ::= { wfDls 43 }

    wfDlsNonPeakInBandwidth OBJECT-TYPE
        SYNTAX  INTEGER(0..2147483647)
        ACCESS  read-write
        STATUS  mandatory
        DESCRIPTION
                "Bandwidth amount for the incoming DLSw traffic,
		 to use in RSVP reservations for unconfigured peers
		 during non-peak hours"
        DEFVAL  { 0 }
        ::= { wfDls 44 }

    wfDlsNonPeakInBurstSize OBJECT-TYPE
        SYNTAX  INTEGER(0..2147483647)
        ACCESS  read-write
        STATUS  mandatory
        DESCRIPTION
                "Burst Size amount for the incoming DLSw traffic,
		 to use in RSVP reservations for unconfigured peers
		 during non-peak hours"
        DEFVAL  { 0 }
        ::= { wfDls 45 }

    wfDlsNonPeakStartTime OBJECT-TYPE
        SYNTAX  INTEGER(0..2400)
        ACCESS  read-write
        STATUS  mandatory
        DESCRIPTION
                "Start time of the non-peak hours in hhmm format and
		 24 hour clock. If start time is greater in value than
		 end time, non-peak hours ends the next day."
        DEFVAL  { 0 }
        ::= { wfDls 46 }

    wfDlsNonPeakEndTime OBJECT-TYPE
        SYNTAX  INTEGER(0..2400)
        ACCESS  read-write
        STATUS  mandatory
        DESCRIPTION
                "End time of the non-peak hours in hhmm 24 hour clock format"
        DEFVAL  { 0 }
        ::= { wfDls 47 }

    wfDlsNonPeakStartDays OBJECT-TYPE
        SYNTAX	Counter
        ACCESS  read-write
        STATUS  mandatory
        DESCRIPTION
               "Bitmap of the starting days of the week for a non-peak
		reservations.
		The MSBit represents Sunday, the next most significant
		bit represents Monday, and so on...
                Default is 0 - non-peak parameters are not used."
        ::= { wfDls 48 }

    wfDlsMultislotCacheUpdate OBJECT-TYPE
        SYNTAX  INTEGER {
                    enabled(1),
                    disabled(2)
                }
        ACCESS  read-write
        STATUS  mandatory
        DESCRIPTION
                "Allow learned MAC-IP cache resolutions to be  promulgated
                to all other DLSw slots."
        DEFVAL  { enabled }
        ::= { wfDls 49 }


   wfDlsMacAddrTranslation OBJECT-TYPE
        SYNTAX  INTEGER {
                    enabled(1),
                    disabled(2)
                }
        ACCESS  read-write
        STATUS  mandatory
        DESCRIPTION
                "Enables/Disables use of Mac Address Translation by DLSw"
        DEFVAL  { disabled }
        ::= { wfDls 50 }

   wfDlsBan2Support OBJECT-TYPE
        SYNTAX  INTEGER {
                    enabled(1),
                    disabled(2)
                }
        ACCESS  read-write
        STATUS  mandatory
        DESCRIPTION
                "Enables/Disables BAN-2 local termination between SRB
		 interfaces in single DLS switch configs"
        DEFVAL  { disabled }

        ::= { wfDls 51 }

   wfDlsVirtualRingBridgeCheck OBJECT-TYPE
        SYNTAX  INTEGER {
                    enabled(1),
                    disabled(2)
                }
        ACCESS  read-write
        STATUS  mandatory
        DESCRIPTION
                " DLSw Virtual Ring ID and SRB Bridge ID will be checked."
        DEFVAL  { disabled }
        ::= { wfDls 52 }

    wfDlsAcceptBadVendorSpecificCapex OBJECT-TYPE
         SYNTAX  INTEGER {
                     enabled(1),
                     disabled(2)
                 }
         ACCESS  read-write
         STATUS  mandatory
         DESCRIPTION
                 "Accept a capex request containing a Vendor Specific Control Vector
                  but no Vendor Context. The Control Vector will be ignored"
         DEFVAL  { disabled }
         ::= { wfDls 53 }

   wfDlsDiagSwitch  OBJECT-TYPE
        SYNTAX  INTEGER {
                    enabled(1),
                    disabled(2)
                }
        ACCESS  read-write
        STATUS  mandatory
        DESCRIPTION
                "Available MIB for diagnostic workspaces. Allows optional conditional debugging"
        DEFVAL  { disabled }

        ::= { wfDls 54 }

   wfDlsAllowSpecAddrNbDatagram  OBJECT-TYPE
        SYNTAX  INTEGER {
                    enabled(1),
                    disabled(2)
                }
        ACCESS  read-write
        STATUS  mandatory
        DESCRIPTION
                "Allows acceptance of NETBIOS Datagrams sent to other than the NETBIOS Group
                 address as the destination MAC address. This is an override MIB. When enabled,
                 DLS will bypass its check for that group address and allow the packet."
        DEFVAL  { disabled }

        ::= { wfDls 55 }

    wfDlsInterfaceTable OBJECT-TYPE
        SYNTAX	SEQUENCE OF WfDlsInterfaceEntry
        ACCESS	not-accessible
        STATUS	mandatory
        DESCRIPTION
                "A table that contains information about every interface that is associated
                with DLSw inst_id[1] = wfDlsInterfaceCircuit"
        ::= { wfDlsGroup 2 }

    wfDlsInterfaceEntry OBJECT-TYPE
        SYNTAX	WfDlsInterfaceEntry
        ACCESS	not-accessible
        STATUS	mandatory
        DESCRIPTION
                "An entry in wfDlsInterface"
        INDEX	{ wfDlsInterfaceCircuit }
        ::= { wfDlsInterfaceTable 1 }

    WfDlsInterfaceEntry ::= SEQUENCE {
    	    wfDlsInterfaceDelete
    		INTEGER,
    	    wfDlsInterfaceDisable
    		INTEGER,
    	    wfDlsInterfaceState
    		INTEGER,
    	    wfDlsInterfaceCircuit
    		INTEGER,
    	    wfDlsInterfaceBridgeId
    		INTEGER,
    	    wfDlsInterfaceLanId
    		INTEGER,
    	    wfDlsInterfaceDlcType
    		INTEGER,
    	    wfDlsInterfaceSdlcMode
    		INTEGER,
            wfDlsInterfaceNbBcastDgramReduce
                INTEGER,
    	    wfDlsInterfaceExplorerType
    		INTEGER,
            wfDlsInterfaceNbBcastDgramCache
                INTEGER,
            wfDlsInterfaceClrCallEnable
                INTEGER
        }

    wfDlsInterfaceDelete OBJECT-TYPE
        SYNTAX	INTEGER {
    		    created(1),
    		    deleted(2)
    		}
        ACCESS	read-write
        STATUS	mandatory
        DESCRIPTION
                "Create/Delete parameter. Default is created. Users perform an SNMP SET
                operation on this object in order to create/delete an interface"
        DEFVAL	{ created }
        ::= { wfDlsInterfaceEntry 1 }

    wfDlsInterfaceDisable OBJECT-TYPE
        SYNTAX	INTEGER {
    		    enabled(1),
    		    disabled(2)
    		}
        ACCESS	read-write
        STATUS	mandatory
        DESCRIPTION
                "Enable/Disable parameter. Default is enabled. Users perform an SNMP SET
                operation on this object in order to enable/disable an interface"
        DEFVAL	{ enabled }
        ::= { wfDlsInterfaceEntry 2 }

    wfDlsInterfaceState OBJECT-TYPE
        SYNTAX	INTEGER {
    		    up(1),
    		    down(2),
    		    init(3),
    		    notpresent(4)
    		}
        ACCESS	read-only
        STATUS	mandatory
        DESCRIPTION
                "The current state of the interface"
        DEFVAL	{ down }
        ::= { wfDlsInterfaceEntry 3 }

    wfDlsInterfaceCircuit OBJECT-TYPE
        SYNTAX	INTEGER
        ACCESS	read-only
        STATUS	mandatory
        DESCRIPTION
                "The circuit that this interface runs over"
        ::= { wfDlsInterfaceEntry 4 }

    wfDlsInterfaceBridgeId OBJECT-TYPE
        SYNTAX	INTEGER(1..15)
        ACCESS	read-write
        STATUS	mandatory
        DESCRIPTION
                "The Bridge Id of the 'bridge' from the internal Lan to the TCP/IP ring.
                This must be a non-Wellfleet bridge number. Valid Values (1-15)"
        ::= { wfDlsInterfaceEntry 5 }

    wfDlsInterfaceLanId OBJECT-TYPE
        SYNTAX	INTEGER(1..4095)
        ACCESS	read-write
        STATUS	mandatory
        DESCRIPTION
                "The Lan Id of the interface.  Valid Values (1-4095)"
        ::= { wfDlsInterfaceEntry 6 }

    wfDlsInterfaceDlcType OBJECT-TYPE
        SYNTAX	INTEGER {
    		    sync(1),
    		    srb(2),
    		    tb(3),
    		    encaps(4),
    		    fr(5),
    		    token(6)
    		}
        ACCESS	read-write
        STATUS	mandatory
        DESCRIPTION
                "The Data Link Control Type on this interface."
        DEFVAL	{ srb }
        ::= { wfDlsInterfaceEntry 7 }

    wfDlsInterfaceSdlcMode OBJECT-TYPE
        SYNTAX	INTEGER {
    		    primary(1),
    		    pp(2),
    		    mp(3),
		    negot(4)
    		}
        ACCESS	read-write
        STATUS	mandatory
        DESCRIPTION
                "The SDLC Mode on this interface."
        DEFVAL	{ primary }
        ::= { wfDlsInterfaceEntry 8 }

    wfDlsInterfaceNbBcastDgramReduce OBJECT-TYPE
        SYNTAX  INTEGER {
                    on(1),
                    off(2)
                }
        ACCESS  read-write
        STATUS  mandatory
        DESCRIPTION
                "This allows the NetBios Broadcast dgram reduction code built
                into dls to be turned off."
        DEFVAL  { on }
        ::= { wfDlsInterfaceEntry 9 }

  wfDlsInterfaceExplorerType OBJECT-TYPE
        SYNTAX  INTEGER {
                      ste(1),
                      are(2)
                }
        ACCESS  read-write
        STATUS  mandatory
        DESCRIPTION
                "This allows CANUREACH test frames to be sent as
                single-route or all-routes explorer frames."
        DEFVAL  { ste }
        ::= { wfDlsInterfaceEntry 10 }

  wfDlsInterfaceNbBcastDgramCache OBJECT-TYPE
        SYNTAX  INTEGER {
                    off(1),
                    forward(2),
                    drop(3)
                }
        ACCESS  read-write
        STATUS mandatory
        DESCRIPTION
                "This allows Netbios Broadcast datagram frames to be cached
                 along with allowing these same frames to utilize the netbios
                 caching mechanism. Value 1 means feature not on. Value 2
                 means if frame is not in cache then forward it. Value 3
                 means if frame is not in cache then drop it."
        DEFVAL  { off }
        ::= { wfDlsInterfaceEntry 11 }

  wfDlsInterfaceClrCallEnable OBJECT-TYPE
        SYNTAX  INTEGER {
                    on(1),
                    off(2)
                }
        ACCESS  read-write
        STATUS mandatory
        DESCRIPTION
                 "This allows a generic (e.g. QLLC/X25) call to be cleared when
                  the DLS connection enters a DISCONNECTED state."
        DEFVAL  { off }
        ::= { wfDlsInterfaceEntry 12 }

    wfDlsSlotTable OBJECT-TYPE
        SYNTAX	SEQUENCE OF WfDlsSlotEntry
        ACCESS	not-accessible
        STATUS	mandatory
        DESCRIPTION
                "A table that contains the IP interfaces each slot must use for the TCP
                connections to non-Wellfleet switches.  The IP interface may exist anywhere
                on the box.  inst_id[1] = wfDlsSlotNumber"
        ::= { wfDlsGroup 3 }

    wfDlsSlotEntry OBJECT-TYPE
        SYNTAX	WfDlsSlotEntry
        ACCESS	not-accessible
        STATUS	mandatory
        DESCRIPTION
                "An entry in wfDlsSlot"
        INDEX	{ wfDlsSlotNumber }
        ::= { wfDlsSlotTable 1 }

    WfDlsSlotEntry ::= SEQUENCE {
    	    wfDlsSlotDelete
    		INTEGER,
    	    wfDlsSlotNumber
    		INTEGER,
    	    wfDlsSlotIpAddr
    		IpAddress,
    	    wfDlsCurrentMemory
    		INTEGER,
    	    wfDlsMaxAllowedMemory
    		Gauge,
    	    wfDlsHiWaterMark
                INTEGER,
            wfDlsSlotGenDestination
                INTEGER,
            wfDlsSlotGenSessions
                INTEGER,
            wfDlsSlotGenUpperMAC
                INTEGER,
            wfDlsSlotCurrentSessions
                INTEGER,
            wfDlsSlotHiWaterSessions
                INTEGER,
            wfDlsSlotHiWaterReset
   		INTEGER
        }

    wfDlsSlotDelete OBJECT-TYPE
        SYNTAX	INTEGER {
    		    created(1),
    		    deleted(2)
    		}
        ACCESS	read-write
        STATUS	mandatory
        DESCRIPTION
                "Create/Delete parameter. Default is created. Users perform an SNMP SET
                operation on this object in order to create/delete a DLSw slot IP record"
        DEFVAL	{ created }
        ::= { wfDlsSlotEntry 1 }

    wfDlsSlotNumber OBJECT-TYPE
        SYNTAX	INTEGER
        ACCESS	read-only
        STATUS	mandatory
        DESCRIPTION
                "The slot that uses this IP interface"
        ::= { wfDlsSlotEntry 2 }

    wfDlsSlotIpAddr OBJECT-TYPE
        SYNTAX	IpAddress
        ACCESS	read-write
        STATUS	mandatory
        DESCRIPTION
                "The IP interface to use for TCP connections based on this slot"
        ::= { wfDlsSlotEntry 3 }

    wfDlsCurrentMemory OBJECT-TYPE
        SYNTAX	INTEGER
        ACCESS	read-only
        STATUS	mandatory
        DESCRIPTION
                "Memory currently available on this slot"
        ::= { wfDlsSlotEntry 4 }

    wfDlsMaxAllowedMemory OBJECT-TYPE
        SYNTAX	Gauge
        ACCESS	read-write
        STATUS	mandatory
        DESCRIPTION
                "Maximum amount of memory allowed to be allocated for DLS on this slot.
                4294967295 = 0xFFFFFFFF stands for infinite. (i.e. all available memory)"
        DEFVAL	{ 4294967295 }
        ::= { wfDlsSlotEntry 5 }

    wfDlsHiWaterMark OBJECT-TYPE
        SYNTAX	INTEGER
        ACCESS	read-only
        STATUS	mandatory
        DESCRIPTION
                "This is the maximum amount of memory ever allocated by DLS on this slot
                since the last boot"
        ::= { wfDlsSlotEntry 6 }

    wfDlsSlotGenDestination OBJECT-TYPE
        SYNTAX  INTEGER(0..14)
        ACCESS  read-write
        STATUS  mandatory
        DESCRIPTION
                "This is a destination slot of the GEN tool if the value is 0.
                 For any non-zero number, the slot is a GEN source and the
                 value of wfDlsSlotGenDestination is its destination slot."
        DEFVAL  { 0 }
        ::= { wfDlsSlotEntry 7 }

    wfDlsSlotGenSessions OBJECT-TYPE
        SYNTAX  INTEGER(0..10000)
        ACCESS  read-write
        STATUS  mandatory
        DESCRIPTION
                "The maximum number of Generator sessions to support per slot"
        DEFVAL  { 0 }
        ::= { wfDlsSlotEntry 8 }

    wfDlsSlotGenUpperMAC OBJECT-TYPE
        SYNTAX  INTEGER(0..2147418112)
        ACCESS  read-write
        STATUS  mandatory
        DESCRIPTION
                "The upper MAC address for this slot."
        DEFVAL  { 0 }
        ::= { wfDlsSlotEntry 9 }

   wfDlsSlotCurrentSessions OBJECT-TYPE
        SYNTAX  INTEGER
        ACCESS  read-only
        STATUS  mandatory
        DESCRIPTION
                "The number of sessions connected on this slot."
        DEFVAL  { 0 }
        ::= { wfDlsSlotEntry 10}

    wfDlsSlotHiWaterSessions OBJECT-TYPE
        SYNTAX  INTEGER
        ACCESS  read-only
        STATUS  mandatory
        DESCRIPTION
                "The highest number of sessions connected at one time on this slot."
        DEFVAL  { 0 }
        ::= { wfDlsSlotEntry 11 }

    wfDlsSlotHiWaterReset OBJECT-TYPE
        SYNTAX  INTEGER {
                    normal(1),
                    reset(2)
                }
        ACCESS  read-write
        STATUS  mandatory
        DESCRIPTION
                "Setting to 2 (reset) sets HiWaterSessions to CurrentSessions."
        DEFVAL  { normal }
        ::= { wfDlsSlotEntry 12}


    wfDlsSapTable OBJECT-TYPE
        SYNTAX	SEQUENCE OF WfDlsSapEntry
        ACCESS	not-accessible
        STATUS	mandatory
        DESCRIPTION
                "A table that contains the SAPS to be terminated by DLSw.
                inst_id[1] = wfDlsSapAddr"
        ::= { wfDlsGroup 4 }

    wfDlsSapEntry OBJECT-TYPE
        SYNTAX	WfDlsSapEntry
        ACCESS	not-accessible
        STATUS	mandatory
        DESCRIPTION
                "An entry in wfDlsSap"
        INDEX	{ wfDlsSapAddr }
        ::= { wfDlsSapTable 1 }

    WfDlsSapEntry ::= SEQUENCE {
    	    wfDlsSapDelete
    		INTEGER,
    	    wfDlsSapAddr
    		INTEGER,
    	    wfDlsSapCredit
    		INTEGER
        }

    wfDlsSapDelete OBJECT-TYPE
        SYNTAX	INTEGER {
    		    created(1),
    		    deleted(2)
    		}
        ACCESS	read-write
        STATUS	mandatory
        DESCRIPTION
                "Create/Delete parameter. Default is created. Users perform an SNMP SET
                operation on this object in order to create/delete a DLSw SAP record"
        DEFVAL	{ created }
        ::= { wfDlsSapEntry 1 }

    wfDlsSapAddr OBJECT-TYPE
        SYNTAX	INTEGER
        ACCESS	read-only
        STATUS	mandatory
        DESCRIPTION
                "The SAP to be terminated by DLSw"
        ::= { wfDlsSapEntry 2 }

    wfDlsSapCredit OBJECT-TYPE
        SYNTAX	INTEGER(6..200)
        ACCESS	read-write
        STATUS	mandatory
        DESCRIPTION
                "The LLC2 flow control credit size for this SAP. Flow control procedures
                will be invoked based on this parameter"
        DEFVAL	{ 10 }
        ::= { wfDlsSapEntry 3 }

    wfDlsPeerTable OBJECT-TYPE
        SYNTAX	SEQUENCE OF WfDlsPeerEntry
        ACCESS	not-accessible
        STATUS	mandatory
        DESCRIPTION
                "A table that contains the IP addresses of the DLSw peers with which we will
                establish TCP connections.  inst_id[4] = wfDlsPeerAddr"
        ::= { wfDlsGroup 5 }

    wfDlsPeerEntry OBJECT-TYPE
        SYNTAX	WfDlsPeerEntry
        ACCESS	not-accessible
        STATUS	mandatory
        DESCRIPTION
                "An entry in wfDlsPeer"
        INDEX	{ wfDlsPeerIpAddr }
        ::= { wfDlsPeerTable 1 }

    WfDlsPeerEntry ::= SEQUENCE {
    	    wfDlsPeerDelete
    		INTEGER,
    	    wfDlsPeerState
    		INTEGER,
    	    wfDlsPeerIpAddr
    		IpAddress,
    	    wfDlsPeerDefinedBy
    		INTEGER,
    	    wfDlsPeerPPriDisable
    		INTEGER,
    	    wfDlsPeerPPriMaxQBuf
    		INTEGER,
    	    wfDlsPeerPPriMaxQSize
    		INTEGER,
    	    wfDlsPeerPPriClearStats
    		INTEGER,
            wfDlsPeerType
            INTEGER,
            wfDlsPeerTransportType
		    INTEGER,
            wfDlsPeerBackupConfig
            INTEGER,
            wfDlsPeerBackupIpAddr
    		IpAddress,	
            wfDlsPeerBackupMaxUpTime
            INTEGER,
            wfDlsPeerBackupHoldDownTime
            INTEGER,
            wfDlsPeerBackupStartTime
            INTEGER,
            wfDlsPeerBackupEndTime
            INTEGER,
            wfDlsPeerInteroperability
            INTEGER,
            wfDlsPeerBackupType
	    INTEGER,
	    wfDlsPeerRsvpMode
		INTEGER,
	    wfDlsPeerRsvpSlots
		Counter,
	    wfDlsPeerOutBandwidth
		INTEGER,
	    wfDlsPeerOutBurstSize
		INTEGER,
	    wfDlsPeerInBandwidth
		INTEGER,
	    wfDlsPeerInBurstSize
		INTEGER,
	    wfDlsPeerNonPeakOutBandwidth
		INTEGER,
	    wfDlsPeerNonPeakOutBurstSize
		INTEGER,
	    wfDlsPeerNonPeakInBandwidth
		INTEGER,
	    wfDlsPeerNonPeakInBurstSize
		INTEGER,
	    wfDlsPeerNonPeakStartTime
		INTEGER,
	    wfDlsPeerNonPeakEndTime
		INTEGER,
	    wfDlsPeerNonPeakStartDays
		Counter,
	    wfDlsPeerBackupOutBandwidth
		INTEGER,
	    wfDlsPeerBackupOutBurstSize
		INTEGER,
	    wfDlsPeerBackupInBandwidth
		INTEGER,
	    wfDlsPeerBackupInBurstSize
		INTEGER
        }

    wfDlsPeerDelete OBJECT-TYPE
        SYNTAX	INTEGER {
    		    created(1),
    		    deleted(2)
    		}
        ACCESS	read-write
        STATUS	mandatory
        DESCRIPTION
                "Create/Delete parameter. Default is created. Users perform an SNMP SET
                operation on this object in order to create/delete a DLSw peer record"
        DEFVAL	{ created }
        ::= { wfDlsPeerEntry 1 }

    wfDlsPeerState OBJECT-TYPE
        SYNTAX	INTEGER {
    		    connect(1),
                backup(2),
    		    notconn(3),
    		    invalid(4)
    		}
        ACCESS	read-only
        STATUS	mandatory
        DESCRIPTION
                "The current state of the TCP connection with this DLSw peer"
        DEFVAL	{ notconn }
        ::= { wfDlsPeerEntry 2 }

    wfDlsPeerIpAddr OBJECT-TYPE
        SYNTAX	IpAddress
        ACCESS	read-only
        STATUS	mandatory
        DESCRIPTION
                "The IP address of the DLSw peer"
        ::= { wfDlsPeerEntry 3 }

    wfDlsPeerDefinedBy OBJECT-TYPE
        SYNTAX	INTEGER {
    		    configured(1),
    		    learned(2)
    		}
        ACCESS	read-only
        STATUS	mandatory
        DESCRIPTION
                "The method by which this peer was defined"
        DEFVAL	{ configured }
        ::= { wfDlsPeerEntry 4 }

    wfDlsPeerPPriDisable OBJECT-TYPE
        SYNTAX	INTEGER {
    		    enabled(1),
    		    disabled(2)
    		}
        ACCESS	read-write
        STATUS	mandatory
        DESCRIPTION
                "DLSw Protocol Priority enabled/disabled for this Peer. The default
                is to use the value specified in the DLS Base record (wfDlsPPriDisable).
                Site Manager handles the setting of the default."
        DEFVAL	{ disabled }
        ::= { wfDlsPeerEntry 5 }

    wfDlsPeerPPriMaxQBuf OBJECT-TYPE
        SYNTAX	INTEGER {
    		    default(50)
    		}
        ACCESS	read-write
        STATUS	mandatory
        DESCRIPTION
                "Protocol Priority Queue Maximum number of allocated buffers queued."
        DEFVAL	{ default }
        ::= { wfDlsPeerEntry 6 }

    wfDlsPeerPPriMaxQSize OBJECT-TYPE
        SYNTAX	INTEGER {
    		    default(16000)
    		}
        ACCESS	read-write
        STATUS	mandatory
        DESCRIPTION
                "Protocol Priority Queue Maximum number of octets queued."
        DEFVAL	{ default }
        ::= { wfDlsPeerEntry 7 }

    wfDlsPeerPPriClearStats OBJECT-TYPE
        SYNTAX	INTEGER
        ACCESS	read-write
        STATUS	mandatory
        DESCRIPTION
                "Clear Protocol Priority Statistics. If prioritization is
                enabled for this Peer, then modifying this attribute will
                cause all Statistics kept (Queue's, CC, etc) to be cleared."
        ::= { wfDlsPeerEntry 8 }

    wfDlsPeerType OBJECT-TYPE
        SYNTAX  INTEGER {
                    rfc1795(1),
                    rfc1434(2),
                    local(3),
  		            v20unicast(4),
                    rfc2166(5),
                    unknown(6)
                }
        ACCESS  read-only
        STATUS  mandatory
        DESCRIPTION
                "The protocol type of this DLSw peer"
        DEFVAL  { unknown }
        ::= { wfDlsPeerEntry 9 }

    wfDlsPeerTransportType OBJECT-TYPE
        SYNTAX  INTEGER {
                    tcp(1),
                    udp(2),
                    unknown(3)
                }
        ACCESS  read-write
        STATUS  mandatory
        DESCRIPTION
                "The transport type of this DLSw peer"
        DEFVAL  { unknown }
        ::= { wfDlsPeerEntry 10 }

    wfDlsPeerBackupConfig OBJECT-TYPE
        SYNTAX	INTEGER {
    		    yes(1),
    		    no(2)
    		}
        ACCESS	read-write
        STATUS	mandatory
        DESCRIPTION
                "The indication of whether or not a backup peer
                 is to be configured for the primary peer.  The
                 default is no which means that there is no backup
                 peer configured by default.  A backup peer can only
                 be configured for a RFC1434 or RFC1795 peer."
        DEFVAL	{ no }
        ::= { wfDlsPeerEntry 11 }

    wfDlsPeerBackupIpAddr OBJECT-TYPE
        SYNTAX	IpAddress
        ACCESS	read-write
        STATUS	mandatory
        DESCRIPTION
                "The IP Address of the backup DLSw peer."
        ::= { wfDlsPeerEntry 12 }

    wfDlsPeerBackupMaxUpTime OBJECT-TYPE
        SYNTAX	INTEGER(0..999999)
        ACCESS	read-write
        STATUS	mandatory
        DESCRIPTION
                "The maximum amount of time (in seconds) allowed for a
                 TCP connection to stay established to the backup DLSw
                 peer.  If set to zero, this feature is disabled.  Set
                 to anything greater than zero to enable the feature."
        DEFVAL	{ 0 }
        ::= { wfDlsPeerEntry 13 }

    wfDlsPeerBackupHoldDownTime OBJECT-TYPE
        SYNTAX	INTEGER(0..2147483647)
        ACCESS	read-write
        STATUS	mandatory
        DESCRIPTION
                "The amount of time (in seconds) to wait before starting
                 a new TCP connection to the backup DLSw peer."
        DEFVAL	{ 120 }
        ::= { wfDlsPeerEntry 14 }

    wfDlsPeerBackupStartTime OBJECT-TYPE
        SYNTAX	INTEGER(0..2400)
        ACCESS	read-write
        STATUS	mandatory
        DESCRIPTION
                "Used in conjunction with the EndTime attribute.  Together
                 these define a time interval for when a backup peer can
                 be active.  The start time is the beginning time of day
                 that a backup peer can be established.  (HHMM format)"
        DEFVAL	{ 0001 }
        ::= { wfDlsPeerEntry 15 }

    wfDlsPeerBackupEndTime OBJECT-TYPE
        SYNTAX	INTEGER(1..2400)
        ACCESS	read-write
        STATUS	mandatory
        DESCRIPTION
                "Used in conjunction with the StartTime attribute.  Together
                 these define a time interval for when a backup peer can
                 be active.  The end time is the end time of day that a
                 backup peer can be established.  If a backup peer is active
                 and the current time is after this end time, the backup
                 peer will be brought down.  (HHMM format)"
        DEFVAL	{ 2400 }
        ::= { wfDlsPeerEntry 16 }

    wfDlsPeerInteroperability OBJECT-TYPE
	SYNTAX  INTEGER {
    		    enabled(1),
    		    disabled(2)
                }
        ACCESS  read-write
        STATUS  mandatory
        DESCRIPTION
                "If enabled, open write to read tcp connection for 1434 and
		 1795 type of peers.
		 Let the other side to open the other connection."
        DEFVAL  { enabled }
        ::= { wfDlsPeerEntry 17 }

    wfDlsPeerBackupType OBJECT-TYPE
	SYNTAX  INTEGER {
                    multicast(1),
                    v20udp(2),
                    v20unknown(3),
                    v20tcp(4),
		    tcp1795(5)
                }
        ACCESS  read-write
        STATUS  mandatory
        DESCRIPTION
                "The type of this DLSw backup peer"
        DEFVAL  { v20unknown }
        ::= { wfDlsPeerEntry 18 }

    wfDlsPeerRsvpMode OBJECT-TYPE
	SYNTAX  INTEGER {
                    usePeerCfgParams(1),
                    noRsvpForPeer(2),
                    useGlobalCfgParams(3)
                }
        ACCESS  read-write
        STATUS  mandatory
        DESCRIPTION
                "Defines rsvp mode of operation for the peer:
		 - 1 use rsvp parameters configured in the peer;
		 - 2 do NOT use rsvp for this peer;
		 - 3 use rsvp parameters configures in wfDls object."
        DEFVAL  { useGlobalCfgParams }
        ::= { wfDlsPeerEntry 19 }

    wfDlsPeerRsvpSlots OBJECT-TYPE
        SYNTAX	Counter
        ACCESS	read-write
        STATUS	mandatory
        DESCRIPTION
                "Bit mask field representing the slots,
	         that may make RSVP resevations for this peer.
		 The MSBit represents slot 1, the next most significant
		 bit represents slot 2, and so on...  Slots can be 1-14.
                 Default is all slots on a BCN."
        ::= { wfDlsPeerEntry 20 }

    wfDlsPeerOutBandwidth OBJECT-TYPE
	SYNTAX  INTEGER
        ACCESS  read-write
        STATUS  mandatory
        DESCRIPTION
                "Bandwidth amount for the outgoing DLSw traffic,
		 to use in RSVP reservations for this peer"
        DEFVAL  { 0 }
        ::= { wfDlsPeerEntry 21 }

    wfDlsPeerOutBurstSize OBJECT-TYPE
	SYNTAX  INTEGER
        ACCESS  read-write
        STATUS  mandatory
        DESCRIPTION
                "Burst Size amount for the outgoing DLSw traffic,
		 to use in RSVP reservations for this peer"
        DEFVAL  { 0 }
        ::= { wfDlsPeerEntry 22 }

    wfDlsPeerInBandwidth OBJECT-TYPE
	SYNTAX  INTEGER
        ACCESS  read-write
        STATUS  mandatory
        DESCRIPTION
                "Bandwidth amount for the incoming DLSw traffic,
		 to use in RSVP reservations for this peer"
        DEFVAL  { 0 }
        ::= { wfDlsPeerEntry 23 }

    wfDlsPeerInBurstSize OBJECT-TYPE
	SYNTAX  INTEGER
        ACCESS  read-write
        STATUS  mandatory
        DESCRIPTION
                "Burst Size amount for the incoming DLSw traffic,
		 to use in RSVP reservations for this peer"
        DEFVAL  { 0 }
        ::= { wfDlsPeerEntry 24 }

    wfDlsPeerNonPeakOutBandwidth OBJECT-TYPE
	SYNTAX  INTEGER
        ACCESS  read-write
        STATUS  mandatory
        DESCRIPTION
                "Bandwidth amount for the outgoing DLSw traffic,
		 to use in RSVP reservations for this peer
		 during non-peak hours"
        DEFVAL  { 0 }
        ::= { wfDlsPeerEntry 25 }

    wfDlsPeerNonPeakOutBurstSize OBJECT-TYPE
	SYNTAX  INTEGER
        ACCESS  read-write
        STATUS  mandatory
        DESCRIPTION
                "Burst Size amount for the outgoing DLSw traffic,
		 to use in RSVP reservations for this peer
		 during non-peak hours"
        DEFVAL  { 0 }
        ::= { wfDlsPeerEntry 26 }

    wfDlsPeerNonPeakInBandwidth OBJECT-TYPE
	SYNTAX  INTEGER
        ACCESS  read-write
        STATUS  mandatory
        DESCRIPTION
                "Bandwidth amount for the incoming DLSw traffic,
		 to use in RSVP reservations for this peer
		 during non-peak hours"
        DEFVAL  { 0 }
        ::= { wfDlsPeerEntry 27 }

    wfDlsPeerNonPeakInBurstSize OBJECT-TYPE
	SYNTAX  INTEGER
        ACCESS  read-write
        STATUS  mandatory
        DESCRIPTION
                "Burst Size amount for the incoming DLSw traffic,
		 to use in RSVP reservations for this peer
		 during non-peak hours"
        DEFVAL  { 0 }
        ::= { wfDlsPeerEntry 28 }

    wfDlsPeerNonPeakStartTime OBJECT-TYPE
        SYNTAX  INTEGER
        ACCESS  read-write
        STATUS  mandatory
        DESCRIPTION
                "Start time of the non-peak hours in hhmm format and
		 24 hour clock. If start time is greater in value than
		 end time, non-peak hours ends the next day."
        DEFVAL  { 0 }
        ::= { wfDlsPeerEntry 29 }

    wfDlsPeerNonPeakEndTime OBJECT-TYPE
        SYNTAX  INTEGER
        ACCESS  read-write
        STATUS  mandatory
        DESCRIPTION
                "End time of the non-peak hours in hhmm 24 hour clock format"
        DEFVAL  { 0 }
        ::= { wfDlsPeerEntry 30 }

    wfDlsPeerNonPeakStartDays OBJECT-TYPE
        SYNTAX	Counter
        ACCESS  read-write
        STATUS  mandatory
        DESCRIPTION
               "Bitmap of the starting days of the week for a non-peak
		reservations.
		The MSBit represents Sunday, the next most significant
		bit represents Monday, and so on...
                Default is 0 - non-peak parameters are not used."
        ::= { wfDlsPeerEntry 31 }

    wfDlsPeerBackupOutBandwidth OBJECT-TYPE
	SYNTAX  INTEGER(0..2147483647)
        ACCESS  read-write
        STATUS  mandatory
        DESCRIPTION
                "Bandwidth amount for the outgoing DLSw traffic,
		 to use in RSVP reservations for the backup peer"
        DEFVAL  { 0 }
        ::= { wfDlsPeerEntry 32 }

    wfDlsPeerBackupOutBurstSize OBJECT-TYPE
	SYNTAX  INTEGER(0..2147483647)
        ACCESS  read-write
        STATUS  mandatory
        DESCRIPTION
                "Burst Size amount for the outgoing DLSw traffic,
		 to use in RSVP reservations for the backup peer"
        DEFVAL  { 0 }
        ::= { wfDlsPeerEntry 33 }

    wfDlsPeerBackupInBandwidth OBJECT-TYPE
	SYNTAX  INTEGER(0..2147483647)
        ACCESS  read-write
        STATUS  mandatory
        DESCRIPTION
                "Bandwidth amount for the incoming DLSw traffic,
		 to use in RSVP reservations for the backup peer"
        DEFVAL  { 0 }
        ::= { wfDlsPeerEntry 34 }

    wfDlsPeerBackupInBurstSize OBJECT-TYPE
	SYNTAX  INTEGER(0..2147483647)
        ACCESS  read-write
        STATUS  mandatory
        DESCRIPTION
                "Burst Size amount for the incoming DLSw traffic,
		 to use in RSVP reservations for the backup peer"
        DEFVAL  { 0 }
        ::= { wfDlsPeerEntry 35 }


    wfDlsConnectionTable OBJECT-TYPE
        SYNTAX	SEQUENCE OF WfDlsConnectionEntry
        ACCESS	not-accessible
        STATUS	mandatory
        DESCRIPTION
                "A table that contains the information about the current DLSw connections in
                progress.
                inst_id[15] = wfDlsConnectionCct wfDlsConnectionSrcMac wfDlsConnectionDstMac
                              wfDlsConnectionSaps"
        ::= { wfDlsGroup 6 }

    wfDlsConnectionEntry OBJECT-TYPE
        SYNTAX	WfDlsConnectionEntry
        ACCESS	not-accessible
        STATUS	mandatory
        DESCRIPTION
                "An entry in wfDlsConnection"
        INDEX	{ wfDlsConnectionCct,
    		  wfDlsConnectionDstMac,
    		  wfDlsConnectionSrcMac,
    		  wfDlsConnectionSaps }
        ::= { wfDlsConnectionTable 1 }

    WfDlsConnectionEntry ::= SEQUENCE {
    	    wfDlsConnectionCct
    		INTEGER,
    	    wfDlsConnectionDstMac
    		OCTET STRING,
    	    wfDlsConnectionSrcMac
    		OCTET STRING,
    	    wfDlsConnectionSaps
    		OCTET STRING,
    	    wfDlsConnectionState
    		INTEGER,
    	    wfDlsConnectionRemoteIpAddr
    		IpAddress,
    	    wfDlsConnectionRemoteRxPort
    		INTEGER,
    	    wfDlsConnectionLocalIpAddr
    		IpAddress,
    	    wfDlsConnectionLocalTxPort
    		INTEGER,
    	    wfDlsConnectionTxIFrames
    		Counter,
    	    wfDlsConnectionRxIFrames
    		Counter,
    	    wfDlsConnectionTxRnrs
    		Counter,
    	    wfDlsConnectionRxRnrs
    		Counter,
            wfDlsConnectionLocalBlockNum
            DisplayString,
            wfDlsConnectionLocalIdNum
            DisplayString,
            wfDlsConnectionLocalCpName
            DisplayString,
            wfDlsConnectionRif
            OCTET STRING,
            wfDlsConnectionRemoteBlockNum
            DisplayString,
            wfDlsConnectionRemoteIdNum
            DisplayString,
            wfDlsConnectionRemoteCpName
            DisplayString,
            wfDlsConnectionLocalDLCorr
            OCTET STRING,
            wfDlsConnectionKilled
            INTEGER,
            wfDlsConnectionRemoteDLCorr
            OCTET STRING
        }

    wfDlsConnectionCct OBJECT-TYPE
        SYNTAX	INTEGER
        ACCESS	read-only
        STATUS	mandatory
        DESCRIPTION
                "The circuit this from which this connection originated"
        ::= { wfDlsConnectionEntry 1 }

    wfDlsConnectionDstMac OBJECT-TYPE
        SYNTAX	OCTET STRING (SIZE (6))
        ACCESS	read-only
        STATUS	mandatory
        DESCRIPTION
                "The Destination MAC address (the LLC session target)"
        ::= { wfDlsConnectionEntry 2 }

    wfDlsConnectionSrcMac OBJECT-TYPE
        SYNTAX	OCTET STRING (SIZE (6))
        ACCESS	read-only
        STATUS	mandatory
        DESCRIPTION
                "The Source MAC address (the LLC session originator)"
        ::= { wfDlsConnectionEntry 3 }

    wfDlsConnectionSaps OBJECT-TYPE
        SYNTAX	OCTET STRING (SIZE (2))
        ACCESS	read-only
        STATUS	mandatory
        DESCRIPTION
                "The SAPs for this connection (DSAP, SSAP)"
        ::= { wfDlsConnectionEntry 4 }

    wfDlsConnectionState OBJECT-TYPE
        SYNTAX	INTEGER {
    		    connect(1),
    		    ccestab(2),
    		    notconn(3)
    		}
        ACCESS	read-only
        STATUS	mandatory
        DESCRIPTION
                "The DLSw state of this connection. These are the steady states of the
                DLSw state machine.  Transition states are not reflected"
        DEFVAL	{ notconn }
        ::= { wfDlsConnectionEntry 5 }

    wfDlsConnectionRemoteIpAddr OBJECT-TYPE
        SYNTAX	IpAddress
        ACCESS	read-only
        STATUS	mandatory
        DESCRIPTION
                "The IP address of the remote DLSw peer over which
                this connection is established"
        ::= { wfDlsConnectionEntry 6 }

    wfDlsConnectionRemoteRxPort OBJECT-TYPE
        SYNTAX	INTEGER
        ACCESS	read-only
        STATUS	mandatory
        DESCRIPTION
                "The TCP receive port number of the remote DLSw peer over which
                this connection is established"
        ::= { wfDlsConnectionEntry 7 }

    wfDlsConnectionLocalIpAddr OBJECT-TYPE
        SYNTAX	IpAddress
        ACCESS	read-only
        STATUS	mandatory
        DESCRIPTION
                "The IP address of the local DLSw peer over which
                this connection is established"
        ::= { wfDlsConnectionEntry 8 }

    wfDlsConnectionLocalTxPort OBJECT-TYPE
        SYNTAX	INTEGER
        ACCESS	read-only
        STATUS	mandatory
        DESCRIPTION
                "The TCP transmit port number of the local DLSw peer over which
                this connection is established"
        ::= { wfDlsConnectionEntry 9 }

    wfDlsConnectionTxIFrames OBJECT-TYPE
        SYNTAX	Counter
        ACCESS	read-only
        STATUS	mandatory
        DESCRIPTION
                "The number of Information frames transmitted from this switch
                to the remote DLSw switch"
        ::= { wfDlsConnectionEntry 10 }

    wfDlsConnectionRxIFrames OBJECT-TYPE
        SYNTAX	Counter
        ACCESS	read-only
        STATUS	mandatory
        DESCRIPTION
                "The number of Information frames received at this switch
                from the remote DLSw switch"
        ::= { wfDlsConnectionEntry 11 }

    wfDlsConnectionTxRnrs OBJECT-TYPE
        SYNTAX	Counter
        ACCESS	read-only
        STATUS	mandatory
        DESCRIPTION
                "The number of RNR frames transmitted from this switch
                to the remote DLSw switch"
        ::= { wfDlsConnectionEntry 12 }

    wfDlsConnectionRxRnrs OBJECT-TYPE
        SYNTAX	Counter
        ACCESS	read-only
        STATUS	mandatory
        DESCRIPTION
                "The number of RNR frames received at this switch
                from the remote DLSw switch"
        ::= { wfDlsConnectionEntry 13 }

    wfDlsConnectionLocalBlockNum OBJECT-TYPE
        SYNTAX	DisplayString
        ACCESS	read-only
        STATUS	mandatory
        DESCRIPTION
                "The block number is the first 3 hexadecimal digits of
                 node identification field of local XID"
        ::= { wfDlsConnectionEntry 14 }

    wfDlsConnectionLocalIdNum OBJECT-TYPE
        SYNTAX	DisplayString
        ACCESS	read-only
        STATUS	mandatory
        DESCRIPTION
                "The ID number is the last 5 hexadecimal digits of
                 node identification field of local XID"
        ::= { wfDlsConnectionEntry 15 }

    wfDlsConnectionLocalCpName OBJECT-TYPE
        SYNTAX	DisplayString
        ACCESS	read-only
        STATUS	mandatory
        DESCRIPTION
                "The local CP name"
        ::= { wfDlsConnectionEntry 16 }

    wfDlsConnectionRif OBJECT-TYPE
        SYNTAX	OCTET STRING
        ACCESS	read-only
        STATUS	mandatory
        DESCRIPTION
                "The Rif information"
        ::= { wfDlsConnectionEntry 17 }

    wfDlsConnectionRemoteBlockNum OBJECT-TYPE
        SYNTAX	DisplayString
        ACCESS	read-only
        STATUS	mandatory
        DESCRIPTION
                "The block number is the first 3 hexadecimal digits of
                 node identification field of remote XID"
        ::= { wfDlsConnectionEntry 18 }

    wfDlsConnectionRemoteIdNum OBJECT-TYPE
        SYNTAX	DisplayString
        ACCESS	read-only
        STATUS	mandatory
        DESCRIPTION
                "The ID number is the last 5 hexadecimal digits of
                 node identification field of remote XID"
        ::= { wfDlsConnectionEntry 19 }

    wfDlsConnectionRemoteCpName OBJECT-TYPE
        SYNTAX	DisplayString
        ACCESS	read-only
        STATUS	mandatory
        DESCRIPTION
                "The remote CP name"
        ::= { wfDlsConnectionEntry 20 }

    wfDlsConnectionLocalDLCorr OBJECT-TYPE
        SYNTAX  OCTET STRING (SIZE (4))
        ACCESS  read-only
        STATUS  mandatory
        DESCRIPTION
                "The local Data Link Correlator for this DLSw circuit"
        ::= { wfDlsConnectionEntry 21 }

    wfDlsConnectionKilled OBJECT-TYPE
        SYNTAX  INTEGER {
                    alive(1),
                    dead(2)
                }
        ACCESS  read-write
        STATUS  mandatory
        DESCRIPTION
                "Set to Dead to delete a connection"
        DEFVAL  { alive }
        ::= { wfDlsConnectionEntry 22 }

    wfDlsConnectionRemoteDLCorr OBJECT-TYPE
        SYNTAX  OCTET STRING (SIZE (4))
        ACCESS  read-only
        STATUS  mandatory
        DESCRIPTION
                "The remote Data Link Correlator for this DLSw circuit"
        ::= { wfDlsConnectionEntry 23 }

    wfDlsNbTable OBJECT-TYPE
        SYNTAX	SEQUENCE OF WfDlsNbEntry
        ACCESS	not-accessible
        STATUS	mandatory
        DESCRIPTION
                "The DLSw NetBIOS name cache table.  inst_id[16] = wfDlsNbName"
        ::= { wfDlsGroup 7 }

    wfDlsNbEntry OBJECT-TYPE
        SYNTAX	WfDlsNbEntry
        ACCESS	not-accessible
        STATUS	mandatory
        DESCRIPTION
                "An entry in wfDlsNb"
        INDEX	{ wfDlsNbName }
        ::= { wfDlsNbTable 1 }

    WfDlsNbEntry ::= SEQUENCE {
    	    wfDlsNbName
    		OCTET STRING,
    	    wfDlsNbPeerIpAddr
    		IpAddress,
    	    wfDlsNbCapablePeerIpAddr
    		IpAddress,
    	    wfDlsNbQueries
    		Counter
        }

    wfDlsNbName OBJECT-TYPE
        SYNTAX	OCTET STRING (SIZE (16))
        ACCESS	read-only
        STATUS	mandatory
        DESCRIPTION
                "The NetBIOS name of the remote station. Names that are shorter than 16
                characters are padded with ASCII spaces (0x20)"
        ::= { wfDlsNbEntry 1 }

    wfDlsNbPeerIpAddr OBJECT-TYPE
        SYNTAX	IpAddress
        ACCESS	read-only
        STATUS	mandatory
        DESCRIPTION
                "The IP address of the DLSw peer for this NetBIOS name"
        ::= { wfDlsNbEntry 2 }

    wfDlsNbCapablePeerIpAddr OBJECT-TYPE
        SYNTAX	IpAddress
        ACCESS	read-only
        STATUS	mandatory
        DESCRIPTION
                "The IP address of the DLSw peer for a capable NetBIOS name"
        ::= { wfDlsNbEntry 3 }

    wfDlsNbQueries OBJECT-TYPE
        SYNTAX	Counter
        ACCESS	read-only
        STATUS	mandatory
        DESCRIPTION
                "The number of NETBIOS_NQ queries sent for this name"
        ::= { wfDlsNbEntry 4 }

    wfDlsMacTable OBJECT-TYPE
        SYNTAX	SEQUENCE OF WfDlsMacEntry
        ACCESS	not-accessible
        STATUS	mandatory
        DESCRIPTION
                "The DLSw MAC address cache table.  inst_id[6] = wfDlsMacAddr"
        ::= { wfDlsGroup 8 }

    wfDlsMacEntry OBJECT-TYPE
        SYNTAX	WfDlsMacEntry
        ACCESS	not-accessible
        STATUS	mandatory
        DESCRIPTION
                "An entry in wfDlsMac"
        INDEX	{ wfDlsMacAddr }
        ::= { wfDlsMacTable 1 }

    WfDlsMacEntry ::= SEQUENCE {
    	    wfDlsMacAddr
    		OCTET STRING,
    	    wfDlsMacPeerIpAddr
    		IpAddress,
    	    wfDlsMacCapablePeerIpAddr
    		IpAddress,
    	    wfDlsMacQueries
    		Counter
        }

    wfDlsMacAddr OBJECT-TYPE
        SYNTAX	OCTET STRING (SIZE (6))
        ACCESS	read-only
        STATUS	mandatory
        DESCRIPTION
                "The MAC address of the remote station"
        ::= { wfDlsMacEntry 1 }

    wfDlsMacPeerIpAddr OBJECT-TYPE
        SYNTAX	IpAddress
        ACCESS	read-only
        STATUS	mandatory
        DESCRIPTION
                "The IP address of the DLSw peer for this MAC address"
        ::= { wfDlsMacEntry 2 }

    wfDlsMacCapablePeerIpAddr OBJECT-TYPE
        SYNTAX	IpAddress
        ACCESS	read-only
        STATUS	mandatory
        DESCRIPTION
                "The IP address of the DLSw peer for a capable MAC address"
        ::= { wfDlsMacEntry 3 }

    wfDlsMacQueries OBJECT-TYPE
        SYNTAX	Counter
        ACCESS	read-only
        STATUS	mandatory
        DESCRIPTION
                "The number of CANUREACH queries sent for this name"
        ::= { wfDlsMacEntry 4 }

    wfDlsTrafficFilterTable OBJECT-TYPE
        SYNTAX	SEQUENCE OF WfDlsTrafficFilterEntry
        ACCESS	not-accessible
        STATUS	mandatory
        DESCRIPTION
                "DLSw Traffic Filters"
        ::= { wfDlsGroup 9 }

    wfDlsTrafficFilterEntry OBJECT-TYPE
        SYNTAX	WfDlsTrafficFilterEntry
        ACCESS	not-accessible
        STATUS	mandatory
        DESCRIPTION
                "An entry in WfDlsTrafficFilterTable"
        INDEX	{ wfDlsTrafficFilterCircuit,
    		  wfDlsTrafficFilterRuleNumber,
    		  wfDlsTrafficFilterFragment }
        ::= { wfDlsTrafficFilterTable 1 }

    WfDlsTrafficFilterEntry ::= SEQUENCE {
    	    wfDlsTrafficFilterCreate
    		INTEGER,
    	    wfDlsTrafficFilterEnable
    		INTEGER,
    	    wfDlsTrafficFilterStatus
    		INTEGER,
    	    wfDlsTrafficFilterCounter
    		Counter,
    	    wfDlsTrafficFilterDefinition
    		OCTET STRING,
    	    wfDlsTrafficFilterReserved
    		INTEGER,
    	    wfDlsTrafficFilterCircuit
    		INTEGER,
    	    wfDlsTrafficFilterRuleNumber
    		INTEGER,
    	    wfDlsTrafficFilterFragment
    		INTEGER,
    	    wfDlsTrafficFilterName
    		DisplayString
        }

    wfDlsTrafficFilterCreate OBJECT-TYPE
        SYNTAX	INTEGER {
    		    created(1),
    		    deleted(2)
    		}
        ACCESS	read-write
        STATUS	mandatory
        DESCRIPTION
                "Defines the existence of the traffic filter rule:
                created - traffic filter exists
                delete - traffic filter does not exist and can be deleted"
        DEFVAL	{ created }
        ::= { wfDlsTrafficFilterEntry 1 }

    wfDlsTrafficFilterEnable OBJECT-TYPE
        SYNTAX	INTEGER {
    		    enabled(1),
    		    disabled(2)
    		}
        ACCESS	read-write
        STATUS	mandatory
        DESCRIPTION
                "Defines whether or not the traffic filter rule should be used:
                enabled - activate the rule.
                disabled - inactivate the rule"
        DEFVAL	{ enabled }
        ::= { wfDlsTrafficFilterEntry 2 }

    wfDlsTrafficFilterStatus OBJECT-TYPE
        SYNTAX	INTEGER {
    		    active(1),
    		    error(2),
    		    inactive(3)
    		}
        ACCESS	read-only
        STATUS	mandatory
        DESCRIPTION
                "Defines the current status of the traffic filter:
                inactive - the rule is not in use.
                active - the rule is being used.
                error - the application detected an error in the rule"
        DEFVAL	{ inactive }
        ::= { wfDlsTrafficFilterEntry 3 }

    wfDlsTrafficFilterCounter OBJECT-TYPE
        SYNTAX	Counter
        ACCESS	read-only
        STATUS	mandatory
        DESCRIPTION
                "The number of received packets that have matched this rule"
        ::= { wfDlsTrafficFilterEntry 4 }

    wfDlsTrafficFilterDefinition OBJECT-TYPE
        SYNTAX	OCTET STRING
        ACCESS	read-write
        STATUS	mandatory
        DESCRIPTION
                "The filter rule definition"
        ::= { wfDlsTrafficFilterEntry 5 }

    wfDlsTrafficFilterReserved OBJECT-TYPE
        SYNTAX	INTEGER
        ACCESS	read-only
        STATUS	mandatory
        DESCRIPTION
                "Reserved field"
        ::= { wfDlsTrafficFilterEntry 6 }

    wfDlsTrafficFilterCircuit OBJECT-TYPE
        SYNTAX	INTEGER
        ACCESS	read-only
        STATUS	mandatory
        DESCRIPTION
                "The ID of the Bridge Circuit to which the filter is applied"
        ::= { wfDlsTrafficFilterEntry 7 }

    wfDlsTrafficFilterRuleNumber OBJECT-TYPE
        SYNTAX	INTEGER
        ACCESS	read-only
        STATUS	mandatory
        DESCRIPTION
                "ID for the rule"
        ::= { wfDlsTrafficFilterEntry 8 }

    wfDlsTrafficFilterFragment OBJECT-TYPE
        SYNTAX	INTEGER
        ACCESS	read-only
        STATUS	mandatory
        DESCRIPTION
                "Fragment number - for large rules"
        ::= { wfDlsTrafficFilterEntry 9 }

    wfDlsTrafficFilterName OBJECT-TYPE
        SYNTAX	DisplayString
        ACCESS	read-write
        STATUS	mandatory
        DESCRIPTION
                "name of the rule number"
        ::= { wfDlsTrafficFilterEntry 10 }

    wfDlsDefaultMacTable OBJECT-TYPE
        SYNTAX	SEQUENCE OF WfDlsDefaultMacEntry
        ACCESS	not-accessible
        STATUS	mandatory
        DESCRIPTION
                "A table that contains DLSw Peer IP addresses for statically defined remote
                MAC addresses.  The IP address in this table will always be used for
                CANUREACH messages to the remote MAC address.
                inst_id[6] = wfDlsDefaultMacAddr"
        ::= { wfDlsGroup 10 }

    wfDlsDefaultMacEntry OBJECT-TYPE
        SYNTAX	WfDlsDefaultMacEntry
        ACCESS	not-accessible
        STATUS	mandatory
        DESCRIPTION
                "An entry in wfDlsNbName"
        INDEX	{ wfDlsDefaultMacAddr }
        ::= { wfDlsDefaultMacTable 1 }

    WfDlsDefaultMacEntry ::= SEQUENCE {
    	    wfDlsDefaultMacDelete
    		INTEGER,
    	    wfDlsDefaultMacAddr
    		OCTET STRING,
    	    wfDlsDefaultMacPeerIp
    		IpAddress
        }

    wfDlsDefaultMacDelete OBJECT-TYPE
        SYNTAX	INTEGER {
    		    created(1),
    		    deleted(2)
    		}
        ACCESS	read-write
        STATUS	mandatory
        DESCRIPTION
                "Create/Delete parameter. Default is created. Users perform an SNMP SET
                operation on this object in order to create/delete a DLSw Default MAC
                record"
        DEFVAL	{ created }
        ::= { wfDlsDefaultMacEntry 1 }

    wfDlsDefaultMacAddr OBJECT-TYPE
        SYNTAX	OCTET STRING (SIZE (6))
        ACCESS	read-only
        STATUS	mandatory
        DESCRIPTION
                "The MAC address of the destination station"
        ::= { wfDlsDefaultMacEntry 2 }

    wfDlsDefaultMacPeerIp OBJECT-TYPE
        SYNTAX	IpAddress
        ACCESS	read-write
        STATUS	mandatory
        DESCRIPTION
                "The peer IP address to use for this MAC address"
        ::= { wfDlsDefaultMacEntry 3 }

    wfDlsDefaultNbTable OBJECT-TYPE
        SYNTAX	SEQUENCE OF WfDlsDefaultNbEntry
        ACCESS	not-accessible
        STATUS	mandatory
        DESCRIPTION
                "A table that contains DLSw Peer IP addresses for statically defined remote
                NetBIOS names.  The IP address in this table will always be used for
                CANUREACH messages to the remote NetBIOS name.
                inst_id[16] = wfDlsDefaultNbName"
        ::= { wfDlsGroup 11 }

    wfDlsDefaultNbEntry OBJECT-TYPE
        SYNTAX	WfDlsDefaultNbEntry
        ACCESS	not-accessible
        STATUS	mandatory
        DESCRIPTION
                "An entry in wfDlsDefaultNb"
        INDEX	{ wfDlsDefaultNbName }
        ::= { wfDlsDefaultNbTable 1 }

    WfDlsDefaultNbEntry ::= SEQUENCE {
    	    wfDlsDefaultNbDelete
    		INTEGER,
    	    wfDlsDefaultNbName
    		OCTET STRING,
    	    wfDlsDefaultNbPeerIp
    		IpAddress
        }

    wfDlsDefaultNbDelete OBJECT-TYPE
        SYNTAX	INTEGER {
    		    created(1),
    		    deleted(2)
    		}
        ACCESS	read-write
        STATUS	mandatory
        DESCRIPTION
                "Create/Delete parameter. Default is created. Users perform an SNMP SET
                operation on this object in order to create/delete a DLSw Default NetBIOS
                record"
        DEFVAL	{ created }
        ::= { wfDlsDefaultNbEntry 1 }

    wfDlsDefaultNbName OBJECT-TYPE
        SYNTAX	OCTET STRING (SIZE (16))
        ACCESS	read-only
        STATUS	mandatory
        DESCRIPTION
                "The NetBIOS name of the destination station"
        ::= { wfDlsDefaultNbEntry 2 }

    wfDlsDefaultNbPeerIp OBJECT-TYPE
        SYNTAX	IpAddress
        ACCESS	read-write
        STATUS	mandatory
        DESCRIPTION
                "The peer IP address to use for this NetBIOS name"
        ::= { wfDlsDefaultNbEntry 3 }

    wfDlsLocalDeviceTable OBJECT-TYPE
        SYNTAX	SEQUENCE OF WfDlsLocalDeviceEntry
        ACCESS	not-accessible
        STATUS	mandatory
        DESCRIPTION
                "The configuration table for devices locally terminated through DLSw"
        ::= { wfDlsGroup 12 }

    wfDlsLocalDeviceEntry OBJECT-TYPE
        SYNTAX	WfDlsLocalDeviceEntry
        ACCESS	not-accessible
        STATUS	mandatory
        DESCRIPTION
                "An entry in the DLSw Local Device table"
        INDEX	{ wfDlsLocalDeviceCct,
    		  wfDlsLocalDeviceAddr }
        ::= { wfDlsLocalDeviceTable 1 }

    WfDlsLocalDeviceEntry ::= SEQUENCE {
    	    wfDlsLocalDeviceDelete
    		INTEGER,
    	    wfDlsLocalDeviceDisable
    		INTEGER,
    	    wfDlsLocalDeviceState
    		INTEGER,
    	    wfDlsLocalDeviceCct
    		INTEGER,
    	    wfDlsLocalDeviceAddr
    		INTEGER,
    	    wfDlsLocalDeviceSourceMac
    		OCTET STRING,
    	    wfDlsLocalDeviceSourceSap
    		INTEGER,
    	    wfDlsLocalDeviceDestMac
    		OCTET STRING,
    	    wfDlsLocalDeviceDestSap
    		INTEGER,
    	    wfDlsLocalDeviceXidValue
    		OCTET STRING,
    	    wfDlsLocalDeviceCanureachTimer
    		INTEGER,
    	    wfDlsLocalDeviceCanureachRetries
    		Gauge,
    	    wfDlsLocalDeviceLSTimer
    		INTEGER,
    	    wfDlsLocalDeviceLSRetries
    		Gauge,
    	    wfDlsLocalDeviceRcvCredit
    		INTEGER,
    	    wfDlsLocalDeviceTxCredit
    		INTEGER,
    	    wfDlsLocalDeviceCurTimer2
    		INTEGER,
    	    wfDlsLocalDeviceCurRetries2
    		Gauge,
            wfDlsLocalDeviceEnableXidPassthru
               INTEGER,
            wfDlsLocalDeviceActivationSequence
               INTEGER

        }

    wfDlsLocalDeviceDelete OBJECT-TYPE
        SYNTAX	INTEGER {
    		    created(1),
    		    deleted(2)
    		}
        ACCESS	read-write
        STATUS	mandatory
        DESCRIPTION
                "Create/Delete parameter. Default is created. Users perform an SNMP SET
                operation on this object in order to create/delete a DLSw Local Device"
        DEFVAL	{ created }
        ::= { wfDlsLocalDeviceEntry 1 }

    wfDlsLocalDeviceDisable OBJECT-TYPE
        SYNTAX	INTEGER {
    		    enabled(1),
    		    disabled(2)
    		}
        ACCESS	read-write
        STATUS	mandatory
        DESCRIPTION
                "Enable/Disable parameter. Default is enabled. Users perform an SNMP SET
                operation on this object in order to enable/disable a DLSw Local Device"
        DEFVAL	{ enabled }
        ::= { wfDlsLocalDeviceEntry 2 }

    wfDlsLocalDeviceState OBJECT-TYPE
        SYNTAX	INTEGER {
    		    up(1),
    		    down(2),
    		    init(3),
    		    notpresent(4)
    		}
        ACCESS	read-only
        STATUS	mandatory
        DESCRIPTION
                "The current state of DLSw"
        DEFVAL	{ notpresent }
        ::= { wfDlsLocalDeviceEntry 3 }

    wfDlsLocalDeviceCct OBJECT-TYPE
        SYNTAX	INTEGER
        ACCESS	read-only
        STATUS	mandatory
        DESCRIPTION
                "The circuit on which this device is configured. Valid range (1-1023)"
        ::= { wfDlsLocalDeviceEntry 4 }

    wfDlsLocalDeviceAddr OBJECT-TYPE
        SYNTAX	INTEGER
        ACCESS	read-only
        STATUS	mandatory
        DESCRIPTION
                "The physical address for this device. Valid range is based on media"
        ::= { wfDlsLocalDeviceEntry 5 }

    wfDlsLocalDeviceSourceMac OBJECT-TYPE
        SYNTAX	OCTET STRING
        ACCESS	read-write
        STATUS	mandatory
        DESCRIPTION
                "The source MAC address of an emulated Token Ring end station for this
                device.  Values are standard MSB Token Ring MAC addresses"
        ::= { wfDlsLocalDeviceEntry 6 }

    wfDlsLocalDeviceSourceSap OBJECT-TYPE
        SYNTAX	INTEGER(0..254)
        ACCESS	read-write
        STATUS	mandatory
        DESCRIPTION
                "The source SAP of an emulated Token Ring end station for this device.
                Values are standard SNA SAPs"
        DEFVAL	{ 4 }
        ::= { wfDlsLocalDeviceEntry 7 }

    wfDlsLocalDeviceDestMac OBJECT-TYPE
        SYNTAX	OCTET STRING
        ACCESS	read-write
        STATUS	mandatory
        DESCRIPTION
                "The destination MAC address for this device. Values are standard MSB Token
                Ring MAC addresses"
        ::= { wfDlsLocalDeviceEntry 8 }

    wfDlsLocalDeviceDestSap OBJECT-TYPE
        SYNTAX	INTEGER(0..254)
        ACCESS	read-write
        STATUS	mandatory
        DESCRIPTION
                "The destination SAP for this device.  Values are standard SNA SAPs"
        DEFVAL	{ 4 }
        ::= { wfDlsLocalDeviceEntry 9 }

    wfDlsLocalDeviceXidValue OBJECT-TYPE
        SYNTAX	OCTET STRING
        ACCESS	read-write
        STATUS	mandatory
        DESCRIPTION
                "The station XID value. Value must match the IDBLK and IDNUM on the host"
        ::= { wfDlsLocalDeviceEntry 10 }

    wfDlsLocalDeviceCanureachTimer OBJECT-TYPE
        SYNTAX	INTEGER(0..3600)
        ACCESS	read-write
        STATUS	mandatory
        DESCRIPTION
                "The time interval in seconds that a canureach is sent to the remote DLS
                peer to establish a session. A minimum value of 1 means that a canureach
                will be transmitted once a second, a maximum value of 3600 means that a
                canureach will be transmitted once an hour, and a value of 0 means that
                no canureach will be transmitted"
        DEFVAL	{ 30 }
        ::= { wfDlsLocalDeviceEntry 11 }

    wfDlsLocalDeviceCanureachRetries OBJECT-TYPE
        SYNTAX	Gauge(0..4294967295)
        ACCESS	read-write
        STATUS	mandatory
        DESCRIPTION
                "The maximum number of times a canureach is sent to the remote DLS peer to
                establish a session.  A minimum value of 0 means that no canureach messages
                will be transmitted, a maximum value of 0xFFFFFFFF means that an infinite
                number of canureach messages will be transmitted for this connection.
                The default is set to 10"
        DEFVAL	{ 10 }
        ::= { wfDlsLocalDeviceEntry 12 }

    wfDlsLocalDeviceLSTimer OBJECT-TYPE
        SYNTAX	INTEGER(0..3600)
        ACCESS	read-write
        STATUS	mandatory
        DESCRIPTION
                "The time interval in seconds that a connect request is sent to the local
                SDLC device to establish a session.  A minimum value of 1 means that a
                connect request will be sent once a second, a maximum value of 3600 means
                that a connect request will be sent once an hour, and a value of 0 means
                that no connect requests will be sent"
        DEFVAL	{ 30 }
        ::= { wfDlsLocalDeviceEntry 13 }

    wfDlsLocalDeviceLSRetries OBJECT-TYPE
        SYNTAX	Gauge(0..4294967295)
        ACCESS	read-write
        STATUS	mandatory
        DESCRIPTION
                "The maximum number of times a connect request is sent to the local SDLC
                device to establish a session.  A minimum value of 0 means that no connect
                requests will be sent, a maximum value of 0xFFFFFFFF means that an infinite
                number of connect requests will be sent for this connection.
                The default is set to 10"
        DEFVAL	{ 10 }
        ::= { wfDlsLocalDeviceEntry 14 }

    wfDlsLocalDeviceRcvCredit OBJECT-TYPE
        SYNTAX	INTEGER(0..200)
        ACCESS	read-write
        STATUS	mandatory
        DESCRIPTION
                "Receive credit count. Maximum number of frames SDLC is allowed to send to
                DLS.  A minimum value of 1 means that DLS will only accept up to 1 frame
                from SDLC before it updates SDLCs credit.  A value of 0 means that DLS
                can receive an infinite number of frames from SDLC without the need to
                update SDLC's credit"
        DEFVAL	{ 10 }
        ::= { wfDlsLocalDeviceEntry 15 }

    wfDlsLocalDeviceTxCredit OBJECT-TYPE
        SYNTAX	INTEGER(0..200)
        ACCESS	read-write
        STATUS	mandatory
        DESCRIPTION
                "Transmit credit count. Maximum number of frames DLS is allowed to send to
                SDLC.  A minimum value of 1 means that DLS can only send one frame to SDLC
                until it receives credit update from SDLC.  A value of 0 means that DLS can
                send an infinite number of frames to SDLC without the need to update SDLC's
                credit"
        DEFVAL	{ 10 }
        ::= { wfDlsLocalDeviceEntry 16 }

    wfDlsLocalDeviceCurTimer2 OBJECT-TYPE
        SYNTAX	INTEGER(0..2147483647)
        ACCESS	read-write
        STATUS	mandatory
        DESCRIPTION
                "The time interval in seconds that a canureach is sent to the remote DLS
                peer to establish a session. A minimum value of 1 means that a canureach
                will be transmitted once a second, a maximum value means that a
                canureach will be transmitted once every timer2 seconds, and a value
                of 0 means that no canureach will be transmitted"
        DEFVAL	{ 30 }
        ::= { wfDlsLocalDeviceEntry 17 }

    wfDlsLocalDeviceCurRetries2 OBJECT-TYPE
        SYNTAX	Gauge(0..4294967295)
        ACCESS	read-write
        STATUS	mandatory
        DESCRIPTION
                "The maximum number of times a canureach is sent to the remote DLS peer to
                establish a session.  A minimum value of 0 means that no canureach messages
                will be transmitted, a maximum value of 0xFFFFFFFF means that an infinite
                number of canureach messages will be transmitted for this connection.
                The default is set to infinite: 4294967295  = 0xFFFFFFFF"
        DEFVAL	{ 4294967295 }
        ::= { wfDlsLocalDeviceEntry 18 }

    wfDlsLocalDeviceEnableXidPassthru OBJECT-TYPE
        SYNTAX  INTEGER {
                    enabled(1),
                    disabled(2)
                }
        ACCESS  read-write
        STATUS  mandatory
        DESCRIPTION
                "XID passthru Enable/Disable parameter. Default is enabled.
                Used for pu2.1 circuits to allow the XID to be passed thru to SDLC
                when host is connected to token ring and remote is SDLC."
        DEFVAL  { disabled }
        ::= { wfDlsLocalDeviceEntry 19 }

    wfDlsLocalDeviceActivationSequence OBJECT-TYPE
        SYNTAX  INTEGER {
                    localdevicefirst(1),
                    peerfirst(2)
                }
        ACCESS  read-write
        STATUS  mandatory
        DESCRIPTION
                "Sequence of activation for SDLC PU2.0 fixed format
                 primary devices.  LocalDeviceFirst specifies that DLS 
                 establishes a connection with the SDLC End Station first.
                 Once the Local Device successfully responds, DLS then starts
                 up the SSP connection to the peer.
                 PeerFirst specifies that DLS starts the SSP connection 
                 first, and contacts the SDLC End Station only 
                 after receiving a CONTACT message from the peer. "
        DEFVAL  { localdevicefirst }
        ::= { wfDlsLocalDeviceEntry 20 }

    wfDlsLocalCircuitTable OBJECT-TYPE
        SYNTAX	SEQUENCE OF WfDlsLocalCircuitEntry
        ACCESS	not-accessible
        STATUS	mandatory
        DESCRIPTION
                "communicate with each other via a virtual circuit gate"
        ::= { wfDlsGroup 13 }

    wfDlsLocalCircuitEntry OBJECT-TYPE
        SYNTAX	WfDlsLocalCircuitEntry
        ACCESS	not-accessible
        STATUS	mandatory
        DESCRIPTION
                "An entry in the DLSw Local Circuit table"
        INDEX	{ wfDlsLocalCircuitCct }
        ::= { wfDlsLocalCircuitTable 1 }

    WfDlsLocalCircuitEntry ::= SEQUENCE {
    	    wfDlsLocalCircuitDelete
    		INTEGER,
    	    wfDlsLocalCircuitDisable
    		INTEGER,
    	    wfDlsLocalCircuitState
    		INTEGER,
    	    wfDlsLocalCircuitCct
    		INTEGER,
    	    wfDlsLocalCircuitClientCount
    		INTEGER,
    	    wfDlsLocalCircuitFrameCount
    		INTEGER,
    	    wfDlsLocalCircuitSlot
    		INTEGER,
    	    wfDlsLocalCctDefaultMac
    		OCTET STRING
        }

    wfDlsLocalCircuitDelete OBJECT-TYPE
        SYNTAX	INTEGER {
    		    created(1),
    		    deleted(2)
    		}
        ACCESS	read-write
        STATUS	mandatory
        DESCRIPTION
                "Create/Delete parameter"
        DEFVAL	{ created }
        ::= { wfDlsLocalCircuitEntry 1 }

    wfDlsLocalCircuitDisable OBJECT-TYPE
        SYNTAX	INTEGER {
    		    enabled(1),
    		    disabled(2)
    		}
        ACCESS	read-write
        STATUS	mandatory
        DESCRIPTION
                "Disable parameter"
        DEFVAL	{ enabled }
        ::= { wfDlsLocalCircuitEntry 2 }

    wfDlsLocalCircuitState OBJECT-TYPE
        SYNTAX	INTEGER {
    		    up(1),
    		    down(2)
    		}
        ACCESS	read-only
        STATUS	mandatory
        DESCRIPTION
                "Circuit state"
        DEFVAL	{ down }
        ::= { wfDlsLocalCircuitEntry 3 }

    wfDlsLocalCircuitCct OBJECT-TYPE
        SYNTAX	INTEGER
        ACCESS	read-write
        STATUS	mandatory
        DESCRIPTION
                "Local Circuit  ID"
        ::= { wfDlsLocalCircuitEntry 4 }

    wfDlsLocalCircuitClientCount OBJECT-TYPE
        SYNTAX	INTEGER
        ACCESS	read-only
        STATUS	mandatory
        DESCRIPTION
                "Number of clients registerd"
        ::= { wfDlsLocalCircuitEntry 5 }

    wfDlsLocalCircuitFrameCount OBJECT-TYPE
        SYNTAX	INTEGER
        ACCESS	read-only
        STATUS	mandatory
        DESCRIPTION
                "Total number of frames passed"
        ::= { wfDlsLocalCircuitEntry 6 }

    wfDlsLocalCircuitSlot OBJECT-TYPE
        SYNTAX	INTEGER
        ACCESS	read-write
        STATUS	mandatory
        DESCRIPTION
                "Slot on which this cct resides"
        ::= { wfDlsLocalCircuitEntry 7 }

    wfDlsLocalCctDefaultMac OBJECT-TYPE
        SYNTAX	OCTET STRING
        ACCESS	read-write
        STATUS	mandatory
        DESCRIPTION
                "Default Mac address associated with this circuit"
        ::= { wfDlsLocalCircuitEntry 8 }

    wfDlsGenToolTable OBJECT-TYPE
        SYNTAX  SEQUENCE OF WfDlsGenToolEntry
        ACCESS  not-accessible
        STATUS  mandatory
        DESCRIPTION
                "A table that contains the Gen Tool characteristics to be used
                 on Bay Network Routers. inst_id[1] = wfDlsSlotNumber"
        ::= { wfDlsGroup 14 }

    wfDlsGenToolEntry OBJECT-TYPE
        SYNTAX  WfDlsGenToolEntry
        ACCESS  not-accessible
        STATUS  mandatory
        DESCRIPTION
                "An characteristics for wfDlsGenTool"
        INDEX   { wfDlsSlotNumber }
        ::= { wfDlsGenToolTable 1 }

    WfDlsGenToolEntry ::= SEQUENCE {
            wfDlsGenDelete
                INTEGER,
            wfDlsGenDisable
                INTEGER,
            wfDlsGenDefaultSessions
                INTEGER,
            wfDlsGenStartupTime
                INTEGER,
            wfDlsGenIFramePerSec
                INTEGER,
            wfDlsGenMacAddrOffset
                INTEGER,
            wfDlsGenVariableDstMAC
                INTEGER,
            wfDlsGenDefaultUpperMAC
                INTEGER,
            wfDlsGenDataLength
                INTEGER,
            wfDlsGenNumSapPerMac
                INTEGER,
            wfDlsGenSapIncrement
                INTEGER
        }

    wfDlsGenDelete OBJECT-TYPE
        SYNTAX  INTEGER {
                    created(1),
                    deleted(2)
                }
        ACCESS  read-write
        STATUS  mandatory
        DESCRIPTION
                "Create/Delete parameter. Default is created."
        DEFVAL  { created }
        ::= { wfDlsGenToolEntry 1 }

    wfDlsGenDisable OBJECT-TYPE
        SYNTAX  INTEGER {
                    enabled(1),
                    disabled(2)
                }
        ACCESS  read-write
        STATUS  mandatory
        DESCRIPTION
                "Enable/Disable parameter. Default is disabled. Users perform an
SNMP SET
                operation on this object in order to enable/disable DLSw Generat
or
"
        DEFVAL  { disabled }
        ::= { wfDlsGenToolEntry 2 }

    wfDlsGenDefaultSessions OBJECT-TYPE
        SYNTAX  INTEGER(5..10000)
        ACCESS  read-write
        STATUS  mandatory
        DESCRIPTION
                "Number of DLSw Generator Sessions to be brought up if
                specific numbers are not configured per slot."
        DEFVAL  { 250 }
        ::= { wfDlsGenToolEntry 3 }

    wfDlsGenStartupTime OBJECT-TYPE
        SYNTAX  INTEGER(50..100000)
        ACCESS  read-write
        STATUS  mandatory
        DESCRIPTION
                "Time between connection setup requests in
                milliseconds."
        DEFVAL  { 1000 }
        ::= { wfDlsGenToolEntry 4 }

    wfDlsGenIFramePerSec OBJECT-TYPE
        SYNTAX  INTEGER(0..5000)
        ACCESS  read-write
        STATUS  mandatory
        DESCRIPTION
                "Number of I frames to be sent per second."
        DEFVAL  { 256 }
        ::= { wfDlsGenToolEntry 5 }

    wfDlsGenMacAddrOffset OBJECT-TYPE
        SYNTAX  INTEGER(0..5000)
        ACCESS  read-write
        STATUS  mandatory
        DESCRIPTION
                "Offset for MAC addresses to be created for GEN."
        DEFVAL  { 0 }
        ::= { wfDlsGenToolEntry 6 }

    wfDlsGenVariableDstMAC OBJECT-TYPE
        SYNTAX  INTEGER{
                    enabled(1),
                    disabled(2)
                }
        ACCESS  read-write
        STATUS  mandatory
        DESCRIPTION
                "Allows varying destination MAC address."
        DEFVAL  { disabled }
        ::= { wfDlsGenToolEntry 7 }

    wfDlsGenDefaultUpperMAC OBJECT-TYPE
        SYNTAX  INTEGER(0..2147418112)
        ACCESS  read-write
        STATUS  mandatory
        DESCRIPTION
                "Allows varying upper MAC address."
        DEFVAL  { 1079705600 }
        ::= {wfDlsGenToolEntry 8  }

    wfDlsGenDataLength OBJECT-TYPE
        SYNTAX  INTEGER(0..2052)
        ACCESS  read-write
        STATUS  mandatory
        DESCRIPTION
                "Gen data frame size"
        DEFVAL  { 250 }
        ::= { wfDlsGenToolEntry 9 }

    wfDlsGenNumSapPerMac OBJECT-TYPE
        SYNTAX  INTEGER(1..255)
        ACCESS  read-write
        STATUS  mandatory
        DESCRIPTION
                "Gen number of saps for each mac"
        DEFVAL  { 1 }
        ::= { wfDlsGenToolEntry 10  }

    wfDlsGenSapIncrement OBJECT-TYPE
        SYNTAX  INTEGER(1..100)
        ACCESS  read-write
        STATUS  mandatory
        DESCRIPTION
                "Gen sap incremental value"
        DEFVAL  { 4 }
        ::= { wfDlsGenToolEntry 11 }


    wfDlsMcastIpTable OBJECT-TYPE
        SYNTAX	SEQUENCE OF WfDlsMcastIpEntry
        ACCESS	not-accessible
        STATUS	mandatory
        DESCRIPTION
                "A table that contains the Multicast IP addresses that
		will be used by DLSw ro send and receive explorer traffic."
        ::= { wfDlsGroup 15 }

    wfDlsMcastIpEntry OBJECT-TYPE
        SYNTAX	WfDlsMcastIpEntry
        ACCESS	not-accessible
        STATUS	mandatory
        DESCRIPTION
                "An entry in the wfDlsMcastIpTable"
        INDEX	{ wfDlsMcastIpAddr }
        ::= { wfDlsMcastIpTable 1 }

    WfDlsMcastIpEntry ::= SEQUENCE {
    	    wfDlsMcastIpDelete
    		INTEGER,
    	    wfDlsMcastIpState
    		INTEGER,
    	    wfDlsMcastIpAddr
    		IpAddress,
    	    wfDlsMcastIpSlots
    		Gauge,
            wfDlsMcastIpBackupConfig
            INTEGER,
            wfDlsMcastIpBackupIpAddr
    		IpAddress,	
            wfDlsMcastIpBackupMaxUpTime
            INTEGER,
            wfDlsMcastIpBackupHoldDownTime
            INTEGER,
            wfDlsMcastIpBackupStartTime
            INTEGER,
            wfDlsMcastIpBackupEndTime
            INTEGER,
	    wfDlsMcastIpBackupType
	    INTEGER
        }

    wfDlsMcastIpDelete OBJECT-TYPE
        SYNTAX	INTEGER {
    		    created(1),
    		    deleted(2)
    		}
        ACCESS	read-write
        STATUS	mandatory
        DESCRIPTION
                "Create/Delete parameter. Default is created. Users perform an
		 SNMP SET operation on this object in order to create/delete a
		 DLSw multicast IP record"
        DEFVAL	{ created }
        ::= { wfDlsMcastIpEntry 1 }

    wfDlsMcastIpState OBJECT-TYPE
        SYNTAX	INTEGER {
    		    active(1),
		    inactive(2),
		    notpresent(3)
    		}
        ACCESS	read-only
        STATUS	mandatory
        DESCRIPTION
                "The current state of this DLSw McastIpEntry. Active indicates
		 that it is possible to accept or sent CURs to/from the multicast
		 IP group address specified in this entry. Inactive indicates that
		 DLSw in not a member of this multicast IP group. The initial
		 state is notpresent and this state will be maintained until this
		 mib record has been read."
        DEFVAL	{ notpresent }
        ::= { wfDlsMcastIpEntry 2 }

    wfDlsMcastIpAddr OBJECT-TYPE
        SYNTAX	IpAddress
        ACCESS	read-only
        STATUS	mandatory
        DESCRIPTION
                "The Multicast IP address of this entry"
        ::= { wfDlsMcastIpEntry 3 }

    wfDlsMcastIpSlots OBJECT-TYPE
        SYNTAX	Gauge(0..4294967295)
        ACCESS	read-write
        STATUS	mandatory
        DESCRIPTION
                "Bit mask field representing the slots upon which this
	         DlsMcastIpEntry can receive and transmit multicast data.
		 The MSBit represents slot 1, the next most significant
		 bit represents slot 2, and so on...  Slots can be 1-14.
                 Default is all slots on a BCN."
        DEFVAL  { 4294705152 }
        ::= { wfDlsMcastIpEntry 4 }

    wfDlsMcastIpBackupConfig OBJECT-TYPE
        SYNTAX	INTEGER {
    		    yes(1),
    		    no(2)
    		}
        ACCESS	read-write
        STATUS	mandatory
        DESCRIPTION
                "The indication of whether or not a backup peer
                 is to be configured for the primary peer.  The
                 default is no which means that there is no backup
                 peer configured by default."
        DEFVAL	{ no }
        ::= { wfDlsMcastIpEntry 5 }

    wfDlsMcastIpBackupIpAddr OBJECT-TYPE
        SYNTAX	IpAddress
        ACCESS	read-write
        STATUS	mandatory
        DESCRIPTION
                "The IP Address of the backup DLSw peer."
        ::= { wfDlsMcastIpEntry 6 }

    wfDlsMcastIpBackupMaxUpTime OBJECT-TYPE
        SYNTAX	INTEGER(0..999999)
        ACCESS	read-write
        STATUS	mandatory
        DESCRIPTION
                "The maximum amount of time (in seconds) allowed for a
                 TCP connection to stay established to the backup DLSw
                 peer.  If set to zero, this feature is disabled.  Set
                 to anything greater than zero to enable the feature."
        DEFVAL	{ 0 }
        ::= { wfDlsMcastIpEntry 7 }

    wfDlsMcastIpBackupHoldDownTime OBJECT-TYPE
        SYNTAX	INTEGER(0..2147483647)
        ACCESS	read-write
        STATUS	mandatory
        DESCRIPTION
                "The amount of time (in seconds) to wait before starting
                 a new TCP connection to the backup DLSw peer."
        DEFVAL	{ 120 }
        ::= { wfDlsMcastIpEntry 8 }

    wfDlsMcastIpBackupStartTime OBJECT-TYPE
        SYNTAX	INTEGER(0..2400)
        ACCESS	read-write
        STATUS	mandatory
        DESCRIPTION
                "Used in conjunction with the EndTime attribute.  Together
                 these define a time interval for when a backup peer can
                 be active.  The start time is the beginning time of day
                 that a backup peer can be established.  (HHMM format)"
        DEFVAL	{ 0001 }
        ::= { wfDlsMcastIpEntry 9 }

    wfDlsMcastIpBackupEndTime OBJECT-TYPE
        SYNTAX	INTEGER(1..2400)
        ACCESS	read-write
        STATUS	mandatory
        DESCRIPTION
                "Used in conjunction with the StartTime attribute.  Together
                 these define a time interval for when a backup peer can
                 be active.  The end time is the end time of day that a
                 backup peer can be established.  If a backup peer is active
                 and the current time is after this end time, the backup
                 peer will be brought down.  (HHMM format)"
        DEFVAL	{ 2400 }
        ::= { wfDlsMcastIpEntry 10 }

    wfDlsMcastIpBackupType OBJECT-TYPE
	SYNTAX  INTEGER {
                    multicast(1),
                    v20udp(2),
                    v20unknown(3),
                    v20tcp(4),
		    tcp1795(5)
                }
        ACCESS  read-write
        STATUS  mandatory
        DESCRIPTION
                "The type of this DLSw backup peer"
        DEFVAL  { v20unknown }
        ::= { wfDlsMcastIpEntry 11 }


    wfDlsTranslateMacTable OBJECT-TYPE
        SYNTAX	SEQUENCE OF WfDlsTranslateMacEntry
        ACCESS	not-accessible
        STATUS	mandatory
        DESCRIPTION
                "A table that contains destination MAC addresses which can be 
		replaced with another remote MAC addresses.  These new MAC addresses
		will be used to establish SNA sessions instead of previously 
	        configured on end nodes."
        ::= { wfDlsGroup 16 }    

    
     wfDlsTranslateMacEntry OBJECT-TYPE
        SYNTAX	WfDlsTranslateMacEntry
        ACCESS	not-accessible
        STATUS	mandatory
        DESCRIPTION
                "An entry in wfDlsTranslateMacTable"
        INDEX	{ wfDlsOriginDestMacAddr }
        ::= { wfDlsTranslateMacTable 1 }


      WfDlsTranslateMacEntry ::= SEQUENCE {
    	    wfDlsTranslateMacDelete
    		INTEGER,
    	    wfDlsOriginDestMacAddr
    		OCTET STRING,
    	    wfDlsTranslateDestMacAddr
    		OCTET STRING
        }
     

       wfDlsTranslateMacDelete OBJECT-TYPE
        SYNTAX	INTEGER {
    		    created(1),
    		    deleted(2)
    		}
        ACCESS	read-write
        STATUS	mandatory
        DESCRIPTION
                "Create/Delete parameter. Translate is created."
        DEFVAL	{ created }
        ::= { wfDlsTranslateMacEntry 1 }

    wfDlsOriginDestMacAddr OBJECT-TYPE
        SYNTAX	OCTET STRING (SIZE (6))
        ACCESS	read-only
        STATUS	mandatory
        DESCRIPTION
                "The originally configured MAC address of the destination station"
        ::= { wfDlsTranslateMacEntry 2 }

    wfDlsTranslateDestMacAddr OBJECT-TYPE
        SYNTAX	OCTET STRING (SIZE (6))
        ACCESS	read-write
        STATUS	mandatory
        DESCRIPTION
                "The translated MAC address of the destination station"
        ::= { wfDlsTranslateMacEntry 3 }

	
    END  -- Wellfleet-DLS-MIB
