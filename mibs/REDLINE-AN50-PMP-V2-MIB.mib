-- **************************************************************
-- Redline AN50-PMP v2 MIB
-- ECO Rev 1.00
-- Copyright (c) 2006 by Redline Communications, Inc
-- All rights reserved
-- **************************************************************

REDLINE-AN50-PMP-V2-MIB DEFINITIONS ::= BEGIN

IMPORTS
  redlineMgmt
    FROM REDLINE-MIB
  MODULE-IDENTITY,
  OBJECT-TYPE,
  Counter32,
  Integer32,
  TimeTicks
    FROM SNMPv2-SMI
  OBJECT-GROUP
    FROM SNMPv2-CONF
  RowStatus
    FROM SNMPv2-TC;

redlineAN50PMPV2 MODULE-IDENTITY
  LAST-UPDATED "200503160000Z"  -- Mar 16, 2005 12:00:00 AM
  ORGANIZATION "Redline Communications, Inc."
  CONTACT-INFO
    "Primary Authors: Ari Mark Sodhi
                   Octavian Banica
    postal:
            Redline Communications Inc.
            302 Town Centre Blvd.
            Markham, ON
            Canada L3R 0E8
    phone:  +1 905 479-8344
    email:  asodhi@redlinecommunications.com"
  DESCRIPTION
    "This MIB contains Redline-defined attributes for AN-50 PMP switched device based on V2 processor. The device can connect multiple subscriber stations to a central base station."
  -- 1.3.6.1.4.1.10728.2.51
  ::= { redlineMgmt 51 }


-- -----------------------------
-- Link and Connections Table
-- -----------------------------

an50pmpLinkTable OBJECT-TYPE
  SYNTAX  SEQUENCE OF An50pmpLinkEntry
  MAX-ACCESS not-accessible
  STATUS current
  DESCRIPTION
    "Table with Wireless links and connections
    information configured into AN50 PMP device
    based on V1 processor."
  -- 1.3.6.1.4.1.10728.2.51.1
  ::= { redlineAN50PMPV2 1 }


an50pmpLinkEntry OBJECT-TYPE
  SYNTAX  An50pmpLinkEntry
  MAX-ACCESS not-accessible
  STATUS current
  DESCRIPTION
    "A unique set of link parameters."
  INDEX {
    an50pmpLinkID }
  -- 1.3.6.1.4.1.10728.2.51.1.1
  ::= { an50pmpLinkTable 1 }


An50pmpLinkEntry ::= SEQUENCE {

  an50pmpLinkID             INTEGER,
  an50pmpLinkName           OCTET STRING,
  an50pmpLinkGroupId        INTEGER,
  an50pmpLinkPeerMac        OCTET STRING,
  an50pmpLinkMaxDLBurstRate INTEGER,
  an50pmpLinkMaxULBurstRate INTEGER,
  an50pmpLinkMaxHost        Integer32,
  an50pmpLinkCIDDLCIR       INTEGER,
  an50pmpLinkCIDDLPIR       INTEGER,
  an50pmpLinkCIDULCIR       INTEGER,
  an50pmpLinkCIDULPIR       INTEGER,
  an50pmpLinkDLQoS          INTEGER,
  an50pmpLinkULQoS          INTEGER,
  an50pmpLinkRowStatus      RowStatus,
  an50pmpLinkEncryptionKey  OCTET STRING }


an50pmpLinkID OBJECT-TYPE
  SYNTAX  INTEGER (0..65536)
  MAX-ACCESS not-accessible
  STATUS current
  DESCRIPTION
    "Link ID, a unique number between 1 and 65536 that
    identifies a particular link."
  -- 1.3.6.1.4.1.10728.2.51.1.1.1
  ::= { an50pmpLinkEntry 1 }


an50pmpLinkName OBJECT-TYPE
  SYNTAX  OCTET STRING (SIZE (1..15))
  MAX-ACCESS read-write
  STATUS current
  DESCRIPTION
    "The name of the Link/Connection"
  -- 1.3.6.1.4.1.10728.2.51.1.1.2
  ::= { an50pmpLinkEntry 2 }


an50pmpLinkGroupId OBJECT-TYPE
  SYNTAX  INTEGER (1..1024)
  MAX-ACCESS read-write
  STATUS obsolete
  DESCRIPTION
    "Group assigned to this link."
  -- 1.3.6.1.4.1.10728.2.51.1.1.3
  ::= { an50pmpLinkEntry 3 }


an50pmpLinkPeerMac OBJECT-TYPE
  SYNTAX  OCTET STRING (SIZE (0..6))
  MAX-ACCESS read-write
  STATUS current
  DESCRIPTION
    "Link Destination MAC address."
  -- 1.3.6.1.4.1.10728.2.51.1.1.4
  ::= { an50pmpLinkEntry 4 }


an50pmpLinkMaxDLBurstRate OBJECT-TYPE
  SYNTAX  INTEGER (1..8)
  MAX-ACCESS read-write
  STATUS current
  DESCRIPTION
    "Maximum downlink rate for this link.
    Rate range: 6Mb/s=1, 9Mb/s=2, 12Mb/s=3, 18Mb/s=4,
    24Mb/s=5, 36Mb/s=6, 48Mb/s=7, 54Mbs=8."
  -- 1.3.6.1.4.1.10728.2.51.1.1.5
  ::= { an50pmpLinkEntry 5 }


an50pmpLinkMaxULBurstRate OBJECT-TYPE
  SYNTAX  INTEGER (1..8)
  MAX-ACCESS read-write
  STATUS current
  DESCRIPTION
    "Maximum uplink rate for this link.
    Rate range: 6Mb/s=1, 9Mb/s=2, 12Mb/s=3, 18Mb/s=4,
    24Mb/s=5, 36Mb/s=6, 48Mb/s=7, 54Mbs=8."
  -- 1.3.6.1.4.1.10728.2.51.1.1.6
  ::= { an50pmpLinkEntry 6 }


an50pmpLinkMaxHost OBJECT-TYPE
  SYNTAX  Integer32
  MAX-ACCESS read-write
  STATUS obsolete
  DESCRIPTION
    "Group this Link belongs to."
  -- 1.3.6.1.4.1.10728.2.51.1.1.7
  ::= { an50pmpLinkEntry 7 }


an50pmpLinkCIDDLCIR OBJECT-TYPE
  SYNTAX  INTEGER (0..65535)
  MAX-ACCESS read-write
  STATUS obsolete
  DESCRIPTION
    "The downlink commited rate for this connection in kb/s."
  -- 1.3.6.1.4.1.10728.2.51.1.1.8
  ::= { an50pmpLinkEntry 8 }


an50pmpLinkCIDDLPIR OBJECT-TYPE
  SYNTAX  INTEGER (1..65535)
  MAX-ACCESS read-write
  STATUS obsolete
  DESCRIPTION
    "The downlink peak rate for this connection in kb/s."
  -- 1.3.6.1.4.1.10728.2.51.1.1.9
  ::= { an50pmpLinkEntry 9 }


an50pmpLinkCIDULCIR OBJECT-TYPE
  SYNTAX  INTEGER (0..65535)
  MAX-ACCESS read-write
  STATUS obsolete
  DESCRIPTION
    "The uplink commited rate for this connection in kb/s."
  -- 1.3.6.1.4.1.10728.2.51.1.1.10
  ::= { an50pmpLinkEntry 10 }


an50pmpLinkCIDULPIR OBJECT-TYPE
  SYNTAX  INTEGER (0..65535)
  MAX-ACCESS read-write
  STATUS obsolete
  DESCRIPTION
    "The uplink peak rate for this connection in kb/s."
  -- 1.3.6.1.4.1.10728.2.51.1.1.11
  ::= { an50pmpLinkEntry 11 }


an50pmpLinkDLQoS OBJECT-TYPE
  SYNTAX  INTEGER (1..54)
  MAX-ACCESS read-write
  STATUS obsolete
  DESCRIPTION
    "The downlink  QoS level."
  -- 1.3.6.1.4.1.10728.2.51.1.1.12
  ::= { an50pmpLinkEntry 12 }


an50pmpLinkULQoS OBJECT-TYPE
  SYNTAX  INTEGER (1..54)
  MAX-ACCESS read-write
  STATUS obsolete
  DESCRIPTION
    "The uplink QoS level."
  -- 1.3.6.1.4.1.10728.2.51.1.1.13
  ::= { an50pmpLinkEntry 13 }


an50pmpLinkEncryptionKey OBJECT-TYPE
  SYNTAX  OCTET STRING (SIZE (0..16))
  MAX-ACCESS read-write
  STATUS current
  DESCRIPTION
    "The encryption key"
  -- 1.3.6.1.4.1.10728.2.51.1.1.15
  ::= { an50pmpLinkEntry 15 }


an50pmpLinkRowStatus OBJECT-TYPE
  SYNTAX  RowStatus
  MAX-ACCESS read-write
  STATUS current
  DESCRIPTION
    "Status of the row"
  DEFVAL { createAndWait }
  -- 1.3.6.1.4.1.10728.2.51.1.1.14
  ::= { an50pmpLinkEntry 14 }


an50pmpLinkStatusTable OBJECT-TYPE
  SYNTAX  SEQUENCE OF An50pmpLinkStatusEntry
  MAX-ACCESS not-accessible
  STATUS current
  DESCRIPTION
    "Statistics per uplink connections."
  -- 1.3.6.1.4.1.10728.2.51.2
  ::= { redlineAN50PMPV2 2 }


an50pmpLinkStatusEntry OBJECT-TYPE
  SYNTAX  An50pmpLinkStatusEntry
  MAX-ACCESS not-accessible
  STATUS current
  DESCRIPTION
    "Statistics for a link connection."
  INDEX {
    an50pmpLinkStatusID }
  -- 1.3.6.1.4.1.10728.2.51.2.1
  ::= { an50pmpLinkStatusTable 1 }


An50pmpLinkStatusEntry ::= SEQUENCE {

  an50pmpLinkStatusID         INTEGER,
  an50pmpLinkStatus           INTEGER,
  an50pmpLinkStatusCode       Integer32,
  an50pmpLinkRegConn          INTEGER,
  an50pmpLinkDLBurstRate      INTEGER,
  an50pmpLinkDLRSSI           Integer32,
  an50pmpLinkDLSINADR         Integer32,
  an50pmpLinkDLStatLostFrm    Integer32,
  an50pmpLinkDLStatBlksTot    Integer32,
  an50pmpLinkDLStatBlksRetr   Integer32,
  an50pmpLinkDLStatBlksDisc   Integer32,
  an50pmpLinkDLCIDStatPktDisc Integer32,
  an50pmpLinkDLCIDStatPktTran Integer32,
  an50pmpLinkDLCIDStatPktRecv Integer32,
  an50pmpLinkULBurstRate      INTEGER,
  an50pmpLinkULRSSI           Integer32,
  an50pmpLinkULSINADR         Integer32,
  an50pmpLinkULStatLostFrm    Integer32,
  an50pmpLinkULStatBlksTot    Integer32,
  an50pmpLinkULStatBlksRetr   Integer32,
  an50pmpLinkULStatBlksDisc   Integer32,
  an50pmpLinkULCIDStatPktDisc Integer32,
  an50pmpLinkULCIDStatPktTran Integer32,
  an50pmpLinkULCIDStatPktRecv Integer32,
  an50pmpLinkUpTime           TimeTicks,
  an50pmpLinkLostCount        Integer32 }


an50pmpLinkStatusID OBJECT-TYPE
  SYNTAX  INTEGER (1..1024)
  MAX-ACCESS not-accessible
  STATUS current
  DESCRIPTION
    "Index for an50pmpLinkStatusTable table"
  -- 1.3.6.1.4.1.10728.2.51.2.1.1
  ::= { an50pmpLinkStatusEntry 1 }


an50pmpLinkStatus OBJECT-TYPE
  SYNTAX  INTEGER {
      up(1),
      down(2) }
  MAX-ACCESS read-only
  STATUS current
  DESCRIPTION
    "Status of the Link."
  -- 1.3.6.1.4.1.10728.2.51.2.1.2
  ::= { an50pmpLinkStatusEntry 2 }


an50pmpLinkStatusCode OBJECT-TYPE
  SYNTAX  Integer32
  MAX-ACCESS read-only
  STATUS current
  DESCRIPTION
    "Alarm bits shown as a hex number."
  -- 1.3.6.1.4.1.10728.2.51.2.1.3
  ::= { an50pmpLinkStatusEntry 3 }


an50pmpLinkRegConn OBJECT-TYPE
  SYNTAX  INTEGER (1..1024)
  MAX-ACCESS read-only
  STATUS current
  DESCRIPTION
    "Number of connections configured for this link."
  -- 1.3.6.1.4.1.10728.2.51.2.1.4
  ::= { an50pmpLinkStatusEntry 4 }


an50pmpLinkDLBurstRate OBJECT-TYPE
  SYNTAX  INTEGER {
      tx6Mbs(1),
      tx9Mbs(2),
      tx12Mbs(3),
      tx18Mbs(4),
      tx24Mbs(5),
      tx36Mbs(6),
      tx48Mbs(7),
      tx54Mbs(8) }
  MAX-ACCESS read-only
  STATUS current
  DESCRIPTION
    "Current master Tx burst rate.
    Rate range: 6Mb/s=1, 9Mb/s=2, 12Mb/s=3, 18Mb/s=4,
    24Mb/s=5, 36Mb/s=6, 48Mb/s=7, 54Mbs=8."
  -- 1.3.6.1.4.1.10728.2.51.2.1.5
  ::= { an50pmpLinkStatusEntry 5 }


an50pmpLinkDLRSSI OBJECT-TYPE
  SYNTAX  Integer32
  MAX-ACCESS read-only
  STATUS current
  DESCRIPTION
    "RSSI (Received Signal Strength Indicator) at slave."
  -- 1.3.6.1.4.1.10728.2.51.2.1.6
  ::= { an50pmpLinkStatusEntry 6 }


an50pmpLinkDLSINADR OBJECT-TYPE
  SYNTAX  Integer32
  MAX-ACCESS read-only
  STATUS current
  DESCRIPTION
    "SINADR (Signal Interference and Noise Distorsion Ratio) at slave."
  -- 1.3.6.1.4.1.10728.2.51.2.1.7
  ::= { an50pmpLinkStatusEntry 7 }


an50pmpLinkDLStatLostFrm OBJECT-TYPE
  SYNTAX  Integer32
  MAX-ACCESS read-only
  STATUS current
  DESCRIPTION
    "SINADR at slave."
  -- 1.3.6.1.4.1.10728.2.51.2.1.8
  ::= { an50pmpLinkStatusEntry 8 }


an50pmpLinkDLStatBlksTot OBJECT-TYPE
  SYNTAX  Integer32
  MAX-ACCESS read-only
  STATUS current
  DESCRIPTION
    "Blocks transmitted from master to slave."
  -- 1.3.6.1.4.1.10728.2.51.2.1.9
  ::= { an50pmpLinkStatusEntry 9 }


an50pmpLinkDLStatBlksRetr OBJECT-TYPE
  SYNTAX  Integer32
  MAX-ACCESS read-only
  STATUS current
  DESCRIPTION
    "Block re-transmitted from master to slave."
  -- 1.3.6.1.4.1.10728.2.51.2.1.10
  ::= { an50pmpLinkStatusEntry 10 }


an50pmpLinkDLStatBlksDisc OBJECT-TYPE
  SYNTAX  Integer32
  MAX-ACCESS read-only
  STATUS current
  DESCRIPTION
    "Blocks lost from master to slave"
  -- 1.3.6.1.4.1.10728.2.51.2.1.11
  ::= { an50pmpLinkStatusEntry 11 }


an50pmpLinkDLCIDStatPktDisc OBJECT-TYPE
  SYNTAX  Integer32
  MAX-ACCESS read-only
  STATUS current
  DESCRIPTION
    "Packets discarded by master due to buffer full."
  -- 1.3.6.1.4.1.10728.2.51.2.1.12
  ::= { an50pmpLinkStatusEntry 12 }


an50pmpLinkDLCIDStatPktTran OBJECT-TYPE
  SYNTAX  Integer32
  MAX-ACCESS read-only
  STATUS current
  DESCRIPTION
    "Packets transmitted from master to slave."
  -- 1.3.6.1.4.1.10728.2.51.2.1.13
  ::= { an50pmpLinkStatusEntry 13 }


an50pmpLinkDLCIDStatPktRecv OBJECT-TYPE
  SYNTAX  Integer32
  MAX-ACCESS read-only
  STATUS current
  DESCRIPTION
    "Packets received by slave"
  -- 1.3.6.1.4.1.10728.2.51.2.1.14
  ::= { an50pmpLinkStatusEntry 14 }


an50pmpLinkULBurstRate OBJECT-TYPE
  SYNTAX  INTEGER {
      tx6Mbs(1),
      tx9Mbs(2),
      tx12Mbs(3),
      tx18Mbs(4),
      tx24Mbs(5),
      tx36Mbs(6),
      tx48Mbs(7),
      tx54Mbs(8) }
  MAX-ACCESS read-only
  STATUS current
  DESCRIPTION
    "Current Slave Tx Burst Rate.
    Rate range: 6Mb/s=1, 9Mb/s=2, 12Mb/s=3, 18Mb/s=4,
    24Mb/s=5, 36Mb/s=6, 48Mb/s=7, 54Mbs=8."
  -- 1.3.6.1.4.1.10728.2.51.2.1.15
  ::= { an50pmpLinkStatusEntry 15 }


an50pmpLinkULRSSI OBJECT-TYPE
  SYNTAX  Integer32
  MAX-ACCESS read-only
  STATUS current
  DESCRIPTION
    "RSSI at master."
  -- 1.3.6.1.4.1.10728.2.51.2.1.16
  ::= { an50pmpLinkStatusEntry 16 }


an50pmpLinkULSINADR OBJECT-TYPE
  SYNTAX  Integer32
  MAX-ACCESS read-only
  STATUS current
  DESCRIPTION
    "SINADR at master."
  -- 1.3.6.1.4.1.10728.2.51.2.1.17
  ::= { an50pmpLinkStatusEntry 17 }


an50pmpLinkULStatLostFrm OBJECT-TYPE
  SYNTAX  Integer32
  MAX-ACCESS read-only
  STATUS current
  DESCRIPTION
    "Frames lost from slave to master"
  -- 1.3.6.1.4.1.10728.2.51.2.1.18
  ::= { an50pmpLinkStatusEntry 18 }


an50pmpLinkULStatBlksTot OBJECT-TYPE
  SYNTAX  Integer32
  MAX-ACCESS read-only
  STATUS current
  DESCRIPTION
    "Blocks transmitted slave to master."
  -- 1.3.6.1.4.1.10728.2.51.2.1.19
  ::= { an50pmpLinkStatusEntry 19 }


an50pmpLinkULStatBlksRetr OBJECT-TYPE
  SYNTAX  Integer32
  MAX-ACCESS read-only
  STATUS current
  DESCRIPTION
    "Block re-transmitted slave to master."
  -- 1.3.6.1.4.1.10728.2.51.2.1.20
  ::= { an50pmpLinkStatusEntry 20 }


an50pmpLinkULStatBlksDisc OBJECT-TYPE
  SYNTAX  Integer32
  MAX-ACCESS read-only
  STATUS current
  DESCRIPTION
    "Blocks lost from slave to master."
  -- 1.3.6.1.4.1.10728.2.51.2.1.21
  ::= { an50pmpLinkStatusEntry 21 }


an50pmpLinkULCIDStatPktDisc OBJECT-TYPE
  SYNTAX  Integer32
  MAX-ACCESS read-only
  STATUS current
  DESCRIPTION
    "Packets discarded by slave due to buffer full."
  -- 1.3.6.1.4.1.10728.2.51.2.1.22
  ::= { an50pmpLinkStatusEntry 22 }


an50pmpLinkULCIDStatPktTran OBJECT-TYPE
  SYNTAX  Integer32
  MAX-ACCESS read-only
  STATUS current
  DESCRIPTION
    "Packets transmitted from slave to master."
  -- 1.3.6.1.4.1.10728.2.51.2.1.23
  ::= { an50pmpLinkStatusEntry 23 }


an50pmpLinkULCIDStatPktRecv OBJECT-TYPE
  SYNTAX  Integer32
  MAX-ACCESS read-only
  STATUS current
  DESCRIPTION
    "Packets received by master from slave."
  -- 1.3.6.1.4.1.10728.2.51.2.1.24
  ::= { an50pmpLinkStatusEntry 24 }


an50pmpLinkUpTime OBJECT-TYPE
  SYNTAX  TimeTicks
  MAX-ACCESS read-only
  STATUS current
  DESCRIPTION
    "Time since the link is UP (in hundreths of a second)."
  -- 1.3.6.1.4.1.10728.2.51.2.1.25
  ::= { an50pmpLinkStatusEntry 25 }


an50pmpLinkLostCount OBJECT-TYPE
  SYNTAX  Integer32
  MAX-ACCESS read-only
  STATUS current
  DESCRIPTION
    "Number of times the link has been lost."
  -- 1.3.6.1.4.1.10728.2.51.2.1.26
  ::= { an50pmpLinkStatusEntry 26 }


an50pmpCIDSaveConfig OBJECT-TYPE
  SYNTAX  INTEGER {
      doNothing(1),   -- do not save configuration
      saveConfig(2)   -- save configuration
      }
  MAX-ACCESS read-write
  STATUS current
  DESCRIPTION
    "The attribute saves the entire config set of the AN50 PMP."
  -- 1.3.6.1.4.1.10728.2.51.3
  ::= { redlineAN50PMPV2 3 }


an50pmpLastModifiedCID OBJECT-TYPE
  SYNTAX  INTEGER (4..1023)
  MAX-ACCESS read-only
  STATUS current
  DESCRIPTION
    "The attribute represents the last modified CID."
  -- 1.3.6.1.4.1.10728.2.51.4
  ::= { redlineAN50PMPV2 4 }


an50pmpLastMissedSsMacAddress OBJECT-TYPE
  SYNTAX  OCTET STRING
  MAX-ACCESS read-only
  STATUS current
  DESCRIPTION
    "MAC address of the SS that missed the registration with the BS."
  -- 1.3.6.1.4.1.10728.2.51.5
  ::= { redlineAN50PMPV2 5 }


an50pmpLastRegisteredSsMacAddress OBJECT-TYPE
  SYNTAX  OCTET STRING
  MAX-ACCESS read-only
  STATUS current
  DESCRIPTION
    "MAC address of the last SS that successfuly registered with the BS."
  -- 1.3.6.1.4.1.10728.2.51.6
  ::= { redlineAN50PMPV2 6 }


an50pmpLastSuccessfulID OBJECT-TYPE
  SYNTAX  INTEGER (4..1023)
  MAX-ACCESS read-only
  STATUS current
  DESCRIPTION
    "The ID of the Link registered in BS table that is sent through
    LastSuccessfulRegisteredSS Trap(number10)."
  -- 1.3.6.1.4.1.10728.2.51.7
  ::= { redlineAN50PMPV2 7 }


an50pmpLastDeniedSsMacAddress OBJECT-TYPE
  SYNTAX  OCTET STRING
  MAX-ACCESS read-write
  STATUS current
  DESCRIPTION
    "MAC address of the SS that will be denied by this BS."
  -- 1.3.6.1.4.1.10728.2.51.8
  ::= { redlineAN50PMPV2 8 }


an50pmpGroupTable OBJECT-TYPE
  SYNTAX  SEQUENCE OF An50pmpGroupEntry
  MAX-ACCESS not-accessible
  STATUS current
  DESCRIPTION ""
  -- 1.3.6.1.4.1.10728.2.51.9
  ::= { redlineAN50PMPV2 9 }


an50pmpGroupEntry OBJECT-TYPE
  SYNTAX  An50pmpGroupEntry
  MAX-ACCESS not-accessible
  STATUS current
  DESCRIPTION ""
  INDEX {
    an50pmpGroupId }
  -- 1.3.6.1.4.1.10728.2.51.9.1
  ::= { an50pmpGroupTable 1 }


An50pmpGroupEntry ::= SEQUENCE {

  an50pmpGroupId              INTEGER,
  an50pmpGroupName            OCTET STRING,
  an50pmpGroupBSPortTagging   INTEGER,
  an50pmpGroupVlanId          INTEGER,
  an50pmpGroupDefaultPriority INTEGER,
  an50pmpGroupBSPortEnabled   INTEGER,
  an50pmpGroupQos             INTEGER,
  an50pmpGroupRowStatus       RowStatus }


an50pmpGroupId OBJECT-TYPE
  SYNTAX  INTEGER (1..65536)
  MAX-ACCESS not-accessible
  STATUS current
  DESCRIPTION ""
  -- 1.3.6.1.4.1.10728.2.51.9.1.1
  ::= { an50pmpGroupEntry 1 }


an50pmpGroupName OBJECT-TYPE
  SYNTAX  OCTET STRING (SIZE (0..15))
  MAX-ACCESS read-write
  STATUS current
  DESCRIPTION ""
  -- 1.3.6.1.4.1.10728.2.51.9.1.2
  ::= { an50pmpGroupEntry 2 }


an50pmpGroupBSPortTagging OBJECT-TYPE
  SYNTAX  INTEGER {
      passThrough(1),
      tagged(2) }
  MAX-ACCESS read-write
  STATUS current
  DESCRIPTION ""
  -- 1.3.6.1.4.1.10728.2.51.9.1.3
  ::= { an50pmpGroupEntry 3 }


an50pmpGroupVlanId OBJECT-TYPE
  SYNTAX  INTEGER (1..65536)
  MAX-ACCESS read-write
  STATUS current
  DESCRIPTION ""
  -- 1.3.6.1.4.1.10728.2.51.9.1.4
  ::= { an50pmpGroupEntry 4 }


an50pmpGroupDefaultPriority OBJECT-TYPE
  SYNTAX  INTEGER (0..65536)
  MAX-ACCESS read-write
  STATUS current
  DESCRIPTION
    "Has meaning only for PassThrough groups"
  DEFVAL { 0 }
  -- 1.3.6.1.4.1.10728.2.51.9.1.5
  ::= { an50pmpGroupEntry 5 }


an50pmpGroupBSPortEnabled OBJECT-TYPE
  SYNTAX  INTEGER {
      off(1),
      on(2) }
  MAX-ACCESS read-write
  STATUS current
  DESCRIPTION ""
  DEFVAL { off }
  -- 1.3.6.1.4.1.10728.2.51.9.1.6
  ::= { an50pmpGroupEntry 6 }


an50pmpGroupQos OBJECT-TYPE
  SYNTAX  INTEGER (0..65536)
  MAX-ACCESS read-write
  STATUS current
  DESCRIPTION
    "The QOS value for the group."
  -- 1.3.6.1.4.1.10728.2.51.9.1.7
  ::= { an50pmpGroupEntry 7 }


an50pmpGroupRowStatus OBJECT-TYPE
  SYNTAX  RowStatus
  MAX-ACCESS read-write
  STATUS current
  DESCRIPTION
    ""
  DEFVAL { createAndWait }
  -- 1.3.6.1.4.1.10728.2.51.9.1.8
  ::= { an50pmpGroupEntry 8 }


an50pmpConnectionTable OBJECT-TYPE
  SYNTAX  SEQUENCE OF An50pmpConnectionEntry
  MAX-ACCESS not-accessible
  STATUS current
  DESCRIPTION ""
  -- 1.3.6.1.4.1.10728.2.51.10
  ::= { redlineAN50PMPV2 10 }


an50pmpConnectionEntry OBJECT-TYPE
  SYNTAX  An50pmpConnectionEntry
  MAX-ACCESS not-accessible
  STATUS current
  DESCRIPTION ""
  INDEX {
    an50pmpConnectionId }
  -- 1.3.6.1.4.1.10728.2.51.10.1
  ::= { an50pmpConnectionTable 1 }


An50pmpConnectionEntry ::= SEQUENCE {

  an50pmpConnectionId              INTEGER,
  an50pmpConnectionName            OCTET STRING,
  an50pmpConnectionPortTagging     INTEGER,
  an50pmpConnectionVlanId          INTEGER,
  an50pmpConnectionDefaultPriority INTEGER,
  an50pmpConnectionParentLink      INTEGER,
  an50pmpConnectionParentGroup     INTEGER,
  an50pmpConnectionDLQoS           INTEGER,
  an50pmpConnectionULQoS           INTEGER,
  an50pmpConnectionRowStatus       RowStatus }


an50pmpConnectionId OBJECT-TYPE
  SYNTAX  INTEGER (1..65536)
  MAX-ACCESS not-accessible
  STATUS current
  DESCRIPTION
    "Id for the connection as assigned by the system"
  -- 1.3.6.1.4.1.10728.2.51.10.1.1
  ::= { an50pmpConnectionEntry 1 }


an50pmpConnectionName OBJECT-TYPE
  SYNTAX  OCTET STRING (SIZE (0..15))
  MAX-ACCESS read-write
  STATUS current
  DESCRIPTION
    "The name of the connection"
  -- 1.3.6.1.4.1.10728.2.51.10.1.2
  ::= { an50pmpConnectionEntry 2 }


an50pmpConnectionPortTagging OBJECT-TYPE
  SYNTAX  INTEGER {
      passThrough(1),
      tagged(2) }
  MAX-ACCESS read-write
  STATUS current
  DESCRIPTION
    "Specified the way egress packets are treated."
  -- 1.3.6.1.4.1.10728.2.51.10.1.3
  ::= { an50pmpConnectionEntry 3 }


an50pmpConnectionVlanId OBJECT-TYPE
  SYNTAX  INTEGER (0..65536)
  MAX-ACCESS read-write
  STATUS current
  DESCRIPTION
    "The VLAN Id associated with the group."
  -- 1.3.6.1.4.1.10728.2.51.10.1.4
  ::= { an50pmpConnectionEntry 4 }


an50pmpConnectionDefaultPriority OBJECT-TYPE
  SYNTAX  INTEGER (0..65536)
  MAX-ACCESS read-write
  STATUS current
  DESCRIPTION
    "The default priority in the case of PassThrough"
  -- 1.3.6.1.4.1.10728.2.51.10.1.5
  ::= { an50pmpConnectionEntry 5 }


an50pmpConnectionParentLink OBJECT-TYPE
  SYNTAX  INTEGER (0..65536)
  MAX-ACCESS read-write
  STATUS current
  DESCRIPTION
    "The parent link id"
  -- 1.3.6.1.4.1.10728.2.51.10.1.6
  ::= { an50pmpConnectionEntry 6 }


an50pmpConnectionParentGroup OBJECT-TYPE
  SYNTAX  INTEGER (0..65536)
  MAX-ACCESS read-write
  STATUS current
  DESCRIPTION
    "The parent group id."
  -- 1.3.6.1.4.1.10728.2.51.10.1.7
  ::= { an50pmpConnectionEntry 7 }


an50pmpConnectionDLQoS OBJECT-TYPE
  SYNTAX  INTEGER (0..65536)
  MAX-ACCESS read-write
  STATUS current
  DESCRIPTION
    "Downlink QoS parameter for this connection."
  -- 1.3.6.1.4.1.10728.2.51.10.1.8
  ::= { an50pmpConnectionEntry 8 }


an50pmpConnectionULQoS OBJECT-TYPE
  SYNTAX  INTEGER (0..65536)
  MAX-ACCESS read-write
  STATUS current
  DESCRIPTION
    "The uplink QoS for this connection"
  -- 1.3.6.1.4.1.10728.2.51.10.1.9
  ::= { an50pmpConnectionEntry 9 }


an50pmpConnectionRowStatus OBJECT-TYPE
  SYNTAX  RowStatus
  MAX-ACCESS read-write
  STATUS current
  DESCRIPTION
    ""
  DEFVAL { createAndWait }
  -- 1.3.6.1.4.1.10728.2.51.10.1.10
  ::= { an50pmpConnectionEntry 10 }


an50pmpGroupStatusTable OBJECT-TYPE
  SYNTAX  SEQUENCE OF An50pmpGroupStatusEntry
  MAX-ACCESS not-accessible
  STATUS current
  DESCRIPTION ""
  -- 1.3.6.1.4.1.10728.2.51.11
  ::= { redlineAN50PMPV2 11 }


an50pmpGroupStatusEntry OBJECT-TYPE
  SYNTAX  An50pmpGroupStatusEntry
  MAX-ACCESS not-accessible
  STATUS current
  DESCRIPTION ""
  INDEX {
    an50pmpGroupStatusId }
  -- 1.3.6.1.4.1.10728.2.51.11.1
  ::= { an50pmpGroupStatusTable 1 }


An50pmpGroupStatusEntry ::= SEQUENCE {

  an50pmpGroupStatusId                INTEGER,
  an50pmpGroupStatusDLPacketsDiscards Counter32,
  an50pmpGroupStatusDLPacketsTx       Counter32,
  an50pmpGroupStatusDLPacketsRx       Counter32,
  an50pmpGroupStatusULPacketsDiscards Counter32,
  an50pmpGroupStatusULPacketsTx       Counter32,
  an50pmpGroupStatusULPacketsRx       Counter32 }


an50pmpGroupStatusId OBJECT-TYPE
  SYNTAX  INTEGER (1..65536)
  MAX-ACCESS not-accessible
  STATUS current
  DESCRIPTION
    "The an50pmpGroupId"
  -- 1.3.6.1.4.1.10728.2.51.11.1.1
  ::= { an50pmpGroupStatusEntry 1 }


an50pmpGroupStatusDLPacketsDiscards OBJECT-TYPE
  SYNTAX  Counter32
  MAX-ACCESS read-only
  STATUS current
  DESCRIPTION
    "The packets discarded at master due to full buffer"
  -- 1.3.6.1.4.1.10728.2.51.11.1.2
  ::= { an50pmpGroupStatusEntry 2 }


an50pmpGroupStatusDLPacketsTx OBJECT-TYPE
  SYNTAX  Counter32
  MAX-ACCESS read-only
  STATUS current
  DESCRIPTION
    "Packets transmitted by master"
  -- 1.3.6.1.4.1.10728.2.51.11.1.3
  ::= { an50pmpGroupStatusEntry 3 }


an50pmpGroupStatusDLPacketsRx OBJECT-TYPE
  SYNTAX  Counter32
  MAX-ACCESS read-only
  STATUS current
  DESCRIPTION
    "Packets received by slave"
  -- 1.3.6.1.4.1.10728.2.51.11.1.4
  ::= { an50pmpGroupStatusEntry 4 }


an50pmpGroupStatusULPacketsDiscards OBJECT-TYPE
  SYNTAX  Counter32
  MAX-ACCESS read-only
  STATUS current
  DESCRIPTION
    "The packets discarded at slave due to full buffer"
  -- 1.3.6.1.4.1.10728.2.51.11.1.5
  ::= { an50pmpGroupStatusEntry 5 }


an50pmpGroupStatusULPacketsTx OBJECT-TYPE
  SYNTAX  Counter32
  MAX-ACCESS read-only
  STATUS current
  DESCRIPTION
    "Packets transmitted by slave"
  -- 1.3.6.1.4.1.10728.2.51.11.1.6
  ::= { an50pmpGroupStatusEntry 6 }


an50pmpGroupStatusULPacketsRx OBJECT-TYPE
  SYNTAX  Counter32
  MAX-ACCESS read-only
  STATUS current
  DESCRIPTION
    "Packets received by master"
  -- 1.3.6.1.4.1.10728.2.51.11.1.7
  ::= { an50pmpGroupStatusEntry 7 }


an50pmpConnectionStatusTable OBJECT-TYPE
  SYNTAX  SEQUENCE OF An50pmpConnectionStatusEntry
  MAX-ACCESS not-accessible
  STATUS current
  DESCRIPTION ""
  -- 1.3.6.1.4.1.10728.2.51.12
  ::= { redlineAN50PMPV2 12 }


an50pmpConnectionStatusEntry OBJECT-TYPE
  SYNTAX  An50pmpConnectionStatusEntry
  MAX-ACCESS not-accessible
  STATUS current
  DESCRIPTION ""
  INDEX {
    an50pmpConnectionStatusId }
  -- 1.3.6.1.4.1.10728.2.51.12.1
  ::= { an50pmpConnectionStatusTable 1 }


An50pmpConnectionStatusEntry ::= SEQUENCE {

  an50pmpConnectionStatusId                INTEGER,
  an50pmpConnectionStatusDLPacketsDiscards Counter32,
  an50pmpConnectionStatusDLPacketsTx       Counter32,
  an50pmpConnectionStatusDLPacketsRx       Counter32,
  an50pmpConnectionStatusULPacketsDiscards Counter32,
  an50pmpConnectionStatusULPacketsTx       Counter32,
  an50pmpConnectionStatusULPacketsRx       Counter32 }


an50pmpConnectionStatusId OBJECT-TYPE
  SYNTAX  INTEGER (1..65536)
  MAX-ACCESS not-accessible
  STATUS current
  DESCRIPTION
    "The an50pmpGroupId"
  -- 1.3.6.1.4.1.10728.2.51.12.1.1
  ::= { an50pmpConnectionStatusEntry 1 }


an50pmpConnectionStatusDLPacketsDiscards OBJECT-TYPE
  SYNTAX  Counter32
  MAX-ACCESS read-only
  STATUS current
  DESCRIPTION
    "The packets discarded at master due to full buffer"
  -- 1.3.6.1.4.1.10728.2.51.12.1.2
  ::= { an50pmpConnectionStatusEntry 2 }


an50pmpConnectionStatusDLPacketsTx OBJECT-TYPE
  SYNTAX  Counter32
  MAX-ACCESS read-only
  STATUS current
  DESCRIPTION
    "Packets transmitted by master"
  -- 1.3.6.1.4.1.10728.2.51.12.1.3
  ::= { an50pmpConnectionStatusEntry 3 }


an50pmpConnectionStatusDLPacketsRx OBJECT-TYPE
  SYNTAX  Counter32
  MAX-ACCESS read-only
  STATUS current
  DESCRIPTION
    "Packets received by slave"
  -- 1.3.6.1.4.1.10728.2.51.12.1.4
  ::= { an50pmpConnectionStatusEntry 4 }


an50pmpConnectionStatusULPacketsDiscards OBJECT-TYPE
  SYNTAX  Counter32
  MAX-ACCESS read-only
  STATUS current
  DESCRIPTION
    "The packets discarded at slave due to full buffer"
  -- 1.3.6.1.4.1.10728.2.51.12.1.5
  ::= { an50pmpConnectionStatusEntry 5 }


an50pmpConnectionStatusULPacketsTx OBJECT-TYPE
  SYNTAX  Counter32
  MAX-ACCESS read-only
  STATUS current
  DESCRIPTION
    "Packets transmitted by slave"
  -- 1.3.6.1.4.1.10728.2.51.12.1.6
  ::= { an50pmpConnectionStatusEntry 6 }


an50pmpConnectionStatusULPacketsRx OBJECT-TYPE
  SYNTAX  Counter32
  MAX-ACCESS read-only
  STATUS current
  DESCRIPTION
    "Packets received by master"
  -- 1.3.6.1.4.1.10728.2.51.12.1.7
  ::= { an50pmpConnectionStatusEntry 7 }


an50PMPObjectGroup OBJECT-GROUP
  OBJECTS {
    an50pmpLinkName,
    an50pmpLinkPeerMac,
    an50pmpLinkMaxDLBurstRate,
    an50pmpLinkMaxULBurstRate,
    an50pmpLinkEncryptionKey,
    an50pmpLinkRowStatus,
    an50pmpLinkStatus,
    an50pmpLinkStatusCode,
    an50pmpLinkRegConn,
    an50pmpLinkDLBurstRate,
    an50pmpLinkDLRSSI,
    an50pmpLinkDLSINADR,
    an50pmpLinkDLStatLostFrm,
    an50pmpLinkDLStatBlksTot,
    an50pmpLinkDLStatBlksRetr,
    an50pmpLinkDLStatBlksDisc,
    an50pmpLinkDLCIDStatPktDisc,
    an50pmpLinkDLCIDStatPktTran,
    an50pmpLinkDLCIDStatPktRecv,
    an50pmpLinkULBurstRate,
    an50pmpLinkULRSSI,
    an50pmpLinkULSINADR,
    an50pmpLinkULStatLostFrm,
    an50pmpLinkULStatBlksTot,
    an50pmpLinkULStatBlksRetr,
    an50pmpLinkULStatBlksDisc,
    an50pmpLinkULCIDStatPktDisc,
    an50pmpLinkULCIDStatPktTran,
    an50pmpLinkULCIDStatPktRecv,
    an50pmpLinkUpTime,
    an50pmpLinkLostCount,
    an50pmpCIDSaveConfig,
    an50pmpLastModifiedCID,
    an50pmpLastMissedSsMacAddress,
    an50pmpLastRegisteredSsMacAddress,
    an50pmpLastSuccessfulID,
    an50pmpLastDeniedSsMacAddress,
    an50pmpGroupName,
    an50pmpGroupBSPortTagging,
    an50pmpGroupVlanId,
    an50pmpGroupDefaultPriority,
    an50pmpGroupBSPortEnabled,
    an50pmpGroupQos,
    an50pmpGroupRowStatus,
    an50pmpConnectionName,
    an50pmpConnectionPortTagging,
    an50pmpConnectionVlanId,
    an50pmpConnectionDefaultPriority,
    an50pmpConnectionParentLink,
    an50pmpConnectionParentGroup,
    an50pmpConnectionDLQoS,
    an50pmpConnectionULQoS,
    an50pmpConnectionRowStatus,
    an50pmpGroupStatusDLPacketsDiscards,
    an50pmpGroupStatusDLPacketsTx,
    an50pmpGroupStatusDLPacketsRx,
    an50pmpGroupStatusULPacketsDiscards,
    an50pmpGroupStatusULPacketsTx,
    an50pmpGroupStatusULPacketsRx,
    an50pmpConnectionStatusDLPacketsDiscards,
    an50pmpConnectionStatusDLPacketsTx,
    an50pmpConnectionStatusDLPacketsRx,
    an50pmpConnectionStatusULPacketsDiscards,
    an50pmpConnectionStatusULPacketsTx,
    an50pmpConnectionStatusULPacketsRx }
  STATUS current
  DESCRIPTION
    "All the current members"
  -- 1.3.6.1.4.1.10728.2.51.13
  ::= { redlineAN50PMPV2 13 }

an50PMPObsoleteObjectGroup OBJECT-GROUP
  OBJECTS {
    an50pmpLinkGroupId,
    an50pmpLinkMaxHost,
    an50pmpLinkCIDDLCIR,
    an50pmpLinkCIDDLPIR,
    an50pmpLinkCIDULCIR,
    an50pmpLinkCIDULPIR,
    an50pmpLinkDLQoS,
    an50pmpLinkULQoS }
  STATUS obsolete
  DESCRIPTION
    "All the obsolete objects"
  -- 1.3.6.1.4.1.10728.2.51.14
  ::= { redlineAN50PMPV2 14 }

END
