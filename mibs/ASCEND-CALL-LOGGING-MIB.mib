-- $Id: call_log.mib,v 29.5.38.2 1999/11/24 07:35:13 asarma Exp $
--
--			Ascend RADIUS MIB
--
--			Ascend Communications, Inc
--			1275 Harbor Bay Pkwy
--			Alameda, CA 94502
--			+1 510 769 6001
--			info@ascend.com
--
--		Copyright (c) 1993-1997 Ascend Communications, Inc.
--		All rights reserved.
--
--
-- 16 Jun 98:	mbannach	Initial release.
-- 07 Jul 98:   knguyen		Added callLoggingCompatMode 
-- 12 Aug 99:	mk		Modified the range for callLoggingPortNumber.

ASCEND-CALL-LOGGING-MIB DEFINITIONS ::= BEGIN

    IMPORTS
	callLoggingGroup
	    FROM ASCEND-MIB
	IpAddress
	    FROM RFC1155-SMI
	OBJECT-TYPE
	    FROM RFC-1212;

	--
	-- Ascend Call Logging Group
	--
	-- This group contains configuration and status information
	-- as well as action triggers for CALL LOGGING, a special 
	-- Ascend Management feature for service management.


--  Host Table for configuring the Call Logging servers

    callLoggingNumServers OBJECT-TYPE
	SYNTAX		INTEGER
	ACCESS		read-only
	STATUS		mandatory
	DESCRIPTION	"The maximum number of Call Logging
			servers supported by the system."
	::= { callLoggingGroup 1 }

    callLoggingServerTable	OBJECT-TYPE
	SYNTAX		SEQUENCE OF CallLoggingServerEntry
	ACCESS		not-accessible
	STATUS		mandatory
	DESCRIPTION	"A list of entries for Call Logging Server    
			addresses."
	::= { callLoggingGroup 2 }

    callLoggingServerEntry	OBJECT-TYPE
	SYNTAX		CallLoggingServerEntry
	ACCESS		not-accessible
	STATUS		mandatory
	DESCRIPTION	"Entry holding information about the currently
			active Call Logging Server and the address of 
			a Server."
	INDEX		{ callLoggingServerIndex }
	::= { callLoggingServerTable 1 }

    CallLoggingServerEntry ::=
	SEQUENCE {
		callLoggingServerIndex
			INTEGER,
		callLoggingCurrentServerFlag
			INTEGER,
		callLoggingServerIPAddress
			IpAddress,
	        callLoggingEnableActiveServer
	                INTEGER
       }

    callLoggingServerIndex	OBJECT-TYPE
	SYNTAX		INTEGER
	ACCESS		read-only
	STATUS		mandatory
	DESCRIPTION	"The index number for this Call Logging server
			entry. Its value ranges from 1 to 
			'callLoggingNumServers'. and identifies which 
			server entry is associated with."
	::= { callLoggingServerEntry 1 }

    callLoggingCurrentServerFlag OBJECT-TYPE
	SYNTAX		INTEGER {
			    active(1),
			    standby(2)
			}
	ACCESS		read-only
	STATUS		mandatory
	DESCRIPTION	"Value indicates whether this entry is the current
			Call Logging server or not."
	::= { callLoggingServerEntry 2 }

    callLoggingServerIPAddress OBJECT-TYPE
	SYNTAX		IpAddress
	ACCESS		read-write
	STATUS		mandatory
	DESCRIPTION	"The IP address of Call Logging server. The 
			value 0.0.0.0 is returned if entry is invalid."
	::= { callLoggingServerEntry 3 }

    callLoggingEnableActiveServer  OBJECT-TYPE
         SYNTAX          INTEGER {
                             notApplicable(1),
                             enable(2)
                         }
         ACCESS          read-write
         STATUS          mandatory
         DESCRIPTION     "This is used to set the active call Logging server.
                         If set to enable(2) it will enable the call Logging server,
                          A read on the variable will return notApplicable(1)."
         ::= { callLoggingServerEntry 4 }


--  Call logging configuration attributes and actions

    callLoggingStatus	OBJECT-TYPE
	SYNTAX		INTEGER	{
			    enabled(1),
			    disabled(2)
                        }
	ACCESS		read-write
	STATUS		mandatory
	DESCRIPTION	"Enable/Disable call loggin support.
			Note: Prior to enable the call Logging, one of
			the Call Logging server must be setup with a
			valid IP address.  If the server IP address is
			not setup, a SET to this object will return with
			a bad value error."
	::= { callLoggingGroup 3 }

    callLoggingPortNumber OBJECT-TYPE
	SYNTAX		INTEGER ( 0.. 'FFFF'h )
	ACCESS		read-write
	STATUS		mandatory
	DESCRIPTION	"The UDP server port to use for Call Logging
			packets."
	::= { callLoggingGroup 4 }

    callLoggingKey	OBJECT-TYPE
	SYNTAX		OCTET STRING (SIZE (0..20))
	ACCESS		read-write
	STATUS		mandatory
	DESCRIPTION	"The (RADIUS_ACCT) call logging key to access
			server."
	::= { callLoggingGroup 5 }

    callLoggingTimeout	OBJECT-TYPE
	SYNTAX		INTEGER
	ACCESS		read-write
	STATUS		mandatory
	DESCRIPTION	"Number of seconds to wait for a response to 
			previous Call Logging request sent to server."
	::= { callLoggingGroup 6 }

    callLoggingIdBase	OBJECT-TYPE
	SYNTAX		INTEGER	{
			    other(1),	-- none of the followings
			    invalid(2),	
			    base10(10),
			    base16(16)
                        }
	ACCESS		read-write
	STATUS		mandatory
	DESCRIPTION	"The Base to use in reporting Call Logging ID."
	::= { callLoggingGroup 7 }

    callLoggingResetTime  OBJECT-TYPE
	SYNTAX		INTEGER ( 0..'7FFFFFFF'h )
	ACCESS		read-write
	STATUS		mandatory
	DESCRIPTION	"The time to reset to the primary server after
			it has failed."
	::= { callLoggingGroup 8 }

    callLoggingStopPacketsOnly OBJECT-TYPE
	SYNTAX		INTEGER	{
			    enabled(1),
			    disabled(2)
                        }
	ACCESS		read-write
	STATUS		mandatory
	DESCRIPTION	"Send call log Stop packets that have username=0.
			These are caused by connections that are dropped 
			before authentication is done."
	::= { callLoggingGroup 9 }

    callLoggingRetryLimit  OBJECT-TYPE
	SYNTAX		INTEGER
	ACCESS		read-write
	STATUS		mandatory
	DESCRIPTION	"Number of retries before removing Call Logging 
			packet. 0 means leave on retry list until maximum
			retry entries are exceeded."
	::= { callLoggingGroup 10 }

    callLoggingAssStatus  OBJECT-TYPE
	SYNTAX		INTEGER	{
		            idle(1),
			    active(2),
			    aborted(3)
                        }
	ACCESS		read-write
	STATUS		mandatory
	DESCRIPTION	"Indicates the status of Active Session Snapshot
			protocol. 
			Writing the attribute with a nonzero value causes
			the start of an Active Session Snapshot. If no 
			server is configured the Active Session Snapshot
			will abort immediatly, an active session can not 
			be aborted"
	::= { callLoggingGroup 11 }
   
    callLoggingDroppedPacketCount OBJECT-TYPE
	SYNTAX		INTEGER
	ACCESS		read-only
	STATUS		mandatory
	DESCRIPTION	"Number of dropped Call Logging packets since the
			last Active Session Snapshot"
	::= { callLoggingGroup 12 }

    callLoggingRadCompatMode OBJECT-TYPE
	SYNTAX		INTEGER	{
			    other(1),	-- none of the followings 
			    invalid(2),
			    radOldAscend(3),
			    radVendorSpecific(4)
                        }
	ACCESS		read-only
	STATUS		mandatory
	DESCRIPTION	"Indicates call logging RADIUS compatibility mode.
			 This variable is deprecated, starting with TAOS 
                         Release 8.0. this variable has a fixed value of 
                         radVendorSpecific(4)"
	::= { callLoggingGroup 13 }

END
