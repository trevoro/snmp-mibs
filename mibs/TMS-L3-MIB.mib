TMS-L3-MIB DEFINITIONS ::= BEGIN

------------------------------------------------------------------------------
------------------------------------------------------------------------------
--
--  File         : tmsL3Mib.mi2
--  Description  : Sample TMS Layer 3 Enterprise MIB - Hardware Independent 
--  Version      : 0.14
--  Date         : April 12, 2001     
--
--  Copyright (c) 2000-2001 Wind River Systems, Inc.  All Rights Reserved.
--
--  Reproduction of this document is authorized on condition that this
--  copyright notice is included.  This sample TMS Layer 3 Enterprise MIB
--  embodies proprietary intellectual property of Wind River Systems (WRS). 
--  WRS retains all title and ownership in the specification, including any
--  revisions.
--
--  It is the intent of WRS to encourage the widespread use of this
--  specification in connection with the management of TMS-based products.  
--  WRS grants vendors, end-users, and other interested parties a
--  non-exclusive license to use this specification in connection with the
--  management of TMS products.
--
--  This specification is supplied "AS IS", and WRS makes no warranty,
--  either express or implied, as to the use, operations, condition,
--  or performance of this specification.
--
------------------------------------------------------------------------------
------------------------------------------------------------------------------
--  Sample WRS TMS Generic Layer 3 Enterprise MIB
--
--  NOTES:
--   1. This is a SMIv2 MIB.
--
--   2. The Layer 3 (L3) routing groups are defined independent of the
--      underlying hardware or architecture.
--
--   3. This MIB is designed to be used with both "Layer 2 and Layer 3 hybrid
--      switches" (L2/L3 hybrid) or with "Layer 3 only" (L3 only) switches.
--
--  The following groups are supported in the WRS TMS L3 Enterprise MIB:
--   - tmsL3Mib             TMS Generic Layer 3 Routing MIB:
--      - tmsL3IpMisc       Configure and retrieve global L3 objects   
--      - tmsL3IpSubnet     Configure and retrieve IP subnet objects   
--      - tmsL3IpStatic     Configure and retrieve IP static routes   
--      - tmsL3IpDynamic    Configure and retrieve IP dynamic routes   
--      - tmsL3IpRoute      Configure and retrieve IP routing info   
--
------------------------------------------------------------------------------
------------------------------------------------------------------------------

    IMPORTS
        MODULE-IDENTITY, OBJECT-TYPE,
        Counter32, Gauge32,
        Unsigned32, Integer32,
        IpAddress                               FROM SNMPv2-SMI
        
        RowStatus, TruthValue, 
        DisplayString, MacAddress               FROM SNMPv2-TC
        
        MODULE-COMPLIANCE, OBJECT-GROUP         FROM SNMPv2-CONF
        
        tmsGeneric                              FROM WRS-MASTER-MIB;       

    tmsL3Mib MODULE-IDENTITY
        LAST-UPDATED    "200104120000Z"  -- April 12, 2001
        ORGANIZATION    "Wind River Systems, Inc."
        CONTACT-INFO    "Wind River Systems, Inc.
                         E-mail: support@windriver.com"

        DESCRIPTION     "TMS Generic Layer 3 MIB definition."

        REVISION        "200104120000Z"  -- April 12, 2001
        DESCRIPTION     "Initial MIB creation."

        ::= { tmsGeneric 2 }

------------------------------------------------------------------------------
-- Textual Conventions (i.e., these do not affect object encoding):
------------------------------------------------------------------------------
--
-- "DURABLE":
--    Objects that are saved across a system reset and/or power cycle
--    are noted as "DURABLE" for convenience in the DESCRIPTION
--    section of the object definition.  Code must be explicitly
--    written to implement these DURABLE objects.
--

------------------------------------------------------------------------------
--  groups in the TMS Layer 3 MIB
------------------------------------------------------------------------------
    tmsL3IpMisc             OBJECT IDENTIFIER ::= { tmsL3Mib 1 }
    tmsL3IpSubnet           OBJECT IDENTIFIER ::= { tmsL3Mib 2 }
    tmsL3IpStatic           OBJECT IDENTIFIER ::= { tmsL3Mib 3 }
    tmsL3IpDynamic          OBJECT IDENTIFIER ::= { tmsL3Mib 4 }
    tmsL3IpRoute            OBJECT IDENTIFIER ::= { tmsL3Mib 5 }
    tmsL3MibConformance     OBJECT IDENTIFIER ::= { tmsL3Mib 6 }
    tmsL3MibGroups          OBJECT IDENTIFIER ::= { tmsL3MibConformance 1 }
    tmsL3MibCompliances     OBJECT IDENTIFIER ::= { tmsL3MibConformance 2 }


------------------------------------------------------------------------------
--
--  tmsL3IpMisc:
--      This group is used to configure and retrieve miscellaneous global
--      Layer 3 parameters.
--
------------------------------------------------------------------------------
--
    tmsL3IpMiscNumLogicalPorts OBJECT-TYPE
        SYNTAX Integer32
        MAX-ACCESS  read-only
        STATUS  current
        DESCRIPTION
            "The number of logical ports (i.e., L2/L3 hybrid Aggregators or
             L3 only interfaces).  For TMS, this is normally equal to the
             number of physical ports."
        ::= { tmsL3IpMisc 1 }

    tmsL3IpMiscRoutingProtocol OBJECT-TYPE
        SYNTAX  INTEGER {
            none(1),        -- no dynamic routing protocols
            rip(2),         -- RIPv1/v2
            ospf(3)         -- OSPFv2
                }
        MAX-ACCESS  read-write
        STATUS  current
        DESCRIPTION
            "DURABLE: { none }
             The selected dynamic routing protocol.

             Note that static routing is still functional even when this
             object is set to none(1)."
        ::= { tmsL3IpMisc 2 }
        
        
    tmsL3IpMiscOspfv2Config OBJECT-TYPE
        SYNTAX OCTET STRING (SIZE (0..4096))
        MAX-ACCESS read-only
        STATUS current
        DESCRIPTION
             "This object is used for retrieving the RFC1850
              Open Shortest Path First version 2 (OSPFv2) nonvolatile
              (NVM) configuration data in an ASCII character string format."
             
        REFERENCE
              "RFC1583 OSPFv2,
               RFC1850 OSPFv2 MIB, 
               WindNet OSPFv2 1.1 Release Notes,
               WindNet OSPFv2 1.1 User's Guide, Section 6 Configuration" 
        ::= { tmsL3IpMisc 3 }        


------------------------------------------------------------------------------
--
--  tmsL3IpSubnet:
--      This group is used to configure and retrieve subnet parameters
--      required for the basic routing functionality.  Before a "L2/L3 hybrid"
--      VLAN or a "L3 only" interface is used for routing, it must be assigned
--      to at least one subnet.  Although TMS supports multiple subnets per
--      VLAN or L3 interface, TMS recommends using one subnet per interface.
--
--      Note that the subnet IP address is added indirectly.  It is calculated
--      by logically AND'ing the Agent's IP address (tmsL3IpSubnetAgentIpAddr)
--      for this subnet with its subnet mask (tmsL3IpSubnetMask).  These
--      subnets are automatically added to the software Routing Table by IP
--      and can be seen in the tmsL3IpDynamicRouteTable.
--
--      For a L2/L3 hybrid switch, a static VLAN must be created for the
--      specified tmsL3IpSubnetVidIface VLAN ID value before this entry can
--      be used.
--
--      Note that one of the entries for the first interface in this table
--      (i.e., tmsL3IpSubnetIfIndex for the 'sw0' swEND driver) is directly
--      mapped to the IP address parameters in the TMS Common MIB
--      (TMS-COMMON-MIB; i.e., tmsCommonIPIpAddress, tmsCommonIPNetMask).
--      This allows the initial agent IP address to be set using the serial
--      console, BOOTP, or DHCP.  The remaining subnet entries can be entered
--      using SNMP or the Web management interfaces.
--
------------------------------------------------------------------------------
--
    tmsL3IpSubnetMaxRows  OBJECT-TYPE
        SYNTAX Unsigned32
        MAX-ACCESS read-only
        STATUS current
        DESCRIPTION
            "The maximum possible number of rows in the 'tmsL3IpSubnetTable'."
        ::= { tmsL3IpSubnet 1 }

    tmsL3IpSubnetCurrentRows  OBJECT-TYPE
        SYNTAX Unsigned32
        MAX-ACCESS read-only
        STATUS current
        DESCRIPTION
            "The current number of rows in the 'tmsL3IpSubnetTable'."
        ::= { tmsL3IpSubnet 2 }

    tmsL3IpSubnetTable OBJECT-TYPE
        SYNTAX SEQUENCE OF TmsL3IpSubnetEntry
        MAX-ACCESS not-accessible
        STATUS current
        DESCRIPTION
            "A table of subnet parameters.  There is one entry
             available for each of the 'tmsL3IpSubnetMaxRows'
             supported IP subnets."
        ::= { tmsL3IpSubnet 3 }

    tmsL3IpSubnetEntry OBJECT-TYPE
        SYNTAX TmsL3IpSubnetEntry
        MAX-ACCESS not-accessible
        STATUS current
        DESCRIPTION
            "A list of subnet parameters."
        INDEX { tmsL3IpSubnetIfIndex, tmsL3IpSubnetAgentIpAddr }
        ::= { tmsL3IpSubnetTable 1 }

    TmsL3IpSubnetEntry ::= SEQUENCE {
        tmsL3IpSubnetIfIndex        Integer32,
        tmsL3IpSubnetAgentIpAddr    IpAddress,
        tmsL3IpSubnetMask           IpAddress,
        tmsL3IpSubnetVidIface       Integer32,
        tmsL3IpSubnetName           DisplayString,
        tmsL3IpSubnetRowStatus      RowStatus
    }

    tmsL3IpSubnetIfIndex  OBJECT-TYPE
        SYNTAX Integer32
        MAX-ACCESS not-accessible
        STATUS current
        DESCRIPTION
            "DURABLE:
             The ifIndex of the swEND driver associated with this subnet."
        ::= { tmsL3IpSubnetEntry 1 }

    tmsL3IpSubnetAgentIpAddr  OBJECT-TYPE
        SYNTAX IpAddress
        MAX-ACCESS not-accessible
        STATUS current
        DESCRIPTION
            "DURABLE:
             The network management station uses this IP Address to talk
             with the Agent on this subnet.  This IP address logically
             AND'ed with 'tmsL3IpSubnetMask' yields the actual subnet
             value for this subnet."
        ::= { tmsL3IpSubnetEntry 2 }

    tmsL3IpSubnetMask  OBJECT-TYPE
        SYNTAX IpAddress
        MAX-ACCESS read-create
        STATUS current
        DESCRIPTION
            "DURABLE:
             The subnet mask for this subnet.  It contains 1's in the
             bit positions for the net and subnet IDs and 0's in the
             bit positions for host ID.  The 1's must be contiguous,
             starting with the left most bit."
        ::= { tmsL3IpSubnetEntry 3 }

    tmsL3IpSubnetVidIface  OBJECT-TYPE
        SYNTAX Integer32 (0..4094)
        MAX-ACCESS read-create
        STATUS current
        DESCRIPTION
            "DURABLE: { default=0:all }
             For a L2/L3 hybrid switch, this object contains the actual
             VLAN ID (VID) from 1 to 4094 or 0 if the VID is unassigned.
             For a L3 only switch, this object contains the actual switch
             interface from 1 to 4094 or 0 if unassigned.
             
             Changing this object for this row causes all rows with the same
             'tmsL3IpSubnetIfIndex' as this row to be changed to this new
             'tmsL3IpSubnetVidIface' value."
        ::= { tmsL3IpSubnetEntry 4 }

    tmsL3IpSubnetName  OBJECT-TYPE
        SYNTAX DisplayString (SIZE (0..16))
        MAX-ACCESS read-create
        STATUS current
        DESCRIPTION
            "DURABLE:  { '':all )
             A user reference name for this subnet."
        ::= { tmsL3IpSubnetEntry 5 }

    tmsL3IpSubnetRowStatus OBJECT-TYPE
        SYNTAX  RowStatus
        MAX-ACCESS  read-create
        STATUS  current
        DESCRIPTION
            "DURABLE:
             This object indicates the status of this entry.  A row in this
             table must be created using the createAndWait(5) action state
             (i.e., createAndGo(4) is not supported).  This object can only
             be set to active(1) after all objects for this row are valid.
             The 'tmsL3IpSubnetName' is optional.
             
             Note that the notInService(2) state is not supported.  Objects
             in this table row can be changed when this object is notReady(3)
             or active(1)."
        ::= { tmsL3IpSubnetEntry 6 }


------------------------------------------------------------------------------
--
--  tmsL3IpStatic:
--      This group is used to configure and retrieve static routes for both
--      host and subnet IP destinations.
--
--      This group is independent of the underlying switch hardware and
--      architecture.  It indicates how many Host IDs and Subnet IDs that
--      the hardware can directly support, if any.  In general, hardware
--      entries route much faster than software entries.
--      
--      The user can choose to reserve zero, some, or all of the available
--      hardware entries for use as static routes.  The remaining entries,
--      if any, are reserved for dynamic routes (e.g., RIP, OSPF, etc.).
--
--      Note that the default route entry (0.0.0.0) cannot be placed in this
--      table.  If the default route was ever placed into the hardware route
--      table, unknown routes would never be sent to the CPU (i.e., this would
--      prevent new routes from being learned and/or placed into the hardware
--      route table).  The default route is reserved for use by the agent.
--
------------------------------------------------------------------------------
--
    tmsL3IpStaticMaxHwHosts  OBJECT-TYPE
        SYNTAX Unsigned32
        MAX-ACCESS read-only
        STATUS current
        DESCRIPTION
            "The maximum number, if any, of hosts that the hardware
             can support in its routing table.
             
             Note that if the hardware supports both hosts and subnets
             in the same table, this number represents both and 
             'tmsL3IpStaticMaxHwSubnets' is zero (0)."
        ::= { tmsL3IpStatic 1 }

    tmsL3IpStaticNumStaticHwHosts  OBJECT-TYPE
        SYNTAX Unsigned32
        MAX-ACCESS read-write
        STATUS current
        DESCRIPTION
            "DURABLE:
             The number of 'tmsL3IpStaticMaxHwHosts' hosts that the user
             would like to reserve for static routes.  A SNMPv1 badValue
             or SNMPv2 wrongValue is returned if the user attempts to use
             a value less than zero or greater than 'tmsL3IpStaticMaxHwHosts'.
             
             WARNING: This value is only used during system initialization
             (i.e., after a reset)."
        ::= { tmsL3IpStatic 2 }

    tmsL3IpStaticMaxHwSubnets  OBJECT-TYPE
        SYNTAX Unsigned32
        MAX-ACCESS read-only
        STATUS current
        DESCRIPTION
            "The maximum number, if any, of subnets that the hardware
             can support in its routing table.

             Note that if the hardware supports both hosts and subnets
             in the same table, this value is zero (0)."
        ::= { tmsL3IpStatic 3 }

    tmsL3IpStaticNumStaticHwSubnets  OBJECT-TYPE
        SYNTAX Unsigned32
        MAX-ACCESS read-write
        STATUS current
        DESCRIPTION
            "DURABLE:
             The number of 'tmsL3IpStaticMaxHwSubnets' subnets that the user
             would like to reserve for static routes.  An A SNMPv1 badValue
             or SNMPv2 wrongValue is returned if the user attempts to use a
             value less than zero or greater than 'tmsL3IpStaticMaxHwSubnets'.
             
             WARNING: This value is only used during system initialization
             (i.e., after a reset)."
        ::= { tmsL3IpStatic 4 }

    tmsL3IpStaticRouteMaxRows  OBJECT-TYPE
        SYNTAX Unsigned32
        MAX-ACCESS read-only
        STATUS current
        DESCRIPTION
            "The maximum possible number of rows in the 
             'tmsL3IpStaticRouteTable'."
        ::= { tmsL3IpStatic 5 }

    tmsL3IpStaticRouteCurrentRows  OBJECT-TYPE
        SYNTAX Unsigned32
        MAX-ACCESS read-only
        STATUS current
        DESCRIPTION
            "The current number of rows in the 'tmsL3IpStaticRouteTable'."
        ::= { tmsL3IpStatic 6 }

    tmsL3IpStaticRouteTable OBJECT-TYPE
        SYNTAX SEQUENCE OF TmsL3IpStaticRouteEntry
        MAX-ACCESS not-accessible
        STATUS current
        DESCRIPTION
            "A table of static routes."
        ::= { tmsL3IpStatic 7 }

    tmsL3IpStaticRouteEntry OBJECT-TYPE
        SYNTAX TmsL3IpStaticRouteEntry
        MAX-ACCESS not-accessible
        STATUS current
        DESCRIPTION
            "A list of static route parameters."
        INDEX { tmsL3IpStaticDestIpAddr }
        ::= { tmsL3IpStaticRouteTable 1 }

    TmsL3IpStaticRouteEntry ::= SEQUENCE {
        tmsL3IpStaticDestIpAddr     IpAddress,
        tmsL3IpStaticMask           IpAddress,
        tmsL3IpStaticNextHop        IpAddress,
        tmsL3IpStaticName           DisplayString,
        tmsL3IpStaticUseHw          TruthValue,
        tmsL3IpStaticInHw           TruthValue,
        tmsL3IpStaticGateway        TruthValue,
        tmsL3IpStaticRowStatus      RowStatus
    }

    tmsL3IpStaticDestIpAddr  OBJECT-TYPE
        SYNTAX IpAddress
        MAX-ACCESS not-accessible
        STATUS current
        DESCRIPTION
            "DURABLE:
             The static route host or subnet IP destination address.
             All IP destination addresses must be non-zero."
        ::= { tmsL3IpStaticRouteEntry 1 }

    tmsL3IpStaticMask  OBJECT-TYPE
        SYNTAX IpAddress
        MAX-ACCESS read-create
        STATUS current
        DESCRIPTION
            "DURABLE:
             The mask for this IP destination.  It contains 1's in the
             bit positions for the net and subnet IDs and 0's in the
             bit positions for host ID.  The 1's must be contiguous,
             starting with the left most bit.
             
             Note that a host route uses a 255.255.255.255 mask."
        ::= { tmsL3IpStaticRouteEntry 2 }

    tmsL3IpStaticNextHop OBJECT-TYPE
        SYNTAX  IpAddress
        MAX-ACCESS  read-create
        STATUS  current
        DESCRIPTION
            "The IP address of the next hop of this route.
            (In the case of a route bound to an interface
            which is realized via a broadcast media, the value
            of this field is the agent's IP address on that
            interface.)"
        ::= { tmsL3IpStaticRouteEntry 3 }

    tmsL3IpStaticName  OBJECT-TYPE
        SYNTAX DisplayString (SIZE (0..16))
        MAX-ACCESS read-create
        STATUS current
        DESCRIPTION
            "DURABLE:  { '':all )
             A user reference name for this Static Route."
        ::= { tmsL3IpStaticRouteEntry 4 }

    tmsL3IpStaticUseHw  OBJECT-TYPE
        SYNTAX TruthValue
        MAX-ACCESS read-create
        STATUS current
        DESCRIPTION
            "DURABLE: { false:all )
             By setting this object to true(1), the user indicates the
             desire to use hardware routing for this entry.  To disable
             hardware routing for this entry, set this object to false(2).
             If the underlying switch fabric does not support hardware
             routing, this object is ignored.

             There is usually limited space in the hardware routing table.
             Consequently, if the user enables hardware routing on 'too'
             many entries, the agent assigns routes on a first come, first
             serve basis (i.e., the user may not get the expected results)."
        DEFVAL  { false }
        ::= { tmsL3IpStaticRouteEntry 5 }

    tmsL3IpStaticInHw  OBJECT-TYPE
        SYNTAX TruthValue
        MAX-ACCESS read-only
        STATUS current
        DESCRIPTION
            "If this object is true(1), this static route is actually in
             the hardware Route Table.  Otherwise it is false(2)."
        ::= { tmsL3IpStaticRouteEntry 6 }

    tmsL3IpStaticGateway  OBJECT-TYPE
        SYNTAX TruthValue
        MAX-ACCESS read-create
        STATUS current
        DESCRIPTION
            "DURABLE: { false:all )
             By setting this object to true(1), the user indicates that this
             subnet route is a gateway route (i.e., connected to external
             router).  By setting it to false(2), the user indicates that this
             is a direct route.  If 'tmsL3IpStaticMask' is '255.255.255.255'
             (i.e., a host route) for this entry, this object cannot be set
             to true(1)."
        DEFVAL  { false }
        ::= { tmsL3IpStaticRouteEntry 7 }

    tmsL3IpStaticRowStatus OBJECT-TYPE
        SYNTAX  RowStatus
        MAX-ACCESS  read-create
        STATUS  current
        DESCRIPTION
            "DURABLE:
             This object indicates the status of this entry.  A row in this
             table must be created using the createAndWait(5) action state
             (i.e., createAndGo(4) is not supported).  This object can only
             be set to active(1) after all objects for this row are valid.
             The 'tmsL3IpStaticName' is optional.
             
             Note that the notInService(2) state is not supported.  Objects
             in this table row can be changed when this object is notReady(3)
             or active(1)."
        ::= { tmsL3IpStaticRouteEntry 8 }


------------------------------------------------------------------------------
--
--  tmsL3IpDynamic:
--      This group is used to configure and retrieve dynamic routes for both
--      host and subnet IP destinations.  Dynamic routes are generated from:
--       - RIP
--       - OSPF
--       - other dynamic routing protocols
--       - TCP/IP stack creating host routes for existing subnets
--
--      It is independent of the underlying switch hardware and architecture.
--      
--      This table allows the user to add, modify, and delete "dynamic"
--      routes, but none of these dynamic routes are saved in NVM.  Use the
--      'tmsL3IpStaticRouteTable' to set up static routes that can be saved
--      in NVM.
--
--      When a subnet is removed from the 'tmsL3IpSubnetTable', the associated
--      dynamic route entry, and any other entries resulting from that subnet,
--      are automatically removed from this table.
--      
--      Note that the default route entry (0.0.0.0) cannot be placed in this
--      table.  If the default route was ever placed into the hardware route
--      table, unknown routes would never be sent to the CPU (i.e., this would
--      prevent new routes from being learned and/or placed into the hardware
--      route table).  The default route is reserved for use by the agent.
--
------------------------------------------------------------------------------
--
    tmsL3IpDynamicRouteCurrentRows  OBJECT-TYPE
        SYNTAX Unsigned32
        MAX-ACCESS read-only
        STATUS current
        DESCRIPTION
            "The current number of rows in the 'tmsL3IpDynamicRouteTable'."
        ::= { tmsL3IpDynamic 1 }

    tmsL3IpDynamicRouteTable OBJECT-TYPE
        SYNTAX SEQUENCE OF TmsL3IpDynamicRouteEntry
        MAX-ACCESS not-accessible
        STATUS current
        DESCRIPTION
            "A table of dynamic routes generated by RIP, OSPF, other routing
             protocols, and by the TCP/IP stack when creating host routes
             for existing subnets."
        ::= { tmsL3IpDynamic 2 }

    tmsL3IpDynamicRouteEntry OBJECT-TYPE
        SYNTAX TmsL3IpDynamicRouteEntry
        MAX-ACCESS not-accessible
        STATUS current
        DESCRIPTION
            "A list of dynamic route parameters."
        INDEX { tmsL3IpDynamicDestIpAddr }
        ::= { tmsL3IpDynamicRouteTable 1 }

    TmsL3IpDynamicRouteEntry ::= SEQUENCE {
        tmsL3IpDynamicDestIpAddr    IpAddress,
        tmsL3IpDynamicMask          IpAddress,
        tmsL3IpDynamicNextHop       IpAddress,
        tmsL3IpDynamicName          DisplayString,
        tmsL3IpDynamicUseHw         TruthValue,
        tmsL3IpDynamicInHw          TruthValue,
        tmsL3IpDynamicGateway       TruthValue,
        tmsL3IpDynamicRowStatus     RowStatus
    }

    tmsL3IpDynamicDestIpAddr  OBJECT-TYPE
        SYNTAX IpAddress
        MAX-ACCESS not-accessible
        STATUS current
        DESCRIPTION
            "The dynamic route host or subnet IP destination address.
             All IP destination addresses must be non-zero."
        ::= { tmsL3IpDynamicRouteEntry 1 }

    tmsL3IpDynamicMask  OBJECT-TYPE
        SYNTAX IpAddress
        MAX-ACCESS read-create
        STATUS current
        DESCRIPTION
            "The mask for this IP destination.  It contains 1's in the
             bit positions for the net and subnet IDs and 0's in the
             bit positions for host ID.  The 1's must be contiguous,
             starting with the left most bit.
             
             Note that a host route uses a 255.255.255.255 mask."
        ::= { tmsL3IpDynamicRouteEntry 2 }

    tmsL3IpDynamicNextHop OBJECT-TYPE
        SYNTAX  IpAddress
        MAX-ACCESS  read-create
        STATUS  current
        DESCRIPTION
            "The IP address of the next hop of this route.
            (In the case of a route bound to an interface
            which is realized via a broadcast media, the value
            of this field is the agent's IP address on that
            interface.)"
        ::= { tmsL3IpDynamicRouteEntry 3 }

    tmsL3IpDynamicName  OBJECT-TYPE
        SYNTAX DisplayString (SIZE (0..16))
        MAX-ACCESS read-create
        STATUS current
        DESCRIPTION
            "A user reference name for this Dynamic Route."
        ::= { tmsL3IpDynamicRouteEntry 4 }

    tmsL3IpDynamicUseHw  OBJECT-TYPE
        SYNTAX TruthValue
        MAX-ACCESS read-create
        STATUS current
        DESCRIPTION
            "By setting this object to true(1), the user indicates the
             desire to use hardware routing for this entry.  To disable
             hardware routing for this entry, set this object to false(2).
             If the underlying switch fabric does not support hardware
             routing, this object is ignored.

             There is usually limited space in the hardware routing table.
             Consequently, if the user enables hardware routing on 'too'
             many entries, the agent assigns routes on a first come, first
             serve basis (i.e., the user may not get the expected results)."
        DEFVAL  { true }
        ::= { tmsL3IpDynamicRouteEntry 5 }

    tmsL3IpDynamicInHw  OBJECT-TYPE
        SYNTAX TruthValue
        MAX-ACCESS read-only
        STATUS current
        DESCRIPTION
            "If this object is true(1), this dynamic route is actually in
             the hardware Route Table.  Otherwise it is false(2)."
        ::= { tmsL3IpDynamicRouteEntry 6 }

    tmsL3IpDynamicGateway  OBJECT-TYPE
        SYNTAX TruthValue
        MAX-ACCESS read-create
        STATUS current
        DESCRIPTION
            "By setting this object to true(1), the user indicates that this
             subnet route is a gateway route (i.e., connected to external
             router).  By setting it to false(2), the user indicates that this
             is a direct route.  If 'tmsL3IpDynamicMask' is '255.255.255.255'
             (i.e., a host route) for this entry, this object cannot be set
             to true(1)."
        DEFVAL  { false }
        ::= { tmsL3IpDynamicRouteEntry 7 }

    tmsL3IpDynamicRowStatus OBJECT-TYPE
        SYNTAX  RowStatus
        MAX-ACCESS  read-create
        STATUS  current
        DESCRIPTION
            "This object indicates the status of this entry.  A row in this
             table must be created using the createAndWait(5) action state
             (i.e., createAndGo(4) is not supported).  This object can only
             be set to active(1) after all objects for this row are valid.
             The 'tmsL3IpDynamicName' is optional.
             
             Note that the notInService(2) state is not supported.  Objects
             in this table row can be changed when this object is notReady(3)
             or active(1)."
        ::= { tmsL3IpDynamicRouteEntry 8 }


------------------------------------------------------------------------------
--
--  tmsL3IpRoute:
--      The MIB II Routing Table (ipRouteTable) does not include the 
--      information required to support the UNIX style "netstat -nr" command.
--      This group replicates some of the ipRouteTable objects and adds
--      additional objects to support the "netstat -nr" functionality.
--
--      Note that the "netstat -nr" functionality has not been implemented.
--
--      This table also provides 'RowStatus' support for the 'ipRouteTable'
--      objects contained in this table.
--
--      The ipRouteTable objects are not actually duplicated, but use the IDB+
--      "alternate object" capability to point back to the MIB II ipRouteTable.
--      Note that the utilized ipRouteTable objects are presented here
--      in a more logical order (similar to RFC1354).
--
------------------------------------------------------------------------------
--
    tmsL3IpRouteTableCurrentSwEntries  OBJECT-TYPE
        SYNTAX Unsigned32
        MAX-ACCESS read-only
        STATUS current
        DESCRIPTION
            "The number of current entries in the software Routing Table."
        ::= { tmsL3IpRoute 1 }

    tmsL3IpRouteCurrentHwHosts  OBJECT-TYPE
        SYNTAX Unsigned32
        MAX-ACCESS read-only
        STATUS current
        DESCRIPTION
            "The number of hardware host routing table entries currently
             in use.  If the hardware does not have routing table support,
             this value is zero (0).
             
             If the hardware supports both hosts and subnets
             in the same table, this number represents both and
             'tmsL3IpRouteCurrentHwSubnets' is zero (0)."
        ::= { tmsL3IpRoute 2 }

    tmsL3IpRouteCurrentHwSubnets  OBJECT-TYPE
        SYNTAX Unsigned32
        MAX-ACCESS read-only
        STATUS current
        DESCRIPTION
            "The number of hardware subnet routing table entries currently
             in use.  If the hardware does not have routing table support,
             this value is zero (0).

             Note that if the hardware supports both hosts and subnets
             in the same table, this value is zero (0)."
        ::= { tmsL3IpRoute 3 }

    tmsL3IpRouteTable OBJECT-TYPE
        SYNTAX  SEQUENCE OF TmsL3IpRouteEntry
        MAX-ACCESS  not-accessible
        STATUS  current
        DESCRIPTION
            "Provides Routing Table access.  This table can be used to
             modify or add Routing Table entries.  Changes made with this
             table are not saved to NVM (nonvolatile memory).  To save
             static routes to NVM, use the tmsL3IpStaticRouteTable."
        ::= { tmsL3IpRoute 4 }

    tmsL3IpRouteEntry OBJECT-TYPE
        SYNTAX  TmsL3IpRouteEntry
        MAX-ACCESS  not-accessible
        STATUS  current
        DESCRIPTION
            "Provides enough routing information to support the UNIX style
             'netstat -nr' command and to support maintenance of the
             Routing Table."
        INDEX   { tmsL3IpRouteDest }
        ::= { tmsL3IpRouteTable 1 }

    TmsL3IpRouteEntry ::=
        SEQUENCE {
            tmsL3IpRouteDest        IpAddress,
            tmsL3IpRouteMask        IpAddress,
            tmsL3IpRouteNextHopIp   IpAddress,
            tmsL3IpRouteNextHopMac  MacAddress,
            tmsL3IpRouteIfIndex     Integer32,
            tmsL3IpRouteType        INTEGER,
            tmsL3IpRouteProto       INTEGER,
            tmsL3IpRouteAge         Unsigned32,
            tmsL3IpRouteMetric1     Integer32,
            tmsL3IpRouteUsingHw     TruthValue,
            tmsL3IpRouteIsStatic    TruthValue,
            tmsL3IpRouteFlags       Unsigned32,
            tmsL3IpRouteRef         Gauge32,
            tmsL3IpRouteUse         Counter32,
            tmsL3IpRouteRowStatus   RowStatus
        }

    tmsL3IpRouteDest OBJECT-TYPE
        SYNTAX  IpAddress
        MAX-ACCESS  not-accessible
        STATUS  current
        DESCRIPTION
            "The destination IP address of this route.  An
            entry with a value of 0.0.0.0 is considered a
            default route.  Multiple routes to a single
            destination can appear in the table, but access to
            such multiple entries is dependent on the table-
            access mechanisms defined by the network
            management protocol in use."
        ::= { tmsL3IpRouteEntry 1 }

    tmsL3IpRouteMask OBJECT-TYPE
        SYNTAX  IpAddress
        MAX-ACCESS  read-create
        STATUS  current
        DESCRIPTION
            "Indicate the mask to be logical-ANDed with the
            destination address before being compared to the
            value in the tmsL3IpRouteDest field.

            If the value of the tmsL3IpRouteDest is 0.0.0.0 (a
            default route), then the mask value is also
            0.0.0.0.  It should be noted that all IP routing
            subsystems implicitly use this mechanism."
        ::= { tmsL3IpRouteEntry 2 }
        
    tmsL3IpRouteNextHopIp OBJECT-TYPE
        SYNTAX  IpAddress
        MAX-ACCESS  read-create
        STATUS  current
        DESCRIPTION
            "The IP address of the next hop of this route.
            (In the case of a route bound to an interface
            which is realized via a broadcast media, the value
            of this field is the agent's IP address on that
            interface.)"
        ::= { tmsL3IpRouteEntry 3 }

    tmsL3IpRouteNextHopMac OBJECT-TYPE
        SYNTAX  MacAddress
        MAX-ACCESS  read-only
        STATUS  current
        DESCRIPTION
            "The six byte MAC address of the next hop of this
            route.  If the underlying hardware does not support this
            object, an octet string of zero length is returned."
        ::= { tmsL3IpRouteEntry 4 }

    tmsL3IpRouteIfIndex OBJECT-TYPE
        SYNTAX  Integer32
        MAX-ACCESS  read-only
        STATUS  current
        DESCRIPTION
            "The index value which uniquely identifies the
            local interface through which the next hop of this
            route should be reached.  The interface identified
            by a particular value of this index is the same
            interface as identified by the same value of
            ifIndex."
        ::= { tmsL3IpRouteEntry 5 }

    tmsL3IpRouteType OBJECT-TYPE
        SYNTAX  INTEGER {
            other(1),       -- none of the following
            invalid(2),     -- an invalidated route
            direct(3),      -- route to directly connected (sub-)network
            indirect(4)     -- route to a non-local 
                            -- host/network/sub-network
                }
        MAX-ACCESS  read-create
        STATUS  current
        DESCRIPTION
            "The type of route.  Note that the values
            direct(3) and indirect(4) refer to the notion of
            direct and indirect routing in the IP architecture.

            Setting this object to the value invalid(2) has
            the effect of invalidating the corresponding entry
            in the tmsL3IpRouteTable object.  That is, it
            effectively disassociates the destination
            identified with said entry from the route
            identified with said entry.  It is an
            implementation-specific matter as to whether the
            agent removes an invalidated entry from the table.
            Accordingly, management stations must be prepared
            to receive tabular information from agents that
            corresponds to entries not currently in use.
            Proper interpretation of such entries requires
            examination of the relevant tmsL3IpRouteType object."
        ::= { tmsL3IpRouteEntry 6 }

    tmsL3IpRouteProto OBJECT-TYPE
        SYNTAX  INTEGER {
            other(1),       -- none of the following

                            -- non-protocol information,
            local(2),       -- e.g., manually configured entries

            netmgmt(3),     -- set via a network management protocol

            icmp(4),        -- obtained via ICMP, e.g., Redirect

                            -- the remaining values are all gateway
                            -- routing protocols
            egp(5),
            ggp(6),
            hello(7),
            rip(8),
            is-is(9),
            es-is(10),
            ciscoIgrp(11),
            bbnSpfIgp(12),
            ospf(13),
            bgp(14)
                }
        MAX-ACCESS  read-only
        STATUS  current
        DESCRIPTION
            "The routing mechanism via which this route was
            learned.  Inclusion of values for gateway routing
            protocols is not intended to imply that hosts
            should support those protocols."
        ::= { tmsL3IpRouteEntry 7 }

    tmsL3IpRouteAge OBJECT-TYPE
        SYNTAX  Unsigned32
        MAX-ACCESS  read-only
        STATUS  current
        DESCRIPTION
            "The number of seconds since this route was last
            updated or otherwise determined to be correct.
            Note that no semantics of `too old' can be implied
            except through knowledge of the routing protocol
            by which the route was learned."
        ::= { tmsL3IpRouteEntry 8 }

    tmsL3IpRouteMetric1 OBJECT-TYPE
        SYNTAX  Integer32
        MAX-ACCESS  read-only
        STATUS  current
        DESCRIPTION
            "The primary routing metric for this route.  The
            semantics of this metric are determined by the
            routing-protocol specified in the route's
            tmsL3IpRouteProto value.  If this metric is not used,
            its value should be set to -1."
        ::= { tmsL3IpRouteEntry 9 }

    tmsL3IpRouteUsingHw OBJECT-TYPE
        SYNTAX  TruthValue
        MAX-ACCESS  read-only
        STATUS  current
        DESCRIPTION
            "This object is true(1) if this route is contained in
            the hardware routing table; otherwise, it is false(2)."
        ::= { tmsL3IpRouteEntry 10 }

    tmsL3IpRouteIsStatic OBJECT-TYPE
        SYNTAX  TruthValue
        MAX-ACCESS  read-only
        STATUS  current
        DESCRIPTION
            "This object is true(1) if this route is defined in the
            'tmsL3IpStaticRouteTable'.  This object is false(2) if this
            route was created dynamically (e.g., with RIP, OSPF) or was
            manually created using this table ('tmsL3IpRouteTable') or 
            the RFC1213 'ipRouteTable'."
        ::= { tmsL3IpRouteEntry 11 }

    tmsL3IpRouteFlags OBJECT-TYPE
        SYNTAX  Unsigned32
        MAX-ACCESS  read-only
        STATUS  current
        DESCRIPTION
            "Not implemented.  Returns '0'.
             
             Contains the information required for a netstat-like
             'Flags' field.
             
             The flags field represents a decimal value of the flags
             specified for a given route.  The following is a list of
             currently available flag values:
                 0x1     | - route is usable (that is, 'up')
                 0x2     | - destination is a gateway
                 0x4     | - host specific routing entry
                 0x8     | - host or net unreachable
                 0x10    | - created dynamically (by redirect)
                 0x20    | - modified dynamically (by redirect)
                 0x40    | - message confirmed
                 0x80    | - subnet mask present
                 0x100   | - generate new routes on use
                 0x200   | - external daemon resolves name
                 0x400   | - generated by ARP
                 0x800   | - manually added (static)
                 0x1000  | - just discard packets (during updates)
                 0x2000  | - modified by management protocol
                 0x4000  | - protocol specific routing flag
                 0x8000  | - protocol specific routing flag

            For example, if the entry in the Routing Table has a flag
            value of decimal 5, (0x1 OR'ed with 0x4), then this route
            is 'up' and usable and is host-specific."
        ::= { tmsL3IpRouteEntry 12 }

    tmsL3IpRouteRef OBJECT-TYPE
        SYNTAX  Gauge32
        MAX-ACCESS  read-only
        STATUS  current
        DESCRIPTION
            "Not implemented.  Returns '0'.
            
             Contains the information required for the netstat 'Ref'
             field, which indicates the number active uses for this
             route."
        ::= { tmsL3IpRouteEntry 13 }

    tmsL3IpRouteUse OBJECT-TYPE
        SYNTAX  Counter32
        MAX-ACCESS  read-only
        STATUS  current
        DESCRIPTION
            "Not implemented.  Returns '0'.
            
             Contains the information required for the netstat 'Use'
             field, which indicates the number of packets sent with
             this route."
        ::= { tmsL3IpRouteEntry 14 }

    tmsL3IpRouteRowStatus OBJECT-TYPE
        SYNTAX  RowStatus
        MAX-ACCESS  read-create
        STATUS  current
        DESCRIPTION
            "This object indicates the status of this entry.  A row in this
             table must be created using the createAndWait(5) action state
             (i.e., createAndGo(4) is not supported).  This object can only
             be set to active(1) for the specified 'tmsL3IpRouteDest' index
             value after the 'tmsL3IpRouteMask' and 'tmsL3IpRouteNextHop'
             objects for this row are valid.  Setting 'tmsL3IpRouteType' is
             optional.
             
             Note that the notInService(2) state is not supported.  Objects
             in this table row can be changed when this object is notReady(3)
             or active(1)."
        ::= { tmsL3IpRouteEntry 15 }


------------------------------------------------------------------------------
--  conformance information
------------------------------------------------------------------------------

------------------------------------------------------------------------------
--  units of conformance
------------------------------------------------------------------------------

    tmsL3IpMiscGroup    OBJECT-GROUP
        OBJECTS {
            tmsL3IpMiscNumLogicalPorts,
            tmsL3IpMiscRoutingProtocol,
            tmsL3IpMiscOspfv2Config
        }
        STATUS  current
        DESCRIPTION
           "This group configures and retrieves global, miscellaneous
            L3 objects."
        ::= { tmsL3MibGroups 1 }
    
    tmsL3IpSubnetGroup  OBJECT-GROUP
        OBJECTS {
            tmsL3IpSubnetMaxRows,
            tmsL3IpSubnetCurrentRows,
            tmsL3IpSubnetMask,
            tmsL3IpSubnetVidIface,
            tmsL3IpSubnetName,
            tmsL3IpSubnetRowStatus
        }
        STATUS  current
        DESCRIPTION
           "This group configures and retrieves IP subnet objects."
        ::= { tmsL3MibGroups 2 }
    
    tmsL3IpStaticGroup  OBJECT-GROUP
        OBJECTS {
            tmsL3IpStaticMaxHwHosts,
            tmsL3IpStaticNumStaticHwHosts,
            tmsL3IpStaticMaxHwSubnets,
            tmsL3IpStaticNumStaticHwSubnets,
            tmsL3IpStaticRouteMaxRows,
            tmsL3IpStaticRouteCurrentRows,
            tmsL3IpStaticMask,
            tmsL3IpStaticNextHop,
            tmsL3IpStaticName,
            tmsL3IpStaticUseHw,
            tmsL3IpStaticInHw,
            tmsL3IpStaticGateway,
            tmsL3IpStaticRowStatus
        }
        STATUS  current
        DESCRIPTION
           "This group configures and retrieves IP static routes."
        ::= { tmsL3MibGroups 3 }

    tmsL3IpDynamicGroup  OBJECT-GROUP
        OBJECTS {
            tmsL3IpDynamicRouteCurrentRows,
            tmsL3IpDynamicMask,
            tmsL3IpDynamicNextHop,
            tmsL3IpDynamicName,
            tmsL3IpDynamicUseHw,
            tmsL3IpDynamicInHw,
            tmsL3IpDynamicGateway,
            tmsL3IpDynamicRowStatus
        }
        STATUS  current
        DESCRIPTION
           "This group configures and retrieves IP static routes."
        ::= { tmsL3MibGroups 4 }

    tmsL3IpRouteGroup   OBJECT-GROUP
        OBJECTS {
            tmsL3IpRouteTableCurrentSwEntries,
            tmsL3IpRouteCurrentHwHosts,
            tmsL3IpRouteCurrentHwSubnets,
            tmsL3IpRouteMask,
            tmsL3IpRouteNextHopIp,
            tmsL3IpRouteNextHopMac,
            tmsL3IpRouteIfIndex,
            tmsL3IpRouteType,
            tmsL3IpRouteProto,
            tmsL3IpRouteAge,
            tmsL3IpRouteMetric1,
            tmsL3IpRouteUsingHw,
            tmsL3IpRouteIsStatic,
            tmsL3IpRouteFlags,
            tmsL3IpRouteRef,
            tmsL3IpRouteUse,
            tmsL3IpRouteRowStatus
        }
        STATUS  current
        DESCRIPTION
           "This group configures and retrieves IP routing info."
        ::= { tmsL3MibGroups 5 }

------------------------------------------------------------------------------
--  compliance statements
------------------------------------------------------------------------------

    tmsL3MibCompliance MODULE-COMPLIANCE
        STATUS  current
        DESCRIPTION
           "The compliance statement."
        MODULE  -- this module
        MANDATORY-GROUPS {
             tmsL3IpMiscGroup,
             tmsL3IpSubnetGroup,
             tmsL3IpStaticGroup,
             tmsL3IpDynamicGroup,
             tmsL3IpRouteGroup
        }
        ::= { tmsL3MibCompliances 1 }

--
-- END of TMS-L3-MIB
--

END
