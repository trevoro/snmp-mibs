--			Ascend mibport1 MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBPORT1-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibportProfile  OBJECT IDENTIFIER ::= { configuration 102}

	-- The mibportProfile table
	--
	-- This table contains parameters for the mibportProfile profile
	--

    mibportProfileTable	OBJECT-TYPE
	SYNTAX		SEQUENCE OF MibportProfileEntry
	ACCESS		not-accessible
	STATUS		mandatory
	DESCRIPTION	"A list of mibportProfile profile entries."
	::= { mibportProfile 1 }

    mibportProfileEntry	OBJECT-TYPE
	SYNTAX		MibportProfileEntry
	ACCESS		not-accessible
	STATUS		mandatory
	DESCRIPTION	"A mibportProfile entry containing objects that
			 maps to the parameters of mibportProfile profile."
	INDEX		{ portProfile-Shelf-o, portProfile-Slot-o, portProfile-Item-o }
	::= { mibportProfileTable 1 }

    MibportProfileEntry ::=
	SEQUENCE {
	    portProfile-Shelf-o
		INTEGER,
	    portProfile-Slot-o
		INTEGER,
	    portProfile-Item-o
		INTEGER,
	    portProfile-PhysicalAddress-Shelf
		INTEGER,
	    portProfile-PhysicalAddress-Slot
		INTEGER,
	    portProfile-PhysicalAddress-ItemNumber
		INTEGER,
	    portProfile-Name
		DisplayString,
	    portProfile-LastModificationTime
		INTEGER,
	    portProfile-PortAnswerNumber1
		DisplayString,
	    portProfile-PortAnswerNumber2
		DisplayString,
	    portProfile-PortAnswerNumber3
		DisplayString,
	    portProfile-PortAnswerNumber4
		DisplayString,
	    portProfile-oIdle
		INTEGER,
	    portProfile-oDial
		INTEGER,
	    portProfile-PortAnswer
		INTEGER,
	    portProfile-oClear
		INTEGER,
	    portProfile-PortMinPriBw
		INTEGER,
	    portProfile-PortTerminalTiming
		INTEGER,
	    portProfile-oRS366Esc
		INTEGER,
	    portProfile-oEarlyCD
		INTEGER,
	    portProfile-PortDs0MinReset
		INTEGER,
	    portProfile-MaxPortDs0Mins
		INTEGER,
	    portProfile-MaxCallDurationTimer
		INTEGER,
	    portProfile-DialPlan
		INTEGER,
	    portProfile-TrunkGroupsNa
		INTEGER,
	    portProfile-PortPassword
		DisplayString,
	    portProfile-Action-o
		INTEGER
	}

    portProfile-Shelf-o	OBJECT-TYPE
	SYNTAX	INTEGER
	ACCESS	read-only
	STATUS	mandatory
	DESCRIPTION	""
	::= { mibportProfileEntry 1 }

    portProfile-Slot-o	OBJECT-TYPE
	SYNTAX	INTEGER
	ACCESS	read-only
	STATUS	mandatory
	DESCRIPTION	""
	::= { mibportProfileEntry 2 }

    portProfile-Item-o	OBJECT-TYPE
	SYNTAX	INTEGER
	ACCESS	read-only
	STATUS	mandatory
	DESCRIPTION	""
	::= { mibportProfileEntry 3 }

    portProfile-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibportProfileEntry 4 }

    portProfile-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibportProfileEntry 5 }

    portProfile-PhysicalAddress-ItemNumber	OBJECT-TYPE
	SYNTAX	INTEGER
	ACCESS	read-write
	STATUS	mandatory
	DESCRIPTION	"A number that specifies an addressable entity within the context of shelf and slot."
	::= { mibportProfileEntry 6 }

    portProfile-Name	OBJECT-TYPE
	SYNTAX	DisplayString
	ACCESS	read-write
	STATUS	mandatory
	DESCRIPTION	"Ports can be named, e.g. CODEC, Router, etc. The name is provided by the user. It is a standard null terminated ASCII string."
	::= { mibportProfileEntry 7 }

    portProfile-LastModificationTime	OBJECT-TYPE
	SYNTAX	INTEGER
	ACCESS	read-write
	STATUS	mandatory
	DESCRIPTION	""
	::= { mibportProfileEntry 8 }

    portProfile-PortAnswerNumber1	OBJECT-TYPE
	SYNTAX	DisplayString
	ACCESS	read-write
	STATUS	mandatory
	DESCRIPTION	"The way in which calls are answered."
	::= { mibportProfileEntry 9 }

    portProfile-PortAnswerNumber2	OBJECT-TYPE
	SYNTAX	DisplayString
	ACCESS	read-write
	STATUS	mandatory
	DESCRIPTION	"The way in which calls are answered."
	::= { mibportProfileEntry 10 }

    portProfile-PortAnswerNumber3	OBJECT-TYPE
	SYNTAX	DisplayString
	ACCESS	read-write
	STATUS	mandatory
	DESCRIPTION	"The way in which calls are answered."
	::= { mibportProfileEntry 11 }

    portProfile-PortAnswerNumber4	OBJECT-TYPE
	SYNTAX	DisplayString
	ACCESS	read-write
	STATUS	mandatory
	DESCRIPTION	"The way in which calls are answered."
	::= { mibportProfileEntry 12 }

    portProfile-oIdle	OBJECT-TYPE
	SYNTAX	INTEGER {
		    none (1),
		    call (2)
		}
	ACCESS	read-write
	STATUS	mandatory
	DESCRIPTION	"What to do when a port goes idle."
	::= { mibportProfileEntry 13 }

    portProfile-oDial	OBJECT-TYPE
	SYNTAX	INTEGER {
		    portDialTerminal (1),
		    portDialDtr (2),
		    portDialRs366 (3),
		    portDialRs366x (4),
		    portDialV25bis (5),
		    portDialV25bisC (6),
		    portDialX21 (7),
		    portDialX21x (8),
		    portDialX21Ptel (9),
		    numberOfPortDial (10)
		}
	ACCESS	read-write
	STATUS	mandatory
	DESCRIPTION	"The way in which calls are originated."
	::= { mibportProfileEntry 14 }

    portProfile-PortAnswer	OBJECT-TYPE
	SYNTAX	INTEGER {
		    portAnswerAuto (1),
		    portAnswerDtr (2),
		    portAnswerDtrRing (3),
		    portAnswerV25bis (4),
		    portAnswerV25bisC (5),
		    portAnswerTerminal (6),
		    portAnswerNone (7),
		    portAnswerX21 (8),
		    portAnswerAutoManual (9),
		    numberOfPortAnswer (10)
		}
	ACCESS	read-write
	STATUS	mandatory
	DESCRIPTION	""
	::= { mibportProfileEntry 15 }

    portProfile-oClear	OBJECT-TYPE
	SYNTAX	INTEGER {
		    dtrActive (1),
		    dtrInactive (2),
		    rtsActive (3),
		    rtsInactive (4),
		    terminal (5)
		}
	ACCESS	read-write
	STATUS	mandatory
	DESCRIPTION	"The way in which calls are cleared, as given above."
	::= { mibportProfileEntry 16 }

    portProfile-PortMinPriBw	OBJECT-TYPE
	SYNTAX	INTEGER
	ACCESS	read-write
	STATUS	mandatory
	DESCRIPTION	"Minimum priority bandwidth allocated to this port. Part of IDBM."
	::= { mibportProfileEntry 17 }

    portProfile-PortTerminalTiming	OBJECT-TYPE
	SYNTAX	INTEGER {
		    no (1),
		    yes (2)
		}
	ACCESS	read-write
	STATUS	mandatory
	DESCRIPTION	"Terminal timing enabled for this port?"
	::= { mibportProfileEntry 18 }

    portProfile-oRS366Esc	OBJECT-TYPE
	SYNTAX	INTEGER {
		    star (1),
		    pound (2),
		    n-5 (3),
		    n-6 (4),
		    n-7 (5),
		    n-9 (6),
		    n-0 (7),
		    n-00 (8),
		    numberEsc366 (9)
		}
	ACCESS	read-write
	STATUS	mandatory
	DESCRIPTION	"RS-366 dialing escape character."
	::= { mibportProfileEntry 19 }

    portProfile-oEarlyCD	OBJECT-TYPE
	SYNTAX	INTEGER {
		    none (1),
		    answer (2),
		    originate (3),
		    both (4)
		}
	ACCESS	read-write
	STATUS	mandatory
	DESCRIPTION	"If and when to perform early DCD on the host port."
	::= { mibportProfileEntry 20 }

    portProfile-PortDs0MinReset	OBJECT-TYPE
	SYNTAX	INTEGER {
		    off (1),
		    daily (2),
		    monthly (3)
		}
	ACCESS	read-write
	STATUS	mandatory
	DESCRIPTION	"For billing-cap features related to this port, the duration for the billing cap reset or disabled if apprpriate."
	::= { mibportProfileEntry 21 }

    portProfile-MaxPortDs0Mins	OBJECT-TYPE
	SYNTAX	INTEGER
	ACCESS	read-write
	STATUS	mandatory
	DESCRIPTION	"The maximum number of minutes that can be billed to this port in the duration set above. If the number exceeds the value set, all switched-calls will be cleared by the system."
	::= { mibportProfileEntry 22 }

    portProfile-MaxCallDurationTimer	OBJECT-TYPE
	SYNTAX	INTEGER
	ACCESS	read-write
	STATUS	mandatory
	DESCRIPTION	"The maximum length of time for a call to be active on this port. If a call is up longer than this time, the call is cleared automatically. This is all part of the no-surprises phone bill feature set."
	::= { mibportProfileEntry 23 }

    portProfile-DialPlan	OBJECT-TYPE
	SYNTAX	INTEGER
	ACCESS	read-write
	STATUS	mandatory
	DESCRIPTION	""
	::= { mibportProfileEntry 24 }

    portProfile-TrunkGroupsNa	OBJECT-TYPE
	SYNTAX	INTEGER {
		    no (1),
		    yes (2)
		}
	ACCESS	read-write
	STATUS	mandatory
	DESCRIPTION	""
	::= { mibportProfileEntry 25 }

    portProfile-PortPassword	OBJECT-TYPE
	SYNTAX	DisplayString
	ACCESS	read-write
	STATUS	mandatory
	DESCRIPTION	"Port password used to authenticate DBA call's password. Authentication is automatic if port password is not defined."
	::= { mibportProfileEntry 26 }

    portProfile-Action-o	OBJECT-TYPE
	SYNTAX	INTEGER {
		    noAction (1),
		    createProfile (2),
		    deleteProfile (3)
		}
	ACCESS	read-write
	STATUS	mandatory
	DESCRIPTION	""
	::= { mibportProfileEntry 27 }

END
