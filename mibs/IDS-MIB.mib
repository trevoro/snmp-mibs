IDS-MIB DEFINITIONS ::= BEGIN

-- Title:      RADWARE
--             This Private MIB supports the Vgate
-- Version:    2.9
-- Date:       9 Apr 2000
-- By:         RMA (Radware MIB Authority)
-- E-mail:     US:            support@radware.com
--             International: support_int@radware.com

IMPORTS
       NetworkAddress,
       IpAddress,
       Counter,
       Gauge,
       enterprises
              FROM RFC1155-SMI
       OBJECT-TYPE
              FROM RFC-1212
       DisplayString,
       PhysAddress,
       ipAddrEntry
              FROM RFC1213-MIB
       TRAP-TYPE
                    FROM RFC-1215
       rsIDS
                    FROM RADWARE-MIB;

    TruthValue ::= INTEGER {
         true (1),
         false (2)
        }
    RowStatus ::= INTEGER {
        active(1),
        notInService(2),
        notReady(3),
        createAndGo(4),
        createAndWait(5),
        destroy(6)
        }
    NetNumber ::=  OCTET STRING (SIZE(4))

-- Some MIB compilers require that the following 7 lines which define the path
-- to RND MIB are commented out:

-- mib            OBJECT IDENTIFIER ::= { mgmt 1  }
-- directory      OBJECT IDENTIFIER ::= { internet 1  }
-- experimental   OBJECT IDENTIFIER ::= { internet 3  }
-- private        OBJECT IDENTIFIER ::= { internet 4  }
-- enterprises    OBJECT IDENTIFIER ::= { private 1  }



 rsIDSTrackingTable OBJECT-TYPE
    SYNTAX SEQUENCE OF RsIDSTrackingEntry
    ACCESS not-accessible
    STATUS  mandatory
    DESCRIPTION
      "Table containing the parameters that are needed to detect intrusions"
    ::=  {rsIDS 1}


rsIDStrackingEntry OBJECT-TYPE
    SYNTAX RsIDSTrackingEntry
    ACCESS not-accessible
    STATUS  mandatory
    DESCRIPTION
       "The row definition for this table."
    INDEX { rsIDSFilterGroupName }
    ::=  { rsIDSTrackingTable 1 }

RsIDSTrackingEntry::= SEQUENCE {
    rsIDSFilterGroupName DisplayString,
    rsIDSTrackingTime INTEGER,
    rsIDSThreshold INTEGER,
    rsIDSFilterGroupType INTEGER,
    rsIDSTrackingType INTEGER,
    rsIDSStatus    RowStatus
}

rsIDSFilterGroupName OBJECT-TYPE
    SYNTAX DisplayString (SIZE(0..20))
    ACCESS  read-only
    STATUS  mandatory
    DESCRIPTION
      "The Name for the filter/group must be unique.
       that name should be the same as the name of the
       appropriate filter/group"
    ::=  {rsIDStrackingEntry 1}

rsIDSTrackingTime OBJECT-TYPE
    SYNTAX INTEGER
    ACCESS  read-write
    STATUS  mandatory
    DESCRIPTION
       "This variable indicates the time interval, in miliseconds,
        to track a detection"
    DEFVAL  { 1000 }
    ::=  { rsIDStrackingEntry 2 }

rsIDSThreshold OBJECT-TYPE
    SYNTAX INTEGER
    ACCESS  read-write
    STATUS  mandatory
    DESCRIPTION
       "This variable indicates the threshold "
    DEFVAL  { 50 }
    ::=  { rsIDStrackingEntry 3 }

rsIDSFilterGroupType OBJECT-TYPE
    SYNTAX INTEGER {
              filter(1),
              group(2) }
    ACCESS  read-write
    STATUS  mandatory
    DESCRIPTION
       "This variable indicates the object type- whether it is a filter or group  "
    ::=  { rsIDStrackingEntry 4}

rsIDSTrackingType OBJECT-TYPE
    SYNTAX INTEGER {
    drop(0),
    reset(1),
    ncps(2),
    ncpd(3),
    ncpsd(4),
    ncpf(5),
    winnuke(6),
    landattack(7),
    synattackack(8),
    tcpsyn(9),
    tcpack(10),
    tcpsynack(11),
    tcprst(12),
    tcpfin(13),
    tcpelse(14) }
    ACCESS  read-write
    STATUS  mandatory
    DESCRIPTION
       "This variable indicates how to count  "
    ::=  { rsIDStrackingEntry 5}

rsIDSStatus OBJECT-TYPE
    SYNTAX RowStatus
    ACCESS  read-write
    STATUS  mandatory
    DESCRIPTION
       "This variable indicates the administrative status of this entry.
        Used to delete an entry of this table."
    ::=  { rsIDStrackingEntry 6 }

rsIDSDummy1 OBJECT-TYPE
    SYNTAX INTEGER
    ACCESS  read-only
    STATUS  mandatory
    DESCRIPTION
        "Dummy variable for stopping getnext."
    ::=  { rsIDSTrackingTable 2 }

rsIDSMechanismStatus OBJECT-TYPE
 SYNTAX INTEGER {
      enable(1),
      disable(2)
   }
    ACCESS read-write
    STATUS mandatory
    DESCRIPTION
      "the IDS trigger"
   DEFVAL  {disable}
    ::= {rsIDS 2}

rsIDSTCPAgingTimeFreq OBJECT-TYPE
 SYNTAX INTEGER
    ACCESS read-write
    STATUS mandatory
    DESCRIPTION
      "the TCP table aging time frequency"
    ::= {rsIDS 3}

rsIDSNCPsAgingTimeFreq OBJECT-TYPE
 SYNTAX INTEGER
    ACCESS read-write
    STATUS mandatory
    DESCRIPTION
      "the NCP's tables aging time frequency"
    ::= {rsIDS 4}

rsIDSStatsAgingTimeFreq OBJECT-TYPE
 SYNTAX INTEGER
    ACCESS read-write
    STATUS mandatory
    DESCRIPTION
      "the statistics table aging time frequency"
    ::= {rsIDS 5}

rsIDSNCPSTableSize OBJECT-TYPE
 SYNTAX INTEGER
    ACCESS read-write
    STATUS mandatory
    DESCRIPTION
      "the NCPS table size"
    ::= {rsIDS 6}

rsIDSNCPDTableSize OBJECT-TYPE
 SYNTAX INTEGER
    ACCESS read-write
    STATUS mandatory
    DESCRIPTION
      "the NCPD table size"
    ::= {rsIDS 7}

rsIDSNCPSDTableSize OBJECT-TYPE
 SYNTAX INTEGER
    ACCESS read-write
    STATUS mandatory
    DESCRIPTION
      "the NCPSD table size"
    ::= {rsIDS 8}

rsIDSTCPTableSize OBJECT-TYPE
 SYNTAX INTEGER
    ACCESS read-write
    STATUS mandatory
    DESCRIPTION
      "the TCP table size"
    ::= {rsIDS 9}

rsIDSSTATSTableSize OBJECT-TYPE
 SYNTAX INTEGER
    ACCESS read-write
    STATUS mandatory
    DESCRIPTION
      "the statistics table size"
    ::= {rsIDS 10}

rsIDSBasic OBJECT-TYPE
 SYNTAX INTEGER {
      enable(1),
      disable(2)
   }
    ACCESS read-write
    STATUS mandatory
    DESCRIPTION
      "the basic protection rule trigger"
   DEFVAL  {disable}
    ::= {rsIDS 11}

rsIDSAllServers OBJECT-TYPE
 SYNTAX INTEGER {
      enable(1),
      disable(2)
   }
    ACCESS read-write
    STATUS mandatory
    DESCRIPTION
      "the All servers rule trigger"
   DEFVAL  {disable}
    ::= {rsIDS 12}


rsIDSUNIXServers OBJECT-TYPE
 SYNTAX INTEGER {
      enable(1),
      disable(2)
   }
    ACCESS read-write
    STATUS mandatory
    DESCRIPTION
      "the unix servers rule trigger"
   DEFVAL  {disable}
    ::= {rsIDS 13}

rsIDSLotusServers OBJECT-TYPE
 SYNTAX INTEGER {
      enable(1),
      disable(2)
   }
    ACCESS read-write
    STATUS mandatory
    DESCRIPTION
      "the Lotus servers rule trigger"
   DEFVAL  {disable}
    ::= {rsIDS 14}

rsIDSMSIISServers OBJECT-TYPE
 SYNTAX INTEGER {
      enable(1),
      disable(2)
   }
    ACCESS read-write
    STATUS mandatory
    DESCRIPTION
      "the MS_IIS servers rule trigger"
   DEFVAL  {disable}
    ::= {rsIDS 15}

rsIDSMSFrontPageServers OBJECT-TYPE
 SYNTAX INTEGER {
      enable(1),
      disable(2)
   }
    ACCESS read-write
    STATUS mandatory
    DESCRIPTION
      "the MS front page servers rule trigger"
   DEFVAL  {disable}
    ::= {rsIDS 16}

rsIDSApacheServers OBJECT-TYPE
 SYNTAX INTEGER {
      enable(1),
      disable(2)
   }
    ACCESS read-write
    STATUS mandatory
    DESCRIPTION
      "the Apache servers rule trigger"
   DEFVAL  {disable}
    ::= {rsIDS 17}

rsIDSNetscapeWebServers OBJECT-TYPE
 SYNTAX INTEGER {
      enable(1),
      disable(2)
   }
    ACCESS read-write
    STATUS mandatory
    DESCRIPTION
      "the Netscape_Web servers rule trigger"
   DEFVAL  {disable}
    ::= {rsIDS 18}

rsIDSNovellServers OBJECT-TYPE
 SYNTAX INTEGER {
      enable(1),
      disable(2)
   }
    ACCESS read-write
    STATUS mandatory
    DESCRIPTION
      "the Novell servers rule trigger"
   DEFVAL  {disable}
    ::= {rsIDS 19}

rsIDSOracleServers OBJECT-TYPE
 SYNTAX INTEGER {
      enable(1),
      disable(2)
   }
    ACCESS read-write
    STATUS mandatory
    DESCRIPTION
      "the Oracle servers rule trigger"
   DEFVAL  {disable}
    ::= {rsIDS 20}

rsIDSOmniHTTPDServers OBJECT-TYPE
 SYNTAX INTEGER {
      enable(1),
      disable(2)
   }
    ACCESS read-write
    STATUS mandatory
    DESCRIPTION
      "the OmniHTTPD servers rule trigger"
   DEFVAL  {disable}
    ::= {rsIDS 21}

rsIDSWebSiteServers OBJECT-TYPE
 SYNTAX INTEGER {
      enable(1),
      disable(2)
   }
    ACCESS read-write
    STATUS mandatory
    DESCRIPTION
      "the WebSite_WebSitePro servers rule trigger"
   DEFVAL  {disable}
    ::= {rsIDS 22}

rsIDSColdfusionServers OBJECT-TYPE
 SYNTAX INTEGER {
      enable(1),
      disable(2)
   }
    ACCESS read-write
    STATUS mandatory
    DESCRIPTION
      "the Allaire_Coldfusion servers rule trigger"
   DEFVAL  {disable}
    ::= {rsIDS 23}

rsIDSIRIXServers OBJECT-TYPE
 SYNTAX INTEGER {
      enable(1),
      disable(2)
   }
    ACCESS read-write
    STATUS mandatory
    DESCRIPTION
      "the IRIX servers rule trigger"
   DEFVAL  {disable}
    ::= {rsIDS 24}

rsIDSNCSAServers OBJECT-TYPE
 SYNTAX INTEGER {
      enable(1),
      disable(2)
   }
    ACCESS read-write
    STATUS mandatory
    DESCRIPTION
      "the NCSA servers rule trigger"
   DEFVAL  {disable}
    ::= {rsIDS 25}

rsIDSCompaqServers OBJECT-TYPE
 SYNTAX INTEGER {
      enable(1),
      disable(2)
   }
    ACCESS read-write
    STATUS mandatory
    DESCRIPTION
      "the Compaq_Web_Servers servers rule trigger"
   DEFVAL  {disable}
    ::= {rsIDS 26}

rsIDSbackdoors OBJECT-TYPE
 SYNTAX INTEGER {
      enable(1),
      disable(2)
   }
    ACCESS read-write
    STATUS mandatory
    DESCRIPTION
      "the backdoors rule trigger"
   DEFVAL  {disable}
    ::= {rsIDS 27}

rsIDSTraps OBJECT-TYPE
 SYNTAX INTEGER {
      enable(1),
      disable(2)
   }
    ACCESS read-write
    STATUS mandatory
    DESCRIPTION
      "the traps sending mechanism trigger"
   DEFVAL  {enable}
    ::= {rsIDS 28}



rsIDSStatsTable OBJECT-TYPE
    SYNTAX SEQUENCE OF RsIDSStatsEntry
    ACCESS not-accessible
    STATUS  mandatory
    DESCRIPTION
      "Table containing the intrusion detection statistics"
    ::=  {rsIDS 29}

rsIDSStatsEntry OBJECT-TYPE
    SYNTAX RsIDSStatsEntry
    ACCESS not-accessible
    STATUS  mandatory
    DESCRIPTION
       "The row definition for this table."
    INDEX { rsIDSAttackIndex }
    ::=  { rsIDSStatsTable 1 }

RsIDSStatsEntry::= SEQUENCE {
    rsIDSAttackIndex   INTEGER,
    rsIDSAttackName    DisplayString,
    rsIDSAttackSrcAddr IpAddress,
    rsIDSAttackDstAddr IpAddress,
    rsIDSAttackStatus  DisplayString,
    rsIDSAttacktime    DisplayString,
    rsIDSStatsStatus   RowStatus
}

rsIDSAttackIndex OBJECT-TYPE
    SYNTAX  INTEGER
    ACCESS  read-only
    STATUS  mandatory
    DESCRIPTION
      "The index of the attack that was detected"
    ::=  {rsIDSStatsEntry 1}

rsIDSAttackName OBJECT-TYPE
    SYNTAX DisplayString (SIZE(0..80))
    ACCESS  read-only
    STATUS  mandatory
    DESCRIPTION
      "The Name for the attack"
    ::=  {rsIDSStatsEntry 2}

rsIDSAttackSrcAddr OBJECT-TYPE
    SYNTAX  IpAddress
    ACCESS  read-only
    STATUS  mandatory
    DESCRIPTION
      "The src address of the attack"
    ::=  {rsIDSStatsEntry 3}

rsIDSAttackDstAddr OBJECT-TYPE
    SYNTAX  IpAddress
    ACCESS  read-only
    STATUS  mandatory
    DESCRIPTION
      "The dest address of the attack"
    ::=  {rsIDSStatsEntry 4}

rsIDSAttackStatus OBJECT-TYPE
    SYNTAX DisplayString (SIZE(0..12))
    ACCESS  read-only
    STATUS  mandatory
    DESCRIPTION
      "The status of the attack(started/terminated/occured)"
    ::=  {rsIDSStatsEntry 5}

rsIDSAttacktime OBJECT-TYPE
    SYNTAX DisplayString (SIZE(0..32))
    ACCESS  read-only
    STATUS  mandatory
    DESCRIPTION
      "The time of the attack"
    ::=  {rsIDSStatsEntry 6}

rsIDSStatsStatus OBJECT-TYPE
    SYNTAX RowStatus
    ACCESS  read-write
    STATUS  mandatory
    DESCRIPTION
       "This variable indicates the administrative status of this entry.
        Used to delete an entry of this table."
    ::=  { rsIDSStatsEntry 7 }

rsIDSDummy2 OBJECT-TYPE
    SYNTAX INTEGER
    ACCESS  read-only
    STATUS  mandatory
    DESCRIPTION
        "Dummy variable for stopping getnext."
    ::=  { rsIDSStatsTable 2 }

rsIDSNCPDTableSizeAfterReset OBJECT-TYPE
    SYNTAX INTEGER
    ACCESS read-write
    STATUS mandatory
    DESCRIPTION
      "the NCPD after-reset table size"
    ::= {rsIDS 30}

rsIDSNCPSDTableSizeAfterReset OBJECT-TYPE
    SYNTAX INTEGER
    ACCESS read-write
    STATUS mandatory
    DESCRIPTION
      "the NCPS after-reset table size"
    ::= {rsIDS 31}

rsIDSTCPTableSizeAfterReset OBJECT-TYPE
    SYNTAX INTEGER
    ACCESS read-write
    STATUS mandatory
    DESCRIPTION
      "the NCPS after-reset table size"
    ::= {rsIDS 32}

 rsIDSSTATSTableSizeAfterReset OBJECT-TYPE
    SYNTAX INTEGER
    ACCESS read-write
    STATUS mandatory
    DESCRIPTION
      "the NCPS after-reset table size"
    ::= {rsIDS 33}



   END
