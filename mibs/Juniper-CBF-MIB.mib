-- *****************************************************************************
-- Juniper-CBF-MIB
--
-- Juniper Networks Enterprise MIB
--   Extensions for Connection-Based Forwarding Protocol Management
--
-- Copyright 2001 Juniper Networks, Inc.  All Rights Reserved.
-- *****************************************************************************

Juniper-CBF-MIB  DEFINITIONS ::= BEGIN

IMPORTS
    MODULE-IDENTITY, OBJECT-TYPE
        FROM SNMPv2-SMI
    RowStatus
        FROM SNMPv2-TC
    MODULE-COMPLIANCE, OBJECT-GROUP
        FROM SNMPv2-CONF
    juniMibs
        FROM Juniper-MIBs
    InterfaceIndex, InterfaceIndexOrZero
        FROM IF-MIB
    JuniNextIfIndex
       FROM Juniper-TC;

juniCbfMIB  MODULE-IDENTITY
    LAST-UPDATED "200209162144Z"  -- 16-Sep-02 05:44 PM EDT
    ORGANIZATION "Juniper Networks, Inc."
    CONTACT-INFO
        "       Juniper Networks, Inc.
        Postal: 10 Technology Park Drive
                Westford, MA  01886-3146
                USA
        Tel:    +1 978 589 5800
        E-mail: mib@Juniper.net"
    DESCRIPTION
        "The Connection-Based Forwarding (CBF) Protocol MIB for the Juniper
        Networks Inc. enterprise."
    -- Revision History
    REVISION    "200209162144Z"  -- 16-Sep-02 05:44 PM EDT  - JUNOSe 5.0
    DESCRIPTION
        "Replaced Unisphere names with Juniper names."
    REVISION    "200103301627Z"  -- 30-Mar-01 11:27 AM EST  - JUNOSe 3.2
    DESCRIPTION
        "Initial version of this MIB module."
    ::= { juniMibs 52 }


-- +++++++++++++++++++++++++++++++++++++++++++++++++++++++++++++++++++++++++++++
-- Managed objects
-- +++++++++++++++++++++++++++++++++++++++++++++++++++++++++++++++++++++++++++++
juniCbfObjects     OBJECT IDENTIFIER ::= { juniCbfMIB 1 }
juniCbfInterface   OBJECT IDENTIFIER ::= { juniCbfObjects 1 }


-- +++++++++++++++++++++++++++++++++++++++++++++++++++++++++++++++++++++++++++++
-- CBF Interface attributes
-- +++++++++++++++++++++++++++++++++++++++++++++++++++++++++++++++++++++++++++++
--
-- IfIndex selection for creating new CBF interfaces
--
juniCbfNextIfIndex  OBJECT-TYPE
    SYNTAX      JuniNextIfIndex
    MAX-ACCESS  read-only
    STATUS      current
    DESCRIPTION
        "Coordinate ifIndex value allocation for entries in juniCbfIfTable.

        A GET of this object returns the next available ifIndex value to be used
        to create an entry in the associated interface table; or zero, if no
        valid ifIndex value is available.  This object also returns a value of
        zero when it is the lexicographic successor of a varbind presented in an
        SNMP GETNEXT or GETBULK request, for which circumstance it is assumed
        that ifIndex allocation is unintended.

        Successive GETs will typically return different values, thus avoiding
        collisions among cooperating management clients seeking to create table
        entries simultaneously.  "
    ::= { juniCbfInterface 1 }


--
-- The CBF Interface Table
--
juniCbfIfTable  OBJECT-TYPE
    SYNTAX      SEQUENCE OF JuniCbfIfEntry
    MAX-ACCESS  not-accessible
    STATUS      current
    DESCRIPTION
        "This table contains entries for CBF interfaces present in the system."
    ::= { juniCbfInterface 2 }

juniCbfIfEntry  OBJECT-TYPE
    SYNTAX      JuniCbfIfEntry
    MAX-ACCESS  not-accessible
    STATUS      current
    DESCRIPTION
        "Each entry describes the characteristics of an CBF interface.
        Creating/deleting entries in this table causes corresponding entries for
        be created /deleted in ifTable/ifXTable/juniIfTable."
    INDEX     { juniCbfIfIndex }
    ::= { juniCbfIfTable 1 }

JuniCbfIfEntry ::= SEQUENCE {
    juniCbfIfIndex          InterfaceIndex,
    juniCbfIfRowStatus      RowStatus,
    juniCbfIfLowerIfIndex   InterfaceIndexOrZero }

juniCbfIfIndex  OBJECT-TYPE
    SYNTAX      InterfaceIndex
    MAX-ACCESS  not-accessible
    STATUS      current
    DESCRIPTION
        "The ifIndex of the CBF interface.  When creating entries in this table,
        suitable values for this object are determined by reading
        juniCbfNextIfIndex."
    ::= { juniCbfIfEntry 1 }

juniCbfIfRowStatus  OBJECT-TYPE
    SYNTAX      RowStatus
    MAX-ACCESS  read-create
    STATUS      current
    DESCRIPTION
        "Controls creation/deletion of entries in this table according to the
        RowStatus textual convention, constrained to support the following
        values only:
            createAndGo
            destroy

        To create an entry in this table, the following entry objects MUST be
        explicitly configured:
            juniCbfIfRowStatus
            juniCbfIfLowerIfIndex

        In addition, when creating an entry the following conditions must hold:

            A value for juniCbfIfIndex must have been determined previously,
            typically by reading juniCbfNextIfIndex.

            The interface identified by a nonzero juniCbfIfLowerIfIndex must
            exist.

        Once created, the following objects may not be modified:
            juniCbfIfLowerIfIndex

        A corresponding entry in ifTable/ifXTable/juniIfTable is created/
        destroyed as a result of creating/destroying an entry in this table."
    ::= { juniCbfIfEntry 2 }

juniCbfIfLowerIfIndex  OBJECT-TYPE
    SYNTAX      InterfaceIndexOrZero
    MAX-ACCESS  read-create
    STATUS      current
    DESCRIPTION
        "The ifIndex of a media interface over which this CBF interface is to be
        layered."
    ::= { juniCbfIfEntry 3 }


-- +++++++++++++++++++++++++++++++++++++++++++++++++++++++++++++++++++++++++++++
-- CBF connection attributes
-- +++++++++++++++++++++++++++++++++++++++++++++++++++++++++++++++++++++++++++++
juniCbfIfConnTable  OBJECT-TYPE
    SYNTAX      SEQUENCE OF JuniCbfIfConnEntry
    MAX-ACCESS  not-accessible
    STATUS      current
    DESCRIPTION
        "This table contains entries for CBF interface connection present in the
        system."
    ::= { juniCbfInterface 4 }

juniCbfIfConnEntry  OBJECT-TYPE
    SYNTAX      JuniCbfIfConnEntry
    MAX-ACCESS  not-accessible
    STATUS      current
    DESCRIPTION
        "Each entry defines a CBF connection."
    INDEX     { juniCbfIfIngressIfIndex }
    ::= { juniCbfIfConnTable 1 }

JuniCbfIfConnEntry ::= SEQUENCE {
    juniCbfIfIngressIfIndex     InterfaceIndex,
    juniCbfIfConnRowStatus      RowStatus,
    juniCbfIfEgressIfIndex      InterfaceIndex }

juniCbfIfIngressIfIndex  OBJECT-TYPE
    SYNTAX      InterfaceIndex
    MAX-ACCESS  not-accessible
    STATUS      current
    DESCRIPTION
        "The ifIndex of the ingress interface for the CBF connection.  When
        creating entries in this table, suitable values for this object are
        walking the juniCbfIfTable and picking the appropriate juniCbfIfIndex."
    ::= { juniCbfIfConnEntry 1 }

juniCbfIfConnRowStatus  OBJECT-TYPE
    SYNTAX      RowStatus
    MAX-ACCESS  read-create
    STATUS      current
    DESCRIPTION
        "Controls creation/deletion of entries in this table according to the
        RowStatus textual convention, constrained to support the following
        values only:
            createAndGo
            destroy

        To create an entry in this table, the following entry objects MUST be
        explicitly configured:
            juniCbfIfRowStatus
            juniCbfIfIngressIfIndex

        Once created, the following objects may not be modified:
            juniCbfIfIngressIfIndex "
    ::= { juniCbfIfConnEntry 2 }

juniCbfIfEgressIfIndex  OBJECT-TYPE
    SYNTAX      InterfaceIndex
    MAX-ACCESS  read-create
    STATUS      current
    DESCRIPTION
        "The ifIndex of the egress interface for the CBF interface.  When
        creating entries in this table, suitable values for this object are
        walking the juniCbfIfTable and picking the appropriate juniCbfIfIndex."
    ::= { juniCbfIfConnEntry 3 }


-- ++++++++++++++++++++++++++++++++++++++++++++++++++++++++++++++++++++++
-- Notifications
-- ++++++++++++++++++++++++++++++++++++++++++++++++++++++++++++++++++++++
-- No notifications are defined in this MIB.  Placeholders follow.
-- juniCbfTrapControl      OBJECT IDENTIFIER ::= { juniCbfMIB 2 }
-- juniCbfTraps            OBJECT IDENTIFIER ::= { juniCbfMIB 3 }
-- juniCbfTrapPrefix       OBJECT IDENTIFIER ::= { juniCbfTraps 0 }


-- ++++++++++++++++++++++++++++++++++++++++++++++++++++++++++++++++++++++
-- Conformance information
-- ++++++++++++++++++++++++++++++++++++++++++++++++++++++++++++++++++++++
juniCbfConformance  OBJECT IDENTIFIER ::= { juniCbfMIB 4 }
juniCbfCompliances  OBJECT IDENTIFIER ::= { juniCbfConformance 1 }
juniCbfGroups       OBJECT IDENTIFIER ::= { juniCbfConformance 2 }

--
-- compliance statements
--
juniCbfCompliance  MODULE-COMPLIANCE
    STATUS      current
    DESCRIPTION
        "The compliance statement for entities which implement the Juniper CBF
        MIB."
    MODULE   -- this module
        MANDATORY-GROUPS {
            juniCbfGroup }
    ::= { juniCbfCompliances 1 }

--
-- units of conformance
--
juniCbfGroup  OBJECT-GROUP
    OBJECTS {
        juniCbfNextIfIndex,

        juniCbfIfRowStatus,
        juniCbfIfLowerIfIndex,
        juniCbfIfConnRowStatus,
        juniCbfIfEgressIfIndex }
    STATUS      current
    DESCRIPTION
        "A collection of objects providing management of CBF interfaces in a
        Juniper product."
    ::= { juniCbfGroups 1 }

END
