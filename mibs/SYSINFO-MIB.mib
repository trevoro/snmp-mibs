SYSINFO-MIB DEFINITIONS ::= BEGIN

IMPORTS
          enterprises, Counter, Gauge, TimeTicks, IpAddress
                  FROM RFC1155-SMI
          DisplayString, PhysAddress
                  FROM RFC1213-MIB
          OBJECT-TYPE
                  FROM RFC-1212;

-- This MIB module uses the extended OBJECT-TYPE macro as
-- defined in RFC 1212.

--
--  The System Information Agent Subtree...
--

-- These Extension groups follow the structure of MIB-II

-- Actual definition of MIB Subtree:

ibm                            OBJECT IDENTIFIER ::= { enterprises 2 }
ibmProd                        OBJECT IDENTIFIER ::= { ibm 6 }
systemsMonitor6000             OBJECT IDENTIFIER ::= { ibmProd 12 }

smProgramInformation           OBJECT IDENTIFIER ::= { systemsMonitor6000 1 }
smSiaSystemInformation         OBJECT IDENTIFIER ::= { systemsMonitor6000 2 }
smSiaCommand                   OBJECT IDENTIFIER ::= { systemsMonitor6000 4 }
smSiaAdministration            OBJECT IDENTIFIER ::= { systemsMonitor6000 20 }
smSiaFileMonitor               OBJECT IDENTIFIER ::= { systemsMonitor6000 21 }

--
-- The Systems Information Agent Subtree
--
-- This subtree contains variables which describe the System Information
-- Agent
--

smSiaProgramData               OBJECT IDENTIFIER ::= { smProgramInformation 10 }
smSiaResourceUsage             OBJECT IDENTIFIER ::= { smProgramInformation 11 }
smSiaProgramMessages           OBJECT IDENTIFIER ::= { smProgramInformation 12 }

smSiaProgramDescription        OBJECT IDENTIFIER ::= { smSiaProgramData 1 }
smSiaProgramControl            OBJECT IDENTIFIER ::= { smSiaProgramData 2 }
smSiaProgramLog                OBJECT IDENTIFIER ::= { smSiaProgramData 3 }
smSiaProgramSetableTestObjects OBJECT IDENTIFIER ::= { smSiaProgramData 5 }

--
--  Program Description Group - information about Systems Information Agent, the
--  product.  Useful for getting version information, etc.
--

smSiaProgramName OBJECT-TYPE
        SYNTAX  DisplayString
        ACCESS  read-only
        STATUS  mandatory
        DESCRIPTION
                "Official name of the Systems Information Agent program."
        ::= { smSiaProgramDescription 1 }

smSiaProgramNumber OBJECT-TYPE
        SYNTAX  DisplayString
        ACCESS  read-only
        STATUS  mandatory
        DESCRIPTION
                "Program number for the Systems Information Agent
                 program."
        ::= { smSiaProgramDescription 2 }

smSiaProgramVersion OBJECT-TYPE
        SYNTAX  DisplayString
        ACCESS  read-only
        STATUS  mandatory
        DESCRIPTION
                "Version number of the Systems Information Agent program."
        ::= { smSiaProgramDescription 3 }

smSiaProgramCompilationDate OBJECT-TYPE
        SYNTAX  DisplayString
        ACCESS  read-only
        STATUS  mandatory
        DESCRIPTION
                "Date and time when the current agent was compiled."
        ::= { smSiaProgramDescription 4 }

smSiaProgramUpTime OBJECT-TYPE
    SYNTAX  TimeTicks
    ACCESS  read-only
    STATUS  mandatory
    DESCRIPTION
            "Time (in hundredths of a second) since the
             Systems Information Agent Program was last re-initialized."
    ::= { smSiaProgramDescription 5 }

smSiaProgramContact OBJECT-TYPE
    SYNTAX  DisplayString
    ACCESS  read-write
    STATUS  mandatory
    DESCRIPTION
            "Textual identification of the contact person
             for the Systems Information Agent program on this managed
	     node and information on how to contact this person."
    ::= { smSiaProgramDescription 6 }

--
-- Program Control Group
--
--  This group contains those variables used to modify operation of the
--  systems monitor
--

smSiaProgramControlLocalConfigurationFile OBJECT-TYPE
        SYNTAX  DisplayString
        ACCESS  read-write
        STATUS  mandatory
        DESCRIPTION
                "Name of a local configuration file.  The local
                 configuration file is written when the
                 smSiaProgramControlSaveConfiguration MIB variable
                 is set to true(2)."
        ::= { smSiaProgramControl 1 }

smSiaProgramControlSavedFlags OBJECT-TYPE
        SYNTAX  DisplayString
        ACCESS  read-write
        STATUS  mandatory
        DESCRIPTION
                "Saved flags which will be used to start the agent.
                 This field can be modified to be used with the
                 smSiaProgramControlReInitializeMonitor function.
                 The flags are saved in the file: /usr/etc/sysinfod.flags"
        ::= { smSiaProgramControl 2 }

smSiaProgramControlAgentAddress OBJECT-TYPE
        SYNTAX  IpAddress
        ACCESS  read-write
        STATUS  mandatory
        DESCRIPTION
                "Address of the box where SIA is running.  This address
                 is used while generating traps."
        ::= { smSiaProgramControl 3 }

smSiaProgramControlReserved1 OBJECT-TYPE
        SYNTAX  INTEGER
        ACCESS  read-write
        STATUS  mandatory
        DESCRIPTION
                "Reserved."
        ::= { smSiaProgramControl 4 }

smSiaProgramControlPercentMultiplier OBJECT-TYPE
        SYNTAX  INTEGER
        ACCESS  read-write
        STATUS  mandatory
        DESCRIPTION
                "Multiplier used to multiply percentage variables.  The
                 default is 1; 0 is treated the same
                 as the default."
        ::= { smSiaProgramControl 5 }

smSiaProgramControlPollTime OBJECT-TYPE
        SYNTAX  INTEGER
        ACCESS  read-write
        STATUS  mandatory
        DESCRIPTION
                "Reserved"
        ::= { smSiaProgramControl 6 }

smSiaProgramControlFlags OBJECT-TYPE
        SYNTAX  INTEGER
        ACCESS  read-write
        STATUS  mandatory
        DESCRIPTION
                "Reserved"
        ::= { smSiaProgramControl 7 }

smSiaProgramControlRetryCount OBJECT-TYPE
        SYNTAX  INTEGER
        ACCESS  read-write
        STATUS  mandatory
        DESCRIPTION
                "Reserved.
                 Default number of retries for actions that can be
                 retried."
        ::= { smSiaProgramControl 8 }

smSiaProgramControlTimeout OBJECT-TYPE
        SYNTAX  TimeTicks
        ACCESS  read-write
        STATUS  mandatory
        DESCRIPTION
                "Reserved.
                 Default number of timeout for actions that can timeout."
        ::= { smSiaProgramControl 9 }

smSiaProgramControlCurrentFlags OBJECT-TYPE
        SYNTAX  DisplayString
        ACCESS  read-only
        STATUS  mandatory
        DESCRIPTION
                "Current flags which were used to start or re-initialize
                 the agent."
        ::= { smSiaProgramControl 10 }

smSiaProgramControlReinitFlags OBJECT-TYPE
        SYNTAX  DisplayString
        ACCESS  read-write
        STATUS  mandatory
        DESCRIPTION
                "Re-intialize flags which will be used to start the agent.
                 This field is set to smSiaProgramControlCurrentFlags
                 at program start or re-initialization.
                 This field can be modified to be used with the
                 smSiaProgramControlReInitializeMonitor function."
        ::= { smSiaProgramControl 11 }

smSiaProgramControlReInitializeMonitor OBJECT-TYPE
        SYNTAX  INTEGER {
                false(1),
                trueReinit(2),
                trueSaved(3)
                }
        ACCESS  read-write
        STATUS  mandatory
        DESCRIPTION
                "Allows the re-initializaton of the Systems Information
                 Agent.  Setting to trueReinit(2) uses the flags in
                 smSiaProgramControlReinitFlags as the start-up
                 flags.  Setting to trueSaved(3) uses the flags
                 in smSiaProgramControlSavedFlags as the start-up
                 flags.  The value of this variable returns to false
                 once the re-start has occurred."
        ::= { smSiaProgramControl 12 }

smSiaProgramControlSaveConfiguration OBJECT-TYPE
        SYNTAX  INTEGER {
                false(1),
                true(2)
                }
        ACCESS  read-write
        STATUS  mandatory
        DESCRIPTION
                "Setting this variable to true(2) results in the current
                 Systems Information Agent configuration being saved
                 to the file specified by the value of the smSiaProgramControl
                 LocalConfigurationFile variable.  The value of this variable
                 returns to false once the configuration is saved."
        ::= { smSiaProgramControl 13 }

--
--  Program Log Group - information about the logging being done
--  by the Systems Information Agent.
--

smSiaProgramLogFileName OBJECT-TYPE
        SYNTAX  DisplayString
        ACCESS  read-write
        STATUS  mandatory
        DESCRIPTION
                "File name for logging information in System Information
                 Agent. The type of information being logged depends
		 on the trace mask (ie. smSiaProgramLogMask)."
        ::= { smSiaProgramLog 1 }

smSiaProgramLogFileSize OBJECT-TYPE
        SYNTAX  INTEGER
        ACCESS  read-only
        STATUS  mandatory
        DESCRIPTION
                "Current size of the log file in bytes."
        ::= { smSiaProgramLog 2 }

smSiaProgramLogMaxFileSize OBJECT-TYPE
        SYNTAX  INTEGER
        ACCESS  read-write
        STATUS  mandatory
        DESCRIPTION
                "Maximum size of the log file in kilobytes."
        ::= { smSiaProgramLog 3 }

smSiaProgramLogNumFiles OBJECT-TYPE
        SYNTAX  INTEGER
        ACCESS  read-write
        STATUS  mandatory
        DESCRIPTION
                "Maximum number of log files to keep.  When the data
		 log file is full, it is rolled over to <logFilename>1.  Files are
		 rolled up until the number of files specified by this field
		 exists (ie. <LogFilename>1 becomes <LogFilename>2, etc.)."
        ::= { smSiaProgramLog 4 }

smSiaProgramLogFileBehavior OBJECT-TYPE
        SYNTAX  INTEGER {
                wrapFlush(1), -- wrap and flush
                wrapNoflush(2), -- wrap and don't flush
                nowrapFlush(3), -- don't wrap and flush
                nowrapNoflush(4) -- don't wrap and don't flush
                }
        ACCESS  read-write
        STATUS  mandatory
        DESCRIPTION
                "This field determines what is done when the maximum
		 file size is exceeded and the number of log files specified
		 already exists.  If wrap is specified, then the oldest
                 log file is removed, all other files are rolled up, and
                 logging continues into a new file.

                 If nowrap is specified, no more data will be logged
                 until either the log file name is changed or
                 the existing files are renamed (or removed).

		 Flushing refers to whether or not each log entry is
                 immediately written to the log file or whether the log
                 data is written out in large chunks containing multiple
                 log entries.  Flushing allows the log file to always contain
                 the latest log entries.  However, CPU time can be saved
		 if flushing is not activated."
        ::= { smSiaProgramLog 5 }

smSiaProgramLogMask OBJECT-TYPE
        SYNTAX  DisplayString
        ACCESS  read-write
        STATUS  mandatory
        DESCRIPTION
                "The log mask field is used to indicate the type of
                 information that is being logged.
		

		 The log mask may contain the following literals:

		    none          logs nothing
		    inform        logs informational messages
		    warning       logs warning messages
		    error         logs error messages
		    base          logs System Information Agent base information
		    command       logs command table information
		    smux          logs SMUX interface traffic
		    call          logs all internal functions called
		    all           logs all information"
        ::= { smSiaProgramLog 6 }


--
-- The System Information Agent Settable Test objects group
--
-- This group is used only for internal test purposes, and has no function
--

smSiaProgramControlSetableInteger OBJECT-TYPE
        SYNTAX  INTEGER
        ACCESS  read-write
        STATUS  mandatory
        DESCRIPTION
                "A settable integer with no function."
        ::= { smSiaProgramSetableTestObjects 1 }

smSiaProgramControlSetableCounter OBJECT-TYPE
        SYNTAX  Counter
        ACCESS  read-write
        STATUS  mandatory
        DESCRIPTION
                "A settable counter with no function."
        ::= { smSiaProgramSetableTestObjects 2 }

smSiaProgramControlSetableGauge OBJECT-TYPE
        SYNTAX  Gauge
        ACCESS  read-write
        STATUS  mandatory
        DESCRIPTION
                "A settable gauge with no function."
        ::= { smSiaProgramSetableTestObjects 3 }

smSiaProgramControlSetableIpAddress OBJECT-TYPE
        SYNTAX  IpAddress
        ACCESS  read-write
        STATUS  mandatory
        DESCRIPTION
                "A settable IP address with no function."
        ::= { smSiaProgramSetableTestObjects 4 }

smSiaProgramControlSetableTimeTicks OBJECT-TYPE
        SYNTAX  TimeTicks
        ACCESS  read-write
        STATUS  mandatory
        DESCRIPTION
                "A settable TimeTicks with no function."
        ::= { smSiaProgramSetableTestObjects 5 }

smSiaProgramControlSetableOctetString OBJECT-TYPE
        SYNTAX  DisplayString
        ACCESS  read-write
        STATUS  mandatory
        DESCRIPTION
                "A settable DisplayString with no function."
        ::= { smSiaProgramSetableTestObjects 6 }


--
-- The System Information Agent Self-Monitoring Group
--
--	This group is used to see how much of the system resources the
--	system monitor itself is using up
--

smSiaResourceUsageTable OBJECT-TYPE
        SYNTAX  SEQUENCE OF SmSiaResourceUsageEntry
        ACCESS  not-accessible
        STATUS  mandatory
        DESCRIPTION
                "Systems Information Agent resource utilization table."
        ::= { smSiaResourceUsage 1 }

smSiaResourceUsageEntry OBJECT-TYPE
        SYNTAX  SmSiaResourceUsageEntry
        ACCESS  not-accessible
        STATUS  mandatory
        DESCRIPTION
                "Each entry contains a different resource summary."
	INDEX { smSiaResourceUsageName }
        ::= { smSiaResourceUsageTable 1 }

SmSiaResourceUsageEntry ::= SEQUENCE {
	smSiaResourceUsageName
	DisplayString,
	smSiaResourceUsageUserTime
	TimeTicks,
	smSiaResourceUsageSystemTime
        TimeTicks,
	smSiaResourceUsageTotalTime
        TimeTicks,
	smSiaResourceUsageMaxrss
        Counter,
	smSiaResourceUsageIxrss
        Counter,
	smSiaResourceUsageIdrss
        Counter,
	smSiaResourceUsageIsrss
        Counter,
	smSiaResourceUsageMinflt
        Counter,
	smSiaResourceUsageMajflt
        Counter,
	smSiaResourceUsageNSwap
        Counter,
	smSiaResourceUsageInBlock
        Counter,
	smSiaResourceUsageOutBlock
        Counter,
	smSiaResourceUsageMsgsnd
        Counter,
	smSiaResourceUsageMsgrcv
        Counter,
	smSiaResourceUsageNSignals
        Counter,
	smSiaResourceUsageVcsw
        Counter,
	smSiaResourceUsageIcsw
        Counter
}

smSiaResourceUsageName OBJECT-TYPE
        SYNTAX  DisplayString
        ACCESS  read-only
        STATUS  mandatory
        DESCRIPTION
          "Self, child, and total."
        ::= { smSiaResourceUsageEntry 1 }

smSiaResourceUsageUserTime OBJECT-TYPE
        SYNTAX  TimeTicks
        ACCESS  read-only
        STATUS  mandatory
        DESCRIPTION
          "Amount of CPU time in user mode since start-up."
        ::= { smSiaResourceUsageEntry 2 }

smSiaResourceUsageSystemTime OBJECT-TYPE
        SYNTAX  TimeTicks
        ACCESS  read-only
        STATUS  mandatory
        DESCRIPTION
           "Amount of CPU time in system mode since start-up."
        ::= { smSiaResourceUsageEntry 3 }

smSiaResourceUsageTotalTime OBJECT-TYPE
        SYNTAX  TimeTicks
        ACCESS  read-only
        STATUS  mandatory
        DESCRIPTION
                "Total CPU time for process since start-up."
        ::= { smSiaResourceUsageEntry 4 }

smSiaResourceUsageMaxrss OBJECT-TYPE
        SYNTAX  Counter
        ACCESS  read-only
        STATUS  mandatory
        DESCRIPTION
                "Maximum resident set size.

                 Not supported on Sun Solaris 2.x."
        ::= { smSiaResourceUsageEntry 5 }

smSiaResourceUsageIxrss OBJECT-TYPE
        SYNTAX  Counter
        ACCESS  read-only
        STATUS  mandatory
        DESCRIPTION
                "Integral size (kilobyte-seconds).

                 Not supported on Sun Solaris 2.x."
        ::= { smSiaResourceUsageEntry 6 }

smSiaResourceUsageIdrss OBJECT-TYPE
        SYNTAX  Counter
        ACCESS  read-only
        STATUS  mandatory
        DESCRIPTION
                "Unshared resident set size (kilobyte-seconds).

                 Not supported on Sun Solaris 2.x."
        ::= { smSiaResourceUsageEntry 7 }

smSiaResourceUsageIsrss OBJECT-TYPE
        SYNTAX  Counter
        ACCESS  read-only
        STATUS  mandatory
        DESCRIPTION
                "Unshared stack set size (kilobyte-seconds).

                 Not supported on Sun Solaris 2.x."
        ::= { smSiaResourceUsageEntry 8 }

smSiaResourceUsageMinflt OBJECT-TYPE
        SYNTAX  Counter
        ACCESS  read-only
        STATUS  mandatory
        DESCRIPTION
                "Page faults serviced without I/O activity."
        ::= { smSiaResourceUsageEntry 9 }

smSiaResourceUsageMajflt OBJECT-TYPE
        SYNTAX  Counter
        ACCESS  read-only
        STATUS  mandatory
        DESCRIPTION
                "Page faults serviced with I/O activity."
        ::= { smSiaResourceUsageEntry 10 }

smSiaResourceUsageNSwap OBJECT-TYPE
        SYNTAX  Counter
        ACCESS  read-only
        STATUS  mandatory
        DESCRIPTION
                "Number of times a process swapped."
        ::= { smSiaResourceUsageEntry 11 }

smSiaResourceUsageInBlock OBJECT-TYPE
        SYNTAX  Counter
        ACCESS  read-only
        STATUS  mandatory
        DESCRIPTION
                "Number of times a file system performed input."
        ::= { smSiaResourceUsageEntry 12 }

smSiaResourceUsageOutBlock OBJECT-TYPE
        SYNTAX  Counter
        ACCESS  read-only
        STATUS  mandatory
        DESCRIPTION
                "Number of times a file system performed output."
        ::= { smSiaResourceUsageEntry 13 }

smSiaResourceUsageMsgsnd OBJECT-TYPE
        SYNTAX  Counter
        ACCESS  read-only
        STATUS  mandatory
        DESCRIPTION
                "Number of IPC messages sent."
        ::= { smSiaResourceUsageEntry 14 }

smSiaResourceUsageMsgrcv OBJECT-TYPE
        SYNTAX  Counter
        ACCESS  read-only
        STATUS  mandatory
        DESCRIPTION
                "Number of IPC messages received."
        ::= { smSiaResourceUsageEntry 15 }

smSiaResourceUsageNSignals OBJECT-TYPE
        SYNTAX  Counter
        ACCESS  read-only
        STATUS  mandatory
        DESCRIPTION
                "Number of signals received."
        ::= { smSiaResourceUsageEntry 16 }

smSiaResourceUsageVcsw OBJECT-TYPE
        SYNTAX  Counter
        ACCESS  read-only
        STATUS  mandatory
        DESCRIPTION
                "Number of voluntary context switches."
        ::= { smSiaResourceUsageEntry 17 }

smSiaResourceUsageIcsw OBJECT-TYPE
        SYNTAX  Counter
        ACCESS  read-only
        STATUS  mandatory
        DESCRIPTION
                "Number of involuntary context switches."
        ::= { smSiaResourceUsageEntry 18 }


--
--  The System Information Agent Message Group
--  Information and error messages are available here, most recent first
--

smSiaProgramMessagesTable OBJECT-TYPE
        SYNTAX  SEQUENCE OF SmSiaProgramMessagesEntry
        ACCESS  not-accessible
        STATUS  mandatory
        DESCRIPTION
                "Systems Information Agent information and error
                messages."
        ::= { smSiaProgramMessages 1 }

smSiaProgramMessagesEntry OBJECT-TYPE
        SYNTAX  SmSiaProgramMessagesEntry
        ACCESS  not-accessible
        STATUS  mandatory
        DESCRIPTION
                "Each entry contains a different message summary."
	INDEX { smSiaProgramMessagesRowNumber }
        ::= { smSiaProgramMessagesTable 1 }

--
--

SmSiaProgramMessagesEntry ::= SEQUENCE {
	smSiaProgramMessagesRowNumber
	INTEGER,
	smSiaProgramMessagesTime
	DisplayString,
	smSiaProgramMessagesText
        DisplayString,
	smSiaProgramMessagesTimeStamp
	INTEGER
}

smSiaProgramMessagesRowNumber OBJECT-TYPE
        SYNTAX  INTEGER
        ACCESS  read-only
        STATUS  mandatory
        DESCRIPTION
          "Table index - no real meaning."
        ::= { smSiaProgramMessagesEntry 1 }

smSiaProgramMessagesTime OBJECT-TYPE
        SYNTAX  DisplayString
        ACCESS  read-only
        STATUS  mandatory
        DESCRIPTION
                "Time at which the message was generated."
        ::= { smSiaProgramMessagesEntry 2 }

smSiaProgramMessagesText OBJECT-TYPE
        SYNTAX  DisplayString
        ACCESS  read-only
        STATUS  mandatory
        DESCRIPTION
                "Text of the message. "
        ::= { smSiaProgramMessagesEntry 3 }

smSiaProgramMessagesTimeStamp OBJECT-TYPE
        SYNTAX  INTEGER
        ACCESS  read-only
        STATUS  mandatory
        DESCRIPTION
           "Time (in seconds) at which message was generated."
        ::= { smSiaProgramMessagesEntry 4 }


--
--  The System Information Agent System Information Group
--
--  This subtree provides information about the system on which the
--  systems monitor is running.
--

smSiaSystemDescription       OBJECT IDENTIFIER ::= { smSiaSystemInformation 1 }
smSiaSystemConfiguration     OBJECT IDENTIFIER ::= { smSiaSystemInformation 2 }
smSiaSystemDevice     	     OBJECT IDENTIFIER ::= { smSiaSystemInformation 3 }
smSiaSystemPagingInformation OBJECT IDENTIFIER ::= { smSiaSystemInformation 4 }
smSiaSystemFileSystem        OBJECT IDENTIFIER ::= { smSiaSystemInformation 5 }
smSiaSystemSubSystems        OBJECT IDENTIFIER ::= { smSiaSystemInformation 6 }
smSiaSystemProcess           OBJECT IDENTIFIER ::= { smSiaSystemInformation 7 }
smSiaSystemUsers             OBJECT IDENTIFIER ::= { smSiaSystemInformation 8 }
smSiaSystemUtilization       OBJECT IDENTIFIER ::= { smSiaSystemInformation 9 }
smSiaSystemMiscellaneous     OBJECT IDENTIFIER ::= { smSiaSystemInformation 11 }

--
--  Following is basically the same as the information from uname
--

smSiaSystemNodeName OBJECT-TYPE
    SYNTAX  DisplayString
    ACCESS  read-only
    STATUS  mandatory
    DESCRIPTION
            "Node name."
    ::= { smSiaSystemDescription 1 }

smSiaSystemSysName OBJECT-TYPE
    SYNTAX  DisplayString
    ACCESS  read-only
    STATUS  mandatory
    DESCRIPTION
            "System name."
    ::= { smSiaSystemDescription 2 }

smSiaSystemVersion OBJECT-TYPE
    SYNTAX  DisplayString
    ACCESS  read-only
    STATUS  mandatory
    DESCRIPTION
            "Operating System version."
    ::= { smSiaSystemDescription 3 }

smSiaSystemRelease OBJECT-TYPE
    SYNTAX  DisplayString
    ACCESS  read-only
    STATUS  mandatory
    DESCRIPTION
            "Operating System release."
    ::= { smSiaSystemDescription 4 }

smSiaSystemMachine OBJECT-TYPE
    SYNTAX  DisplayString
    ACCESS  read-only
    STATUS  mandatory
    DESCRIPTION
            "Hardware type."
    ::= { smSiaSystemDescription 5 }

smSiaSystemTime OBJECT-TYPE
    SYNTAX  DisplayString
    ACCESS  read-only
    STATUS  mandatory
    DESCRIPTION
            "Current system time."
    ::= { smSiaSystemDescription 6 }


--
--  Paging status group
--
--  Provides total paging space information, plus a percentage which can
--  be thresholded.
--

smSiaSystemFreePagingSpace OBJECT-TYPE
        SYNTAX  INTEGER
        ACCESS  read-only
        STATUS  mandatory
        DESCRIPTION
                "Free paging space in the system, in megabytes.
                 It can be useful to set a threshold on this variable
                 to indicate when it drops below a certain number of Mbs,
                 (for instance, for AIX, the threshold is 2 Mb)
                 because when there is less than adequate free paging
                 space, the kernel sends a SIGDANGER to all processes on
                 the system, and if the free paging space continues
                 to drop, the kernel will begin killing large processes
                 until it can get back 512 pages (enough to prevent
                 a system crash)."
 	
        ::= { smSiaSystemPagingInformation 1 }

smSiaSystemFreePagingSpaceUntilKill OBJECT-TYPE
        SYNTAX  INTEGER
        ACCESS  read-only
        STATUS  mandatory
        DESCRIPTION
                "Free paging space until kill threshold, in megabytes.

                 On HP-UX and Sun Solaris, this variable
                 is the same as smSiaSystemFreePagingSpace.
                 On Digital UNIX, this variable is the low
                 water mark for paging space (20 Mb)."
        ::= { smSiaSystemPagingInformation 2 }

smSiaSystemKillThresholdToFreePagingSpacePercent OBJECT-TYPE
        SYNTAX  INTEGER
        ACCESS  read-only
        STATUS  mandatory
        DESCRIPTION
                "Ratio of kill threshold to free paging space expressed
                 as a percentage.  This value remains zero until the kill
                 threshold becomes >= 1% of the free paging space.

                 On HP-UX and Sun Solaris, this variable
                 is computed as the percentage of paging space used.

                 On Digital UNIX, this variable is the difference between
                 free paging space and the FreePagingSpaceUntilKill
                 expressed as a percent."
        ::= { smSiaSystemPagingInformation 3 }


--
--  The PagingSpace Group
--
--  The following provide information on different paging spaces in the system
--

smSiaSystemPagingSpace       OBJECT IDENTIFIER ::= { smSiaSystemPagingInformation 4 }
smSiaSystemPagingStatistics  OBJECT IDENTIFIER ::= { smSiaSystemPagingInformation 5 }

smSiaSystemPagingSpaceCount OBJECT-TYPE
        SYNTAX  Gauge
        ACCESS  read-only
        STATUS  mandatory
        DESCRIPTION
                "The number of paging spaces."
        ::= { smSiaSystemPagingSpace 1 }

--  The PagingSpace Table

smSiaSystemPagingSpaceTable OBJECT-TYPE
        SYNTAX  SEQUENCE OF SmSiaSystemPagingSpaceEntry
        ACCESS  not-accessible
        STATUS  mandatory
        DESCRIPTION
                "Paging space table."
        ::= { smSiaSystemPagingSpace 2 }

smSiaSystemPagingSpaceEntry OBJECT-TYPE
        SYNTAX  SmSiaSystemPagingSpaceEntry
        ACCESS  not-accessible
        STATUS  mandatory
        DESCRIPTION
                "Each entry contains objects for a particular paging
                 space."
	INDEX { smSiaSystemPagingSpaceName }
        ::= { smSiaSystemPagingSpaceTable 1 }

SmSiaSystemPagingSpaceEntry ::= SEQUENCE {
    smSiaSystemPagingSpaceName
        DisplayString,
    smSiaSystemPagingSpacePhysicalVolume
        DisplayString,
    smSiaSystemPagingSpaceVolumeGroup
        DisplayString,
    smSiaSystemPagingSpaceSize
        INTEGER,
    smSiaSystemPagingSpacePercentUsed
        Gauge,
    smSiaSystemPagingSpaceActive
        DisplayString,
    smSiaSystemPagingSpaceAuto
        DisplayString,
    smSiaSystemPagingSpaceType
	DisplayString
}

smSiaSystemPagingSpaceName OBJECT-TYPE
        SYNTAX  DisplayString
        ACCESS  read-only
        STATUS  mandatory
        DESCRIPTION
                "Paging space name."
        ::= { smSiaSystemPagingSpaceEntry 1 }

smSiaSystemPagingSpacePhysicalVolume OBJECT-TYPE
        SYNTAX  DisplayString
        ACCESS  read-only
        STATUS  mandatory
        DESCRIPTION
                "Physical volume on which paging space resides.

                 Not supported on Digital UNIX."
        ::= { smSiaSystemPagingSpaceEntry 2 }

smSiaSystemPagingSpaceVolumeGroup OBJECT-TYPE
        SYNTAX  DisplayString
        ACCESS  read-only
        STATUS  mandatory
        DESCRIPTION
                "Volume group of paging space.

                 Not supported on HP-UX, Sun Solaris and Digital UNIX."
        ::= { smSiaSystemPagingSpaceEntry 3 }

smSiaSystemPagingSpaceSize OBJECT-TYPE
        SYNTAX  INTEGER
        ACCESS  read-only
        STATUS  mandatory
        DESCRIPTION
                "Size in megabytes."
        ::= { smSiaSystemPagingSpaceEntry 4 }

smSiaSystemPagingSpacePercentUsed OBJECT-TYPE
        SYNTAX  Gauge
        ACCESS  read-only
        STATUS  mandatory
        DESCRIPTION
                "Percent used.  This value can be helpful in
                 maintaining acceptable system performance.  When
                 the percent of paging space used goes above
                 approximately 80 percent, the system performance
                 can be affected."
        ::= { smSiaSystemPagingSpaceEntry 5 }

smSiaSystemPagingSpaceActive OBJECT-TYPE
	SYNTAX  DisplayString
        ACCESS  read-only
        STATUS  mandatory
        DESCRIPTION
                "Active indicator --- Yes or No

                 Not supported on Digital UNIX."
        ::= { smSiaSystemPagingSpaceEntry 6 }

smSiaSystemPagingSpaceAuto OBJECT-TYPE
   	SYNTAX  DisplayString
        ACCESS  read-only
        STATUS  mandatory
        DESCRIPTION
                "Auto indicator --- Yes or No

                 Not supported on HP-UX or Digital UNIX."
        ::= { smSiaSystemPagingSpaceEntry 7 }

smSiaSystemPagingSpaceType OBJECT-TYPE
        SYNTAX  DisplayString
        ACCESS  read-only
        STATUS  mandatory
        DESCRIPTION
                "Paging space type.

                 Not supported on Digital UNIX."
        ::= { smSiaSystemPagingSpaceEntry 8 }


--
--  The Paging Statistics Subtree
--

smSiaSystemPagingStatisticsPollingInterval OBJECT-TYPE
        SYNTAX  INTEGER
        ACCESS  read-only
        STATUS  mandatory
        DESCRIPTION
                "Polling interval for paging statistics data.
                 Currently reserved."
        ::= { smSiaSystemPagingStatistics 1 }

--
--  The Paging Statistics Table
--
--  This table provides information on paging activity
--

smSiaSystemPagingStatisticsTable OBJECT-TYPE
        SYNTAX  SEQUENCE OF SmSiaSystemPagingStatisticsEntry
        ACCESS  not-accessible
        STATUS  mandatory
        DESCRIPTION
                "Input/Output statistics table."
        ::= { smSiaSystemPagingStatistics 2 }

smSiaSystemPagingStatisticsEntry OBJECT-TYPE
        SYNTAX  SmSiaSystemPagingStatisticsEntry
        ACCESS  not-accessible
        STATUS  mandatory
        DESCRIPTION
                "Each instance contains paging statistics over a
                 different interval. - same information as vmstat"
        INDEX { smSiaSystemPagingStatisticsName }
        ::= { smSiaSystemPagingStatisticsTable 1 }

SmSiaSystemPagingStatisticsEntry ::= SEQUENCE {
    smSiaSystemPagingStatisticsName
        DisplayString,
    smSiaSystemPagingStatisticsIntervalStartTime
        DisplayString,
    smSiaSystemPagingStatisticsIntervalLength
        TimeTicks,
    smSiaSystemPagingStatisticsPageFaults
        INTEGER,
    smSiaSystemPagingStatisticsPageReclaims
        INTEGER,
    smSiaSystemPagingStatisticsPagesPagedIn
        INTEGER,
    smSiaSystemPagingStatisticsPagesPagedOut
        INTEGER,
    smSiaSystemPagingStatisticsPageInsFromPagingSpace
        INTEGER,
    smSiaSystemPagingStatisticsPageOutsFromPagingSpace
        INTEGER,
    smSiaSystemPagingStatisticsStartIOs
        INTEGER,
    smSiaSystemPagingStatisticsDoneIOs
        INTEGER,
    smSiaSystemPagingStatisticsPageScans
        INTEGER,
    smSiaSystemPagingStatisticsScanClockCycles
        INTEGER,
    smSiaSystemPagingStatisticsPageSteals
        INTEGER,
    smSiaSystemPagingStatisticsFreeFrameWaits
        INTEGER,
    smSiaSystemPagingStatisticsExtendXPTWaits
        INTEGER,
    smSiaSystemPagingStatisticsPendingIOWaits
        INTEGER,
    smSiaSystemPagingStatisticsPageFaultsMinimum
        INTEGER,
    smSiaSystemPagingStatisticsPageReclaimsMinimum
        INTEGER,
    smSiaSystemPagingStatisticsPagesPagedInMinimum
        INTEGER,
    smSiaSystemPagingStatisticsPagesPagedOutMinimum
        INTEGER,
    smSiaSystemPagingStatisticsPageInsFromPagingSpaceMinimum
        INTEGER,
    smSiaSystemPagingStatisticsPageOutsFromPagingSpaceMinimum
        INTEGER,
    smSiaSystemPagingStatisticsStartIOsMinimum
        INTEGER,
    smSiaSystemPagingStatisticsDoneIOsMinimum
        INTEGER,
    smSiaSystemPagingStatisticsPageScansMinimum
        INTEGER,
    smSiaSystemPagingStatisticsScanClockCyclesMinimum
        INTEGER,
    smSiaSystemPagingStatisticsPageStealsMinimum
        INTEGER,
    smSiaSystemPagingStatisticsFreeFrameWaitsMinimum
        INTEGER,
    smSiaSystemPagingStatisticsExtendXPTWaitsMinimum
        INTEGER,
    smSiaSystemPagingStatisticsPendingIOWaitsMinimum
        INTEGER,
    smSiaSystemPagingStatisticsPageFaultsMaximum
        INTEGER,
    smSiaSystemPagingStatisticsPageReclaimsMaximum
        INTEGER,
    smSiaSystemPagingStatisticsPagesPagedInMaximum
        INTEGER,
    smSiaSystemPagingStatisticsPagesPagedOutMaximum
        INTEGER,
    smSiaSystemPagingStatisticsPageInsFromPagingSpaceMaximum
        INTEGER,
    smSiaSystemPagingStatisticsPageOutsFromPagingSpaceMaximum
        INTEGER,
    smSiaSystemPagingStatisticsStartIOsMaximum
        INTEGER,
    smSiaSystemPagingStatisticsDoneIOsMaximum
        INTEGER,
    smSiaSystemPagingStatisticsPageScansMaximum
        INTEGER,
    smSiaSystemPagingStatisticsScanClockCyclesMaximum
        INTEGER,
    smSiaSystemPagingStatisticsPageStealsMaximum
        INTEGER,
    smSiaSystemPagingStatisticsFreeFrameWaitsMaximum
        INTEGER,
    smSiaSystemPagingStatisticsExtendXPTWaitsMaximum
        INTEGER,
    smSiaSystemPagingStatisticsPendingIOWaitsMaximum
        INTEGER
}

smSiaSystemPagingStatisticsName OBJECT-TYPE
        SYNTAX  DisplayString
        ACCESS  read-only
        STATUS  mandatory
        DESCRIPTION
                "Description of interval."
        ::= { smSiaSystemPagingStatisticsEntry 1 }

smSiaSystemPagingStatisticsIntervalStartTime OBJECT-TYPE
        SYNTAX  DisplayString
        ACCESS  read-only
        STATUS  mandatory
        DESCRIPTION
                "Start time of interval."
        ::= { smSiaSystemPagingStatisticsEntry 2 }

smSiaSystemPagingStatisticsIntervalLength OBJECT-TYPE
        SYNTAX  TimeTicks
        ACCESS  read-only
        STATUS  mandatory
        DESCRIPTION
                "Length of interval during which paging statistics are
                 computed."
        ::= { smSiaSystemPagingStatisticsEntry 3 }

smSiaSystemPagingStatisticsPageFaults OBJECT-TYPE
        SYNTAX  INTEGER
        ACCESS  read-only
        STATUS  mandatory
        DESCRIPTION
                "Total number of page faults over the interval.

                 Not supported on Digital UNIX."
         ::= { smSiaSystemPagingStatisticsEntry 4 }

smSiaSystemPagingStatisticsPageReclaims OBJECT-TYPE
        SYNTAX  INTEGER
        ACCESS  read-only
        STATUS  mandatory
        DESCRIPTION
                "Total number of page reclaims over the interval.
                 On Digital UNIX, this variable is the number of
                 pages freed."
         ::= { smSiaSystemPagingStatisticsEntry 5 }

smSiaSystemPagingStatisticsPagesPagedIn OBJECT-TYPE
        SYNTAX  INTEGER
        ACCESS  read-only
        STATUS  mandatory
        DESCRIPTION
                "Total number of Pages Paged In over the interval"
         ::= { smSiaSystemPagingStatisticsEntry 6 }

smSiaSystemPagingStatisticsPagesPagedOut OBJECT-TYPE
        SYNTAX  INTEGER
        ACCESS  read-only
        STATUS  mandatory
        DESCRIPTION
                "Total number of Pages Paged Out over the interval"
         ::= { smSiaSystemPagingStatisticsEntry 7 }

smSiaSystemPagingStatisticsPageInsFromPagingSpace OBJECT-TYPE
        SYNTAX  INTEGER
        ACCESS  read-only
        STATUS  mandatory
        DESCRIPTION
                "Total number of Page Ins From Paging Space.

                 Not supported on Digital UNIX."
         ::= { smSiaSystemPagingStatisticsEntry 8 }

smSiaSystemPagingStatisticsPageOutsFromPagingSpace OBJECT-TYPE
        SYNTAX  INTEGER
        ACCESS  read-only
        STATUS  mandatory
        DESCRIPTION
                "Total number of Page Outs From Paging Space

                 Not supported on Digital UNIX."
         ::= { smSiaSystemPagingStatisticsEntry 9 }

smSiaSystemPagingStatisticsStartIOs OBJECT-TYPE
        SYNTAX  INTEGER
        ACCESS  read-only
        STATUS  mandatory
        DESCRIPTION
                "Total number of IO Starts

                 Not supported on HP-UX, Sun Solaris and Digital UNIX."
        ::= { smSiaSystemPagingStatisticsEntry 10 }

smSiaSystemPagingStatisticsDoneIOs OBJECT-TYPE
        SYNTAX  INTEGER
        ACCESS  read-only
        STATUS  mandatory
        DESCRIPTION
                "Total number of IOs Done

                 Not supported on HP-UX, Sun Solaris and Digital UNIX."
        ::= { smSiaSystemPagingStatisticsEntry 11 }

smSiaSystemPagingStatisticsPageScans OBJECT-TYPE
        SYNTAX  INTEGER
        ACCESS  read-only
        STATUS  mandatory
        DESCRIPTION
                "Total number of page scans"
         ::= { smSiaSystemPagingStatisticsEntry 12 }

smSiaSystemPagingStatisticsScanClockCycles OBJECT-TYPE
        SYNTAX  INTEGER
        ACCESS  read-only
        STATUS  mandatory
        DESCRIPTION
                "Total page scan clock cycles.

                 Not supported on Digital UNIX."
         ::= { smSiaSystemPagingStatisticsEntry 13 }

smSiaSystemPagingStatisticsPageSteals OBJECT-TYPE
        SYNTAX  INTEGER
        ACCESS  read-only
        STATUS  mandatory
        DESCRIPTION
                "Total number of page steals

                 Not supported on HP-UX or Digital UNIX."
        ::= { smSiaSystemPagingStatisticsEntry 14 }

smSiaSystemPagingStatisticsFreeFrameWaits OBJECT-TYPE
        SYNTAX  INTEGER
        ACCESS  read-only
        STATUS  mandatory
        DESCRIPTION
                "Total number of free frame waits.

                 Not supported on HP-UX, Sun Solaris and Digital UNIX."
        ::= { smSiaSystemPagingStatisticsEntry 15 }

smSiaSystemPagingStatisticsExtendXPTWaits OBJECT-TYPE
        SYNTAX  INTEGER
        ACCESS  read-only
        STATUS  mandatory
        DESCRIPTION
                "Total number of extend XPT waits.

                 Not supported on HP-UX, Sun Solaris and Digital UNIX."
        ::= { smSiaSystemPagingStatisticsEntry 16 }

smSiaSystemPagingStatisticsPendingIOWaits OBJECT-TYPE
        SYNTAX  INTEGER
        ACCESS  read-only
        STATUS  mandatory
        DESCRIPTION
                "Total number of Pending I/O waits

                 Not supported on HP-UX, Sun Solaris and Digital UNIX."
        ::= { smSiaSystemPagingStatisticsEntry 17 }

smSiaSystemPagingStatisticsPageFaultsMinimum OBJECT-TYPE
        SYNTAX  INTEGER
        ACCESS  read-only
        STATUS  mandatory
        DESCRIPTION
                "Minimum page faults.

                 Not supported on Digital UNIX."
        ::= { smSiaSystemPagingStatisticsEntry 18 }

smSiaSystemPagingStatisticsPageReclaimsMinimum OBJECT-TYPE
        SYNTAX  INTEGER
        ACCESS  read-only
        STATUS  mandatory
        DESCRIPTION
                "Minimum page reclaims"
        ::= { smSiaSystemPagingStatisticsEntry 19 }

smSiaSystemPagingStatisticsPagesPagedInMinimum OBJECT-TYPE
        SYNTAX  INTEGER
        ACCESS  read-only
        STATUS  mandatory
        DESCRIPTION
                "Minimum pages paged in"
        ::= { smSiaSystemPagingStatisticsEntry 20 }

smSiaSystemPagingStatisticsPagesPagedOutMinimum OBJECT-TYPE
        SYNTAX  INTEGER
        ACCESS  read-only
        STATUS  mandatory
        DESCRIPTION
                "Minimum pages paged out"
        ::= { smSiaSystemPagingStatisticsEntry 21 }

smSiaSystemPagingStatisticsPageInsFromPagingSpaceMinimum OBJECT-TYPE
        SYNTAX  INTEGER
        ACCESS  read-only
        STATUS  mandatory
        DESCRIPTION
                "Minimum Page Ins From Paging Space.

                 Not supported on Digital UNIX."
        ::= { smSiaSystemPagingStatisticsEntry 22 }

smSiaSystemPagingStatisticsPageOutsFromPagingSpaceMinimum OBJECT-TYPE
        SYNTAX  INTEGER
        ACCESS  read-only
        STATUS  mandatory
        DESCRIPTION
                "Minimum Page Outs From Paging Space.

                 Not supported on Digital UNIX."
        ::= { smSiaSystemPagingStatisticsEntry 23 }

smSiaSystemPagingStatisticsStartIOsMinimum OBJECT-TYPE
        SYNTAX  INTEGER
        ACCESS  read-only
        STATUS  mandatory
        DESCRIPTION
                "Minimum IO Starts

                 Not supported on HP-UX or Digital UNIX."
        ::= { smSiaSystemPagingStatisticsEntry 24 }

smSiaSystemPagingStatisticsDoneIOsMinimum OBJECT-TYPE
        SYNTAX  INTEGER
        ACCESS  read-only
        STATUS  mandatory
        DESCRIPTION
                "Minimum IOs Done

                 Not supported on HP-UX or Digital UNIX."
        ::= { smSiaSystemPagingStatisticsEntry 25 }

smSiaSystemPagingStatisticsPageScansMinimum OBJECT-TYPE
        SYNTAX  INTEGER
        ACCESS  read-only
        STATUS  mandatory
        DESCRIPTION
                "Minimum number of page scans"
        ::= { smSiaSystemPagingStatisticsEntry 26 }

smSiaSystemPagingStatisticsScanClockCyclesMinimum OBJECT-TYPE
        SYNTAX  INTEGER
        ACCESS  read-only
        STATUS  mandatory
        DESCRIPTION
                "Minimum page scan clock cycles

                 Not supported on Digital UNIX."
        ::= { smSiaSystemPagingStatisticsEntry 27 }

smSiaSystemPagingStatisticsPageStealsMinimum OBJECT-TYPE
        SYNTAX  INTEGER
        ACCESS  read-only
        STATUS  mandatory
        DESCRIPTION
                "Minimum page steals

                 Not supported on HP-UX or Digital UNIX."
        ::= { smSiaSystemPagingStatisticsEntry 28 }

smSiaSystemPagingStatisticsFreeFrameWaitsMinimum OBJECT-TYPE
        SYNTAX  INTEGER
        ACCESS  read-only
        STATUS  mandatory
        DESCRIPTION
                "Minimum free frame waits

                 Not supported on HP-UX or Digital UNIX."
        ::= { smSiaSystemPagingStatisticsEntry 29 }

smSiaSystemPagingStatisticsExtendXPTWaitsMinimum OBJECT-TYPE
        SYNTAX  INTEGER
        ACCESS  read-only
        STATUS  mandatory
        DESCRIPTION
                "Minimum Extend XPT waits.

                 Not supported on HP-UX or Digital UNIX."
        ::= { smSiaSystemPagingStatisticsEntry 30 }

smSiaSystemPagingStatisticsPendingIOWaitsMinimum OBJECT-TYPE
        SYNTAX  INTEGER
        ACCESS  read-only
        STATUS  mandatory
        DESCRIPTION
                "Minimum Pending I/O waits

                 Not supported on HP-UX or Digital UNIX."
        ::= { smSiaSystemPagingStatisticsEntry 31 }

smSiaSystemPagingStatisticsPageFaultsMaximum OBJECT-TYPE
        SYNTAX  INTEGER
        ACCESS  read-only
        STATUS  mandatory
        DESCRIPTION
                "Maximum page faults

                 Not supported on Digital UNIX."
        ::= { smSiaSystemPagingStatisticsEntry 32 }

smSiaSystemPagingStatisticsPageReclaimsMaximum OBJECT-TYPE
        SYNTAX  INTEGER
        ACCESS  read-only
        STATUS  mandatory
        DESCRIPTION
                "Maximum page reclaims"
        ::= { smSiaSystemPagingStatisticsEntry 33 }

smSiaSystemPagingStatisticsPagesPagedInMaximum OBJECT-TYPE
        SYNTAX  INTEGER
        ACCESS  read-only
        STATUS  mandatory
        DESCRIPTION
                "Maximum Pages Paged In"
        ::= { smSiaSystemPagingStatisticsEntry 34 }

smSiaSystemPagingStatisticsPagesPagedOutMaximum OBJECT-TYPE
        SYNTAX  INTEGER
        ACCESS  read-only
        STATUS  mandatory
        DESCRIPTION
                "Maximum Pages Paged Out"
        ::= { smSiaSystemPagingStatisticsEntry 35 }

smSiaSystemPagingStatisticsPageInsFromPagingSpaceMaximum OBJECT-TYPE
        SYNTAX  INTEGER
        ACCESS  read-only
        STATUS  mandatory
        DESCRIPTION
                "Maximum Page Ins From Paging Space

                 Not supported on Digital UNIX."
        ::= { smSiaSystemPagingStatisticsEntry 36 }

smSiaSystemPagingStatisticsPageOutsFromPagingSpaceMaximum OBJECT-TYPE
        SYNTAX  INTEGER
        ACCESS  read-only
        STATUS  mandatory
        DESCRIPTION
                "Maximum Page Outs From Paging Space

                 Not supported on Digital UNIX."
        ::= { smSiaSystemPagingStatisticsEntry 37 }

smSiaSystemPagingStatisticsStartIOsMaximum OBJECT-TYPE
        SYNTAX  INTEGER
        ACCESS  read-only
        STATUS  mandatory
        DESCRIPTION
                "Maximum IO Starts

                 Not supported on HP-UX or Digital UNIX."
        ::= { smSiaSystemPagingStatisticsEntry 38 }

smSiaSystemPagingStatisticsDoneIOsMaximum OBJECT-TYPE
        SYNTAX  INTEGER
        ACCESS  read-only
        STATUS  mandatory
        DESCRIPTION
                "Maximum IOs Done

                 Not supported on HP-UX or Digital UNIX."
        ::= { smSiaSystemPagingStatisticsEntry 39 }

smSiaSystemPagingStatisticsPageScansMaximum OBJECT-TYPE
        SYNTAX  INTEGER
        ACCESS  read-only
        STATUS  mandatory
        DESCRIPTION
                "Maximum number of page scans"
        ::= { smSiaSystemPagingStatisticsEntry 40 }

smSiaSystemPagingStatisticsScanClockCyclesMaximum OBJECT-TYPE
        SYNTAX  INTEGER
        ACCESS  read-only
        STATUS  mandatory
        DESCRIPTION
                "Maximum page scan clock cycles

                 Not supported on Digital UNIX."
        ::= { smSiaSystemPagingStatisticsEntry 41 }

smSiaSystemPagingStatisticsPageStealsMaximum OBJECT-TYPE
        SYNTAX  INTEGER
        ACCESS  read-only
        STATUS  mandatory
        DESCRIPTION
                "Maximum page steals

                 Not supported on HP-UX or Digital UNIX."
        ::= { smSiaSystemPagingStatisticsEntry 42 }

smSiaSystemPagingStatisticsFreeFrameWaitsMaximum OBJECT-TYPE
        SYNTAX  INTEGER
        ACCESS  read-only
        STATUS  mandatory
        DESCRIPTION
                "Maximum free frame waits

                 Not supported on HP-UX or Digital UNIX."
        ::= { smSiaSystemPagingStatisticsEntry 43 }

smSiaSystemPagingStatisticsExtendXPTWaitsMaximum OBJECT-TYPE
        SYNTAX  INTEGER
        ACCESS  read-only
        STATUS  mandatory
        DESCRIPTION
                "Maximum Extend XPT waits.

                 Not supported on HP-UX or Digital UNIX."
        ::= { smSiaSystemPagingStatisticsEntry 44 }

smSiaSystemPagingStatisticsPendingIOWaitsMaximum OBJECT-TYPE
        SYNTAX  INTEGER
        ACCESS  read-only
        STATUS  mandatory
        DESCRIPTION
                "Maximum Pending I/O waits

                 Not supported on HP-UX or Digital UNIX."
        ::= { smSiaSystemPagingStatisticsEntry 45 }


--
--  The following variables provide system configuration information
--

smSiaSystemBufferPoolMark OBJECT-TYPE
        SYNTAX  INTEGER
        ACCESS  read-only
        STATUS  mandatory
        DESCRIPTION
                "Buffer Pool High water mark

                On Sun Solaris, the mbuf high water mark includes
                only the normal mbuf and not the cluster mbuf.

                Not supported on Digital UNIX."
        ::= { smSiaSystemConfiguration 1 }

smSiaSystemMaxMbufs OBJECT-TYPE
        SYNTAX  INTEGER
        ACCESS  read-only
        STATUS  mandatory
        DESCRIPTION
                "Max mbufs high-water mark.

                 Not supported on Sun Solaris 2.x or Digital UNIX."
        ::= { smSiaSystemConfiguration 2 }


smSiaSystemMaxUserProcesses OBJECT-TYPE
        SYNTAX  INTEGER
        ACCESS  read-only
        STATUS  mandatory
        DESCRIPTION
                "Maximum number of processes per user."
        ::= { smSiaSystemConfiguration 3 }

smSiaSystemMaxSystemProcesses OBJECT-TYPE
        SYNTAX  INTEGER
        ACCESS  read-only
        STATUS  mandatory
        DESCRIPTION
                "Maximum number of processes on the system.

                 Not supported on Digital UNIX."
        ::= { smSiaSystemConfiguration 4 }

smSiaSystemRecordLockTableSize OBJECT-TYPE
        SYNTAX  INTEGER
        ACCESS  read-only
        STATUS  mandatory
        DESCRIPTION
                "Number of entries in record lock table.

                 Not supported on Sun Solaris."
        ::= { smSiaSystemConfiguration 5 }

smSiaSystemOpenFileTableSize OBJECT-TYPE
        SYNTAX  INTEGER
        ACCESS  read-only
        STATUS  mandatory
	DESCRIPTION
                "Maximum number of entries in open file table.

                 Not supported on Sun Solaris 2.x."
        ::= { smSiaSystemConfiguration 6 }

smSiaSystemCBlockArraySize OBJECT-TYPE
        SYNTAX  INTEGER
        ACCESS  read-only
        STATUS  mandatory
        DESCRIPTION
                "Maximum number of cblocks in cblock array.

                 For Sun Solaris 2.x, it is the number of
                 clists allocated.

                 Not supported on Digital UNIX."
        ::= { smSiaSystemConfiguration 7 }

smSiaSystemDiskIOHistory OBJECT-TYPE
        SYNTAX  INTEGER {
                disabled(1),
                enabled(2)
                }
        ACCESS  read-only
        STATUS  mandatory
        DESCRIPTION
                "Disk I/O History enabled.

                 Not supported on HP-UX, Sun Solaris and Digital UNIX."
        ::= { smSiaSystemConfiguration 8 }

smSiaSystemAutomaticBootAfterHalt OBJECT-TYPE
        SYNTAX  INTEGER {
                disabled(1),
                enabled(2)
                }
        ACCESS  read-only
        STATUS  mandatory
        DESCRIPTION
                "Automatic boot after halt.

                 Not supported on HP-UX or Digital UNIX.

                On Sun Solaris, this variable reflects the value of
                the openprom option variable <watchdog-reboot?>."
        ::= { smSiaSystemConfiguration 9 }

smSiaSystemMemScrub OBJECT-TYPE
        SYNTAX  INTEGER {
                disabled(1),
                enabled(2)
                }
        ACCESS  read-only
        STATUS  mandatory
        DESCRIPTION
                "Memory scrubbing enabled.

                 Not supported on HP-UX, Sun Solaris and Digital UNIX."
        ::= { smSiaSystemConfiguration 10 }

smSiaSystemLeastPriv OBJECT-TYPE
        SYNTAX  INTEGER
        ACCESS  read-only
        STATUS  mandatory
        DESCRIPTION
                "Least privilege enablement.

                 Not supported on HP-UX, Sun Solaris and Digital UNIX."
        ::= { smSiaSystemConfiguration 11 }

smSiaSystemMaxPout OBJECT-TYPE
        SYNTAX  INTEGER
        ACCESS  read-only
        STATUS  mandatory
        DESCRIPTION
                "Number of file pageouts at which waiting occurs.

                 Not supported on HP-UX, Sun Solaris and Digital UNIX."
        ::= { smSiaSystemConfiguration 12 }

smSiaSystemMinPout OBJECT-TYPE
        SYNTAX  INTEGER
        ACCESS  read-only
        STATUS  mandatory
        DESCRIPTION
                "Number of file pageouts at which ready occurs.

                 Not supported on HP-UX, Sun Solaris and Digital UNIX."
        ::= { smSiaSystemConfiguration 13 }

smSiaSystemPageSize OBJECT-TYPE
        SYNTAX  INTEGER
        ACCESS  read-only
        STATUS  mandatory
        DESCRIPTION
                "System page size (from getpagesize())"
        ::= { smSiaSystemConfiguration 14 }

smSiaSystemProcessMaxOpenFiles OBJECT-TYPE
        SYNTAX  INTEGER
        ACCESS  read-only
        STATUS  mandatory
        DESCRIPTION
                "Maximum open files per process."
        ::= { smSiaSystemConfiguration 15 }

smSiaSystemProcessMaxOpenStreams OBJECT-TYPE
        SYNTAX  INTEGER
        ACCESS  read-only
        STATUS  mandatory
        DESCRIPTION
                "Maximum open streams per process

                 On Sun Solaris, there is no limit on the number of
                 streams in the system or per processor.  The maximum
                 open streams per process is limited by the number of
                 open files per process.  That is, this variable always
                 has the same value as smSiaSystemProcessMaxOpenFiles."
        ::= { smSiaSystemConfiguration 16 }

smSiaSystemProcessDescriptorTableSize OBJECT-TYPE
        SYNTAX  INTEGER
        ACCESS  read-only
        STATUS  mandatory
        DESCRIPTION
                "Descriptor table size for System Information Agent."
        ::= { smSiaSystemConfiguration 17 }

smSiaSystemPhysicalMemorySize OBJECT-TYPE
        SYNTAX  INTEGER
        ACCESS  read-only
        STATUS  mandatory
        DESCRIPTION
                "Amount of usable physical memory in Mbytes"
        ::= { smSiaSystemConfiguration 18 }


--
--  The Device Group
--
--  Information on devices installed on the system
--

smSiaSystemDeviceList        OBJECT IDENTIFIER ::= { smSiaSystemDevice 1 }
smSiaSystemDeviceTokenRing   OBJECT IDENTIFIER ::= { smSiaSystemDevice 2 }
smSiaSystemDeviceEthernet    OBJECT IDENTIFIER ::= { smSiaSystemDevice 3 }
smSiaSystemDeviceX25         OBJECT IDENTIFIER ::= { smSiaSystemDevice 4 }

smSiaSystemDeviceListInstalled OBJECT-TYPE
        SYNTAX  INTEGER
        ACCESS  read-only
        STATUS  mandatory
        DESCRIPTION
                "The number of devices installed."
        ::= { smSiaSystemDeviceList 1 }

--
--  The Device Table
--

smSiaSystemDeviceListTable OBJECT-TYPE
        SYNTAX  SEQUENCE OF SmSiaSystemDeviceListEntry
        ACCESS  not-accessible
        STATUS  mandatory
        DESCRIPTION
                "Device list table."
        ::= { smSiaSystemDeviceList 2 }

smSiaSystemDeviceListEntry OBJECT-TYPE
        SYNTAX  SmSiaSystemDeviceListEntry
        ACCESS  not-accessible
        STATUS  mandatory
        DESCRIPTION
                "Each entry contains objects for a particular device."
	INDEX { smSiaSystemDeviceListName }
        ::= { smSiaSystemDeviceListTable 1 }

SmSiaSystemDeviceListEntry ::= SEQUENCE {
    smSiaSystemDeviceListName
        DisplayString,
    smSiaSystemDeviceListDescription
        DisplayString,
    smSiaSystemDeviceListLocation
        DisplayString,
    smSiaSystemDeviceListVPD
        DisplayString,
    smSiaSystemDeviceListAttributes
        DisplayString,
    smSiaSystemDeviceListDiagnostics
        DisplayString
}

smSiaSystemDeviceListName OBJECT-TYPE
        SYNTAX  DisplayString
        ACCESS  read-only
        STATUS  mandatory
        DESCRIPTION
                "Names of devices installed."
        ::= { smSiaSystemDeviceListEntry 1 }

smSiaSystemDeviceListDescription OBJECT-TYPE
        SYNTAX  DisplayString
        ACCESS  read-only
        STATUS  mandatory
        DESCRIPTION
                "Location of device. Shows status, location and description"
        ::= { smSiaSystemDeviceListEntry 2 }

smSiaSystemDeviceListLocation OBJECT-TYPE
        SYNTAX  DisplayString
        ACCESS  read-only
        STATUS  mandatory
        DESCRIPTION
                "Location of device.

                 Not supported on Sun Solaris."
        ::= { smSiaSystemDeviceListEntry 3 }

smSiaSystemDeviceListVPD OBJECT-TYPE
        SYNTAX  DisplayString
        ACCESS  read-only
        STATUS  mandatory
        DESCRIPTION
                "Vital Product Data.

                 Not supported on HP-UX, Sun Solaris and Digital UNIX."
        ::= { smSiaSystemDeviceListEntry 4 }

smSiaSystemDeviceListAttributes OBJECT-TYPE
        SYNTAX  DisplayString
        ACCESS  read-only
        STATUS  mandatory
        DESCRIPTION
                "Device Attributes.

                 Not supported on HP-UX, Sun Solaris and Digital UNIX."
        ::= { smSiaSystemDeviceListEntry 5 }

smSiaSystemDeviceListDiagnostics OBJECT-TYPE
        SYNTAX  DisplayString
        ACCESS  read-only
        STATUS  mandatory
        DESCRIPTION
                "Results of diagnostic tests.
                 Currently reserved"
        ::= { smSiaSystemDeviceListEntry 6 }


--
--  The Token Ring Table
--

smSiaSystemDeviceTokenRingInstalled OBJECT-TYPE
        SYNTAX  INTEGER
        ACCESS  read-only
        STATUS  mandatory
        DESCRIPTION
                "The number of devices installed."
        ::= { smSiaSystemDeviceTokenRing 1 }

smSiaSystemDeviceTokenRingTable OBJECT-TYPE
        SYNTAX  SEQUENCE OF SmSiaSystemDeviceTokenRingEntry
        ACCESS  not-accessible
        STATUS  mandatory
        DESCRIPTION
                "Adapter table."
        ::= { smSiaSystemDeviceTokenRing 2 }

smSiaSystemDeviceTokenRingEntry OBJECT-TYPE
        SYNTAX  SmSiaSystemDeviceTokenRingEntry
        ACCESS  not-accessible
        STATUS  mandatory
        DESCRIPTION
                "Each entry contains objects for a particular device."
	INDEX { smSiaSystemDeviceTokenRingNumber }
        ::= { smSiaSystemDeviceTokenRingTable 1 }

SmSiaSystemDeviceTokenRingEntry ::= SEQUENCE {
    smSiaSystemDeviceTokenRingNumber
        INTEGER,
    smSiaSystemDeviceTokenRingHardwareAddress
        PhysAddress,
    smSiaSystemDeviceTokenRingCurrentAddress
        PhysAddress,
    smSiaSystemDeviceTokenRingReceiveDataOffset
        INTEGER,
    smSiaSystemDeviceTokenRingBroadwrap
        INTEGER,
    smSiaSystemDeviceTokenRingTxByteMcnt
        Counter,
    smSiaSystemDeviceTokenRingTxByteLcnt
        Counter,
    smSiaSystemDeviceTokenRingRxByteMcnt
        Counter,
    smSiaSystemDeviceTokenRingRxByteLcnt
        Counter,
    smSiaSystemDeviceTokenRingTxFrameMcnt
        Counter,
    smSiaSystemDeviceTokenRingTxFrameLcnt
        Counter,
    smSiaSystemDeviceTokenRingRxFrameMcnt
        Counter,
    smSiaSystemDeviceTokenRingRxFrameLcnt
        Counter,
    smSiaSystemDeviceTokenRingTxErrCnt
        Counter,
    smSiaSystemDeviceTokenRingRxErrCnt
        Counter,
    smSiaSystemDeviceTokenRingNidTblHigh
        INTEGER,
    smSiaSystemDeviceTokenRingTxQueHigh
        Gauge,
    smSiaSystemDeviceTokenRingRxQueHigh
        Gauge,
    smSiaSystemDeviceTokenRingStaQueHigh
        Gauge,
    smSiaSystemDeviceTokenRingIntrLost
        Counter,
    smSiaSystemDeviceTokenRingWdtLost
        Counter,
    smSiaSystemDeviceTokenRingTimoLost
        Counter,
    smSiaSystemDeviceTokenRingStaQueOverflow
        Counter,
    smSiaSystemDeviceTokenRingRxQueOverflow
        Counter,
    smSiaSystemDeviceTokenRingRxQueNoMbuf
        Counter,
    smSiaSystemDeviceTokenRingRxQueNoMbufExt
        Counter,
    smSiaSystemDeviceTokenRingTxIntrCnt
        Counter,
    smSiaSystemDeviceTokenRingRxIntrCnt
        Counter,
    smSiaSystemDeviceTokenRingPktRejCnt
        Counter,
    smSiaSystemDeviceTokenRingPktAccCnt
        Counter,
    smSiaSystemDeviceTokenRingPktTxCnt
        Counter,
    smSiaSystemDeviceTokenRingOvfloPktCnt
        Counter,
    smSiaSystemDeviceTokenRingPktTxErrCnt
        Counter,
    smSiaSystemDeviceTokenRingSpeed
        INTEGER,
    smSiaSystemDeviceTokenRingVPD
        DisplayString,
    smSiaSystemDeviceTokenRingAdapPhysAddr
        PhysAddress,
    smSiaSystemDeviceTokenRingUpstreamNodeAddr
        PhysAddress,
    smSiaSystemDeviceTokenRingUpstreamPhysAddr
        PhysAddress,
    smSiaSystemDeviceTokenRingLastPollAddr
        PhysAddress,
    smSiaSystemDeviceTokenRingAuthorEnv
        INTEGER,
    smSiaSystemDeviceTokenRingTxAccessPriority
        INTEGER,
    smSiaSystemDeviceTokenRingSrcClassAuthor
        INTEGER,
    smSiaSystemDeviceTokenRingLastAttenCode
        INTEGER,
    smSiaSystemDeviceTokenRingLastSrcAddr
        PhysAddress,
    smSiaSystemDeviceTokenRingLastBeaconType
        INTEGER,
    smSiaSystemDeviceTokenRingLastMajorVector
        INTEGER,
    smSiaSystemDeviceTokenRingRingStatus
        INTEGER,
    smSiaSystemDeviceTokenRingSoftErrorTimerVal
        INTEGER,
    smSiaSystemDeviceTokenRingFrontEndTimerVal
        INTEGER,
    smSiaSystemDeviceTokenRingMonitorErrorCode
        INTEGER,
    smSiaSystemDeviceTokenRingBeaconTxType
        INTEGER,
    smSiaSystemDeviceTokenRingBeaconRxType
        INTEGER,
    smSiaSystemDeviceTokenRingFrameCorrSave
        INTEGER,
    smSiaSystemDeviceTokenRingBeaconStationNAUN
        PhysAddress,
    smSiaSystemDeviceTokenRingBeaconStationPhysAddr
        PhysAddress,
    smSiaSystemDeviceTokenRingClear
        INTEGER
}

smSiaSystemDeviceTokenRingNumber OBJECT-TYPE
        SYNTAX  INTEGER
        ACCESS  read-only
        STATUS  mandatory
        DESCRIPTION
                "Token ring number."
        ::= { smSiaSystemDeviceTokenRingEntry 1 }

smSiaSystemDeviceTokenRingHardwareAddress OBJECT-TYPE
        SYNTAX  PhysAddress
        ACCESS  read-only
        STATUS  mandatory
        DESCRIPTION
                "Burned-in MAC Address.

                 On Sun Solaris 2.x, the token ring card does not have a
                 built-in address.  This variable is the same as the
                 smSiaSystemDeviceTokenRingCurrentAddress.

                 On AIX4, this variable is the same as the 
                 smSiaSystemDeviceTokenRingCurrentAddress for devices
                 that are based on CDLI model."
        ::= { smSiaSystemDeviceTokenRingEntry 2 }

smSiaSystemDeviceTokenRingCurrentAddress OBJECT-TYPE
        SYNTAX  PhysAddress
        ACCESS  read-only
        STATUS  mandatory
        DESCRIPTION
                "Current MAC Address."
        ::= { smSiaSystemDeviceTokenRingEntry 3 }

smSiaSystemDeviceTokenRingReceiveDataOffset OBJECT-TYPE
        SYNTAX  INTEGER
        ACCESS  read-only
        STATUS  mandatory
        DESCRIPTION
                "Receive data transfer offset.

                 Not supported on HP-UX, Sun Solaris and Digital UNIX.

                 On AIX4, this variable is not supported for devices
                 that are based on CDLI model."
        ::= { smSiaSystemDeviceTokenRingEntry 4 }

smSiaSystemDeviceTokenRingBroadwrap OBJECT-TYPE
        SYNTAX  INTEGER {
                false(1),  -- not supported
                true(2)    -- supported
                }
        ACCESS  read-only
        STATUS  mandatory
        DESCRIPTION
                "Supports broadcast wrap of data.

                 Not supported on HP-UX, Sun Solaris and Digital UNIX.

                 On AIX4, this variable is not supported for devices
                 that are based on CDLI model."
        ::= { smSiaSystemDeviceTokenRingEntry 5 }

smSiaSystemDeviceTokenRingTxByteMcnt OBJECT-TYPE
        SYNTAX  Counter
        ACCESS  read-only
        STATUS  mandatory
        DESCRIPTION
                "Most significant bits of successfully transmitted byte count.

                 Not supported on HP-UX or Sun Solaris."
        ::= { smSiaSystemDeviceTokenRingEntry 6 }

smSiaSystemDeviceTokenRingTxByteLcnt OBJECT-TYPE
        SYNTAX  Counter
        ACCESS  read-only
        STATUS  mandatory
        DESCRIPTION
                "Least significant bits of successfully transmitted byte count.

                 Not supported on HP-UX or Sun Solaris."
        ::= { smSiaSystemDeviceTokenRingEntry 7 }

smSiaSystemDeviceTokenRingRxByteMcnt OBJECT-TYPE
        SYNTAX  Counter
        ACCESS  read-only
        STATUS  mandatory
        DESCRIPTION
                "Most significant bits of successfully received byte count.

                 Not supported on HP-UX or Sun Solaris."
        ::= { smSiaSystemDeviceTokenRingEntry 8 }

smSiaSystemDeviceTokenRingRxByteLcnt OBJECT-TYPE
        SYNTAX  Counter
        ACCESS  read-only
        STATUS  mandatory
        DESCRIPTION
                "Least significant bits of successfully received byte count.

                 Not supported on HP-UX or Sun Solaris."
        ::= { smSiaSystemDeviceTokenRingEntry 9 }

smSiaSystemDeviceTokenRingTxFrameMcnt OBJECT-TYPE
        SYNTAX  Counter
        ACCESS  read-only
        STATUS  mandatory
        DESCRIPTION
                "Most significant bits of successfully transmitted byte count."
        ::= { smSiaSystemDeviceTokenRingEntry 10 }

smSiaSystemDeviceTokenRingTxFrameLcnt OBJECT-TYPE
        SYNTAX  Counter
        ACCESS  read-only
        STATUS  mandatory
        DESCRIPTION
                "Least significant bits of successfully transmitted byte count."
        ::= { smSiaSystemDeviceTokenRingEntry 11 }

smSiaSystemDeviceTokenRingRxFrameMcnt OBJECT-TYPE
        SYNTAX  Counter
        ACCESS  read-only
        STATUS  mandatory
        DESCRIPTION
                "Most significant bits of successfully received byte count."
        ::= { smSiaSystemDeviceTokenRingEntry 12 }

smSiaSystemDeviceTokenRingRxFrameLcnt OBJECT-TYPE
        SYNTAX  Counter
        ACCESS  read-only
        STATUS  mandatory
        DESCRIPTION
                "Least significant bits of successfully received byte count."
        ::= { smSiaSystemDeviceTokenRingEntry 13 }

smSiaSystemDeviceTokenRingTxErrCnt OBJECT-TYPE
        SYNTAX  Counter
        ACCESS  read-only
        STATUS  mandatory
        DESCRIPTION
                "Frame transmit error count

                 Not supported on Digital UNIX."
        ::= { smSiaSystemDeviceTokenRingEntry 14 }

smSiaSystemDeviceTokenRingRxErrCnt OBJECT-TYPE
        SYNTAX  Counter
        ACCESS  read-only
        STATUS  mandatory
        DESCRIPTION
                "Frame receive error count

                 Not supported on Digital UNIX."
        ::= { smSiaSystemDeviceTokenRingEntry 15 }

smSiaSystemDeviceTokenRingNidTblHigh OBJECT-TYPE
        SYNTAX  INTEGER
        ACCESS  read-only
        STATUS  mandatory
        DESCRIPTION
                "Maximum netids in use.

                 Not supported on HP-UX, Sun Solaris and Digital UNIX.

                 On AIX4, this variable is not supported for devices
                 that are based on CDLI model."
        ::= { smSiaSystemDeviceTokenRingEntry 16 }

smSiaSystemDeviceTokenRingTxQueHigh OBJECT-TYPE
        SYNTAX  Gauge
        ACCESS  read-only
        STATUS  mandatory
        DESCRIPTION
                "Maximum transmits ever queued for adapter.  On an
                 adapter, buffer queue size is 30 by default.  It can
                 be useful to set a threshold on this variable to watch
                 for the value to go over 20, indicating a need to
                 increase buffer queue size to prevent an overflow.

                 Not supported on HP-UX, Sun Solaris and Digital UNIX."
        ::= { smSiaSystemDeviceTokenRingEntry 17 }

smSiaSystemDeviceTokenRingRxQueHigh OBJECT-TYPE
        SYNTAX  Gauge
        ACCESS  read-only
        STATUS  mandatory
        DESCRIPTION
                "Maximum received ever queued for any open.  On an
                 adapter, buffer queue size is 30 by dfault.  It
                 can be useful to set a threshold on this variable
                 to watch for the value to go over 20, indicating a
                 need to increase buffer queue size to prevent an overflow.

                 Not supported on HP-UX, Sun Solaris and Digital UNIX.

                 On AIX4, this variable is not supported for devices
                 that are based on CDLI model."
        ::= { smSiaSystemDeviceTokenRingEntry 18 }

smSiaSystemDeviceTokenRingStaQueHigh OBJECT-TYPE
        SYNTAX  Gauge
        ACCESS  read-only
        STATUS  mandatory
        DESCRIPTION
                "Maximum status blocks queued for any open.

                 Not supported on HP-UX, Sun Solaris and Digital UNIX.

                 On AIX4, this variable is not supported for devices
                 that are based on CDLI model."
        ::= { smSiaSystemDeviceTokenRingEntry 19 }

smSiaSystemDeviceTokenRingIntrLost OBJECT-TYPE
        SYNTAX  Counter
        ACCESS  read-only
        STATUS  mandatory
        DESCRIPTION
                "Interrupts lost.

                 Not supported on HP-UX, Sun Solaris and Digital UNIX.

                 On AIX4, this variable is not supported for devices
                 that are based on CDLI model."
        ::= { smSiaSystemDeviceTokenRingEntry 20 }

smSiaSystemDeviceTokenRingWdtLost OBJECT-TYPE
        SYNTAX  Counter
        ACCESS  read-only
        STATUS  mandatory
        DESCRIPTION
                "Wdt Interrupts lost.

                 Not supported on HP-UX, Sun Solaris and Digital UNIX.

                 On AIX4, this variable is not supported for devices
                 that are based on CDLI model."
        ::= { smSiaSystemDeviceTokenRingEntry 21 }

smSiaSystemDeviceTokenRingTimoLost OBJECT-TYPE
        SYNTAX  Counter
        ACCESS  read-only
        STATUS  mandatory
        DESCRIPTION
                "Timeout Interrupts lost.

                 Not supported on HP-UX, Sun Solaris and Digital UNIX.

                 On AIX4, this variable is not supported for devices
                 that are based on CDLI model."
        ::= { smSiaSystemDeviceTokenRingEntry 22 }

smSiaSystemDeviceTokenRingStaQueOverflow OBJECT-TYPE
        SYNTAX  Counter
        ACCESS  read-only
        STATUS  mandatory
        DESCRIPTION
                "Status lost due to queue overflow.

                 Not supported on HP-UX, Sun Solaris and Digital UNIX.

                 On AIX4, this variable is not supported for devices
                 that are based on CDLI model."
        ::= { smSiaSystemDeviceTokenRingEntry 23 }

smSiaSystemDeviceTokenRingRxQueOverflow OBJECT-TYPE
        SYNTAX  Counter
        ACCESS  read-only
        STATUS  mandatory
        DESCRIPTION
                "Packet lost due to queue overflow.

                 Not supported on HP-UX, Sun Solaris and Digital UNIX.

                 On AIX4, this variable is not supported for devices
                 that are based on CDLI model."
        ::= { smSiaSystemDeviceTokenRingEntry 24 }

smSiaSystemDeviceTokenRingRxQueNoMbuf OBJECT-TYPE
        SYNTAX  Counter
        ACCESS  read-only
        STATUS  mandatory
        DESCRIPTION
                "Packet lost due to no mbufs. If this variable's value
                 is not 0, you should extend mbuf as soon as possible.
                 All data that goes through the adapter is copied from
                 adapter to mbuf.  Thus, if no mbuf is available to
                 receive data, serious errors can occur.  Be conservative
                 when increasing mbuf size, because this takes real
                 machine memory away from other applications.

                 Not supported on HP-UX or Sun Solaris."
        ::= { smSiaSystemDeviceTokenRingEntry 25 }

smSiaSystemDeviceTokenRingRxQueNoMbufExt OBJECT-TYPE
        SYNTAX  Counter
        ACCESS  read-only
        STATUS  mandatory
        DESCRIPTION
                "Packet lost due to no mbuf extensions.  If this variable's
                 value is not 0, you should extend mbuf as soon as
                 possible.  All data that goes through the adapter is
                 copied from adapter to mbuf.  Thus, if no mbuf extension
                 is available to receive data, serious errors can occur.
                 Be conservative when increasing mbuf size, because this takes
                 real machine memory away from other applications.

                 Not supported on HP-UX, Sun Solaris and Digital UNIX.

                 On AIX4, this variable is not supported for devices
                 that are based on CDLI model."
        ::= { smSiaSystemDeviceTokenRingEntry 26 }

smSiaSystemDeviceTokenRingTxIntrCnt OBJECT-TYPE
        SYNTAX  Counter
        ACCESS  read-only
        STATUS  mandatory
        DESCRIPTION
                "Transmit interrupt count.

                 Not supported on HP-UX, Sun Solaris and Digital UNIX."
        ::= { smSiaSystemDeviceTokenRingEntry 27 }

smSiaSystemDeviceTokenRingRxIntrCnt OBJECT-TYPE
        SYNTAX  Counter
        ACCESS  read-only
        STATUS  mandatory
        DESCRIPTION
                "Receive interrupt count.

                 Not supported on HP-UX, Sun Solaris and Digital UNIX."
        ::= { smSiaSystemDeviceTokenRingEntry 28 }

smSiaSystemDeviceTokenRingPktRejCnt OBJECT-TYPE
        SYNTAX  Counter
        ACCESS  read-only
        STATUS  mandatory
        DESCRIPTION
                "Packets rejected no NETID.

                 Not supported on HP-UX, Sun Solaris and Digital UNIX.

                 On AIX4, this variable is not supported for devices
                 that are based on CDLI model."
        ::= { smSiaSystemDeviceTokenRingEntry 29 }

smSiaSystemDeviceTokenRingPktAccCnt OBJECT-TYPE
        SYNTAX  Counter
        ACCESS  read-only
        STATUS  mandatory
        DESCRIPTION
                "Packets accepted - valid NETID.

                 Not supported on HP-UX, Sun Solaris and Digital UNIX.

                 On AIX4, this variable is not supported for devices
                 that are based on CDLI model."
        ::= { smSiaSystemDeviceTokenRingEntry 30 }

smSiaSystemDeviceTokenRingPktTxCnt OBJECT-TYPE
        SYNTAX  Counter
        ACCESS  read-only
        STATUS  mandatory
        DESCRIPTION
                "Packet transmit counter.

                 Not supported on HP-UX or Sun Solaris.

                 On AIX4, this variable is not supported for devices
                 that are based on CDLI model."
        ::= { smSiaSystemDeviceTokenRingEntry 31 }

smSiaSystemDeviceTokenRingOvfloPktCnt OBJECT-TYPE
        SYNTAX  Counter
        ACCESS  read-only
        STATUS  mandatory
        DESCRIPTION
                "Overflow packets received.

                 Not supported on HP-UX or Sun Solaris.

                 On AIX4, this variable is not supported for devices
                 that are based on CDLI model."
        ::= { smSiaSystemDeviceTokenRingEntry 32 }

smSiaSystemDeviceTokenRingPktTxErrCnt OBJECT-TYPE
        SYNTAX  Counter
        ACCESS  read-only
        STATUS  mandatory
        DESCRIPTION
                "Packet transmission errors detected by adapter.

                 Not supported on HP-UX or Sun Solaris.

                 On AIX4, this variable is not supported for devices
                 that are based on CDLI model."
        ::= { smSiaSystemDeviceTokenRingEntry 33 }

smSiaSystemDeviceTokenRingSpeed OBJECT-TYPE
        SYNTAX  INTEGER
        ACCESS  read-only
        STATUS  mandatory
        DESCRIPTION
                "Ring speed, megabits/second.

                 Not supported on HP-UX.

                 On Sun Solaris, the speed of the Sun token
                 ring card is controlled by jumpers on the card.
                 The setting is not available from software.
                 It defaults to return the speed of 16M."
        ::= { smSiaSystemDeviceTokenRingEntry 34 }

smSiaSystemDeviceTokenRingVPD OBJECT-TYPE
        SYNTAX  DisplayString
        ACCESS  read-only
        STATUS  mandatory
        DESCRIPTION
                "Vital Product Data from adapter.

                 Not supported on HP-UX or Digital UNIX.

                 On Sun Solaris, this variable always shows the                           he
                 name of the device, for example, tr0."
        ::= { smSiaSystemDeviceTokenRingEntry 35 }

smSiaSystemDeviceTokenRingAdapPhysAddr OBJECT-TYPE
        SYNTAX  PhysAddress
        ACCESS  read-only
        STATUS  mandatory
        DESCRIPTION
                "Adapter Physical Address.

                 On AIX4, this variable is not supported for devices
                 that are based on CDLI model."
        ::= { smSiaSystemDeviceTokenRingEntry 36 }

smSiaSystemDeviceTokenRingUpstreamNodeAddr OBJECT-TYPE
        SYNTAX  PhysAddress
        ACCESS  read-only
        STATUS  mandatory
        DESCRIPTION
                "Upstream node address.

                 Not supported on HP-UX and Sun Solaris.

                 On AIX4, this variable is not supported for devices
                 that are based on CDLI model."
        ::= { smSiaSystemDeviceTokenRingEntry 37 }

smSiaSystemDeviceTokenRingUpstreamPhysAddr OBJECT-TYPE
        SYNTAX  PhysAddress
        ACCESS  read-only
        STATUS  mandatory
        DESCRIPTION
                "Upstream Physical Address.

                 Not supported on HP-UX and Sun Solaris.

                 On AIX4, this variable is not supported for devices
                 that are based on CDLI model."
        ::= { smSiaSystemDeviceTokenRingEntry 38 }

smSiaSystemDeviceTokenRingLastPollAddr OBJECT-TYPE
        SYNTAX  PhysAddress
        ACCESS  read-only
        STATUS  mandatory
        DESCRIPTION
                "Last Poll address.

                 Not supported on HP-UX, Sun Solaris and Digital UNIX.

                 On AIX4, this variable is not supported for devices
                 that are based on CDLI model."
        ::= { smSiaSystemDeviceTokenRingEntry 39 }

smSiaSystemDeviceTokenRingAuthorEnv OBJECT-TYPE
        SYNTAX  INTEGER
        ACCESS  read-only
        STATUS  mandatory
        DESCRIPTION
                "Authorized environment.

                 Not supported on HP-UX, Sun Solaris and Digital UNIX.

                 On AIX4, this variable is not supported for devices
                 that are based on CDLI model."
        ::= { smSiaSystemDeviceTokenRingEntry 40 }

smSiaSystemDeviceTokenRingTxAccessPriority OBJECT-TYPE
        SYNTAX  INTEGER
        ACCESS  read-only
        STATUS  mandatory
        DESCRIPTION
                "Transmit priority.

                 Not supported on HP-UX and Sun Solaris.

                 On AIX4, this variable is not supported for devices
                 that are based on CDLI model."
        ::= { smSiaSystemDeviceTokenRingEntry 41 }

smSiaSystemDeviceTokenRingSrcClassAuthor OBJECT-TYPE
        SYNTAX  INTEGER
        ACCESS  read-only
        STATUS  mandatory
        DESCRIPTION
                "Source class authorization.

                 Not supported on HP-UX, Sun Solaris and Digital UNIX.

                 On AIX4, this variable is not supported for devices
                 that are based on CDLI model."
        ::= { smSiaSystemDeviceTokenRingEntry 42 }

smSiaSystemDeviceTokenRingLastAttenCode OBJECT-TYPE
        SYNTAX  INTEGER
        ACCESS  read-only
        STATUS  mandatory
        DESCRIPTION
                "Last attention code.

                 Not supported on HP-UX, Sun Solaris and Digital UNIX.

                 On AIX4, this variable is not supported for devices
                 that are based on CDLI model."
        ::= { smSiaSystemDeviceTokenRingEntry 43 }

smSiaSystemDeviceTokenRingLastSrcAddr OBJECT-TYPE
        SYNTAX  PhysAddress
        ACCESS  read-only
        STATUS  mandatory
        DESCRIPTION
                "Last source address.

                 Not supported on HP-UX, Sun Solaris and Digital UNIX.

                 On AIX4, this variable is not supported for devices
                 that are based on CDLI model."
        ::= { smSiaSystemDeviceTokenRingEntry 44 }

smSiaSystemDeviceTokenRingLastBeaconType OBJECT-TYPE
        SYNTAX  INTEGER
        ACCESS  read-only
        STATUS  mandatory
        DESCRIPTION
                "Last beacon type.

                 Not supported on HP-UX, Sun Solaris and Digital UNIX.

                 On AIX4, this variable is not supported for devices
                 that are based on CDLI model."
        ::= { smSiaSystemDeviceTokenRingEntry 45 }

smSiaSystemDeviceTokenRingLastMajorVector OBJECT-TYPE
        SYNTAX  INTEGER
        ACCESS  read-only
        STATUS  mandatory
        DESCRIPTION
                "Last major vector.

                 Not supported on HP-UX and Sun Solaris.

                 On AIX4, this variable is not supported for devices
                 that are based on CDLI model."
        ::= { smSiaSystemDeviceTokenRingEntry 46 }

smSiaSystemDeviceTokenRingRingStatus OBJECT-TYPE
        SYNTAX  INTEGER
        ACCESS  read-only
        STATUS  mandatory
        DESCRIPTION
                "Ring status.

                 Not supported on Sun Solaris."
        ::= { smSiaSystemDeviceTokenRingEntry 47 }

smSiaSystemDeviceTokenRingSoftErrorTimerVal OBJECT-TYPE
        SYNTAX  INTEGER
        ACCESS  read-only
        STATUS  mandatory
        DESCRIPTION
                "Soft Error timer value.

                 Not supported on HP-UX and Sun Solaris.

                 On AIX4, this variable is not supported for devices
                 that are based on CDLI model."
        ::= { smSiaSystemDeviceTokenRingEntry 48 }

smSiaSystemDeviceTokenRingFrontEndTimerVal OBJECT-TYPE
        SYNTAX  INTEGER
        ACCESS  read-only
        STATUS  mandatory
        DESCRIPTION
                "Front end timer value.

                 Not supported on HP-UX, Sun Solaris and Digital UNIX.

                 On AIX4, this variable is not supported for devices
                 that are based on CDLI model."
        ::= { smSiaSystemDeviceTokenRingEntry 49 }

smSiaSystemDeviceTokenRingMonitorErrorCode OBJECT-TYPE
        SYNTAX  INTEGER
        ACCESS  read-only
        STATUS  mandatory
        DESCRIPTION
                "Monitor error code.

                 Not supported on HP-UX and Sun Solaris.

                 On AIX4, this variable is not supported for devices
                 that are based on CDLI model."
        ::= { smSiaSystemDeviceTokenRingEntry 50 }

smSiaSystemDeviceTokenRingBeaconTxType OBJECT-TYPE
        SYNTAX  INTEGER
        ACCESS  read-only
        STATUS  mandatory
        DESCRIPTION
                "Beacon transmit type.

                 Not supported on HP-UX and Sun Solaris.

                 On AIX4, this variable is not supported for devices
                 that are based on CDLI model."
        ::= { smSiaSystemDeviceTokenRingEntry 51 }

smSiaSystemDeviceTokenRingBeaconRxType OBJECT-TYPE
        SYNTAX  INTEGER
        ACCESS  read-only
        STATUS  mandatory
        DESCRIPTION
                "Beacon Receive type.

                 Not supported on HP-UX and Sun Solaris.

                 On AIX4, this variable is not supported for devices
                 that are based on CDLI model."
 ::= { smSiaSystemDeviceTokenRingEntry 52 }

smSiaSystemDeviceTokenRingFrameCorrSave OBJECT-TYPE
        SYNTAX  INTEGER
        ACCESS  read-only
        STATUS  mandatory
        DESCRIPTION
                "Frame Correlator save.

                 Not supported on HP-UX, Sun Solaris and Digital UNIX.

                 On AIX4, this variable is not supported for devices
                 that are based on CDLI model."
        ::= { smSiaSystemDeviceTokenRingEntry 53 }

smSiaSystemDeviceTokenRingBeaconStationNAUN OBJECT-TYPE
        SYNTAX  PhysAddress
        ACCESS  read-only
        STATUS  mandatory
        DESCRIPTION
                "Beaconing station NAUN.

                 Not supported on HP-UX, Sun Solaris and Digital UNIX.

                 On AIX4, this variable is not supported for devices
                 that are based on CDLI model."
        ::= { smSiaSystemDeviceTokenRingEntry 54 }

smSiaSystemDeviceTokenRingBeaconStationPhysAddr OBJECT-TYPE
        SYNTAX  PhysAddress
        ACCESS  read-only
        STATUS  mandatory
        DESCRIPTION
                "Beaconing station physical address.

                 Not supported on HP-UX and Sun Solaris.

                 On AIX4, this variable is not supported for devices
                 that are based on CDLI model."
        ::= { smSiaSystemDeviceTokenRingEntry 55 }

smSiaSystemDeviceTokenRingClear OBJECT-TYPE
        SYNTAX  INTEGER {
                normal(1),
                clear(2)
                }
        ACCESS  read-write
        STATUS  mandatory
        DESCRIPTION
                "Set to clear clearable statistics

                 Not supported on AIX and Digital UNIX."
        ::= { smSiaSystemDeviceTokenRingEntry 56 }


--
-- The Ethernet table
--

smSiaSystemDeviceEthernetInstalled OBJECT-TYPE
        SYNTAX  INTEGER
        ACCESS  read-only
        STATUS  mandatory
        DESCRIPTION
                "The number of devices installed."
        ::= { smSiaSystemDeviceEthernet 1 }

smSiaSystemDeviceEthernetTable OBJECT-TYPE
        SYNTAX  SEQUENCE OF SmSiaSystemDeviceEthernetEntry
        ACCESS  not-accessible
        STATUS  mandatory
        DESCRIPTION
                "Adapter table."
        ::= { smSiaSystemDeviceEthernet 2 }

smSiaSystemDeviceEthernetEntry OBJECT-TYPE
        SYNTAX  SmSiaSystemDeviceEthernetEntry
        ACCESS  not-accessible
        STATUS  mandatory
        DESCRIPTION
                "Each entry contains objects for a particular device"
	INDEX { smSiaSystemDeviceEthernetNumber }
        ::= { smSiaSystemDeviceEthernetTable 1 }

SmSiaSystemDeviceEthernetEntry ::= SEQUENCE {
    smSiaSystemDeviceEthernetNumber
        INTEGER,
    smSiaSystemDeviceEthernetHardwareAddress
        PhysAddress,
    smSiaSystemDeviceEthernetCurrentAddress
        PhysAddress,
    smSiaSystemDeviceEthernetReceiveDataOffset
        INTEGER,
    smSiaSystemDeviceEthernetBroadwrap
        INTEGER,
    smSiaSystemDeviceEthernetTxByteMcnt
        Counter,
    smSiaSystemDeviceEthernetTxByteLcnt
        Counter,
    smSiaSystemDeviceEthernetRxByteMcnt
        Counter,
    smSiaSystemDeviceEthernetRxByteLcnt
        Counter,
    smSiaSystemDeviceEthernetTxFrameMcnt
        Counter,
    smSiaSystemDeviceEthernetTxFrameLcnt
        Counter,
    smSiaSystemDeviceEthernetRxFrameMcnt
        Counter,
    smSiaSystemDeviceEthernetRxFrameLcnt
        Counter,
    smSiaSystemDeviceEthernetTxErrCnt
        Counter,
    smSiaSystemDeviceEthernetRxErrCnt
        Counter,
    smSiaSystemDeviceEthernetNidTblHigh
        INTEGER,
    smSiaSystemDeviceEthernetTxQueHigh
        Gauge,
    smSiaSystemDeviceEthernetRxQueHigh
        Gauge,
    smSiaSystemDeviceEthernetStaQueHigh
        Gauge,
    smSiaSystemDeviceEthernetIntrLost
        Counter,
    smSiaSystemDeviceEthernetWdtLost
        Counter,
    smSiaSystemDeviceEthernetTimoLost
        Counter,
    smSiaSystemDeviceEthernetStaQueOverflow
        Counter,
    smSiaSystemDeviceEthernetRxQueOverflow
        Counter,
    smSiaSystemDeviceEthernetRxQueNoMbuf
        Counter,
    smSiaSystemDeviceEthernetRxQueNoMbufExt
        Counter,
    smSiaSystemDeviceEthernetTxIntrCnt
        Counter,
    smSiaSystemDeviceEthernetRxIntrCnt
        Counter,
    smSiaSystemDeviceEthernetCRCErr
        Counter,
    smSiaSystemDeviceEthernetAlignErr
        Counter,
    smSiaSystemDeviceEthernetOverrun
        Counter,
    smSiaSystemDeviceEthernetTooShort
        Counter,
    smSiaSystemDeviceEthernetTooLong
        Counter,
    smSiaSystemDeviceEthernetNoResources
        Counter,
    smSiaSystemDeviceEthernetPktDiscard
        Counter,
    smSiaSystemDeviceEthernetMaxCollision
        Counter,
    smSiaSystemDeviceEthernetLateCollision
        Counter,
    smSiaSystemDeviceEthernetCarrierLost
        Counter,
    smSiaSystemDeviceEthernetUnderrun
        Counter,
    smSiaSystemDeviceEthernetCTSLost
        Counter,
    smSiaSystemDeviceEthernetTxTimeouts
        Counter,
    smSiaSystemDeviceEthernetParErrCnt
        Counter,
    smSiaSystemDeviceEthernetDiagOverflow
        Counter,
    smSiaSystemDeviceEthernetExecOverflow
        Counter,
    smSiaSystemDeviceEthernetExecCmdErrors
        Counter,
    smSiaSystemDeviceEthernetHostRecEol
        Counter,
    smSiaSystemDeviceEthernetAdptRecEol
        Counter,
    smSiaSystemDeviceEthernetHostRecPkt
        Counter,
    smSiaSystemDeviceEthernetAdptRecPkt
        Counter,
    smSiaSystemDeviceEthernetStartRxCmd
        Counter,
    smSiaSystemDeviceEthernetStartRxDmaTimeouts
        Counter,
    smSiaSystemDeviceEthernetVPD
        DisplayString,
    smSiaSystemDeviceEthernetClear
        INTEGER
}

smSiaSystemDeviceEthernetNumber OBJECT-TYPE
        SYNTAX  INTEGER
        ACCESS  read-only
        STATUS  mandatory
        DESCRIPTION
                "Adapter number.  On Sun Solaris, there can be more than one
                 kind of Ethernet interface on a system; both ie and le can
                 be on the same system.  The Ethernet number does not reflect
                 the device unit number of the interface device; it is just a
                 row index on the MIB table."
        ::= { smSiaSystemDeviceEthernetEntry 1 }

smSiaSystemDeviceEthernetHardwareAddress OBJECT-TYPE
        SYNTAX  PhysAddress
        ACCESS  read-only
        STATUS  mandatory
        DESCRIPTION
                "Burned-in MAC Address.  On Sun Solaris 2.x, the Ethernet
                 interface does not have its own built-in hardware
                 address; instead, all network interfaces use the MAC
                 address in the idprom on the motherboard.  This variable
                 is the same as smSiaSystemDeviceEthernetCurrentAddress.

                 For AIX4 devices supporting CDLI model, this variable is
                 the same as the smSiaSystemDeviceEthernetCurrentAddress."
        ::= { smSiaSystemDeviceEthernetEntry 2 }

smSiaSystemDeviceEthernetCurrentAddress OBJECT-TYPE
        SYNTAX  PhysAddress
        ACCESS  read-only
        STATUS  mandatory
        DESCRIPTION
                "Current MAC Address

                 Not supported on Digital UNIX."
        ::= { smSiaSystemDeviceEthernetEntry 3 }

smSiaSystemDeviceEthernetReceiveDataOffset OBJECT-TYPE
        SYNTAX  INTEGER
        ACCESS  read-only
        STATUS  mandatory
        DESCRIPTION
                "Receive Data transfer Offset

                 Not supported on HP-UX, Sun Solaris and Digital UNIX.

                 On AIX4, this variable is not supported for devices
                 that are based on CDLI model."
        ::= { smSiaSystemDeviceEthernetEntry 4 }

smSiaSystemDeviceEthernetBroadwrap OBJECT-TYPE
        SYNTAX  INTEGER {
                false(1),  -- not supported
                true(2)    -- supported
                }
        ACCESS  read-only
        STATUS  mandatory
        DESCRIPTION
                "Supports broadcast wrap of data.

                 Not supported on HP-UX, Sun Solaris and Digital UNIX.

                 On AIX4, this variable is not supported for devices
                 that are based on CDLI model."
        ::= { smSiaSystemDeviceEthernetEntry 5 }

smSiaSystemDeviceEthernetTxByteMcnt OBJECT-TYPE
        SYNTAX  Counter
        ACCESS  read-only
        STATUS  mandatory
        DESCRIPTION
                "Most significant bits of successfully transmitted byte count.

                 Not supported on HP-UX or Sun Solaris."
        ::= { smSiaSystemDeviceEthernetEntry 6 }

smSiaSystemDeviceEthernetTxByteLcnt OBJECT-TYPE
        SYNTAX  Counter
        ACCESS  read-only
        STATUS  mandatory
        DESCRIPTION
                "Least significant bits of successfully transmitted byte count.

                 Not supported on HP-UX or Sun Solaris."
        ::= { smSiaSystemDeviceEthernetEntry 7 }

smSiaSystemDeviceEthernetRxByteMcnt OBJECT-TYPE
        SYNTAX  Counter
        ACCESS  read-only
        STATUS  mandatory
        DESCRIPTION
                "Most significant bits of successfully received byte count.

                 Not supported on HP-UX or Sun Solaris."
        ::= { smSiaSystemDeviceEthernetEntry 8 }

smSiaSystemDeviceEthernetRxByteLcnt OBJECT-TYPE
        SYNTAX  Counter
        ACCESS  read-only
        STATUS  mandatory
        DESCRIPTION
                "Least significant bits of successfully received byte count.

                 Not supported on HP-UX or Sun Solaris."
        ::= { smSiaSystemDeviceEthernetEntry 9 }

smSiaSystemDeviceEthernetTxFrameMcnt OBJECT-TYPE
        SYNTAX  Counter
        ACCESS  read-only
        STATUS  mandatory
        DESCRIPTION
                "Most significant bits of successfully transmitted byte count."
        ::= { smSiaSystemDeviceEthernetEntry 10 }

smSiaSystemDeviceEthernetTxFrameLcnt OBJECT-TYPE
        SYNTAX  Counter
        ACCESS  read-only
        STATUS  mandatory
        DESCRIPTION
                "Least significant bits of successfully transmitted byte count."
        ::= { smSiaSystemDeviceEthernetEntry 11 }

smSiaSystemDeviceEthernetRxFrameMcnt OBJECT-TYPE
        SYNTAX  Counter
        ACCESS  read-only
        STATUS  mandatory
        DESCRIPTION
                "Most significant bits of successfully received byte count."
        ::= { smSiaSystemDeviceEthernetEntry 12 }

smSiaSystemDeviceEthernetRxFrameLcnt OBJECT-TYPE
        SYNTAX  Counter
        ACCESS  read-only
        STATUS  mandatory
        DESCRIPTION
                "Least significant bits of successfully received byte count."
        ::= { smSiaSystemDeviceEthernetEntry 13 }

smSiaSystemDeviceEthernetTxErrCnt OBJECT-TYPE
        SYNTAX  Counter
        ACCESS  read-only
        STATUS  mandatory
        DESCRIPTION
                "Frame transmit error count

                 Not supported on Digital UNIX."
        ::= { smSiaSystemDeviceEthernetEntry 14 }

smSiaSystemDeviceEthernetRxErrCnt OBJECT-TYPE
        SYNTAX  Counter
        ACCESS  read-only
        STATUS  mandatory
        DESCRIPTION
                "Frame receive error count

                 Not supported on Digital UNIX."
        ::= { smSiaSystemDeviceEthernetEntry 15 }

smSiaSystemDeviceEthernetNidTblHigh OBJECT-TYPE
        SYNTAX  INTEGER
        ACCESS  read-only
        STATUS  mandatory
        DESCRIPTION
                "Maximum netids in use

                 Not supported on HP-UX, Sun Solaris and Digital UNIX.

                 On AIX4, this variable is not supported for devices
                 that are based on CDLI model."
        ::= { smSiaSystemDeviceEthernetEntry 16 }

smSiaSystemDeviceEthernetTxQueHigh OBJECT-TYPE
        SYNTAX  Gauge
        ACCESS  read-only
        STATUS  mandatory
        DESCRIPTION
                "Maximum transmits ever queued for adapter

                 Not supported on HP-UX, Sun Solaris and Digital UNIX."
        ::= { smSiaSystemDeviceEthernetEntry 17 }

smSiaSystemDeviceEthernetRxQueHigh OBJECT-TYPE
        SYNTAX  Gauge
        ACCESS  read-only
        STATUS  mandatory
        DESCRIPTION
                "Maximum received ever queued for any open

                 Not supported on HP-UX, Sun Solaris and Digital UNIX.

                 On AIX4, this variable is not supported for devices
                 that are based on CDLI model."
        ::= { smSiaSystemDeviceEthernetEntry 18 }

smSiaSystemDeviceEthernetStaQueHigh OBJECT-TYPE
        SYNTAX  Gauge
        ACCESS  read-only
        STATUS  mandatory
        DESCRIPTION
                "Maximum status blocks queued for any open

                 Not supported on HP-UX, Sun Solaris and Digital UNIX.

                 On AIX4, this variable is not supported for devices
                 that are based on CDLI model."
        ::= { smSiaSystemDeviceEthernetEntry 19 }

smSiaSystemDeviceEthernetIntrLost OBJECT-TYPE
        SYNTAX  Counter
        ACCESS  read-only
        STATUS  mandatory
        DESCRIPTION
                "Interrupts lost

                 Not supported on HP-UX, Sun Solaris and Digital UNIX.

                 On AIX4, this variable is not supported for devices
                 that are based on CDLI model."
        ::= { smSiaSystemDeviceEthernetEntry 20 }

smSiaSystemDeviceEthernetWdtLost OBJECT-TYPE
        SYNTAX  Counter
        ACCESS  read-only
        STATUS  mandatory
        DESCRIPTION
                "Wdt Interrupts lost

                 Not supported on HP-UX, Sun Solaris and Digital UNIX.

                 On AIX4, this variable is not supported for devices
                 that are based on CDLI model."
        ::= { smSiaSystemDeviceEthernetEntry 21 }

smSiaSystemDeviceEthernetTimoLost OBJECT-TYPE
        SYNTAX  Counter
        ACCESS  read-only
        STATUS  mandatory
        DESCRIPTION
                "Timeout Interrupts lost

                 Not supported on HP-UX, Sun Solaris and Digital UNIX.

                 On AIX4, this variable is not supported for devices
                 that are based on CDLI model."
        ::= { smSiaSystemDeviceEthernetEntry 22 }

smSiaSystemDeviceEthernetStaQueOverflow OBJECT-TYPE
        SYNTAX  Counter
        ACCESS  read-only
        STATUS  mandatory
        DESCRIPTION
                "Status lost due to queue overflow

                 Supported on Sun Solaris 2.4 only.
                 Not supported on HP-UX or Digital UNIX.

                 On AIX4, this variable is not supported for devices
                 that are based on CDLI model."
        ::= { smSiaSystemDeviceEthernetEntry 23 }

smSiaSystemDeviceEthernetRxQueOverflow OBJECT-TYPE
        SYNTAX  Counter
        ACCESS  read-only
        STATUS  mandatory
        DESCRIPTION
                "Packet lost due to queue overflow

                 Not supported on HP-UX, Sun Solaris and Digital UNIX.

                 On AIX4, this variable is not supported for devices
                 that are based on CDLI model."
        ::= { smSiaSystemDeviceEthernetEntry 24 }

smSiaSystemDeviceEthernetRxQueNoMbuf OBJECT-TYPE
        SYNTAX  Counter
        ACCESS  read-only
        STATUS  mandatory
        DESCRIPTION
                "Packet lost due to no mbufs

                 Not supported on HP-UX, Sun Solaris and Digital UNIX.

                 On AIX4, this variable is not supported for devices
                 that are based on CDLI model."
        ::= { smSiaSystemDeviceEthernetEntry 25 }

smSiaSystemDeviceEthernetRxQueNoMbufExt OBJECT-TYPE
        SYNTAX  Counter
        ACCESS  read-only
        STATUS  mandatory
        DESCRIPTION
                "Packet lost due to no mbuf extensions

                 Not supported on HP-UX, Sun Solaris and Digital UNIX.

                 On AIX4, this variable is not supported for devices
                 that are based on CDLI model."
        ::= { smSiaSystemDeviceEthernetEntry 26 }

smSiaSystemDeviceEthernetTxIntrCnt OBJECT-TYPE
        SYNTAX  Counter
        ACCESS  read-only
        STATUS  mandatory
        DESCRIPTION
                "Transmit interrupt count

                 Not supported on HP-UX, Sun Solaris and Digital UNIX."
        ::= { smSiaSystemDeviceEthernetEntry 27 }

smSiaSystemDeviceEthernetRxIntrCnt OBJECT-TYPE
        SYNTAX  Counter
        ACCESS  read-only
        STATUS  mandatory
        DESCRIPTION
                "Receive interrupt count

                 Not supported on HP-UX, Sun Solaris and Digital UNIX."
        ::= { smSiaSystemDeviceEthernetEntry 28 }

smSiaSystemDeviceEthernetCRCErr OBJECT-TYPE
        SYNTAX  Counter
        ACCESS  read-only
        STATUS  mandatory
        DESCRIPTION
                "CRC Errors

                 Not supported on Digital UNIX."
        ::= { smSiaSystemDeviceEthernetEntry 29 }

smSiaSystemDeviceEthernetAlignErr OBJECT-TYPE
        SYNTAX  Counter
        ACCESS  read-only
        STATUS  mandatory
        DESCRIPTION
                "Alignment Errors.  On Sun Solaris, this variable is supported
                 on interface ie, not on interface le.

                 Not supported on Digital UNIX."
        ::= { smSiaSystemDeviceEthernetEntry 30 }

smSiaSystemDeviceEthernetOverrun OBJECT-TYPE
        SYNTAX  Counter
        ACCESS  read-only
        STATUS  mandatory
        DESCRIPTION
                "Overrun Errors.

                 On Sun Solaris 2.x, this variable is supported
                 on interface ie, not on interface le.
                 Not supported on HP-UX."
        ::= { smSiaSystemDeviceEthernetEntry 31 }

smSiaSystemDeviceEthernetTooShort OBJECT-TYPE
        SYNTAX  Counter
        ACCESS  read-only
        STATUS  mandatory
        DESCRIPTION
                "Too short Errors

                 Not supported on HP-UX, Sun Solaris and Digital UNIX."
        ::= { smSiaSystemDeviceEthernetEntry 32 }

smSiaSystemDeviceEthernetTooLong OBJECT-TYPE
        SYNTAX  Counter
        ACCESS  read-only
        STATUS  mandatory
        DESCRIPTION
                "Too long Errors.

                 Not supported on Sun Solaris."
        ::= { smSiaSystemDeviceEthernetEntry 33 }

smSiaSystemDeviceEthernetNoResources OBJECT-TYPE
        SYNTAX  Counter
        ACCESS  read-only
        STATUS  mandatory
        DESCRIPTION
                "Out of resource errors.

                 Not supported on Sun Solaris 2.x or Digital UNIX."
        ::= { smSiaSystemDeviceEthernetEntry 34 }

smSiaSystemDeviceEthernetPktDiscard OBJECT-TYPE
        SYNTAX  Counter
        ACCESS  read-only
        STATUS  mandatory
        DESCRIPTION
                "Packets discarded.

                 Not supported on Sun Solaris."
        ::= { smSiaSystemDeviceEthernetEntry 35 }

smSiaSystemDeviceEthernetMaxCollision OBJECT-TYPE
        SYNTAX  Counter
        ACCESS  read-only
        STATUS  mandatory
        DESCRIPTION
                "Maximum collisions"
        ::= { smSiaSystemDeviceEthernetEntry 36 }

smSiaSystemDeviceEthernetLateCollision OBJECT-TYPE
        SYNTAX  Counter
        ACCESS  read-only
        STATUS  mandatory
        DESCRIPTION
                "Collisions after slot time elapsed.

                 On Sun Solaris, this variable is supported on interface
                 le, not on interface ie.

                 Not supported on Digital UNIX."
        ::= { smSiaSystemDeviceEthernetEntry 37 }

smSiaSystemDeviceEthernetCarrierLost OBJECT-TYPE
        SYNTAX  Counter
        ACCESS  read-only
        STATUS  mandatory
        DESCRIPTION
                "Carrier lost errors"
        ::= { smSiaSystemDeviceEthernetEntry 38 }

smSiaSystemDeviceEthernetUnderrun OBJECT-TYPE
        SYNTAX  Counter
        ACCESS  read-only
        STATUS  mandatory
        DESCRIPTION
                "Underrun errors.

                 On Sun Solaris 2.x, this variable is supported
                 on interface ie, not on interface le.
                 Not supported on HP-UX or Digital UNIX."
        ::= { smSiaSystemDeviceEthernetEntry 39 }

smSiaSystemDeviceEthernetCTSLost OBJECT-TYPE
        SYNTAX  Counter
        ACCESS  read-only
        STATUS  mandatory
        DESCRIPTION
                "Clear to send lost errors.

                 Not supported on HP-UX, Sun Solaris 2.x or Digital UNIX."
        ::= { smSiaSystemDeviceEthernetEntry 40 }

smSiaSystemDeviceEthernetTxTimeouts OBJECT-TYPE
        SYNTAX  Counter
        ACCESS  read-only
        STATUS  mandatory
        DESCRIPTION
                "Transmit Timeouts

                 Not supported on HP-UX or Digital UNIX."
        ::= { smSiaSystemDeviceEthernetEntry 41 }

smSiaSystemDeviceEthernetParErrCnt OBJECT-TYPE
        SYNTAX  Counter
        ACCESS  read-only
        STATUS  mandatory
        DESCRIPTION
                "Parity errors

                 Not supported on HP-UX, Sun Solaris or Digital UNIX.

                 On AIX4, this variable is not supported for devices
                 that are based on CDLI model."
        ::= { smSiaSystemDeviceEthernetEntry 42 }

smSiaSystemDeviceEthernetDiagOverflow OBJECT-TYPE
        SYNTAX  Counter
        ACCESS  read-only
        STATUS  mandatory
        DESCRIPTION
                "Diagnostic overflow.

                 Not supported on HP-UX, Sun Solaris and Digital UNIX.

                 On AIX4, this variable is not supported for devices
                 that are based on CDLI model."
        ::= { smSiaSystemDeviceEthernetEntry 43 }

smSiaSystemDeviceEthernetExecOverflow OBJECT-TYPE
        SYNTAX  Counter
        ACCESS  read-only
        STATUS  mandatory
        DESCRIPTION
                "Execute queue overflows.

                 Not supported on HP-UX, Sun Solaris and Digital UNIX.

                 On AIX4, this variable is not supported for devices
                 that are based on CDLI model."
        ::= { smSiaSystemDeviceEthernetEntry 44 }

smSiaSystemDeviceEthernetExecCmdErrors OBJECT-TYPE
        SYNTAX  Counter
        ACCESS  read-only
        STATUS  mandatory
        DESCRIPTION
                "Execute command errors.

                 Not supported on HP-UX, Sun Solaris and Digital UNIX.

                 On AIX4, this variable is not supported for devices
                 that are based on CDLI model."
        ::= { smSiaSystemDeviceEthernetEntry 45 }

smSiaSystemDeviceEthernetHostRecEol OBJECT-TYPE
        SYNTAX  Counter
        ACCESS  read-only
        STATUS  mandatory
        DESCRIPTION
                "Host received end of list.

                 Not supported on HP-UX, Sun Solaris and Digital UNIX.

                 On AIX4, this variable is not supported for devices
                 that are based on CDLI model."
        ::= { smSiaSystemDeviceEthernetEntry 46 }

smSiaSystemDeviceEthernetAdptRecEol OBJECT-TYPE
        SYNTAX  Counter
        ACCESS  read-only
        STATUS  mandatory
        DESCRIPTION
                "Adapter received end of list.

                 Not supported on HP-UX, Sun Solaris and Digital UNIX.

                 On AIX4, this variable is not supported for devices
                 that are based on CDLI model."
        ::= { smSiaSystemDeviceEthernetEntry 47 }

smSiaSystemDeviceEthernetHostRecPkt OBJECT-TYPE
        SYNTAX  Counter
        ACCESS  read-only
        STATUS  mandatory
        DESCRIPTION
                "Packets host actually received from adapter.

                 Not supported on HP-UX, Sun Solaris and Digital UNIX.

                 On AIX4, this variable is not supported for devices
                 that are based on CDLI model."
        ::= { smSiaSystemDeviceEthernetEntry 48 }

smSiaSystemDeviceEthernetAdptRecPkt OBJECT-TYPE
        SYNTAX  Counter
        ACCESS  read-only
        STATUS  mandatory
        DESCRIPTION
                "Packets to be delivered to host.

                 Not supported on HP-UX and Sun Solaris.

                 On AIX4, this variable is not supported for devices
                 that are based on CDLI model."
        ::= { smSiaSystemDeviceEthernetEntry 49 }

smSiaSystemDeviceEthernetStartRxCmd OBJECT-TYPE
        SYNTAX  Counter
        ACCESS  read-only
        STATUS  mandatory
        DESCRIPTION
                "Start receptions commands issued to adapter.

                 Not supported on HP-UX, Sun Solaris and Digital UNIX."
        ::= { smSiaSystemDeviceEthernetEntry 50 }

smSiaSystemDeviceEthernetStartRxDmaTimeouts OBJECT-TYPE
        SYNTAX  Counter
        ACCESS  read-only
        STATUS  mandatory
        DESCRIPTION
                "DMA timeouts.

                 Not supported on HP-UX, Sun Solaris and Digital UNIX.

                 On AIX4, this variable is not supported for devices
                 that are based on CDLI model."
        ::= { smSiaSystemDeviceEthernetEntry 51 }

smSiaSystemDeviceEthernetVPD OBJECT-TYPE
        SYNTAX  DisplayString
        ACCESS  read-only
        STATUS  mandatory
        DESCRIPTION
                "Vital Product Data from adapter.

                 Not supported on HP-UX, Sun Solaris 2.x and Digital UNIX."
         ::= { smSiaSystemDeviceEthernetEntry 52 }

smSiaSystemDeviceEthernetClear OBJECT-TYPE
        SYNTAX  INTEGER {
                normal(1),
                clear(2)
                }
        ACCESS  read-write
        STATUS  mandatory
        DESCRIPTION
                "Set to clear to clear clearable statistics.

                 Not supported on AIX and Digital UNIX."
        ::= { smSiaSystemDeviceEthernetEntry 53 }


--
-- The X25 table
--

smSiaSystemDeviceX25Installed OBJECT-TYPE
        SYNTAX  INTEGER
        ACCESS  read-only
        STATUS  mandatory
        DESCRIPTION
                "The number of devices installed.

                 Not supported on HP-UX, Sun Solaris and Digital UNIX."
        ::= { smSiaSystemDeviceX25 1 }

smSiaSystemDeviceX25Table OBJECT-TYPE
        SYNTAX  SEQUENCE OF SmSiaSystemDeviceX25Entry
        ACCESS  not-accessible
        STATUS  mandatory
        DESCRIPTION
                "Adapter table.

                 Not supported on HP-UX, Sun Solaris and Digital UNIX."
        ::= { smSiaSystemDeviceX25 2 }

smSiaSystemDeviceX25Entry OBJECT-TYPE
        SYNTAX  SmSiaSystemDeviceX25Entry
        ACCESS  not-accessible
        STATUS  mandatory
        DESCRIPTION
                "Each entry contains objects for a particular device

                 Not supported on HP-UX, Sun Solaris and Digital UNIX."
	INDEX { smSiaSystemDeviceX25Number }
        ::= { smSiaSystemDeviceX25Table 1 }

SmSiaSystemDeviceX25Entry ::= SEQUENCE {
    smSiaSystemDeviceX25Number
        INTEGER,
    smSiaSystemDeviceX25Address
        DisplayString,
    smSiaSystemDeviceX25SupportLevel
        INTEGER,
    smSiaSystemDeviceX25SupportedFacilities
        INTEGER,
    smSiaSystemDeviceX25NetworkId
        PhysAddress,
    smSiaSystemDeviceX25MaxTxPacketSize
        INTEGER,
    smSiaSystemDeviceX25MaxRxPacketSize
        INTEGER,
    smSiaSystemDeviceX25DefaultSvcTxPacketSize
        INTEGER,
    smSiaSystemDeviceX25DefaultSvcRxPacketSize
        INTEGER,
    smSiaSystemDeviceX25ReceiveDataTransferOffset
        INTEGER,
    smSiaSystemDeviceX25MemoryWindowSize
        INTEGER,
    smSiaSystemDeviceX25TxByteMcnt
        Counter,
    smSiaSystemDeviceX25TxByteLcnt
        Counter,
    smSiaSystemDeviceX25RxByteMcnt
        Counter,
    smSiaSystemDeviceX25RxByteLcnt
        Counter,
    smSiaSystemDeviceX25TxFrameMcnt
        Counter,
    smSiaSystemDeviceX25TxFrameLcnt
        Counter,
    smSiaSystemDeviceX25RxFrameMcnt
        Counter,
    smSiaSystemDeviceX25RxFrameLcnt
        Counter,
    smSiaSystemDeviceX25TxErrCnt
        Counter,
    smSiaSystemDeviceX25RxErrCnt
        Counter,
    smSiaSystemDeviceX25NidTblHigh
        INTEGER,
    smSiaSystemDeviceX25TxQueHigh
        Gauge,
    smSiaSystemDeviceX25RxQueHigh
        Gauge,
    smSiaSystemDeviceX25StaQueHigh
        Gauge,
    smSiaSystemDeviceX25IgnoredFTx
        Counter,
    smSiaSystemDeviceX25RrFTx
        Counter,
    smSiaSystemDeviceX25RnrFTx
        Counter,
    smSiaSystemDeviceX25RejFTx
        Counter,
    smSiaSystemDeviceX25InfoFTx
        Counter,
    smSiaSystemDeviceX25SabmFTx
        Counter,
    smSiaSystemDeviceX25SarmDmFTx
        Counter,
    smSiaSystemDeviceX25DiscFTx
        Counter,
    smSiaSystemDeviceX25UaFTx
        Counter,
    smSiaSystemDeviceX25FrmrFTx
        Counter,
    smSiaSystemDeviceX25BadNrFTx
        Counter,
    smSiaSystemDeviceX25UnknownFTx
        Counter,
    smSiaSystemDeviceX25XidFTx
        Counter,
    smSiaSystemDeviceX25BadLengthFTx
        Counter,
    smSiaSystemDeviceX25T1Expirations
        Counter,
    smSiaSystemDeviceX25Lvl2Connects
        Counter,
    smSiaSystemDeviceX25Lvl2Disconnects
        Counter,
    smSiaSystemDeviceX25CarrierLoss
        Counter,
    smSiaSystemDeviceX25ConnectTime
        TimeTicks,
    smSiaSystemDeviceX25T4Expirations
        Counter,
    smSiaSystemDeviceX25T4N2Times
        Counter,
    smSiaSystemDeviceX25IgnoredFRx
        Counter,
    smSiaSystemDeviceX25RrFRx
        Counter,
    smSiaSystemDeviceX25RnrFRx
        Counter,
    smSiaSystemDeviceX25RejFRx
        Counter,
    smSiaSystemDeviceX25InfoFRx
        Counter,
    smSiaSystemDeviceX25SabmFRx
        Counter,
    smSiaSystemDeviceX25SarmDmFRx
        Counter,
    smSiaSystemDeviceX25DiscFRx
        Counter,
    smSiaSystemDeviceX25UaFRx
        Counter,
    smSiaSystemDeviceX25FrmrFRx
        Counter,
    smSiaSystemDeviceX25BadNrFRx
        Counter,
    smSiaSystemDeviceX25UnknownFRx
        Counter,
    smSiaSystemDeviceX25XidFRx
        Counter,
    smSiaSystemDeviceX25BadLengthFRx
        Counter,
    smSiaSystemDeviceX25DataPTx
        Counter,
    smSiaSystemDeviceX25RrPTx
        Counter,
    smSiaSystemDeviceX25RnrPTx
        Counter,
    smSiaSystemDeviceX25InterruptPTx
        Counter,
    smSiaSystemDeviceX25InterruptConfirmPTx
        Counter,
    smSiaSystemDeviceX25CallRequestPTx
        Counter,
    smSiaSystemDeviceX25CallAcceptPTx
        Counter,
    smSiaSystemDeviceX25ClearRequestPTx
        Counter,
    smSiaSystemDeviceX25ClearConfirmPTx
        Counter,
    smSiaSystemDeviceX25ResetRequestPTx
        Counter,
    smSiaSystemDeviceX25ResetConfirmPTx
        Counter,
    smSiaSystemDeviceX25DiagnosticPTx
        Counter,
    smSiaSystemDeviceX25RegistrationPTx
        Counter,
    smSiaSystemDeviceX25RegistrationConfirmPTx
        Counter,
    smSiaSystemDeviceX25RestartPTx
        Counter,
    smSiaSystemDeviceX25RestartConfirmPTx
        Counter,
    smSiaSystemDeviceX25ErrorPTx
        Counter,
    smSiaSystemDeviceX25T20Expirations
        Counter,
    smSiaSystemDeviceX25T21Expirations
        Counter,
    smSiaSystemDeviceX25T22Expirations
        Counter,
    smSiaSystemDeviceX25T23Expirations
        Counter,
    smSiaSystemDeviceX25VcEstablishments
        Counter,
    smSiaSystemDeviceX25T24Expirations
        Counter,
    smSiaSystemDeviceX25T25Expirations
        Counter,
    smSiaSystemDeviceX25T26Expirations
        Counter,
    smSiaSystemDeviceX25T28Expirations
        Counter,
    smSiaSystemDeviceX25DataPRx
        Counter,
    smSiaSystemDeviceX25RrPRx
        Counter,
    smSiaSystemDeviceX25RnrPRx
        Counter,
    smSiaSystemDeviceX25InterruptPRx
        Counter,
    smSiaSystemDeviceX25InterruptConfirmPRx
        Counter,
    smSiaSystemDeviceX25IncomingCallPRx
        Counter,
    smSiaSystemDeviceX25CallConnectedPRx
        Counter,
    smSiaSystemDeviceX25ClearIndicationPRx
        Counter,
    smSiaSystemDeviceX25ClearConfirmPRx
        Counter,
    smSiaSystemDeviceX25ResetIndicationPRx
        Counter,
    smSiaSystemDeviceX25ResetConfirmPRx
        Counter,
    smSiaSystemDeviceX25DiagnosticPRx
        Counter,
    smSiaSystemDeviceX25RegistrationPRx
        Counter,
    smSiaSystemDeviceX25RegistrationConfirmPRx
        Counter,
    smSiaSystemDeviceX25RestartPRx
        Counter,
    smSiaSystemDeviceX25RestartConfirmPRx
        Counter,
    smSiaSystemDeviceX25TxUnknownSize
        Counter,
    smSiaSystemDeviceX25TxReserved1
        Counter,
    smSiaSystemDeviceX25TxReserved2
        Counter,
    smSiaSystemDeviceX25TxReserved3
        Counter,
    smSiaSystemDeviceX25Tx0x15
        Counter,
    smSiaSystemDeviceX25Tx16x31
        Counter,
    smSiaSystemDeviceX25Tx32x63
        Counter,
    smSiaSystemDeviceX25Tx64x127
        Counter,
    smSiaSystemDeviceX25Tx128x255
        Counter,
    smSiaSystemDeviceX25Tx256x511
        Counter,
    smSiaSystemDeviceX25Tx512x1023
        Counter,
    smSiaSystemDeviceX25Tx1024x2047
        Counter,
    smSiaSystemDeviceX25Tx2048x4095
        Counter,
    smSiaSystemDeviceX25TxReserved13
        Counter,
    smSiaSystemDeviceX25TxReserved14
        Counter,
    smSiaSystemDeviceX25TxReserved15
        Counter,
    smSiaSystemDeviceX25TxTotalPackets
        Counter,
    smSiaSystemDeviceX25RxUnknownSize
        Counter,
    smSiaSystemDeviceX25RxReserved1
        Counter,
    smSiaSystemDeviceX25RxReserved2
        Counter,
    smSiaSystemDeviceX25RxReserved3
        Counter,
    smSiaSystemDeviceX25Rx0x15
        Counter,
    smSiaSystemDeviceX25Rx16x31
        Counter,
    smSiaSystemDeviceX25Rx32x63
        Counter,
    smSiaSystemDeviceX25Rx64x127
        Counter,
    smSiaSystemDeviceX25Rx128x255
        Counter,
    smSiaSystemDeviceX25Rx256x511
        Counter,
    smSiaSystemDeviceX25Rx512x1023
        Counter,
    smSiaSystemDeviceX25Rx1024x2047
        Counter,
    smSiaSystemDeviceX25Rx2048x4095
        Counter,
    smSiaSystemDeviceX25RxReserved13
        Counter,
    smSiaSystemDeviceX25RxReserved14
        Counter,
    smSiaSystemDeviceX25RxReserved15
        Counter,
    smSiaSystemDeviceX25RxTotalPackets
        Counter,
    smSiaSystemDeviceX25Clear
        INTEGER
}

smSiaSystemDeviceX25Number OBJECT-TYPE
        SYNTAX  INTEGER
        ACCESS  read-only
        STATUS  mandatory
        DESCRIPTION
                "smSiaSystemDeviceX25Number

                 Not supported on HP-UX, Sun Solaris and Digital UNIX."
        ::= { smSiaSystemDeviceX25Entry 1 }

smSiaSystemDeviceX25Address OBJECT-TYPE
        SYNTAX  DisplayString
        ACCESS  read-only
        STATUS  mandatory
        DESCRIPTION
                "smSiaSystemDeviceX25Address

                 Not supported on HP-UX, Sun Solaris and Digital UNIX."
        ::= { smSiaSystemDeviceX25Entry 2 }

smSiaSystemDeviceX25SupportLevel OBJECT-TYPE
        SYNTAX  INTEGER
        ACCESS  read-only
        STATUS  mandatory
        DESCRIPTION
                "smSiaSystemDeviceX25SupportLevel.

                 Not supported on HP-UX, Sun Solaris and Digital UNIX."
        ::= { smSiaSystemDeviceX25Entry 3 }

smSiaSystemDeviceX25SupportedFacilities OBJECT-TYPE
        SYNTAX  INTEGER
        ACCESS  read-only
        STATUS  mandatory
        DESCRIPTION
                "smSiaSystemDeviceX25SupportedFacilities.

                 Not supported on HP-UX, Sun Solaris and Digital UNIX."
        ::= { smSiaSystemDeviceX25Entry 4 }

smSiaSystemDeviceX25NetworkId OBJECT-TYPE
        SYNTAX  PhysAddress
        ACCESS  read-only
        STATUS  mandatory
        DESCRIPTION
                "smSiaSystemDeviceX25NetworkId.

                 Not supported on HP-UX, Sun Solaris and Digital UNIX."
        ::= { smSiaSystemDeviceX25Entry 5 }

smSiaSystemDeviceX25MaxTxPacketSize OBJECT-TYPE
        SYNTAX  INTEGER
        ACCESS  read-only
        STATUS  mandatory
        DESCRIPTION
                "smSiaSystemDeviceX25MaxTxPacketSize.

                 Not supported on HP-UX, Sun Solaris and Digital UNIX."
        ::= { smSiaSystemDeviceX25Entry 6 }

smSiaSystemDeviceX25MaxRxPacketSize OBJECT-TYPE
        SYNTAX  INTEGER
        ACCESS  read-only
        STATUS  mandatory
        DESCRIPTION
                "smSiaSystemDeviceX25MaxRxPacketSize.

                 Not supported on HP-UX, Sun Solaris and Digital UNIX."
        ::= { smSiaSystemDeviceX25Entry 7 }

smSiaSystemDeviceX25DefaultSvcTxPacketSize OBJECT-TYPE
        SYNTAX  INTEGER
        ACCESS  read-only
        STATUS  mandatory
        DESCRIPTION
                "smSiaSystemDeviceX25DefaultSvcTxPacketSize.

                 Not supported on HP-UX, Sun Solaris and Digital UNIX."
        ::= { smSiaSystemDeviceX25Entry 8 }

smSiaSystemDeviceX25DefaultSvcRxPacketSize OBJECT-TYPE
        SYNTAX  INTEGER
        ACCESS  read-only
        STATUS  mandatory
        DESCRIPTION
                "smSiaSystemDeviceX25DefaultSvcRxPacketSize.

                 Not supported on HP-UX, Sun Solaris and Digital UNIX."
        ::= { smSiaSystemDeviceX25Entry 9 }

smSiaSystemDeviceX25ReceiveDataTransferOffset OBJECT-TYPE
        SYNTAX  INTEGER
        ACCESS  read-only
        STATUS  mandatory
        DESCRIPTION
                "smSiaSystemDeviceX25ReceiveDataTransferOffset.

                 Not supported on HP-UX, Sun Solaris and Digital UNIX."
        ::= { smSiaSystemDeviceX25Entry 10 }

smSiaSystemDeviceX25MemoryWindowSize OBJECT-TYPE
        SYNTAX  INTEGER
        ACCESS  read-only
        STATUS  mandatory
        DESCRIPTION
                "smSiaSystemDeviceX25MemoryWindowSize.

                 Not supported on HP-UX, Sun Solaris and Digital UNIX."
        ::= { smSiaSystemDeviceX25Entry 11 }

smSiaSystemDeviceX25TxByteMcnt OBJECT-TYPE
        SYNTAX  Counter
        ACCESS  read-only
        STATUS  mandatory
        DESCRIPTION
                "Most significant bits of successfully transmitted byte count.

                 Not supported on HP-UX, Sun Solaris and Digital UNIX."
        ::= { smSiaSystemDeviceX25Entry 12 }

smSiaSystemDeviceX25TxByteLcnt OBJECT-TYPE
        SYNTAX  Counter
        ACCESS  read-only
        STATUS  mandatory
        DESCRIPTION
                "Least significant bits of successfully transmitted byte count.

                 Not supported on HP-UX, Sun Solaris and Digital UNIX."
        ::= { smSiaSystemDeviceX25Entry 13 }

smSiaSystemDeviceX25RxByteMcnt OBJECT-TYPE
        SYNTAX  Counter
        ACCESS  read-only
        STATUS  mandatory
        DESCRIPTION
                "Most significant bits of successfully received byte count.

                 Not supported on HP-UX, Sun Solaris and Digital UNIX."
        ::= { smSiaSystemDeviceX25Entry 14 }

smSiaSystemDeviceX25RxByteLcnt OBJECT-TYPE
        SYNTAX  Counter
        ACCESS  read-only
        STATUS  mandatory
        DESCRIPTION
                "Least significant bits of successfully received byte count.

                 Not supported on HP-UX, Sun Solaris and Digital UNIX."
        ::= { smSiaSystemDeviceX25Entry 15 }

smSiaSystemDeviceX25TxFrameMcnt OBJECT-TYPE
        SYNTAX  Counter
        ACCESS  read-only
        STATUS  mandatory
        DESCRIPTION
                "Most significant bits of successfully transmitted byte count.

                 Not supported on HP-UX, Sun Solaris and Digital UNIX."
        ::= { smSiaSystemDeviceX25Entry 16 }

smSiaSystemDeviceX25TxFrameLcnt OBJECT-TYPE
        SYNTAX  Counter
        ACCESS  read-only
        STATUS  mandatory
        DESCRIPTION
                "Least significant bits of successfully transmitted byte count.

                 Not supported on HP-UX, Sun Solaris and Digital UNIX."
        ::= { smSiaSystemDeviceX25Entry 17 }

smSiaSystemDeviceX25RxFrameMcnt OBJECT-TYPE
        SYNTAX  Counter
        ACCESS  read-only
        STATUS  mandatory
        DESCRIPTION
                "Most significant bits of successfully received byte count.

                 Not supported on HP-UX, Sun Solaris and Digital UNIX."
        ::= { smSiaSystemDeviceX25Entry 18 }

smSiaSystemDeviceX25RxFrameLcnt OBJECT-TYPE
        SYNTAX  Counter
        ACCESS  read-only
        STATUS  mandatory
        DESCRIPTION
                "Least significant bits of successfully received byte count.

                 Not supported on HP-UX, Sun Solaris and Digital UNIX."
        ::= { smSiaSystemDeviceX25Entry 19 }

smSiaSystemDeviceX25TxErrCnt OBJECT-TYPE
        SYNTAX  Counter
        ACCESS  read-only
        STATUS  mandatory
        DESCRIPTION
                "Frame transmit error count.

                 Not supported on HP-UX, Sun Solaris and Digital UNIX."
        ::= { smSiaSystemDeviceX25Entry 20 }

smSiaSystemDeviceX25RxErrCnt OBJECT-TYPE
        SYNTAX  Counter
        ACCESS  read-only
        STATUS  mandatory
        DESCRIPTION
                "Frame receive error count.

                 Not supported on HP-UX, Sun Solaris and Digital UNIX."
        ::= { smSiaSystemDeviceX25Entry 21 }

smSiaSystemDeviceX25NidTblHigh OBJECT-TYPE
        SYNTAX  INTEGER
        ACCESS  read-only
        STATUS  mandatory
        DESCRIPTION
                "Maximum netids in use.

                 Not supported on HP-UX, Sun Solaris and Digital UNIX."
        ::= { smSiaSystemDeviceX25Entry 22 }

smSiaSystemDeviceX25TxQueHigh OBJECT-TYPE
        SYNTAX  Gauge
        ACCESS  read-only
        STATUS  mandatory
        DESCRIPTION
                "Maximum transmits ever queued for adapter.

                 Not supported on HP-UX, Sun Solaris and Digital UNIX."
        ::= { smSiaSystemDeviceX25Entry 23 }

smSiaSystemDeviceX25RxQueHigh OBJECT-TYPE
        SYNTAX  Gauge
        ACCESS  read-only
        STATUS  mandatory
        DESCRIPTION
                "Maximum received ever queued for any open.

                 Not supported on HP-UX, Sun Solaris and Digital UNIX."
        ::= { smSiaSystemDeviceX25Entry 24 }

smSiaSystemDeviceX25StaQueHigh OBJECT-TYPE
        SYNTAX  Gauge
        ACCESS  read-only
        STATUS  mandatory
        DESCRIPTION
                "Maximum status blocks queued for any open.

                 Not supported on HP-UX, Sun Solaris and Digital UNIX."
        ::= { smSiaSystemDeviceX25Entry 25 }


smSiaSystemDeviceX25IgnoredFTx OBJECT-TYPE
        SYNTAX  Counter
        ACCESS  read-only
        STATUS  mandatory
        DESCRIPTION
                "smSiaSystemDeviceX25IgnoredFTx.

                 Not supported on HP-UX, Sun Solaris and Digital UNIX."
        ::= { smSiaSystemDeviceX25Entry 26 }

smSiaSystemDeviceX25RrFTx OBJECT-TYPE
        SYNTAX  Counter
        ACCESS  read-only
        STATUS  mandatory
        DESCRIPTION
                "smSiaSystemDeviceX25RrFTx.

                 Not supported on HP-UX, Sun Solaris and Digital UNIX."
        ::= { smSiaSystemDeviceX25Entry 27 }

smSiaSystemDeviceX25RnrFTx OBJECT-TYPE
        SYNTAX  Counter
        ACCESS  read-only
        STATUS  mandatory
        DESCRIPTION
                "smSiaSystemDeviceX25RnrFTx.

                 Not supported on HP-UX, Sun Solaris and Digital UNIX."
        ::= { smSiaSystemDeviceX25Entry 28 }

smSiaSystemDeviceX25RejFTx OBJECT-TYPE
        SYNTAX  Counter
        ACCESS  read-only
        STATUS  mandatory
        DESCRIPTION
                "smSiaSystemDeviceX25RejFTx.

                 Not supported on HP-UX, Sun Solaris and Digital UNIX."
        ::= { smSiaSystemDeviceX25Entry 29 }

smSiaSystemDeviceX25InfoFTx OBJECT-TYPE
        SYNTAX  Counter
        ACCESS  read-only
        STATUS  mandatory
        DESCRIPTION
                "smSiaSystemDeviceX25InfoFTx

                 Not supported on HP-UX."
        ::= { smSiaSystemDeviceX25Entry 30 }

smSiaSystemDeviceX25SabmFTx OBJECT-TYPE
        SYNTAX  Counter
        ACCESS  read-only
        STATUS  mandatory
        DESCRIPTION
                "smSiaSystemDeviceX25SabmFTx.

                 Not supported on HP-UX, Sun Solaris and Digital UNIX."
        ::= { smSiaSystemDeviceX25Entry 31 }

smSiaSystemDeviceX25SarmDmFTx OBJECT-TYPE
        SYNTAX  Counter
        ACCESS  read-only
        STATUS  mandatory
        DESCRIPTION
                "smSiaSystemDeviceX25SarmDmFTx.

                 Not supported on HP-UX, Sun Solaris and Digital UNIX."
        ::= { smSiaSystemDeviceX25Entry 32 }

smSiaSystemDeviceX25DiscFTx OBJECT-TYPE
        SYNTAX  Counter
        ACCESS  read-only
        STATUS  mandatory
        DESCRIPTION
                "smSiaSystemDeviceX25DiscFTx.

                 Not supported on HP-UX, Sun Solaris and Digital UNIX."
        ::= { smSiaSystemDeviceX25Entry 33 }

smSiaSystemDeviceX25UaFTx OBJECT-TYPE
        SYNTAX  Counter
        ACCESS  read-only
        STATUS  mandatory
        DESCRIPTION
                "smSiaSystemDeviceX25UaFTx.

                 Not supported on HP-UX, Sun Solaris and Digital UNIX."
        ::= { smSiaSystemDeviceX25Entry 34 }

smSiaSystemDeviceX25FrmrFTx OBJECT-TYPE
        SYNTAX  Counter
        ACCESS  read-only
        STATUS  mandatory
        DESCRIPTION
                "smSiaSystemDeviceX25FrmrFTx.

                 Not supported on HP-UX, Sun Solaris and Digital UNIX."
        ::= { smSiaSystemDeviceX25Entry 35 }

smSiaSystemDeviceX25BadNrFTx OBJECT-TYPE
        SYNTAX  Counter
        ACCESS  read-only
        STATUS  mandatory
        DESCRIPTION
                "smSiaSystemDeviceX25BadNrFTx.

                 Not supported on HP-UX, Sun Solaris and Digital UNIX."
        ::= { smSiaSystemDeviceX25Entry 36 }

smSiaSystemDeviceX25UnknownFTx OBJECT-TYPE
        SYNTAX  Counter
        ACCESS  read-only
        STATUS  mandatory
        DESCRIPTION
                "smSiaSystemDeviceX25UnknownFTx.

                 Not supported on HP-UX, Sun Solaris and Digital UNIX."
        ::= { smSiaSystemDeviceX25Entry 37 }

smSiaSystemDeviceX25XidFTx OBJECT-TYPE
        SYNTAX  Counter
        ACCESS  read-only
        STATUS  mandatory
        DESCRIPTION
                "smSiaSystemDeviceX25XidFTx.

                 Not supported on HP-UX, Sun Solaris and Digital UNIX."
        ::= { smSiaSystemDeviceX25Entry 38 }

smSiaSystemDeviceX25BadLengthFTx OBJECT-TYPE
        SYNTAX  Counter
        ACCESS  read-only
        STATUS  mandatory
        DESCRIPTION
                "smSiaSystemDeviceX25BadLengthFTx.

                 Not supported on HP-UX, Sun Solaris and Digital UNIX."
        ::= { smSiaSystemDeviceX25Entry 39 }

smSiaSystemDeviceX25T1Expirations OBJECT-TYPE
        SYNTAX  Counter
        ACCESS  read-only
        STATUS  mandatory
        DESCRIPTION
                "smSiaSystemDeviceX25T1Expirations.

                 Not supported on HP-UX, Sun Solaris and Digital UNIX."
        ::= { smSiaSystemDeviceX25Entry 40 }

smSiaSystemDeviceX25Lvl2Connects OBJECT-TYPE
        SYNTAX  Counter
        ACCESS  read-only
        STATUS  mandatory
        DESCRIPTION
                "smSiaSystemDeviceX25Lvl2Connects.

                 Not supported on HP-UX, Sun Solaris and Digital UNIX."
        ::= { smSiaSystemDeviceX25Entry 41 }

smSiaSystemDeviceX25Lvl2Disconnects OBJECT-TYPE
        SYNTAX  Counter
        ACCESS  read-only
        STATUS  mandatory
        DESCRIPTION
                "smSiaSystemDeviceX25Lvl2Disconnects.

                 Not supported on HP-UX, Sun Solaris and Digital UNIX."
        ::= { smSiaSystemDeviceX25Entry 42 }

smSiaSystemDeviceX25CarrierLoss OBJECT-TYPE
        SYNTAX  Counter
        ACCESS  read-only
        STATUS  mandatory
        DESCRIPTION
                "smSiaSystemDeviceX25CarrierLoss.

                 Not supported on HP-UX, Sun Solaris and Digital UNIX."
        ::= { smSiaSystemDeviceX25Entry 43 }

smSiaSystemDeviceX25ConnectTime OBJECT-TYPE
        SYNTAX  TimeTicks
        ACCESS  read-only
        STATUS  mandatory
        DESCRIPTION
                "smSiaSystemDeviceX25ConnectTime.

                 Not supported on HP-UX, Sun Solaris and Digital UNIX."
        ::= { smSiaSystemDeviceX25Entry 44 }

smSiaSystemDeviceX25T4Expirations OBJECT-TYPE
        SYNTAX  Counter
        ACCESS  read-only
        STATUS  mandatory
        DESCRIPTION
                "smSiaSystemDeviceX25T4Expirations.

                 Not supported on HP-UX, Sun Solaris and Digital UNIX."
        ::= { smSiaSystemDeviceX25Entry 45 }

smSiaSystemDeviceX25T4N2Times OBJECT-TYPE
        SYNTAX  Counter
        ACCESS  read-only
        STATUS  mandatory
        DESCRIPTION
                "smSiaSystemDeviceX25T4N2Times.

                 Not supported on HP-UX, Sun Solaris and Digital UNIX."
        ::= { smSiaSystemDeviceX25Entry 46 }

smSiaSystemDeviceX25IgnoredFRx OBJECT-TYPE
        SYNTAX  Counter
        ACCESS  read-only
        STATUS  mandatory
        DESCRIPTION
                "smSiaSystemDeviceX25IgnoredFRx.

                 Not supported on HP-UX, Sun Solaris and Digital UNIX."
        ::= { smSiaSystemDeviceX25Entry 47 }

smSiaSystemDeviceX25RrFRx OBJECT-TYPE
        SYNTAX  Counter
        ACCESS  read-only
        STATUS  mandatory
        DESCRIPTION
                "smSiaSystemDeviceX25RrFRx.

                 Not supported on HP-UX, Sun Solaris and Digital UNIX."
        ::= { smSiaSystemDeviceX25Entry 48 }

smSiaSystemDeviceX25RnrFRx OBJECT-TYPE
        SYNTAX  Counter
        ACCESS  read-only
        STATUS  mandatory
        DESCRIPTION
                "smSiaSystemDeviceX25RnrFRx.

                 Not supported on HP-UX, Sun Solaris and Digital UNIX."
        ::= { smSiaSystemDeviceX25Entry 49 }

smSiaSystemDeviceX25RejFRx OBJECT-TYPE
        SYNTAX  Counter
        ACCESS  read-only
        STATUS  mandatory
        DESCRIPTION
                "smSiaSystemDeviceX25RejFRx.

                 Not supported on HP-UX, Sun Solaris and Digital UNIX."
        ::= { smSiaSystemDeviceX25Entry 50 }

smSiaSystemDeviceX25InfoFRx OBJECT-TYPE
        SYNTAX  Counter
        ACCESS  read-only
        STATUS  mandatory
        DESCRIPTION
                "smSiaSystemDeviceX25InfoFRx.

                 Not supported on HP-UX, Sun Solaris and Digital UNIX."
        ::= { smSiaSystemDeviceX25Entry 51 }

smSiaSystemDeviceX25SabmFRx OBJECT-TYPE
        SYNTAX  Counter
        ACCESS  read-only
        STATUS  mandatory
        DESCRIPTION
                "smSiaSystemDeviceX25SabmFRx.

                 Not supported on HP-UX, Sun Solaris and Digital UNIX."
        ::= { smSiaSystemDeviceX25Entry 52 }

smSiaSystemDeviceX25SarmDmFRx OBJECT-TYPE
        SYNTAX  Counter
        ACCESS  read-only
        STATUS  mandatory
        DESCRIPTION
                "smSiaSystemDeviceX25SarmDmFRx.

                 Not supported on HP-UX, Sun Solaris and Digital UNIX."
        ::= { smSiaSystemDeviceX25Entry 53 }

smSiaSystemDeviceX25DiscFRx OBJECT-TYPE
        SYNTAX  Counter
        ACCESS  read-only
        STATUS  mandatory
        DESCRIPTION
                "smSiaSystemDeviceX25DiscFRx.

                 Not supported on HP-UX, Sun Solaris and Digital UNIX."
        ::= { smSiaSystemDeviceX25Entry 54 }

smSiaSystemDeviceX25UaFRx OBJECT-TYPE
        SYNTAX  Counter
        ACCESS  read-only
        STATUS  mandatory
        DESCRIPTION
                "smSiaSystemDeviceX25UaFRx.

                 Not supported on HP-UX, Sun Solaris and Digital UNIX."
        ::= { smSiaSystemDeviceX25Entry 55 }

smSiaSystemDeviceX25FrmrFRx OBJECT-TYPE
        SYNTAX  Counter
        ACCESS  read-only
        STATUS  mandatory
        DESCRIPTION
                "smSiaSystemDeviceX25FrmrFRx.

                 Not supported on HP-UX, Sun Solaris and Digital UNIX."
        ::= { smSiaSystemDeviceX25Entry 56 }

smSiaSystemDeviceX25BadNrFRx OBJECT-TYPE
        SYNTAX  Counter
        ACCESS  read-only
        STATUS  mandatory
        DESCRIPTION
                "smSiaSystemDeviceX25BadNrFRx.

                 Not supported on HP-UX, Sun Solaris and Digital UNIX."
        ::= { smSiaSystemDeviceX25Entry 57 }

smSiaSystemDeviceX25UnknownFRx OBJECT-TYPE
        SYNTAX  Counter
        ACCESS  read-only
        STATUS  mandatory
        DESCRIPTION
                "smSiaSystemDeviceX25UnknownFRx.

                 Not supported on HP-UX, Sun Solaris and Digital UNIX."
        ::= { smSiaSystemDeviceX25Entry 58 }

smSiaSystemDeviceX25XidFRx OBJECT-TYPE
        SYNTAX  Counter
        ACCESS  read-only
        STATUS  mandatory
        DESCRIPTION
                "smSiaSystemDeviceX25XidFRx.

                 Not supported on HP-UX, Sun Solaris and Digital UNIX."
        ::= { smSiaSystemDeviceX25Entry 59 }

smSiaSystemDeviceX25BadLengthFRx OBJECT-TYPE
        SYNTAX  Counter
        ACCESS  read-only
        STATUS  mandatory
        DESCRIPTION
                "smSiaSystemDeviceX25BadLengthFRx.

                 Not supported on HP-UX, Sun Solaris and Digital UNIX."
        ::= { smSiaSystemDeviceX25Entry 60 }

smSiaSystemDeviceX25DataPTx OBJECT-TYPE
        SYNTAX  Counter
        ACCESS  read-only
        STATUS  mandatory
        DESCRIPTION
                "smSiaSystemDeviceX25DataPTx.

                 Not supported on HP-UX, Sun Solaris and Digital UNIX."
        ::= { smSiaSystemDeviceX25Entry 61 }

smSiaSystemDeviceX25RrPTx OBJECT-TYPE
        SYNTAX  Counter
        ACCESS  read-only
        STATUS  mandatory
        DESCRIPTION
                "smSiaSystemDeviceX25RrPTx.

                 Not supported on HP-UX, Sun Solaris and Digital UNIX."
        ::= { smSiaSystemDeviceX25Entry 62 }

smSiaSystemDeviceX25RnrPTx OBJECT-TYPE
        SYNTAX  Counter
        ACCESS  read-only
        STATUS  mandatory
        DESCRIPTION
                "smSiaSystemDeviceX25RnrPTx.

                 Not supported on HP-UX, Sun Solaris and Digital UNIX."
        ::= { smSiaSystemDeviceX25Entry 63 }

smSiaSystemDeviceX25InterruptPTx OBJECT-TYPE
        SYNTAX  Counter
        ACCESS  read-only
        STATUS  mandatory
        DESCRIPTION
                "smSiaSystemDeviceX25InterruptPTx.

                 Not supported on HP-UX, Sun Solaris and Digital UNIX."
        ::= { smSiaSystemDeviceX25Entry 64 }

smSiaSystemDeviceX25InterruptConfirmPTx OBJECT-TYPE
        SYNTAX  Counter
        ACCESS  read-only
        STATUS  mandatory
        DESCRIPTION
                "smSiaSystemDeviceX25InterruptConfirmPTx.

                 Not supported on HP-UX, Sun Solaris and Digital UNIX."
        ::= { smSiaSystemDeviceX25Entry 65 }

smSiaSystemDeviceX25CallRequestPTx OBJECT-TYPE
        SYNTAX  Counter
        ACCESS  read-only
        STATUS  mandatory
        DESCRIPTION
                "smSiaSystemDeviceX25CallRequestPTx.

                 Not supported on HP-UX, Sun Solaris and Digital UNIX."
        ::= { smSiaSystemDeviceX25Entry 66 }

smSiaSystemDeviceX25CallAcceptPTx OBJECT-TYPE
        SYNTAX  Counter
        ACCESS  read-only
        STATUS  mandatory
        DESCRIPTION
                "smSiaSystemDeviceX25CallAcceptPTx.

                 Not supported on HP-UX, Sun Solaris and Digital UNIX."
        ::= { smSiaSystemDeviceX25Entry 67 }

smSiaSystemDeviceX25ClearRequestPTx OBJECT-TYPE
        SYNTAX  Counter
        ACCESS  read-only
        STATUS  mandatory
        DESCRIPTION
                "smSiaSystemDeviceX25ClearRequestPTx.

                 Not supported on HP-UX, Sun Solaris and Digital UNIX."
        ::= { smSiaSystemDeviceX25Entry 68 }

smSiaSystemDeviceX25ClearConfirmPTx OBJECT-TYPE
        SYNTAX  Counter
        ACCESS  read-only
        STATUS  mandatory
        DESCRIPTION
                "smSiaSystemDeviceX25ClearConfirmPTx.

                 Not supported on HP-UX, Sun Solaris and Digital UNIX."
        ::= { smSiaSystemDeviceX25Entry 69 }

smSiaSystemDeviceX25ResetRequestPTx OBJECT-TYPE
        SYNTAX  Counter
        ACCESS  read-only
        STATUS  mandatory
        DESCRIPTION
                "smSiaSystemDeviceX25ResetRequestPTx.

                 Not supported on HP-UX, Sun Solaris and Digital UNIX."
        ::= { smSiaSystemDeviceX25Entry 70 }

smSiaSystemDeviceX25ResetConfirmPTx OBJECT-TYPE
        SYNTAX  Counter
        ACCESS  read-only
        STATUS  mandatory
        DESCRIPTION
                "smSiaSystemDeviceX25ResetConfirmPTx.

                 Not supported on HP-UX, Sun Solaris and Digital UNIX."
        ::= { smSiaSystemDeviceX25Entry 71 }

smSiaSystemDeviceX25DiagnosticPTx OBJECT-TYPE
        SYNTAX  Counter
        ACCESS  read-only
        STATUS  mandatory
        DESCRIPTION
                "smSiaSystemDeviceX25DiagnosticPTx.

                 Not supported on HP-UX, Sun Solaris and Digital UNIX."
        ::= { smSiaSystemDeviceX25Entry 72 }

smSiaSystemDeviceX25RegistrationPTx OBJECT-TYPE
        SYNTAX  Counter
        ACCESS  read-only
        STATUS  mandatory
        DESCRIPTION
                "smSiaSystemDeviceX25RegistrationPTx.

                 Not supported on HP-UX, Sun Solaris and Digital UNIX."
        ::= { smSiaSystemDeviceX25Entry 73 }

smSiaSystemDeviceX25RegistrationConfirmPTx OBJECT-TYPE
        SYNTAX  Counter
        ACCESS  read-only
        STATUS  mandatory
        DESCRIPTION
                "smSiaSystemDeviceX25RegistrationConfirmPTx.

                 Not supported on HP-UX, Sun Solaris and Digital UNIX."
        ::= { smSiaSystemDeviceX25Entry 74 }

smSiaSystemDeviceX25RestartPTx OBJECT-TYPE
        SYNTAX  Counter
        ACCESS  read-only
        STATUS  mandatory
        DESCRIPTION
                "smSiaSystemDeviceX25RestartPTx.

                 Not supported on HP-UX, Sun Solaris and Digital UNIX."
        ::= { smSiaSystemDeviceX25Entry 75 }

smSiaSystemDeviceX25RestartConfirmPTx OBJECT-TYPE
        SYNTAX  Counter
        ACCESS  read-only
        STATUS  mandatory
        DESCRIPTION
                "smSiaSystemDeviceX25RestartConfirmPTx.

                 Not supported on HP-UX, Sun Solaris and Digital UNIX."
        ::= { smSiaSystemDeviceX25Entry 76 }

smSiaSystemDeviceX25ErrorPTx OBJECT-TYPE
        SYNTAX  Counter
        ACCESS  read-only
        STATUS  mandatory
        DESCRIPTION
                "smSiaSystemDeviceX25ErrorPTx.

                 Not supported on HP-UX, Sun Solaris and Digital UNIX."
        ::= { smSiaSystemDeviceX25Entry 77 }

smSiaSystemDeviceX25T20Expirations OBJECT-TYPE
        SYNTAX  Counter
        ACCESS  read-only
        STATUS  mandatory
        DESCRIPTION
                "smSiaSystemDeviceX25T20Expirations.

                 Not supported on HP-UX, Sun Solaris and Digital UNIX."
        ::= { smSiaSystemDeviceX25Entry 78 }

smSiaSystemDeviceX25T21Expirations OBJECT-TYPE
        SYNTAX  Counter
        ACCESS  read-only
        STATUS  mandatory
        DESCRIPTION
                "smSiaSystemDeviceX25T21Expirations.

                 Not supported on HP-UX, Sun Solaris and Digital UNIX."
        ::= { smSiaSystemDeviceX25Entry 79 }

smSiaSystemDeviceX25T22Expirations OBJECT-TYPE
        SYNTAX  Counter
        ACCESS  read-only
        STATUS  mandatory
        DESCRIPTION
                "smSiaSystemDeviceX25T22Expirations.

                 Not supported on HP-UX, Sun Solaris and Digital UNIX."
        ::= { smSiaSystemDeviceX25Entry 80 }

smSiaSystemDeviceX25T23Expirations OBJECT-TYPE
        SYNTAX  Counter
        ACCESS  read-only
        STATUS  mandatory
        DESCRIPTION
                "smSiaSystemDeviceX25T23Expirations.

                 Not supported on HP-UX, Sun Solaris and Digital UNIX."
        ::= { smSiaSystemDeviceX25Entry 81 }

smSiaSystemDeviceX25VcEstablishments OBJECT-TYPE
        SYNTAX  Counter
        ACCESS  read-only
        STATUS  mandatory
        DESCRIPTION
                "smSiaSystemDeviceX25VcEstablishments.

                 Not supported on HP-UX, Sun Solaris and Digital UNIX."
        ::= { smSiaSystemDeviceX25Entry 82 }

smSiaSystemDeviceX25T24Expirations OBJECT-TYPE
        SYNTAX  Counter
        ACCESS  read-only
        STATUS  mandatory
        DESCRIPTION
                "smSiaSystemDeviceX25T24Expirations.

                 Not supported on HP-UX, Sun Solaris and Digital UNIX."
        ::= { smSiaSystemDeviceX25Entry 83 }

smSiaSystemDeviceX25T25Expirations OBJECT-TYPE
        SYNTAX  Counter
        ACCESS  read-only
        STATUS  mandatory
        DESCRIPTION
                "smSiaSystemDeviceX25T25Expirations.

                 Not supported on HP-UX, Sun Solaris and Digital UNIX."
        ::= { smSiaSystemDeviceX25Entry 84 }

smSiaSystemDeviceX25T26Expirations OBJECT-TYPE
        SYNTAX  Counter
        ACCESS  read-only
        STATUS  mandatory
        DESCRIPTION
                "smSiaSystemDeviceX25T26Expirations.

                 Not supported on HP-UX, Sun Solaris and Digital UNIX."
        ::= { smSiaSystemDeviceX25Entry 85 }

smSiaSystemDeviceX25T28Expirations OBJECT-TYPE
        SYNTAX  Counter
        ACCESS  read-only
        STATUS  mandatory
        DESCRIPTION
                "smSiaSystemDeviceX25T28Expirations.

                 Not supported on HP-UX, Sun Solaris and Digital UNIX."
        ::= { smSiaSystemDeviceX25Entry 86 }

smSiaSystemDeviceX25DataPRx OBJECT-TYPE
        SYNTAX  Counter
        ACCESS  read-only
        STATUS  mandatory
        DESCRIPTION
                "smSiaSystemDeviceX25DataPRx.

                 Not supported on HP-UX, Sun Solaris and Digital UNIX."
        ::= { smSiaSystemDeviceX25Entry 87 }

smSiaSystemDeviceX25RrPRx OBJECT-TYPE
        SYNTAX  Counter
        ACCESS  read-only
        STATUS  mandatory
        DESCRIPTION
                "smSiaSystemDeviceX25RrPRx.

                 Not supported on HP-UX, Sun Solaris and Digital UNIX."
        ::= { smSiaSystemDeviceX25Entry 88 }

smSiaSystemDeviceX25RnrPRx OBJECT-TYPE
        SYNTAX  Counter
        ACCESS  read-only
        STATUS  mandatory
        DESCRIPTION
                "smSiaSystemDeviceX25RnrPRx.

                 Not supported on HP-UX, Sun Solaris and Digital UNIX."
        ::= { smSiaSystemDeviceX25Entry 89 }

smSiaSystemDeviceX25InterruptPRx OBJECT-TYPE
        SYNTAX  Counter
        ACCESS  read-only
        STATUS  mandatory
        DESCRIPTION
                "smSiaSystemDeviceX25InterruptPRx.

                 Not supported on HP-UX, Sun Solaris and Digital UNIX."
        ::= { smSiaSystemDeviceX25Entry 90 }

smSiaSystemDeviceX25InterruptConfirmPRx OBJECT-TYPE
        SYNTAX  Counter
        ACCESS  read-only
        STATUS  mandatory
        DESCRIPTION
                "smSiaSystemDeviceX25InterruptConfirmPRx.

                 Not supported on HP-UX, Sun Solaris and Digital UNIX."
        ::= { smSiaSystemDeviceX25Entry 91 }

smSiaSystemDeviceX25IncomingCallPRx OBJECT-TYPE
        SYNTAX  Counter
        ACCESS  read-only
        STATUS  mandatory
        DESCRIPTION
                "smSiaSystemDeviceX25IncomingCallPRx.

                 Not supported on HP-UX, Sun Solaris and Digital UNIX."
        ::= { smSiaSystemDeviceX25Entry 92 }

smSiaSystemDeviceX25CallConnectedPRx OBJECT-TYPE
        SYNTAX  Counter
        ACCESS  read-only
        STATUS  mandatory
        DESCRIPTION
                "smSiaSystemDeviceX25CallConnectedPRx.

                 Not supported on HP-UX, Sun Solaris and Digital UNIX."
        ::= { smSiaSystemDeviceX25Entry 93 }

smSiaSystemDeviceX25ClearIndicationPRx OBJECT-TYPE
        SYNTAX  Counter
        ACCESS  read-only
        STATUS  mandatory
        DESCRIPTION
                "smSiaSystemDeviceX25ClearIndicationPRx.

                 Not supported on HP-UX, Sun Solaris and Digital UNIX."
        ::= { smSiaSystemDeviceX25Entry 94 }

smSiaSystemDeviceX25ClearConfirmPRx OBJECT-TYPE
        SYNTAX  Counter
        ACCESS  read-only
        STATUS  mandatory
        DESCRIPTION
                "smSiaSystemDeviceX25ClearConfirmPRx.

                 Not supported on HP-UX, Sun Solaris and Digital UNIX."
        ::= { smSiaSystemDeviceX25Entry 95 }

smSiaSystemDeviceX25ResetIndicationPRx OBJECT-TYPE
        SYNTAX  Counter
        ACCESS  read-only
        STATUS  mandatory
        DESCRIPTION
                "smSiaSystemDeviceX25ResetIndicationPRx.

                 Not supported on HP-UX, Sun Solaris and Digital UNIX."
        ::= { smSiaSystemDeviceX25Entry 96 }

smSiaSystemDeviceX25ResetConfirmPRx OBJECT-TYPE
        SYNTAX  Counter
        ACCESS  read-only
        STATUS  mandatory
        DESCRIPTION
                "smSiaSystemDeviceX25ResetConfirmPRx.

                 Not supported on HP-UX, Sun Solaris and Digital UNIX."
        ::= { smSiaSystemDeviceX25Entry 97 }

smSiaSystemDeviceX25DiagnosticPRx OBJECT-TYPE
        SYNTAX  Counter
        ACCESS  read-only
        STATUS  mandatory
        DESCRIPTION
                "smSiaSystemDeviceX25DiagnosticPRx.

                 Not supported on HP-UX, Sun Solaris and Digital UNIX."
        ::= { smSiaSystemDeviceX25Entry 98 }

smSiaSystemDeviceX25RegistrationPRx OBJECT-TYPE
        SYNTAX  Counter
        ACCESS  read-only
        STATUS  mandatory
        DESCRIPTION
                "smSiaSystemDeviceX25RegistrationPRx.

                 Not supported on HP-UX, Sun Solaris and Digital UNIX."
        ::= { smSiaSystemDeviceX25Entry 99 }

smSiaSystemDeviceX25RegistrationConfirmPRx OBJECT-TYPE
        SYNTAX  Counter
        ACCESS  read-only
        STATUS  mandatory
        DESCRIPTION
                "smSiaSystemDeviceX25RegistrationConfirmPRx.

                 Not supported on HP-UX, Sun Solaris and Digital UNIX."
        ::= { smSiaSystemDeviceX25Entry 100 }

smSiaSystemDeviceX25RestartPRx OBJECT-TYPE
        SYNTAX  Counter
        ACCESS  read-only
        STATUS  mandatory
        DESCRIPTION
                "smSiaSystemDeviceX25RestartPRx.

                 Not supported on HP-UX, Sun Solaris and Digital UNIX."
        ::= { smSiaSystemDeviceX25Entry 101 }

smSiaSystemDeviceX25RestartConfirmPRx OBJECT-TYPE
        SYNTAX  Counter
        ACCESS  read-only
        STATUS  mandatory
        DESCRIPTION
                "smSiaSystemDeviceX25RestartConfirmPRx.

                 Not supported on HP-UX, Sun Solaris and Digital UNIX."
        ::= { smSiaSystemDeviceX25Entry 102 }

smSiaSystemDeviceX25TxUnknownSize OBJECT-TYPE
        SYNTAX  Counter
        ACCESS  read-only
        STATUS  mandatory
        DESCRIPTION
                "smSiaSystemDeviceX25TxUnknownSize.

                 Not supported on HP-UX, Sun Solaris and Digital UNIX."
        ::= { smSiaSystemDeviceX25Entry 103 }

smSiaSystemDeviceX25TxReserved1 OBJECT-TYPE
        SYNTAX  Counter
        ACCESS  read-only
        STATUS  mandatory
        DESCRIPTION
                "smSiaSystemDeviceX25TxReserved1.

                 Not supported on HP-UX and Sun
                Solaris."
        ::={ smSiaSystemDeviceX25Entry 104 }

smSiaSystemDeviceX25TxReserved2 OBJECT-TYPE
        SYNTAX  Counter
        ACCESS  read-only
        STATUS  mandatory
        DESCRIPTION
                "smSiaSystemDeviceX25TxReserved2.

                 Not supported on HP-UX, Sun Solaris and Digital UNIX."
        ::= { smSiaSystemDeviceX25Entry 105 }

smSiaSystemDeviceX25TxReserved3 OBJECT-TYPE
        SYNTAX  Counter
        ACCESS  read-only
        STATUS  mandatory
        DESCRIPTION
                "smSiaSystemDeviceX25TxReserved3.

                 Not supported on HP-UX, Sun Solaris and Digital UNIX."
        ::= { smSiaSystemDeviceX25Entry 106 }

smSiaSystemDeviceX25Tx0x15 OBJECT-TYPE
        SYNTAX  Counter
        ACCESS  read-only
        STATUS  mandatory
        DESCRIPTION
                "smSiaSystemDeviceX25Tx0x15.

                 Not supported on HP-UX, Sun Solaris and Digital UNIX."
        ::= { smSiaSystemDeviceX25Entry 107 }

smSiaSystemDeviceX25Tx16x31 OBJECT-TYPE
        SYNTAX  Counter
        ACCESS  read-only
        STATUS  mandatory
        DESCRIPTION
                "smSiaSystemDeviceX25Tx16x31.

                 Not supported on HP-UX, Sun Solaris and Digital UNIX."
        ::= { smSiaSystemDeviceX25Entry 108 }

smSiaSystemDeviceX25Tx32x63 OBJECT-TYPE
        SYNTAX  Counter
        ACCESS  read-only
        STATUS  mandatory
        DESCRIPTION
                "smSiaSystemDeviceX25Tx32x63.

                 Not supported on HP-UX, Sun Solaris and Digital UNIX."
        ::= { smSiaSystemDeviceX25Entry 109 }

smSiaSystemDeviceX25Tx64x127 OBJECT-TYPE
        SYNTAX  Counter
        ACCESS  read-only
        STATUS  mandatory
        DESCRIPTION
                "smSiaSystemDeviceX25Tx64x127.

                 Not supported on HP-UX, Sun Solaris and Digital UNIX."
        ::= { smSiaSystemDeviceX25Entry 110 }

smSiaSystemDeviceX25Tx128x255 OBJECT-TYPE
        SYNTAX  Counter
        ACCESS  read-only
        STATUS  mandatory
        DESCRIPTION
                "smSiaSystemDeviceX25Tx128x255.

                 Not supported on HP-UX, Sun Solaris and Digital UNIX."
        ::= { smSiaSystemDeviceX25Entry 111 }

smSiaSystemDeviceX25Tx256x511 OBJECT-TYPE
        SYNTAX  Counter
        ACCESS  read-only
        STATUS  mandatory
        DESCRIPTION
                "smSiaSystemDeviceX25Tx256x511.

                 Not supported on HP-UX, Sun Solaris and Digital UNIX."
        ::= { smSiaSystemDeviceX25Entry 112 }

smSiaSystemDeviceX25Tx512x1023 OBJECT-TYPE
        SYNTAX  Counter
        ACCESS  read-only
        STATUS  mandatory
        DESCRIPTION
                "smSiaSystemDeviceX25Tx512x1023.

                 Not supported on HP-UX, Sun Solaris and Digital UNIX."
        ::= { smSiaSystemDeviceX25Entry 113 }

smSiaSystemDeviceX25Tx1024x2047 OBJECT-TYPE
        SYNTAX  Counter
        ACCESS  read-only
        STATUS  mandatory
        DESCRIPTION
                "smSiaSystemDeviceX25Tx1024x2047.

                 Not supported on HP-UX, Sun Solaris and Digital UNIX."
        ::= { smSiaSystemDeviceX25Entry 114 }

smSiaSystemDeviceX25Tx2048x4095 OBJECT-TYPE
        SYNTAX  Counter
        ACCESS  read-only
        STATUS  mandatory
        DESCRIPTION
                "smSiaSystemDeviceX25Tx2048x4095.

                 Not supported on HP-UX, Sun Solaris and Digital UNIX."
        ::= { smSiaSystemDeviceX25Entry 115 }

smSiaSystemDeviceX25TxReserved13 OBJECT-TYPE
        SYNTAX  Counter
        ACCESS  read-only
        STATUS  mandatory
        DESCRIPTION
                "smSiaSystemDeviceX25TxReserved13.

                 Not supported on HP-UX, Sun Solaris and Digital UNIX."
        ::= { smSiaSystemDeviceX25Entry 116 }

smSiaSystemDeviceX25TxReserved14 OBJECT-TYPE
        SYNTAX  Counter
        ACCESS  read-only
        STATUS  mandatory
        DESCRIPTION
                "smSiaSystemDeviceX25TxReserved14.

                 Not supported on HP-UX, Sun Solaris and Digital UNIX."
        ::= { smSiaSystemDeviceX25Entry 117 }

smSiaSystemDeviceX25TxReserved15 OBJECT-TYPE
        SYNTAX  Counter
        ACCESS  read-only
        STATUS  mandatory
        DESCRIPTION
                "smSiaSystemDeviceX25TxReserved15.

                 Not supported on HP-UX, Sun Solaris and Digital UNIX."
        ::= { smSiaSystemDeviceX25Entry 118 }

smSiaSystemDeviceX25TxTotalPackets OBJECT-TYPE
        SYNTAX  Counter
        ACCESS  read-only
        STATUS  mandatory
        DESCRIPTION
                "smSiaSystemDeviceX25TxTotalPackets.

                 Not supported on HP-UX, Sun Solaris and Digital UNIX."
        ::= { smSiaSystemDeviceX25Entry 119 }

smSiaSystemDeviceX25RxUnknownSize OBJECT-TYPE
        SYNTAX  Counter
        ACCESS  read-only
        STATUS  mandatory
        DESCRIPTION
                "smSiaSystemDeviceX25RxUnknownSize.

                 Not supported on HP-UX, Sun Solaris and Digital UNIX."
        ::= { smSiaSystemDeviceX25Entry 120 }

smSiaSystemDeviceX25RxReserved1 OBJECT-TYPE
        SYNTAX  Counter
        ACCESS  read-only
        STATUS  mandatory
        DESCRIPTION
                "smSiaSystemDeviceX25RxReserved1.

                 Not supported on HP-UX, Sun Solaris and Digital UNIX."
        ::= { smSiaSystemDeviceX25Entry 121 }

smSiaSystemDeviceX25RxReserved2 OBJECT-TYPE
        SYNTAX  Counter
        ACCESS  read-only
        STATUS  mandatory
        DESCRIPTION
                "smSiaSystemDeviceX25RxReserved2.

                 Not supported on HP-UX, Sun Solaris and Digital UNIX."
        ::= { smSiaSystemDeviceX25Entry 122 }

smSiaSystemDeviceX25RxReserved3 OBJECT-TYPE
        SYNTAX  Counter
        ACCESS  read-only
        STATUS  mandatory
        DESCRIPTION
                "smSiaSystemDeviceX25RxReserved3.

                 Not supported on HP-UX, Sun Solaris and Digital UNIX."
        ::= { smSiaSystemDeviceX25Entry 123 }

smSiaSystemDeviceX25Rx0x15 OBJECT-TYPE
        SYNTAX  Counter
        ACCESS  read-only
        STATUS  mandatory
        DESCRIPTION
                "smSiaSystemDeviceX25Rx0x15.

                 Not supported on HP-UX, Sun Solaris and Digital UNIX."
        ::= { smSiaSystemDeviceX25Entry 124 }

smSiaSystemDeviceX25Rx16x31 OBJECT-TYPE
        SYNTAX  Counter
        ACCESS  read-only
        STATUS  mandatory
        DESCRIPTION
                "smSiaSystemDeviceX25Rx16x31.

                 Not supported on HP-UX, Sun Solaris and Digital UNIX."
        ::= { smSiaSystemDeviceX25Entry 125 }

smSiaSystemDeviceX25Rx32x63 OBJECT-TYPE
        SYNTAX  Counter
        ACCESS  read-only
        STATUS  mandatory
        DESCRIPTION
                "smSiaSystemDeviceX25Rx32x63.

                 Not supported on HP-UX, Sun Solaris and Digital UNIX."
        ::= { smSiaSystemDeviceX25Entry 126 }

smSiaSystemDeviceX25Rx64x127 OBJECT-TYPE
        SYNTAX  Counter
        ACCESS  read-only
        STATUS  mandatory
        DESCRIPTION
                "smSiaSystemDeviceX25Rx64x127.

                 Not supported on HP-UX, Sun Solaris and Digital UNIX."
        ::= { smSiaSystemDeviceX25Entry 127 }

smSiaSystemDeviceX25Rx128x255 OBJECT-TYPE
        SYNTAX  Counter
        ACCESS  read-only
        STATUS  mandatory
        DESCRIPTION
                "smSiaSystemDeviceX25Rx128x255.

                 Not supported on HP-UX, Sun Solaris and Digital UNIX."
        ::= { smSiaSystemDeviceX25Entry 128 }

smSiaSystemDeviceX25Rx256x511 OBJECT-TYPE
        SYNTAX  Counter
        ACCESS  read-only
        STATUS  mandatory
        DESCRIPTION
                "smSiaSystemDeviceX25Rx256x511.

                 Not supported on HP-UX, Sun Solaris and Digital UNIX."
        ::= { smSiaSystemDeviceX25Entry 129 }

smSiaSystemDeviceX25Rx512x1023 OBJECT-TYPE
        SYNTAX  Counter
        ACCESS  read-only
        STATUS  mandatory
        DESCRIPTION
                "smSiaSystemDeviceX25Rx512x1023.

                 Not supported on HP-UX, Sun Solaris and Digital UNIX."
        ::= { smSiaSystemDeviceX25Entry 130 }

smSiaSystemDeviceX25Rx1024x2047 OBJECT-TYPE
        SYNTAX  Counter
        ACCESS  read-only
        STATUS  mandatory
        DESCRIPTION
                "smSiaSystemDeviceX25Rx1024x2047.

                 Not supported on HP-UX, Sun Solaris and Digital UNIX."
        ::= { smSiaSystemDeviceX25Entry 131 }

smSiaSystemDeviceX25Rx2048x4095 OBJECT-TYPE
        SYNTAX  Counter
        ACCESS  read-only
        STATUS  mandatory
        DESCRIPTION
                "smSiaSystemDeviceX25Rx2048x4095.

                 Not supported on HP-UX, Sun Solaris and Digital UNIX."
        ::= { smSiaSystemDeviceX25Entry 132 }

smSiaSystemDeviceX25RxReserved13 OBJECT-TYPE
        SYNTAX  Counter
        ACCESS  read-only
        STATUS  mandatory
        DESCRIPTION
                "smSiaSystemDeviceX25RxReserved13.

                 Not supported on HP-UX, Sun Solaris and Digital UNIX."
        ::= { smSiaSystemDeviceX25Entry 133 }

smSiaSystemDeviceX25RxReserved14 OBJECT-TYPE
        SYNTAX  Counter
        ACCESS  read-only
        STATUS  mandatory
        DESCRIPTION
                "smSiaSystemDeviceX25RxReserved14.

                 Not supported on HP-UX, Sun Solaris and Digital UNIX."
        ::= { smSiaSystemDeviceX25Entry 134 }

smSiaSystemDeviceX25RxReserved15 OBJECT-TYPE
        SYNTAX  Counter
        ACCESS  read-only
        STATUS  mandatory
        DESCRIPTION
                "smSiaSystemDeviceX25RxReserved15.

                 Not supported on HP-UX, Sun Solaris and Digital UNIX."
        ::= { smSiaSystemDeviceX25Entry 135 }

smSiaSystemDeviceX25RxTotalPackets OBJECT-TYPE
        SYNTAX  Counter
        ACCESS  read-only
        STATUS  mandatory
        DESCRIPTION
                "smSiaSystemDeviceX25RxTotalPackets.

                 Not supported on HP-UX, Sun Solaris and Digital UNIX."
        ::= { smSiaSystemDeviceX25Entry 136 }


smSiaSystemDeviceX25Clear OBJECT-TYPE
        SYNTAX  INTEGER {
                normal(1),
                clear(2)
                }
        ACCESS  read-write
        STATUS  mandatory
        DESCRIPTION
                "Set to clear to clear clearable statistics.

                 Not supported on HP-UX, Sun Solaris and Digital UNIX."
        ::= { smSiaSystemDeviceX25Entry 137 }


--
-- The X.25 Routing Table
--

smSiaSystemDeviceX25RouteCount OBJECT-TYPE
        SYNTAX  INTEGER
        ACCESS  read-only
        STATUS  mandatory
        DESCRIPTION
                "The number of devices installed.

                 Not supported on HP-UX, Sun Solaris and Digital UNIX."
        ::= { smSiaSystemDeviceX25 3 }

smSiaSystemDeviceX25RouteTable OBJECT-TYPE
        SYNTAX  SEQUENCE OF SmSiaSystemDeviceX25RouteEntry
        ACCESS  not-accessible
        STATUS  mandatory
        DESCRIPTION
                "Routing information.

                 Not supported on HP-UX, Sun Solaris and Digital UNIX."
        ::= { smSiaSystemDeviceX25 4 }

smSiaSystemDeviceX25RouteEntry OBJECT-TYPE
        SYNTAX  SmSiaSystemDeviceX25RouteEntry
        ACCESS  not-accessible
        STATUS  mandatory
        DESCRIPTION
                "Each entry contains objects for a particular route.

                 Not supported on HP-UX, Sun Solaris and Digital UNIX."
	INDEX { smSiaSystemDeviceX25RouteNumber }
        ::= { smSiaSystemDeviceX25RouteTable 1 }

SmSiaSystemDeviceX25RouteEntry ::= SEQUENCE {
    smSiaSystemDeviceX25RouteNumber
        INTEGER,
    smSiaSystemDeviceX25RouteEntryName
        DisplayString,
    smSiaSystemDeviceX25RouteUserName
        DisplayString,
    smSiaSystemDeviceX25RoutePort
        DisplayString,
    smSiaSystemDeviceX25RouteCallingAddress
        DisplayString,
    smSiaSystemDeviceX25RouteCalledSubaddress
        DisplayString,
    smSiaSystemDeviceX25RouteCallingAddressExt
        DisplayString,
    smSiaSystemDeviceX25RouteCalledAddressExt
        DisplayString,
    smSiaSystemDeviceX25RouteCalledUserData
        DisplayString,
    smSiaSystemDeviceX25RoutePriority
        INTEGER,
    smSiaSystemDeviceX25RouteAction
        INTEGER
}

smSiaSystemDeviceX25RouteNumber OBJECT-TYPE
        SYNTAX  INTEGER
        ACCESS  read-only
        STATUS  mandatory
        DESCRIPTION
                "Route Entry number.

                 Not supported on HP-UX, Sun Solaris and Digital UNIX."
        ::= { smSiaSystemDeviceX25RouteEntry 1 }

smSiaSystemDeviceX25RouteEntryName OBJECT-TYPE
        SYNTAX  DisplayString
        ACCESS  read-only
        STATUS  mandatory
        DESCRIPTION
                "Route name.

                 Not supported on HP-UX, Sun Solaris and Digital UNIX."
        ::= { smSiaSystemDeviceX25RouteEntry 2 }

smSiaSystemDeviceX25RouteUserName OBJECT-TYPE
        SYNTAX  DisplayString
        ACCESS  read-only
        STATUS  mandatory
        DESCRIPTION
                "User name.

                 Not supported on HP-UX, Sun Solaris and Digital UNIX."
        ::= { smSiaSystemDeviceX25RouteEntry 3 }

smSiaSystemDeviceX25RoutePort OBJECT-TYPE
        SYNTAX  DisplayString
        ACCESS  read-only
        STATUS  mandatory
        DESCRIPTION
                "Port.

                 Not supported on HP-UX, Sun Solaris and Digital UNIX."
        ::= { smSiaSystemDeviceX25RouteEntry 4 }

smSiaSystemDeviceX25RouteCallingAddress OBJECT-TYPE
        SYNTAX  DisplayString
        ACCESS  read-only
        STATUS  mandatory
        DESCRIPTION
                "Calling address.

                 Not supported on HP-UX, Sun Solaris and Digital UNIX."
        ::= { smSiaSystemDeviceX25RouteEntry 5 }

smSiaSystemDeviceX25RouteCalledSubaddress OBJECT-TYPE
        SYNTAX  DisplayString
        ACCESS  read-only
        STATUS  mandatory
        DESCRIPTION
                "Called subaddress.

                 Not supported on HP-UX, Sun Solaris and Digital UNIX."
        ::= { smSiaSystemDeviceX25RouteEntry 6 }

smSiaSystemDeviceX25RouteCallingAddressExt OBJECT-TYPE
        SYNTAX  DisplayString
        ACCESS  read-only
        STATUS  mandatory
        DESCRIPTION
                "Calling address extension.

                 Not supported on HP-UX, Sun Solaris and Digital UNIX."
        ::= { smSiaSystemDeviceX25RouteEntry 7 }

smSiaSystemDeviceX25RouteCalledAddressExt OBJECT-TYPE
        SYNTAX  DisplayString
        ACCESS  read-only
        STATUS  mandatory
        DESCRIPTION
                "Called address extension.

                 Not supported on HP-UX, Sun Solaris and Digital UNIX."
        ::= { smSiaSystemDeviceX25RouteEntry 8 }

smSiaSystemDeviceX25RouteCalledUserData OBJECT-TYPE
        SYNTAX  DisplayString
        ACCESS  read-only
        STATUS  mandatory
        DESCRIPTION
                "Called address extension.

                 Not supported on HP-UX, Sun Solaris and Digital UNIX."
        ::= { smSiaSystemDeviceX25RouteEntry 9 }

smSiaSystemDeviceX25RoutePriority OBJECT-TYPE
        SYNTAX  INTEGER
        ACCESS  read-only
        STATUS  mandatory
        DESCRIPTION
                "Priority.

                 Not supported on HP-UX, Sun Solaris and Digital UNIX."
        ::= { smSiaSystemDeviceX25RouteEntry 10 }

smSiaSystemDeviceX25RouteAction OBJECT-TYPE
        SYNTAX  INTEGER {
                forward(1),
                reject(2)
                }
        ACCESS  read-only
        STATUS  mandatory
        DESCRIPTION
                "Action taken when no listening application is running.

                 Not supported on HP-UX, Sun Solaris and Digital UNIX."
        ::= { smSiaSystemDeviceX25RouteEntry 11 }


--
--  The FileSystem Group
--

smSiaSystemFileSystemMounted OBJECT-TYPE
        SYNTAX  Gauge
        ACCESS  read-only
        STATUS  mandatory
        DESCRIPTION
                "The number of file systems mounted."
        ::= { smSiaSystemFileSystem 1 }


--  The FileSystem Table

smSiaSystemFileSystemTable OBJECT-TYPE
        SYNTAX  SEQUENCE OF SmSiaSystemFileSystemEntry
        ACCESS  not-accessible
        STATUS  mandatory
        DESCRIPTION
                "File system table."
        ::= { smSiaSystemFileSystem 2 }

smSiaSystemFileSystemEntry OBJECT-TYPE
        SYNTAX  SmSiaSystemFileSystemEntry
        ACCESS  not-accessible
        STATUS  mandatory
        DESCRIPTION
                "Each entry contains objects for a particular file
                 system."
	INDEX { smSiaSystemFileSystemName }
        ::= { smSiaSystemFileSystemTable 1 }

SmSiaSystemFileSystemEntry ::= SEQUENCE {
    smSiaSystemFileSystemName
        DisplayString,
    smSiaSystemFileSystemSize
        Gauge,
    smSiaSystemFileSystemFree
        Gauge,
    smSiaSystemFileSystemPercentUsed
        Gauge,
    smSiaSystemFileSystemInodesUsed
        Gauge,
    smSiaSystemFileSystemInodesPercentUsed
        Gauge,
    smSiaSystemFileSystemInodeCount
        Gauge,
    smSiaSystemFileSystemFileSystem
	DisplayString,
    smSiaSystemFileSystemRemote
	DisplayString
}

smSiaSystemFileSystemName OBJECT-TYPE
        SYNTAX  DisplayString
        ACCESS  read-only
        STATUS  mandatory
        DESCRIPTION
                "Name of mount point for a file system."
        ::= { smSiaSystemFileSystemEntry 1 }

smSiaSystemFileSystemSize OBJECT-TYPE
        SYNTAX  Gauge
        ACCESS  read-only
        STATUS  mandatory
        DESCRIPTION
                "Total kilobytes in file system."
        ::= { smSiaSystemFileSystemEntry 2 }

smSiaSystemFileSystemFree OBJECT-TYPE
        SYNTAX  Gauge
        ACCESS  read-only
        STATUS  mandatory
        DESCRIPTION
                "Free file system space in kilobytes.  Set a 	
                 threshold against this variable to monitor
                 for a filesystem to run out of space.  The
                 /var and /tmp directories are good candidates
                 for monitoring, since they are often used by
                 applications and an out-of-space condition
                 can result in errors."
        ::= { smSiaSystemFileSystemEntry 3 }

smSiaSystemFileSystemPercentUsed OBJECT-TYPE
        SYNTAX  Gauge
        ACCESS  read-only
        STATUS  mandatory
        DESCRIPTION
                "Percent of file system used."
        ::= { smSiaSystemFileSystemEntry 4 }


smSiaSystemFileSystemInodesUsed OBJECT-TYPE
        SYNTAX  Gauge
        ACCESS  read-only
        STATUS  mandatory
        DESCRIPTION
                "Used inodes in file system.

                 Not supported for remote file systems for HP-UX,
                 Sun Solaris 2.x and Digital UNIX."
        ::= { smSiaSystemFileSystemEntry 5 }

smSiaSystemFileSystemInodesPercentUsed OBJECT-TYPE
        SYNTAX  Gauge
        ACCESS  read-only
        STATUS  mandatory
        DESCRIPTION
                "Percent inodes used.

                 Not supported for remote file systems for HP-UX,
                 Sun Solaris 2.x and Digital UNIX."
        ::= { smSiaSystemFileSystemEntry 6 }

smSiaSystemFileSystemInodeCount OBJECT-TYPE
        SYNTAX  Gauge
        ACCESS  read-only
        STATUS  mandatory
        DESCRIPTION
                "Inode count.

                 Not supported for remote file systems for HP-UX,
                 Sun Solaris 2.x and Digital UNIX."
        ::= { smSiaSystemFileSystemEntry 7 }

smSiaSystemFileSystemFileSystem OBJECT-TYPE
        SYNTAX  DisplayString
        ACCESS  read-only
        STATUS  mandatory
        DESCRIPTION
                "NFS File system."
        ::= { smSiaSystemFileSystemEntry 8 }

smSiaSystemFileSystemRemote OBJECT-TYPE
        SYNTAX  DisplayString
        ACCESS  read-only
        STATUS  mandatory
        DESCRIPTION
                "Remote node for remotely mounted filesystems."
        ::= { smSiaSystemFileSystemEntry 9 }


--
--  The Subsystem Group
--

smSiaSystemSubSystemsCount OBJECT-TYPE
        SYNTAX  Gauge
        ACCESS  read-only
        STATUS  mandatory
        DESCRIPTION
                "The number of subsystems in table.

                 Not supported on HP-UX, Sun Solaris and Digital UNIX."
        ::= { smSiaSystemSubSystems 1 }

--  The SubSystems Table

smSiaSystemSubSystemsTable OBJECT-TYPE
        SYNTAX  SEQUENCE OF SmSiaSystemSubSystemsEntry
        ACCESS  not-accessible
        STATUS  mandatory
        DESCRIPTION
                "Subsystems table.

                 Not supported on HP-UX, Sun Solaris and Digital UNIX."
        ::= { smSiaSystemSubSystems 2 }

smSiaSystemSubSystemsEntry OBJECT-TYPE
        SYNTAX  SmSiaSystemSubSystemsEntry
        ACCESS  not-accessible
        STATUS  mandatory
        DESCRIPTION
                "Each entry contains objects for a particular file
                 system.

                 Not supported on HP-UX, Sun Solaris and Digital UNIX."
	INDEX { smSiaSystemSubSystemsName }
        ::= { smSiaSystemSubSystemsTable 1 }

SmSiaSystemSubSystemsEntry ::= SEQUENCE {
    smSiaSystemSubSystemsName
        DisplayString,
    smSiaSystemSubSystemsPID
        INTEGER,
    smSiaSystemSubSystemsStatusDescription
	DisplayString,
    smSiaSystemSubSystemsStatusText
	DisplayString,
    smSiaSystemSubSystemsStatusCode
	INTEGER
}

smSiaSystemSubSystemsName OBJECT-TYPE
        SYNTAX  DisplayString
        ACCESS  read-only
        STATUS  mandatory
        DESCRIPTION
                "Name of sub system.

                 Not supported on HP-UX, Sun Solaris and Digital UNIX."
        ::= { smSiaSystemSubSystemsEntry 1 }

smSiaSystemSubSystemsPID OBJECT-TYPE
        SYNTAX  INTEGER
        ACCESS  read-only
        STATUS  mandatory
        DESCRIPTION
                "PID of subsystem, if active.

                 Not supported on HP-UX, Sun Solaris and Digital UNIX."
        ::= { smSiaSystemSubSystemsEntry 2 }

smSiaSystemSubSystemsStatusDescription OBJECT-TYPE
        SYNTAX  DisplayString
        ACCESS  read-only
        STATUS  mandatory
        DESCRIPTION
                "Process group.

                 Not supported on HP-UX, Sun Solaris and Digital UNIX."
        ::= { smSiaSystemSubSystemsEntry 3 }

smSiaSystemSubSystemsStatusText OBJECT-TYPE
        SYNTAX  DisplayString
        ACCESS  read-only
        STATUS  mandatory
        DESCRIPTION
                "Status text.

                 Not supported on HP-UX, Sun Solaris and Digital UNIX."

        ::= { smSiaSystemSubSystemsEntry 4 }

smSiaSystemSubSystemsStatusCode OBJECT-TYPE
        SYNTAX  INTEGER
        ACCESS  read-only
        STATUS  mandatory
        DESCRIPTION
                "Integer status code.  Indicates whether the
                 subsystem is active or inoperative.  A value of
                 1 indicates the subsystem is active; a value of
                 11 indicates that it is inoperative.

                 Not supported on HP-UX, Sun Solaris and Digital UNIX."
        ::= { smSiaSystemSubSystemsEntry 5 }


--
--  The Process Group
--

smSiaSystemProcessCount OBJECT-TYPE
        SYNTAX  Gauge
        ACCESS  read-only
        STATUS  mandatory
        DESCRIPTION
                "The number of processes in table."
        ::= { smSiaSystemProcess 1 }

--  The Process Table

smSiaSystemProcessTable OBJECT-TYPE
        SYNTAX  SEQUENCE OF SmSiaSystemProcessEntry
        ACCESS  not-accessible
        STATUS  mandatory
        DESCRIPTION
                "Process table."
        ::= { smSiaSystemProcess 2 }

smSiaSystemProcessEntry OBJECT-TYPE
        SYNTAX  SmSiaSystemProcessEntry
        ACCESS  not-accessible
        STATUS  mandatory
        DESCRIPTION
                "Each entry contains objects for a particular file
                system."
	INDEX { smSiaSystemProcessCommand, smSiaSystemProcessPID }
        ::= { smSiaSystemProcessTable 1 }

SmSiaSystemProcessEntry ::= SEQUENCE {
    smSiaSystemProcessLoginUser
        DisplayString,
    smSiaSystemProcessPID
        INTEGER,
    smSiaSystemProcessParentPID
        INTEGER,
    smSiaSystemProcessCPUTime
        TimeTicks,
    smSiaSystemProcessUserTime
        TimeTicks,
    smSiaSystemProcessSystemTime
        TimeTicks,
    smSiaSystemProcessPageFaultsIO
        Counter,
    smSiaSystemProcessPageFaultsNoIO
        Counter,
    smSiaSystemProcessPriority
        INTEGER,
    smSiaSystemProcessNice
        INTEGER,
    smSiaSystemProcessState
        INTEGER,
    smSiaSystemProcessWait
        INTEGER,
    smSiaSystemProcessDataResidentSetSize
        INTEGER,
    smSiaSystemProcessTextResidentSetSize
        INTEGER,
    smSiaSystemProcessDataVirtualMemorySize
        INTEGER,
    smSiaSystemProcessImageSize
        INTEGER,
    smSiaSystemProcessPercentMemory
        INTEGER,
    smSiaSystemProcessCPU
        INTEGER,
    smSiaSystemProcessStartTime
        DisplayString,
    smSiaSystemProcessCommand
	DisplayString,
    smSiaSystemProcessLoginUID
        INTEGER,
    smSiaSystemProcessEffectiveUID
        INTEGER,
    smSiaSystemProcessEffectiveGID
        INTEGER,
    smSiaSystemProcessEffectiveGroupName
	DisplayString,
    smSiaSystemProcessSUID
        INTEGER,
    smSiaSystemProcessPgrp
        INTEGER,
    smSiaSystemProcessPFlags
        INTEGER,
    smSiaSystemProcessAdspace
        Gauge,
    smSiaSystemProcessTTYp
        INTEGER,
    smSiaSystemProcessTTYd
        INTEGER,
    smSiaSystemProcessNSwap
        Counter,
    smSiaSystemProcessInblocks
        Counter,
    smSiaSystemProcessOutblocks
        Counter,
    smSiaSystemProcessMsgsnd
        Counter,
    smSiaSystemProcessMsgrcv
        Counter,
    smSiaSystemProcessNsignals
        Counter,
    smSiaSystemProcessNVcsw
        Counter,
    smSiaSystemProcessNIvcsw
        Counter,
    smSiaSystemProcessArguments
	DisplayString,
    smSiaSystemProcessSignal
        INTEGER
}

smSiaSystemProcessLoginUser OBJECT-TYPE
        SYNTAX  DisplayString
        ACCESS  read-only
        STATUS  mandatory
        DESCRIPTION
                "Name of user to whom process belongs."
        ::= { smSiaSystemProcessEntry 1 }

smSiaSystemProcessPID OBJECT-TYPE
        SYNTAX  INTEGER
        ACCESS  read-only
        STATUS  mandatory
        DESCRIPTION
                "Process ID.  This can be a useful variable to
                 monitor if you want to make sure a process is
                 running or you want to watch for a process to
                 be started."
        ::= { smSiaSystemProcessEntry 2 }

smSiaSystemProcessParentPID OBJECT-TYPE
        SYNTAX  INTEGER
        ACCESS  read-only
        STATUS  mandatory
        DESCRIPTION
                "Parent Process ID"
        ::= { smSiaSystemProcessEntry 3 }

smSiaSystemProcessCPUTime OBJECT-TYPE
        SYNTAX  TimeTicks
        ACCESS  read-only
        STATUS  mandatory
        DESCRIPTION
                "Total CPU Time used since startup"
        ::= { smSiaSystemProcessEntry 4 }

smSiaSystemProcessUserTime OBJECT-TYPE
        SYNTAX  TimeTicks
        ACCESS  read-only
        STATUS  mandatory
        DESCRIPTION
                "CPU Time used in user mode since startup."
        ::= { smSiaSystemProcessEntry 5 }

smSiaSystemProcessSystemTime OBJECT-TYPE
        SYNTAX  TimeTicks
        ACCESS  read-only
        STATUS  mandatory
        DESCRIPTION
                "CPU Time used in system mode since startup."
        ::= { smSiaSystemProcessEntry 6 }

smSiaSystemProcessPageFaultsIO OBJECT-TYPE
        SYNTAX  Counter
        ACCESS  read-only
        STATUS  mandatory
        DESCRIPTION
                "Number of Page faults requiring I/O."
        ::= { smSiaSystemProcessEntry 7 }

smSiaSystemProcessPageFaultsNoIO OBJECT-TYPE
        SYNTAX  Counter
        ACCESS  read-only
        STATUS  mandatory
        DESCRIPTION
                "Number of Page faults not requiring I/O."
        ::= { smSiaSystemProcessEntry 8 }

smSiaSystemProcessPriority OBJECT-TYPE
        SYNTAX  INTEGER
        ACCESS  read-only
        STATUS  mandatory
        DESCRIPTION
                "Process Priority"
        ::= { smSiaSystemProcessEntry 9 }

smSiaSystemProcessNice OBJECT-TYPE
        SYNTAX  INTEGER
        ACCESS  read-only
        STATUS  mandatory
        DESCRIPTION
                "Process Nice Value "
        ::= { smSiaSystemProcessEntry 10 }

smSiaSystemProcessState OBJECT-TYPE
        SYNTAX  INTEGER {
                sleep(1),  -- Waiting
                run(3),    -- Runable process
                iDL(4),    -- in creation
                zombie(5), -- in termination
                stop(6),   -- Stopped
		none(666)  -- Strangeness
                }
        ACCESS  read-only
        STATUS  mandatory
        DESCRIPTION
                "Current Process state"
        ::= { smSiaSystemProcessEntry 11 }

smSiaSystemProcessWait OBJECT-TYPE
        SYNTAX  INTEGER {
                event(1),  -- Waiting for an event
                lock(2),   -- Waiting for serialization lock
                timer(3),  -- Waiting for timer
                cpu(4),    -- Waiting for CPU
                pageIn(5), -- Waiting for page in
                pageOut(6), -- Waiting for page out level
                pLock(7),   -- Waiting for physical lock
                pageFree(8), -- Waiting for free page frame
                memory(9),   -- Waiting for memory
		none(666)  -- Not waiting
                }
        ACCESS  read-only
        STATUS  mandatory
        DESCRIPTION
                "Process wait reason.

                 On Sun Solaris, the process wait reason may be
                 none or event.  This variable does not provide
                 additional details on the type of event.
                 Not supported on HP-UX or Digital UNIX."
        ::= { smSiaSystemProcessEntry 12 }

smSiaSystemProcessDataResidentSetSize OBJECT-TYPE
        SYNTAX  INTEGER
        ACCESS  read-only
        STATUS  mandatory
        DESCRIPTION
                "Data resident set size in kilobytes.

                 On Digital UNIX, this variable is the resident set 
                 size for the entire process.

                 On Sun Solaris, statistics for resident set size
                 for the text, data, and stack segments are not
                 maintained separately.  This variable is the
                 total resident set size for all three segments."
        ::= { smSiaSystemProcessEntry 13 }

smSiaSystemProcessTextResidentSetSize OBJECT-TYPE
        SYNTAX  INTEGER
        ACCESS  read-only
        STATUS  mandatory
        DESCRIPTION
                "Text resident set size in kilobytes.

                 Not supported on Sun Solaris 2.x or Digital UNIX."
        ::= { smSiaSystemProcessEntry 14 }

smSiaSystemProcessImageSize OBJECT-TYPE
        SYNTAX  INTEGER
        ACCESS  read-only
        STATUS  mandatory
        DESCRIPTION
                "core image size.

                On Sun Solaris, this variable is the total of
                the text, data, and stack segments.

                On AIX and HP-UX, this variable is the same
                as smSiaSystemProcessDataVirtualMemorySize."
        ::= { smSiaSystemProcessEntry 15 }

smSiaSystemProcessDataVirtualMemorySize OBJECT-TYPE
        SYNTAX  INTEGER
        ACCESS  read-only
        STATUS  mandatory
        DESCRIPTION
                "Data Virtual Memory size.

                 Not supported on Digital UNIX."
        ::= { smSiaSystemProcessEntry 16 }

smSiaSystemProcessPercentMemory OBJECT-TYPE
        SYNTAX  INTEGER
        ACCESS  read-only
        STATUS  mandatory
        DESCRIPTION
                "Percentage of real memory used.

                 Not supported on HP-UX."
        ::= { smSiaSystemProcessEntry 17 }

smSiaSystemProcessCPU OBJECT-TYPE
        SYNTAX  INTEGER
        ACCESS  read-only
        STATUS  mandatory
        DESCRIPTION
                "Percentage of CPU used on each process.

                 This variable is not supported on Sun Solaris 2.x."
        ::= { smSiaSystemProcessEntry 18 }

smSiaSystemProcessStartTime OBJECT-TYPE
        SYNTAX  DisplayString
        ACCESS  read-only
        STATUS  mandatory
        DESCRIPTION
                "Process starting time."
        ::= { smSiaSystemProcessEntry 19 }

smSiaSystemProcessCommand OBJECT-TYPE
        SYNTAX  DisplayString
        ACCESS  read-only
        STATUS  mandatory
        DESCRIPTION
                "Process starting command."
        ::= { smSiaSystemProcessEntry 20 }

smSiaSystemProcessLoginUID OBJECT-TYPE
        SYNTAX  INTEGER
        ACCESS  read-only
        STATUS  mandatory
        DESCRIPTION
                "Login User ID

                 Not supported on HP-UX."
        ::= { smSiaSystemProcessEntry 21 }

smSiaSystemProcessEffectiveUID OBJECT-TYPE
        SYNTAX  INTEGER
        ACCESS  read-only
        STATUS  mandatory
        DESCRIPTION
                "Effective User ID"
        ::= { smSiaSystemProcessEntry 22 }

smSiaSystemProcessEffectiveGID OBJECT-TYPE
        SYNTAX  INTEGER
        ACCESS  read-only
        STATUS  mandatory
        DESCRIPTION
                "Effective Group ID.

                 Not supported on HP-UX."
        ::= { smSiaSystemProcessEntry 23 }

smSiaSystemProcessEffectiveGroupName OBJECT-TYPE
        SYNTAX  DisplayString
        ACCESS  read-only
        STATUS  mandatory
        DESCRIPTION
                "Effective Group Name.

                 Not supported on HP-UX."
        ::= { smSiaSystemProcessEntry 24 }

smSiaSystemProcessSUID OBJECT-TYPE
        SYNTAX  INTEGER
        ACCESS  read-only
        STATUS  mandatory
        DESCRIPTION
                "Saved User ID"
        ::= { smSiaSystemProcessEntry 25 }

smSiaSystemProcessPgrp OBJECT-TYPE
        SYNTAX  INTEGER
        ACCESS  read-only
        STATUS  mandatory
        DESCRIPTION
                "Process group"
        ::= { smSiaSystemProcessEntry 26 }

smSiaSystemProcessPFlags OBJECT-TYPE
        SYNTAX  INTEGER
        ACCESS  read-only
        STATUS  mandatory
        DESCRIPTION
                "Process flags - look in /usr/include/sys/proc.h"
        ::= { smSiaSystemProcessEntry 27 }

smSiaSystemProcessAdspace OBJECT-TYPE
        SYNTAX  Gauge
        ACCESS  read-only
        STATUS  mandatory
        DESCRIPTION
                "Process Address space.

                 Not supported on Digital UNIX."
        ::= { smSiaSystemProcessEntry 28 }

smSiaSystemProcessTTYp OBJECT-TYPE
        SYNTAX  INTEGER
        ACCESS  read-only
        STATUS  mandatory
        DESCRIPTION
                "Whether process has a controlling tty."
        ::= { smSiaSystemProcessEntry 29 }

smSiaSystemProcessTTYd OBJECT-TYPE
        SYNTAX  INTEGER
        ACCESS  read-only
        STATUS  mandatory
        DESCRIPTION
                "Process Controlling TTY"
        ::= { smSiaSystemProcessEntry 30 }

smSiaSystemProcessNSwap OBJECT-TYPE
        SYNTAX  Counter
        ACCESS  read-only
        STATUS  mandatory
        DESCRIPTION
                "Number of times process swapped out.

                 Supported on HP-UX 9.0 only on Series 800 machines."
        ::= { smSiaSystemProcessEntry 31 }

smSiaSystemProcessInblocks OBJECT-TYPE
        SYNTAX  Counter
        ACCESS  read-only
        STATUS  mandatory
        DESCRIPTION
                "File blocks input

                 Not supported on HP-UX."
        ::= { smSiaSystemProcessEntry 32 }

smSiaSystemProcessOutblocks OBJECT-TYPE
        SYNTAX  Counter
        ACCESS  read-only
        STATUS  mandatory
        DESCRIPTION
                "File blocks output.

                 Supported on HP-UX 9.0 only on Series 800 machines."
         ::= { smSiaSystemProcessEntry 33 }

smSiaSystemProcessMsgsnd OBJECT-TYPE
        SYNTAX  Counter
        ACCESS  read-only
        STATUS  mandatory
        DESCRIPTION
                "Number of IPC Messages sent.

                 Supported on HP-UX 9.0 only on Series 800 machines."
         ::= { smSiaSystemProcessEntry 34 }

smSiaSystemProcessMsgrcv OBJECT-TYPE
        SYNTAX  Counter
        ACCESS  read-only
        STATUS  mandatory
        DESCRIPTION
                "Number of IPC Messages received.

                 Supported on HP-UX 9.0 only on Series 800 machines."
         ::= { smSiaSystemProcessEntry 35 }

smSiaSystemProcessNsignals OBJECT-TYPE
        SYNTAX  Counter
        ACCESS  read-only
        STATUS  mandatory
        DESCRIPTION
                "Number of Signals delivered.

                 Supported on HP-UX 9.0 only on Series 800 machines."
         ::= { smSiaSystemProcessEntry 36 }

smSiaSystemProcessNVcsw OBJECT-TYPE
        SYNTAX  Counter
        ACCESS  read-only
        STATUS  mandatory
        DESCRIPTION
                "Number of Voluntary context switches.

                Supported on HP-UX 9.0 only on Series 800 machines."
         ::= { smSiaSystemProcessEntry 37 }

smSiaSystemProcessNIvcsw OBJECT-TYPE
        SYNTAX  Counter
        ACCESS  read-only
        STATUS  mandatory
        DESCRIPTION
                "Number of Involuntary context switches.

                Supported on HP-UX 9.0 only on Series 800 machines."
         ::= { smSiaSystemProcessEntry 38 }

smSiaSystemProcessArguments OBJECT-TYPE
        SYNTAX  DisplayString
        ACCESS  read-only
        STATUS  mandatory
        DESCRIPTION
                "Process command syntax in full path"
        ::= { smSiaSystemProcessEntry 39 }

smSiaSystemProcessSignal OBJECT-TYPE
        SYNTAX  INTEGER {
    sighup( 1),      -- hangup, generated when terminal disconnects
    sigint( 2),      -- interrupt, generated from terminal special char
    sigquit( 3),     -- (*) quit, generated from terminal special char
    sigill( 4),      -- (*) illegal instruction(not reset when caught)
    sigtrap( 5),     -- (*) trace trap(not reset when caught)
    sigabrt( 6),     -- (*) abort process
    sigemt( 7),      -- EMT intruction
    sigfpe( 8),      -- (*) floating point exception
    sigkill( 9),     -- kill(cannot be caught or ignored)
    sigbus(10),      -- (*) bus error(specification exception)
    sigsegv(11),     -- (*) segmentation violation
    sigsys(12),      -- (*) bad argument to system call
    sigpipe(13),     -- write on a pipe with no one to read it
    sigalrm(14),     -- alarm clock timeout
    sigterm(15),     -- software termination signal
    sigurg(16),      -- (+) urgent contition on I/O channel
    sigstop(17),     -- (@) stop(cannot be caught or ignored)
    sigtstp(18),     -- (@) interactive stop
    sigcont(19),     -- (!) continue(cannot be caught or ignored)
    sigchld(20),     -- (+) sent to parent on child stop or exit
    sigttin(21),     -- (@) background read attempted from control terminal
    sigttou(22),     -- (@) background write attempted to control terminal
    sigio(23),       -- (+) I/O possible, or completed
    sigxcpu(24),     -- cpu time limit exceeded(see setrlimit())
    sigxfsz(25),     -- file size limit exceeded(see setrlimit())
    sigmsg(27),      -- input data is in the HFT ring buffer
    sigwinch(28),    -- (+) window size changed
    sigpwr(29),      -- (+) power-fail restart
    sigusr1(30),     -- user defined signal 1
    sigusr2(31),     -- user defined signal2
    sigprof(32),     -- profiling time alarm(see setitimer)
    sigdanger(33),   -- system crash imminent; free up some page space
    sigvtalrm(34),   -- virtual time alarm(see setitimer)
    sigmigrate(35),  -- migrate process(see TCF)
    sigpre(36),      -- programming exception
    sigvirt(37),     -- AIX virtual time alarm
    siggrant(60),    -- HFT monitor mode granted
    sigretract(61),  -- HFT monitor mode should be relinguished
    sigsound(62),    -- HFT sound control has completed
    sigsak(63)       -- secure attention key
                }
        ACCESS  read-write
        STATUS  mandatory
        DESCRIPTION
                "Sends a signal to process when set
                 Currently reserved.

                 Not supported on HP-UX."
        ::= { smSiaSystemProcessEntry 40 }


--
--  The Users Group
--

smSiaSystemUsersLoggedIn OBJECT-TYPE
        SYNTAX  Gauge
        ACCESS  read-only
        STATUS  mandatory
        DESCRIPTION
                "The number of users logged in"
        ::= { smSiaSystemUsers 1 }

--  The Users Table

smSiaSystemUsersTable OBJECT-TYPE
        SYNTAX  SEQUENCE OF SmSiaSystemUsersEntry
        ACCESS  not-accessible
        STATUS  mandatory
        DESCRIPTION
                "User table."
        ::= { smSiaSystemUsers 2 }

smSiaSystemUsersEntry OBJECT-TYPE
        SYNTAX  SmSiaSystemUsersEntry
        ACCESS  not-accessible
        STATUS  mandatory
        DESCRIPTION
                "Each entry contains objects for a particular user."
	INDEX { smSiaSystemUsersName, smSiaSystemUsersPID }
        ::= { smSiaSystemUsersTable 1 }

SmSiaSystemUsersEntry ::= SEQUENCE {
    smSiaSystemUsersName
        DisplayString,
    smSiaSystemUsersLine
        DisplayString,
    smSiaSystemUsersTime
        DisplayString,
    smSiaSystemUsersPID
        INTEGER,
    smSiaSystemUsersRemoteHost
        DisplayString
}

smSiaSystemUsersName OBJECT-TYPE
        SYNTAX  DisplayString
        ACCESS  read-only
        STATUS  mandatory
        DESCRIPTION
                "User name"
        ::= { smSiaSystemUsersEntry 1 }

smSiaSystemUsersLine OBJECT-TYPE
        SYNTAX  DisplayString
        ACCESS  read-only
        STATUS  mandatory
        DESCRIPTION
                "Device name"
        ::= { smSiaSystemUsersEntry 2 }

smSiaSystemUsersTime OBJECT-TYPE
        SYNTAX  DisplayString
        ACCESS  read-only
        STATUS  mandatory
        DESCRIPTION
                "Login time"
        ::= { smSiaSystemUsersEntry 3 }

smSiaSystemUsersPID OBJECT-TYPE
        SYNTAX  INTEGER
        ACCESS  read-only
        STATUS  mandatory
        DESCRIPTION
                "Process ID."
        ::= { smSiaSystemUsersEntry 4 }

smSiaSystemUsersRemoteHost OBJECT-TYPE
        SYNTAX  DisplayString
        ACCESS  read-only
        STATUS  mandatory
        DESCRIPTION
                "Remote hostname.  This is a good variable to watch
                 for security appliations.  Monitor for unknown
                 hostnames and send a trap when one is found."
        ::= { smSiaSystemUsersEntry 5 }


--
--  The Miscellaneous group
--

smSiaSystemMiscellaneousTimeText OBJECT-TYPE
	SYNTAX  DisplayString
	ACCESS  read-only
	STATUS  mandatory
	DESCRIPTION
            "Current System Time"
	::= { smSiaSystemMiscellaneous 1 }

smSiaSystemMiscellaneousTime OBJECT-TYPE
	SYNTAX  Counter
	ACCESS  read-only
	STATUS  mandatory
	DESCRIPTION
            "Current system time, seconds since reference time"
	::= { smSiaSystemMiscellaneous 2 }

smSiaSystemMiscellaneousRandom OBJECT-TYPE
	SYNTAX  INTEGER
	ACCESS  read-only
	STATUS  mandatory
	DESCRIPTION
            "A random number generated by the random() call"
	::= { smSiaSystemMiscellaneous 3 }

smSiaSystemMiscellaneousFreeSpace OBJECT-TYPE
	SYNTAX  INTEGER
	ACCESS  read-only
	STATUS  mandatory
	DESCRIPTION
            "Unallocated space in active volume groups, in kilobytes.

             Not supported on HP-UX, Sun Solaris 2.4 and Digital UNIX."
	::= { smSiaSystemMiscellaneous 4 }

smSiaSystemMiscellaneousPublicKey OBJECT-TYPE
	SYNTAX  DisplayString
	ACCESS  read-write
	STATUS  mandatory
	DESCRIPTION
            "Reserved."
	::= { smSiaSystemMiscellaneous 5 }

smSiaSystemMiscellaneousLocalSocket OBJECT-TYPE
	SYNTAX  INTEGER
	ACCESS  read-only
	STATUS  mandatory
	DESCRIPTION
            "Reserved."
	::= { smSiaSystemMiscellaneous 6 }


--
--  The Utilization Group
--

smSiaSystemUtilizationCPU       OBJECT IDENTIFIER ::= { smSiaSystemUtilization 1 }
smSiaSystemUtilizationKernel    OBJECT IDENTIFIER ::= { smSiaSystemUtilization 2 }
smSiaSystemUtilizationIostat    OBJECT IDENTIFIER ::= { smSiaSystemUtilization 3 }

smSiaSystemUtilizationCPUPollingInterval OBJECT-TYPE
        SYNTAX  INTEGER
        ACCESS  read-only
        STATUS  mandatory
        DESCRIPTION
                "Polling Interval for CPU data
                 Currently reserved."
        ::= { smSiaSystemUtilizationCPU 1 }

smSiaSystemUtilizationCPUCount OBJECT-TYPE
        SYNTAX  INTEGER
        ACCESS  read-only
        STATUS  mandatory
        DESCRIPTION
                "Number of CPUs in system"
        ::= { smSiaSystemUtilizationCPU 2 }

--
--  The CPU Utilization Table
--

smSiaSystemUtilizationCPUTable OBJECT-TYPE
        SYNTAX  SEQUENCE OF SmSiaSystemUtilizationCPUEntry
        ACCESS  not-accessible
        STATUS  mandatory
        DESCRIPTION
                "CPU Utilization table."
        ::= { smSiaSystemUtilizationCPU 3 }

smSiaSystemUtilizationCPUEntry OBJECT-TYPE
        SYNTAX  SmSiaSystemUtilizationCPUEntry
        ACCESS  not-accessible
        STATUS  mandatory
        DESCRIPTION
                "Each entry contains CPU over a different interval"
        INDEX { smSiaSystemUtilizationCPUIntervalName }
        ::= { smSiaSystemUtilizationCPUTable 1 }

SmSiaSystemUtilizationCPUEntry ::= SEQUENCE {
    smSiaSystemUtilizationCPUIntervalName
        DisplayString,
    smSiaSystemUtilizationCPUIntervalStartTime
        DisplayString,
    smSiaSystemUtilizationCPUIntervalLength
        TimeTicks,
    smSiaSystemUtilizationCPUUser
        INTEGER,
    smSiaSystemUtilizationCPUSystem
        INTEGER,
    smSiaSystemUtilizationCPUIdle
        INTEGER,
    smSiaSystemUtilizationCPUWait
        INTEGER,
    smSiaSystemUtilizationCPUBusy
        INTEGER,
    smSiaSystemUtilizationCPUUserMinimum
        INTEGER,
    smSiaSystemUtilizationCPUSystemMinimum
        INTEGER,
    smSiaSystemUtilizationCPUIdleMinimum
        INTEGER,
    smSiaSystemUtilizationCPUWaitMinimum
        INTEGER,
    smSiaSystemUtilizationCPUBusyMinimum
        INTEGER,
    smSiaSystemUtilizationCPUUserMaximum
        INTEGER,
    smSiaSystemUtilizationCPUSystemMaximum
        INTEGER,
    smSiaSystemUtilizationCPUIdleMaximum
        INTEGER,
    smSiaSystemUtilizationCPUWaitMaximum
        INTEGER,
    smSiaSystemUtilizationCPUBusyMaximum
        INTEGER,
    smSiaSystemUtilizationCPUNumber
        INTEGER
}

smSiaSystemUtilizationCPUIntervalName OBJECT-TYPE
        SYNTAX  DisplayString
        ACCESS  read-only
        STATUS  mandatory
        DESCRIPTION
                "Description of interval"
        ::= { smSiaSystemUtilizationCPUEntry 1 }

smSiaSystemUtilizationCPUIntervalStartTime OBJECT-TYPE
        SYNTAX  DisplayString
        ACCESS  read-only
        STATUS  mandatory
        DESCRIPTION
                "Start time of interval"
        ::= { smSiaSystemUtilizationCPUEntry 2 }

smSiaSystemUtilizationCPUIntervalLength OBJECT-TYPE
        SYNTAX  TimeTicks
        ACCESS  read-only
        STATUS  mandatory
        DESCRIPTION
                "Length of Interval over which CPU computed"
        ::= { smSiaSystemUtilizationCPUEntry 3 }

smSiaSystemUtilizationCPUUser OBJECT-TYPE
        SYNTAX  INTEGER
        ACCESS  read-only
        STATUS  mandatory
        DESCRIPTION
                "Average Percent CPU in user mode over the interval.
                 Monitor this value to get inforamtion about utilization
                 of CPU in user mode.  This information can also be
                 retrieved using the vmstat or iostat command."
        ::= { smSiaSystemUtilizationCPUEntry 4 }

smSiaSystemUtilizationCPUSystem OBJECT-TYPE
        SYNTAX  INTEGER
        ACCESS  read-only
        STATUS  mandatory
        DESCRIPTION
                "Average Percent CPU in system mode over the interval:
                 the count is incremented whenever the current running
                 process executes in the kernel mode.  This information
                 can also be retrieved using the vmstat or iostat commands."
        ::= { smSiaSystemUtilizationCPUEntry 5 }

smSiaSystemUtilizationCPUIdle OBJECT-TYPE
        SYNTAX  INTEGER
        ACCESS  read-only
        STATUS  mandatory
        DESCRIPTION
                "Average Percent CPU in idle mode over the interval:
                 the cpu idle count is incremented whenever the 'wait'
                 process is the current running process."
        ::= { smSiaSystemUtilizationCPUEntry 6 }

smSiaSystemUtilizationCPUWait OBJECT-TYPE
        SYNTAX  INTEGER
        ACCESS  read-only
        STATUS  mandatory
        DESCRIPTION
                "Average Percent CPU in wait mode over the interval.
                 The count is incremented whenever the current running
                 process is waiting for a block i/o request to complete."
        ::= { smSiaSystemUtilizationCPUEntry 7 }

smSiaSystemUtilizationCPUBusy OBJECT-TYPE
        SYNTAX  INTEGER
        ACCESS  read-only
        STATUS  mandatory
        DESCRIPTION
                "Average Percent CPU in user and system mode over the
                interval.  Gives a good indication of of CPU utilization
                for the whole system.  This information can also be
                retrieved using the vmstat or iostat commands.

                "
        ::= { smSiaSystemUtilizationCPUEntry 8 }

smSiaSystemUtilizationCPUUserMinimum OBJECT-TYPE
        SYNTAX  INTEGER
        ACCESS  read-only
        STATUS  mandatory
        DESCRIPTION
                "Minimum Percent CPU user mode"
        ::= { smSiaSystemUtilizationCPUEntry 9 }

smSiaSystemUtilizationCPUSystemMinimum OBJECT-TYPE
        SYNTAX  INTEGER
        ACCESS  read-only
        STATUS  mandatory
        DESCRIPTION
                "Minimum Percent CPU system mode"
        ::= { smSiaSystemUtilizationCPUEntry 10 }

smSiaSystemUtilizationCPUIdleMinimum OBJECT-TYPE
        SYNTAX  INTEGER
        ACCESS  read-only
        STATUS  mandatory
        DESCRIPTION
                "Minimum Percent CPU idle mode"
        ::= { smSiaSystemUtilizationCPUEntry 11 }

smSiaSystemUtilizationCPUWaitMinimum OBJECT-TYPE
        SYNTAX  INTEGER
        ACCESS  read-only
        STATUS  mandatory
        DESCRIPTION
                "Minimum Percent CPU idle mode"
        ::= { smSiaSystemUtilizationCPUEntry 12 }

smSiaSystemUtilizationCPUBusyMinimum OBJECT-TYPE
        SYNTAX  INTEGER
        ACCESS  read-only
        STATUS  mandatory
        DESCRIPTION
                "Minimum Percent CPU user and system mode

                 "
        ::= { smSiaSystemUtilizationCPUEntry 13 }


smSiaSystemUtilizationCPUUserMaximum OBJECT-TYPE
        SYNTAX  INTEGER
        ACCESS  read-only
        STATUS  mandatory
        DESCRIPTION
                "Maximum Percent CPU user mode"
        ::= { smSiaSystemUtilizationCPUEntry 14 }

smSiaSystemUtilizationCPUSystemMaximum OBJECT-TYPE
        SYNTAX  INTEGER
        ACCESS  read-only
        STATUS  mandatory
        DESCRIPTION
                "Maximum Percent CPU system mode"
        ::= { smSiaSystemUtilizationCPUEntry 15 }

smSiaSystemUtilizationCPUIdleMaximum OBJECT-TYPE
        SYNTAX  INTEGER
        ACCESS  read-only
        STATUS  mandatory
        DESCRIPTION
                "Maximum Percent CPU idle mode"
        ::= { smSiaSystemUtilizationCPUEntry 16 }

smSiaSystemUtilizationCPUWaitMaximum OBJECT-TYPE
        SYNTAX  INTEGER
        ACCESS  read-only
        STATUS  mandatory
        DESCRIPTION
                "Maximum Percent CPU idle mode"
        ::= { smSiaSystemUtilizationCPUEntry 17 }

smSiaSystemUtilizationCPUBusyMaximum OBJECT-TYPE
        SYNTAX  INTEGER
        ACCESS  read-only
        STATUS  mandatory
        DESCRIPTION
                "Maximum Percent CPU user and system mode.

                 "
        ::= { smSiaSystemUtilizationCPUEntry 18 }

smSiaSystemUtilizationCPUNumber OBJECT-TYPE
        SYNTAX  INTEGER
        ACCESS  read-only
        STATUS  mandatory
        DESCRIPTION
                "CPU Number this row applies to "
        ::= { smSiaSystemUtilizationCPUEntry 19 }

--
--  The Kernel Statistics Subtree
--

smSiaSystemUtilizationKernelPollingInterval OBJECT-TYPE
        SYNTAX  INTEGER
        ACCESS  read-only
        STATUS  mandatory
        DESCRIPTION
                "Polling Interval for Utilization kernel data.
                 Currently reserved."
        ::= { smSiaSystemUtilizationKernel 1 }

--
--  The UtilizationKernel Statistics  Table
--

smSiaSystemUtilizationKernelTable OBJECT-TYPE
        SYNTAX  SEQUENCE OF SmSiaSystemUtilizationKernelEntry
        ACCESS  not-accessible
        STATUS  mandatory
        DESCRIPTION
                "Kernel statistics table."
        ::= { smSiaSystemUtilizationKernel 2 }

smSiaSystemUtilizationKernelEntry OBJECT-TYPE
        SYNTAX  SmSiaSystemUtilizationKernelEntry
        ACCESS  not-accessible
        STATUS  mandatory
        DESCRIPTION
                "Each entry contains Utilization Kernel over a different
                interval"
        INDEX { smSiaSystemUtilizationKernelName }
        ::= { smSiaSystemUtilizationKernelTable 1 }

SmSiaSystemUtilizationKernelEntry ::= SEQUENCE {
    smSiaSystemUtilizationKernelName
        DisplayString,
    smSiaSystemUtilizationKernelIntervalStartTime
        DisplayString,
    smSiaSystemUtilizationKernelIntervalLength
        TimeTicks,
    smSiaSystemUtilizationKernelContextSwitches
        INTEGER,
    smSiaSystemUtilizationKernelSystemCalls
        INTEGER,
    smSiaSystemUtilizationKernelSystemReads
        INTEGER,
    smSiaSystemUtilizationKernelSystemWrites
        INTEGER,
    smSiaSystemUtilizationKernelForks
        INTEGER,
    smSiaSystemUtilizationKernelExecs
        INTEGER,
    smSiaSystemUtilizationKernelRunQueue
        INTEGER,
    smSiaSystemUtilizationKernelSwapQueue
        INTEGER,
    smSiaSystemUtilizationKernelSemaphores
        INTEGER,
    smSiaSystemUtilizationKernelMessages
        INTEGER,
    smSiaSystemUtilizationKernelProcessOverflow
        INTEGER,
    smSiaSystemUtilizationKernelBytesRead
        INTEGER,
    smSiaSystemUtilizationKernelBytesWritten
        INTEGER,
    smSiaSystemUtilizationKernelRawTTYOut
        INTEGER,
    smSiaSystemUtilizationKernelContextSwitchesMinimum
        INTEGER,
    smSiaSystemUtilizationKernelSystemCallsMinimum
        INTEGER,
    smSiaSystemUtilizationKernelSystemReadsMinimum
        INTEGER,
    smSiaSystemUtilizationKernelSystemWritesMinimum
        INTEGER,
    smSiaSystemUtilizationKernelForksMinimum
        INTEGER,
    smSiaSystemUtilizationKernelExecsMinimum
        INTEGER,
    smSiaSystemUtilizationKernelRunQueueMinimum
        INTEGER,
    smSiaSystemUtilizationKernelSwapQueueMinimum
        INTEGER,
    smSiaSystemUtilizationKernelSemaphoresMinimum
        INTEGER,
    smSiaSystemUtilizationKernelMessagesMinimum
        INTEGER,
    smSiaSystemUtilizationKernelProcessOverflowMinimum
        INTEGER,
    smSiaSystemUtilizationKernelBytesReadMinimum
        INTEGER,
    smSiaSystemUtilizationKernelBytesWrittenMinimum
        INTEGER,
    smSiaSystemUtilizationKernelRawTTYOutMinimum
        INTEGER,
    smSiaSystemUtilizationKernelContextSwitchesMaximum
        INTEGER,
    smSiaSystemUtilizationKernelSystemCallsMaximum
        INTEGER,
    smSiaSystemUtilizationKernelSystemReadsMaximum
        INTEGER,
    smSiaSystemUtilizationKernelSystemWritesMaximum
        INTEGER,
    smSiaSystemUtilizationKernelForksMaximum
        INTEGER,
    smSiaSystemUtilizationKernelExecsMaximum
        INTEGER,
    smSiaSystemUtilizationKernelRunQueueMaximum
        INTEGER,
    smSiaSystemUtilizationKernelSwapQueueMaximum
        INTEGER,
    smSiaSystemUtilizationKernelSemaphoresMaximum
        INTEGER,
    smSiaSystemUtilizationKernelMessagesMaximum
        INTEGER,
    smSiaSystemUtilizationKernelProcessOverflowMaximum
        INTEGER,
    smSiaSystemUtilizationKernelBytesReadMaximum
        INTEGER,
    smSiaSystemUtilizationKernelBytesWrittenMaximum
        INTEGER,
    smSiaSystemUtilizationKernelRawTTYOutMaximum
        INTEGER
}

smSiaSystemUtilizationKernelName OBJECT-TYPE
        SYNTAX  DisplayString
        ACCESS  read-only
        STATUS  mandatory
        DESCRIPTION
                "Description of interval"
        ::= { smSiaSystemUtilizationKernelEntry 1 }

smSiaSystemUtilizationKernelIntervalStartTime OBJECT-TYPE
        SYNTAX  DisplayString
        ACCESS  read-only
        STATUS  mandatory
        DESCRIPTION
                "Start time of interval- gives the date and time
                 at which the interval started"
        ::= { smSiaSystemUtilizationKernelEntry 2 }

smSiaSystemUtilizationKernelIntervalLength OBJECT-TYPE
        SYNTAX  TimeTicks
        ACCESS  read-only
        STATUS  mandatory
        DESCRIPTION
                "Length of Interval over which Utilization Kernel computed"
        ::= { smSiaSystemUtilizationKernelEntry 3 }

smSiaSystemUtilizationKernelContextSwitches OBJECT-TYPE
        SYNTAX  INTEGER
        ACCESS  read-only
        STATUS  mandatory
        DESCRIPTION
                "The number of context switches per second observed in
                 the sample interval"
        ::= { smSiaSystemUtilizationKernelEntry 4 }

smSiaSystemUtilizationKernelSystemCalls OBJECT-TYPE
        SYNTAX  INTEGER
        ACCESS  read-only
        STATUS  mandatory
        DESCRIPTION
                "The number of system calls per second observed in
                 the sample interval"
        ::= { smSiaSystemUtilizationKernelEntry 5 }

smSiaSystemUtilizationKernelSystemReads OBJECT-TYPE
        SYNTAX  INTEGER
        ACCESS  read-only
        STATUS  mandatory
        DESCRIPTION
                "Total number of system reads"
        ::= { smSiaSystemUtilizationKernelEntry 6 }

smSiaSystemUtilizationKernelSystemWrites OBJECT-TYPE
        SYNTAX  INTEGER
        ACCESS  read-only
        STATUS  mandatory
        DESCRIPTION
                "Total number of system writes"
         ::= { smSiaSystemUtilizationKernelEntry 7 }

smSiaSystemUtilizationKernelForks OBJECT-TYPE
        SYNTAX  INTEGER
        ACCESS  read-only
        STATUS  mandatory
        DESCRIPTION
                "Total number of forks system calls"
         ::= { smSiaSystemUtilizationKernelEntry 8 }

smSiaSystemUtilizationKernelExecs OBJECT-TYPE
        SYNTAX  INTEGER
        ACCESS  read-only
        STATUS  mandatory
        DESCRIPTION
                "Total number of EXEC system calls"
         ::= { smSiaSystemUtilizationKernelEntry 9 }

smSiaSystemUtilizationKernelRunQueue OBJECT-TYPE
        SYNTAX  INTEGER
        ACCESS  read-only
        STATUS  mandatory
        DESCRIPTION
                "Number of jobs per second placed on the run queue
                 during the interval. The processes placed in the run
                 queue are the processes that are ready to run."
         ::= { smSiaSystemUtilizationKernelEntry 10 }

smSiaSystemUtilizationKernelSwapQueue OBJECT-TYPE
        SYNTAX  INTEGER
        ACCESS  read-only
        STATUS  mandatory
        DESCRIPTION
                "Number of jobs per second placed on the swap queue. These
                 are the processes that are inactive because they are waiting
                 to be paged in."
          ::= { smSiaSystemUtilizationKernelEntry 11 }

smSiaSystemUtilizationKernelSemaphores OBJECT-TYPE
        SYNTAX  INTEGER
        ACCESS  read-only
        STATUS  mandatory
        DESCRIPTION
                "Total number of semaphore operations"
         ::= { smSiaSystemUtilizationKernelEntry 12 }

smSiaSystemUtilizationKernelMessages OBJECT-TYPE
        SYNTAX  INTEGER
        ACCESS  read-only
        STATUS  mandatory
        DESCRIPTION
                "Total number of message operations."
        ::= { smSiaSystemUtilizationKernelEntry 13 }

smSiaSystemUtilizationKernelProcessOverflow OBJECT-TYPE
        SYNTAX  INTEGER
        ACCESS  read-only
        STATUS  mandatory
        DESCRIPTION
                "Total number of process creation failures: this
                 field is incremented by one whenever an attempt
                 is made to create a kernel process and one of the
                 following happens:
                      - the user has forked to the maximum limit the
                        user is allowed
                           or
                      - the configuration limit of processes has been
                        reached."
        ::= { smSiaSystemUtilizationKernelEntry 14 }

smSiaSystemUtilizationKernelBytesRead OBJECT-TYPE
        SYNTAX  INTEGER
        ACCESS  read-only
        STATUS  mandatory
        DESCRIPTION
                "Total bytes read.

                 This variable is not supported on HP-UX."
        ::= { smSiaSystemUtilizationKernelEntry 15 }

smSiaSystemUtilizationKernelBytesWritten OBJECT-TYPE
        SYNTAX  INTEGER
        ACCESS  read-only
        STATUS  mandatory
        DESCRIPTION
                "Total bytes written.

                 This variable is not supported on HP-UX."
        ::= { smSiaSystemUtilizationKernelEntry 16 }

smSiaSystemUtilizationKernelRawTTYOut OBJECT-TYPE
        SYNTAX  INTEGER
        ACCESS  read-only
        STATUS  mandatory
        DESCRIPTION
                "Total raw TTY out count"
         ::= { smSiaSystemUtilizationKernelEntry 17 }

smSiaSystemUtilizationKernelContextSwitchesMinimum OBJECT-TYPE
        SYNTAX  INTEGER
        ACCESS  read-only
        STATUS  mandatory
        DESCRIPTION
                "Minimum context switches"
        ::= { smSiaSystemUtilizationKernelEntry 18 }

smSiaSystemUtilizationKernelSystemCallsMinimum OBJECT-TYPE
        SYNTAX  INTEGER
        ACCESS  read-only
        STATUS  mandatory
        DESCRIPTION
                "Minimum system calls"
        ::= { smSiaSystemUtilizationKernelEntry 19 }

smSiaSystemUtilizationKernelSystemReadsMinimum OBJECT-TYPE
        SYNTAX  INTEGER
        ACCESS  read-only
        STATUS  mandatory
        DESCRIPTION
                "Minimum system reads."
        ::= { smSiaSystemUtilizationKernelEntry 20 }

smSiaSystemUtilizationKernelSystemWritesMinimum OBJECT-TYPE
        SYNTAX  INTEGER
        ACCESS  read-only
        STATUS  mandatory
        DESCRIPTION
                "Minimum system writes."
        ::= { smSiaSystemUtilizationKernelEntry 21 }

smSiaSystemUtilizationKernelForksMinimum OBJECT-TYPE
        SYNTAX  INTEGER
        ACCESS  read-only
        STATUS  mandatory
        DESCRIPTION
                "Minimum forks"
        ::= { smSiaSystemUtilizationKernelEntry 22 }

smSiaSystemUtilizationKernelExecsMinimum OBJECT-TYPE
        SYNTAX  INTEGER
        ACCESS  read-only
        STATUS  mandatory
        DESCRIPTION
                "Minimum execs."
        ::= { smSiaSystemUtilizationKernelEntry 23 }

smSiaSystemUtilizationKernelRunQueueMinimum OBJECT-TYPE
        SYNTAX  INTEGER
        ACCESS  read-only
        STATUS  mandatory
        DESCRIPTION
                "Minimum run queue length"
        ::= { smSiaSystemUtilizationKernelEntry 24 }

smSiaSystemUtilizationKernelSwapQueueMinimum OBJECT-TYPE
        SYNTAX  INTEGER
        ACCESS  read-only
        STATUS  mandatory
        DESCRIPTION
                "Minimum swap queue length"
        ::= { smSiaSystemUtilizationKernelEntry 25 }

smSiaSystemUtilizationKernelSemaphoresMinimum OBJECT-TYPE
        SYNTAX  INTEGER
        ACCESS  read-only
        STATUS  mandatory
        DESCRIPTION
                "Minimum semaphore operations."
         ::= { smSiaSystemUtilizationKernelEntry 26 }

smSiaSystemUtilizationKernelMessagesMinimum OBJECT-TYPE
        SYNTAX  INTEGER
        ACCESS  read-only
        STATUS  mandatory
        DESCRIPTION
                "Minimum message operations."
        ::= { smSiaSystemUtilizationKernelEntry 27 }

smSiaSystemUtilizationKernelProcessOverflowMinimum OBJECT-TYPE
        SYNTAX  INTEGER
        ACCESS  read-only
        STATUS  mandatory
        DESCRIPTION
                "Minimum process creation failures."
        ::= { smSiaSystemUtilizationKernelEntry 28 }

smSiaSystemUtilizationKernelBytesReadMinimum OBJECT-TYPE
        SYNTAX  INTEGER
        ACCESS  read-only
        STATUS  mandatory
        DESCRIPTION
                "Minimum bytes read

                 Not supported on HP-UX."
        ::= { smSiaSystemUtilizationKernelEntry 29 }

smSiaSystemUtilizationKernelBytesWrittenMinimum OBJECT-TYPE
        SYNTAX  INTEGER
        ACCESS  read-only
        STATUS  mandatory
        DESCRIPTION
                "Minimum bytes written

                 Not supported on HP-UX."
        ::= { smSiaSystemUtilizationKernelEntry 30 }

smSiaSystemUtilizationKernelRawTTYOutMinimum OBJECT-TYPE
        SYNTAX  INTEGER
        ACCESS  read-only
        STATUS  mandatory
        DESCRIPTION
                "Minimum raw TTY out count"
        ::= { smSiaSystemUtilizationKernelEntry 31 }

smSiaSystemUtilizationKernelContextSwitchesMaximum OBJECT-TYPE
        SYNTAX  INTEGER
        ACCESS  read-only
        STATUS  mandatory
        DESCRIPTION
                "Maximum context switches"
        ::= { smSiaSystemUtilizationKernelEntry 32 }

smSiaSystemUtilizationKernelSystemCallsMaximum OBJECT-TYPE
        SYNTAX  INTEGER
        ACCESS  read-only
        STATUS  mandatory
        DESCRIPTION
                "Maximum system calls"
        ::= { smSiaSystemUtilizationKernelEntry 33 }

smSiaSystemUtilizationKernelSystemReadsMaximum OBJECT-TYPE
        SYNTAX  INTEGER
        ACCESS  read-only
        STATUS  mandatory
        DESCRIPTION
                "Maximum system reads

                 Not supported on HP-UX."
        ::= { smSiaSystemUtilizationKernelEntry 34 }

smSiaSystemUtilizationKernelSystemWritesMaximum OBJECT-TYPE
        SYNTAX  INTEGER
        ACCESS  read-only
        STATUS  mandatory
        DESCRIPTION
                "Maximum system writes."
        ::= { smSiaSystemUtilizationKernelEntry 35 }

smSiaSystemUtilizationKernelForksMaximum OBJECT-TYPE
        SYNTAX  INTEGER
        ACCESS  read-only
        STATUS  mandatory
        DESCRIPTION
                "Maximum forks"
        ::= { smSiaSystemUtilizationKernelEntry 36 }

smSiaSystemUtilizationKernelExecsMaximum OBJECT-TYPE
        SYNTAX  INTEGER
        ACCESS  read-only
        STATUS  mandatory
        DESCRIPTION
                "Maximum execs."
        ::= { smSiaSystemUtilizationKernelEntry 37 }

smSiaSystemUtilizationKernelRunQueueMaximum OBJECT-TYPE
        SYNTAX  INTEGER
        ACCESS  read-only
        STATUS  mandatory
        DESCRIPTION
                "Maximum run queue length"
        ::= { smSiaSystemUtilizationKernelEntry 38 }

smSiaSystemUtilizationKernelSwapQueueMaximum OBJECT-TYPE
        SYNTAX  INTEGER
        ACCESS  read-only
        STATUS  mandatory
        DESCRIPTION
                "Maximum swap queue length"
        ::= { smSiaSystemUtilizationKernelEntry 39 }

smSiaSystemUtilizationKernelSemaphoresMaximum OBJECT-TYPE
        SYNTAX  INTEGER
        ACCESS  read-only
        STATUS  mandatory
        DESCRIPTION
                "Maximum semaphore operations."
        ::= { smSiaSystemUtilizationKernelEntry 40 }

smSiaSystemUtilizationKernelMessagesMaximum OBJECT-TYPE
        SYNTAX  INTEGER
        ACCESS  read-only
        STATUS  mandatory
        DESCRIPTION
                "Maximum message operations."
        ::= { smSiaSystemUtilizationKernelEntry 41 }

smSiaSystemUtilizationKernelProcessOverflowMaximum OBJECT-TYPE
        SYNTAX  INTEGER
        ACCESS  read-only
        STATUS  mandatory
        DESCRIPTION
                "Maximum process creation failures."
        ::= { smSiaSystemUtilizationKernelEntry 42 }

smSiaSystemUtilizationKernelBytesReadMaximum OBJECT-TYPE
        SYNTAX  INTEGER
        ACCESS  read-only
        STATUS  mandatory
        DESCRIPTION
                "Maximum bytes read

                 Not supported on HP-UX."
        ::= { smSiaSystemUtilizationKernelEntry 43 }

smSiaSystemUtilizationKernelBytesWrittenMaximum OBJECT-TYPE
        SYNTAX  INTEGER
        ACCESS  read-only
        STATUS  mandatory
        DESCRIPTION
                "Maximum bytes written

                 Not supported on HP-UX."
        ::= { smSiaSystemUtilizationKernelEntry 44 }

smSiaSystemUtilizationKernelRawTTYOutMaximum OBJECT-TYPE
        SYNTAX  INTEGER
        ACCESS  read-only
        STATUS  mandatory
        DESCRIPTION
                "Maximum raw TTY out count"
        ::= { smSiaSystemUtilizationKernelEntry 45 }


--
--  The Iostat Utilization Group
--

smSiaSystemUtilizationIostatPollingInterval OBJECT-TYPE
        SYNTAX  INTEGER
        ACCESS  read-only
        STATUS  mandatory
        DESCRIPTION
                "Polling interval for IO statistics data.
                 Currently reserved."
        ::= { smSiaSystemUtilizationIostat 1 }

--
--  The Iostat Utilization Table
--

smSiaSystemUtilizationIostatTable OBJECT-TYPE
        SYNTAX  SEQUENCE OF SmSiaSystemUtilizationIostatEntry
        ACCESS  not-accessible
        STATUS  mandatory
        DESCRIPTION
                "Input/Output statistics table.

                 On HP-UX, not supported for some types of disks.

                 On Sun Solaris, removable devices, such as cdroms,
                 must be mounted when sysinfod starts in order
                 to be entered into this table.  When the removable
                 device is dismounted and remounted later, it will
                 be treated as a new device and activities will
                 not be added to the table."
        ::= { smSiaSystemUtilizationIostat 2 }

smSiaSystemUtilizationIostatEntry OBJECT-TYPE
        SYNTAX  SmSiaSystemUtilizationIostatEntry
        ACCESS  not-accessible
        STATUS  mandatory
        DESCRIPTION
                "Each entry contains IO statistics over a different interval"
        INDEX { smSiaSystemUtilizationIostatName }
        ::= { smSiaSystemUtilizationIostatTable 1 }

SmSiaSystemUtilizationIostatEntry ::= SEQUENCE {
    smSiaSystemUtilizationIostatName
        DisplayString,
    smSiaSystemUtilizationIostatIntervalStartTime
        DisplayString,
    smSiaSystemUtilizationIostatIntervalLength
        TimeTicks,
    smSiaSystemUtilizationIostatPercentTimeActive
        INTEGER,
    smSiaSystemUtilizationIostatKilobytesTransferRate
        INTEGER,
    smSiaSystemUtilizationIostatTransfers
        INTEGER,
    smSiaSystemUtilizationIostatKilobytesRead
        INTEGER,
    smSiaSystemUtilizationIostatKilobytesWritten
        INTEGER,
    smSiaSystemUtilizationIostatPercentTimeActiveMinimum
        INTEGER,
    smSiaSystemUtilizationIostatKilobytesTransferRateMinimum
        INTEGER,
    smSiaSystemUtilizationIostatTransfersMinimum
        INTEGER,
    smSiaSystemUtilizationIostatKilobytesReadMinimum
        INTEGER,
    smSiaSystemUtilizationIostatKilobytesWrittenMinimum
        INTEGER,
    smSiaSystemUtilizationIostatPercentTimeActiveMaximum
        INTEGER,
    smSiaSystemUtilizationIostatKilobytesTransferRateMaximum
        INTEGER,
    smSiaSystemUtilizationIostatTransfersMaximum
        INTEGER,
    smSiaSystemUtilizationIostatKilobytesReadMaximum
        INTEGER,
    smSiaSystemUtilizationIostatKilobytesWrittenMaximum
        INTEGER
}

smSiaSystemUtilizationIostatName OBJECT-TYPE
        SYNTAX  DisplayString
        ACCESS  read-only
        STATUS  mandatory
        DESCRIPTION
                "Description of interval - returns hard disk name
                and the interval length"
        ::= { smSiaSystemUtilizationIostatEntry 1 }

smSiaSystemUtilizationIostatIntervalStartTime OBJECT-TYPE
        SYNTAX  DisplayString
        ACCESS  read-only
        STATUS  mandatory
        DESCRIPTION
                "Start time of interval- gives the date and time
                 at which the interval started"
        ::= { smSiaSystemUtilizationIostatEntry 2 }

smSiaSystemUtilizationIostatIntervalLength OBJECT-TYPE
        SYNTAX  TimeTicks
        ACCESS  read-only
        STATUS  mandatory
        DESCRIPTION
                "Length of interval over which IO statistics were computed"
        ::= { smSiaSystemUtilizationIostatEntry 3 }

smSiaSystemUtilizationIostatPercentTimeActive OBJECT-TYPE
        SYNTAX  INTEGER
        ACCESS  read-only
        STATUS  mandatory
        DESCRIPTION
                "Average Percent Time when the hard disk was busy:
                 that is the total time in an interval, when disk i/o
                 took place, divided by the length of interval. The result
                 is multiplied by the programControlPercentMultiplier and
                 then displayed.

                 On HP-UX, not supported for some types of disks."
        ::= { smSiaSystemUtilizationIostatEntry 4 }

smSiaSystemUtilizationIostatKilobytesTransferRate OBJECT-TYPE
        SYNTAX  INTEGER
        ACCESS  read-only
        STATUS  mandatory
        DESCRIPTION
                "Average Transfer Rate: the sum of the kilobyes read
                 and kilobytes written over an interval divided by
                 the length of the interval."
        ::= { smSiaSystemUtilizationIostatEntry 5 }

smSiaSystemUtilizationIostatTransfers OBJECT-TYPE
        SYNTAX  INTEGER
        ACCESS  read-only
        STATUS  mandatory
        DESCRIPTION
                "Average number of kilobytes transfered to and
                 from disk.

                 The value is obtained from the kernel memory
                 using field 'dk_xfers' of structure 'dkstat'
                 defined in iostat.h."
        ::= { smSiaSystemUtilizationIostatEntry 6 }

smSiaSystemUtilizationIostatKilobytesRead OBJECT-TYPE
        SYNTAX  INTEGER
        ACCESS  read-only
        STATUS  mandatory
        DESCRIPTION
                "Number of Kilobytes read over the interval

                 On HP-UX and Digital UNIX, this variable is the
                 total kilobytes transferred (read OR written) during
                 the time interval."
        ::= { smSiaSystemUtilizationIostatEntry 7 }

smSiaSystemUtilizationIostatKilobytesWritten OBJECT-TYPE
        SYNTAX  INTEGER
        ACCESS  read-only
        STATUS  mandatory
        DESCRIPTION
                "Number of kilobytes written over the interval

                 On HP-UX and Digital UNIX, this variable always
                 has a value of zero.  Statistics for kilobytes
                 written are included in the variable
                 smSiaSystemUtilizationIostatKilobytesRead."
        ::= { smSiaSystemUtilizationIostatEntry 8 }

smSiaSystemUtilizationIostatPercentTimeActiveMinimum OBJECT-TYPE
        SYNTAX  INTEGER
        ACCESS  read-only
        STATUS  mandatory
        DESCRIPTION
                "Minimum Percent Time Active"
        ::= { smSiaSystemUtilizationIostatEntry 9 }

smSiaSystemUtilizationIostatKilobytesTransferRateMinimum OBJECT-TYPE
        SYNTAX  INTEGER
        ACCESS  read-only
        STATUS  mandatory
        DESCRIPTION
                "Minimum Transfer Rate: that is sum of minimum number of
                 kilobytes read and written divided by the length of the
                 interval."
        ::= { smSiaSystemUtilizationIostatEntry 10 }

smSiaSystemUtilizationIostatTransfersMinimum OBJECT-TYPE
        SYNTAX  INTEGER
        ACCESS  read-only
        STATUS  mandatory
        DESCRIPTION
                "Minimum Number of Transfers"
        ::= { smSiaSystemUtilizationIostatEntry 11 }

smSiaSystemUtilizationIostatKilobytesReadMinimum OBJECT-TYPE
        SYNTAX  INTEGER
        ACCESS  read-only
        STATUS  mandatory
        DESCRIPTION
                "Minimum kilobytes read"
        ::= { smSiaSystemUtilizationIostatEntry 12 }

smSiaSystemUtilizationIostatKilobytesWrittenMinimum OBJECT-TYPE
        SYNTAX  INTEGER
        ACCESS  read-only
        STATUS  mandatory
        DESCRIPTION
                "Minimum kilobytes written"
        ::= { smSiaSystemUtilizationIostatEntry 13 }


smSiaSystemUtilizationIostatPercentTimeActiveMaximum OBJECT-TYPE
        SYNTAX  INTEGER
        ACCESS  read-only
        STATUS  mandatory
        DESCRIPTION
                "Maximum percentage Time Active."
        ::= { smSiaSystemUtilizationIostatEntry 14 }

smSiaSystemUtilizationIostatKilobytesTransferRateMaximum OBJECT-TYPE
        SYNTAX  INTEGER
        ACCESS  read-only
        STATUS  mandatory
        DESCRIPTION
                "Maximum Transfer Rate"
        ::= { smSiaSystemUtilizationIostatEntry 15 }

smSiaSystemUtilizationIostatTransfersMaximum OBJECT-TYPE
        SYNTAX  INTEGER
        ACCESS  read-only
        STATUS  mandatory
        DESCRIPTION
                "Maximum Number of Transfers"
        ::= { smSiaSystemUtilizationIostatEntry 16 }

smSiaSystemUtilizationIostatKilobytesReadMaximum OBJECT-TYPE
        SYNTAX  INTEGER
        ACCESS  read-only
        STATUS  mandatory
        DESCRIPTION
                "Maximum Number of Kilobytes read"
        ::= { smSiaSystemUtilizationIostatEntry 17 }

smSiaSystemUtilizationIostatKilobytesWrittenMaximum OBJECT-TYPE
        SYNTAX  INTEGER
        ACCESS  read-only
        STATUS  mandatory
        DESCRIPTION
                "Maximum Number of Kilobytes written"
        ::= { smSiaSystemUtilizationIostatEntry 18 }


--
--  The Command Table
--

smSiaCommandTable OBJECT-TYPE
        SYNTAX  SEQUENCE OF SmSiaCommandEntry
        ACCESS  not-accessible
        STATUS  mandatory
        DESCRIPTION
                "Command table."
        ::= { smSiaCommand 1 }

smSiaCommandEntry OBJECT-TYPE
        SYNTAX  SmSiaCommandEntry
        ACCESS  not-accessible
        STATUS  mandatory
        DESCRIPTION
                "Each entry contains objects for a particular command."
	INDEX { smSiaCommandName }
        ::= { smSiaCommandTable 1 }

SmSiaCommandEntry ::= SEQUENCE {
    smSiaCommandState
        INTEGER,
    smSiaCommandName
        DisplayString,
    smSiaCommandDescription
        DisplayString,
    smSiaCommandOwnerID
        DisplayString,
    smSiaCommandGetStringAndParameters
        DisplayString,
    smSiaCommandSetStringAndParameters
        DisplayString,
    smSiaCommandTimeOutValue
        INTEGER,
    smSiaCommandCountToLive
        INTEGER,
    smSiaCommandTimeToLive
        INTEGER,
    smSiaCommandOutputResultIndex
        INTEGER,
    smSiaCommandOutputRowIndex
        INTEGER,
    smSiaCommandOutputColumnIndex
        INTEGER,
    smSiaCommandDisplayStringResult
        DisplayString,
    smSiaCommandIntegerResult
        INTEGER,
    smSiaCommandCounterResult
        Counter,
    smSiaCommandGaugeResult
        Gauge,
    smSiaCommandExecutionReturnCode
        INTEGER,
    smSiaCommandStandardError
        DisplayString
}

smSiaCommandState OBJECT-TYPE
        SYNTAX  INTEGER {
                enabled(3),  -- enabled command
                disabled(1),  -- disabled command
                invalid(2)  -- an invalidated command
                }
        ACCESS  read-write
        STATUS  mandatory
        DESCRIPTION
                "State of command for execution - disabled (1),
                invalid (2), or enabled (3)."
        ::= { smSiaCommandEntry 1 }

smSiaCommandName OBJECT-TYPE
        SYNTAX  DisplayString
        ACCESS  read-write
        STATUS  mandatory
        DESCRIPTION
                "Command name for use as a label and row instance.  The
                 selection of a row in the table uses the command name as
                 the instance for the row selection.  The command name is
                 appended to the row object ID to uniquely identify the
                 instance of this variable.  For example, the instance of
                 smSiaCommandState is smSiaCommandState.smSiaCommandName,
                 where each octet in smSiaCommandName is a value in dot
                 notation for the variable."
        ::= { smSiaCommandEntry 2 }

smSiaCommandDescription OBJECT-TYPE
        SYNTAX  DisplayString
        ACCESS  read-write
        STATUS  mandatory
        DESCRIPTION
                "Command description for the command to execute."
        ::= { smSiaCommandEntry 3 }

smSiaCommandOwnerID OBJECT-TYPE
        SYNTAX  DisplayString
        ACCESS  read-write
        STATUS  mandatory
        DESCRIPTION
                "Owner ID (IP address or hostname) who generated the
                 command entry.  This must be initialized by the user."
        ::= { smSiaCommandEntry 4 }

smSiaCommandGetStringAndParameters OBJECT-TYPE
        SYNTAX  DisplayString
        ACCESS  read-write
        STATUS  mandatory
        DESCRIPTION
                "Command string and parameters for execution on a
                 GET request.  The GET request must be issued to
                 the smSiaCommandDisplayStringResult,
                 smSiaCommandIntegerResult, smSiaCommandCounterResult,
                 or smSiaCommandGaugeResult for the command to be executed.
                 Environment variables which are available on execution are:

                   SM6K_HOSTNAME={hostname running subagent}
                   SM6K_DOMAIN_NAME={fully qualified hostname}
                   SM6K_HOST_ADDRESS={ip address}
                   SM6K_INSTANCE_NAME={instance string of row}
                   SM6K_INSTANCE_ID={instance ASCII octet value of row}
                   SM6K_COMMAND_TIME_OUT_VALUE={value from TimeOutValue}
                   SM6K_COMMAND_OWNERID={string from OwnerID}
                   SM6K_COMMAND_RESULT_TYPE=DisplayString||Integer||Counter||
                                            Gauge
                   SM6K_COMMAND_SET_VALUE={value from get request}
                   SM6K_EXECUTION_REASON=Command_Get"
        ::= { smSiaCommandEntry 5 }

smSiaCommandSetStringAndParameters OBJECT-TYPE
        SYNTAX  DisplayString
        ACCESS  read-write
        STATUS  mandatory
        DESCRIPTION
                "Command string and parameters for execution on a
                 SET request.  The SET request must be issued to
                 the smSiaCommandDisplayStringResult,
                 smSiaCommandIntegerResult, smSiaCommandCounterResult,
                 or smSiaCommandGaugeResult for the command to be executed.
                 The SM6K_COMMAND_SET_VALUE contains the value from the SET
                 request.  If the execution of the command returns a non-zero
                 exit return code then the SET request is rejected and a
                 badValue is returned from the SNMPD agent.
                 Environment variables which are available on
                 command execution are:

                   SM6K_COMMAND_SET_VALUE={value from set request}
                   SM6K_HOSTNAME={hostname running subagent}
                   SM6K_DOMAIN_NAME={fully qualified hostname}
                   SM6K_HOST_ADDRESS={ip address}
                   SM6K_INSTANCE_NAME={instance string of row}
                   SM6K_INSTANCE_ID={instance ASCII octet value of row}
                   SM6K_COMMAND_TIME_OUT_VALUE={value from TimeOutValue}
                   SM6K_COMMAND_OWNERID={string from OwnerID}
                   SM6K_COMMAND_RESULT_TYPE=DisplayString||Integer||Counter||
                                            Gauge
                   SM6K_EXECUTION_REASON=Command_Set"
        ::= { smSiaCommandEntry 6 }

smSiaCommandTimeOutValue OBJECT-TYPE
        SYNTAX  INTEGER (0..4294967295)
        ACCESS  read-write
        STATUS  mandatory
        DESCRIPTION
                "Time out value in seconds for command execution.
                 The default is three seconds.  Time outs over twenty
                 seconds cause subagent performance degradation for
                 multiple requests which may be queued."
        ::= { smSiaCommandEntry 7 }

smSiaCommandCountToLive OBJECT-TYPE
        SYNTAX  INTEGER (0..4294967295)
        ACCESS  read-only
        STATUS  mandatory
        DESCRIPTION
                "Count to live in seconds before the command to execute
                 is executed again.  This value is a count down from the
                 time to live value.  This allows multiple GET requests
                 for parsing of the output from the command execution.
                 It also allows a SET operation followed by a GET request
                 so that the GET command is NOT executed on the GET request."
        ::= { smSiaCommandEntry 8 }

smSiaCommandTimeToLive OBJECT-TYPE
        SYNTAX  INTEGER (0..4294967295)
        ACCESS  read-write
        STATUS  mandatory
        DESCRIPTION
                "Time to live value in seconds before the GET or SET command
                 is executed based on the last time the command was run.
                 The CountToLive variable is set to this value at command
                 execution."
        ::= { smSiaCommandEntry 9 }

smSiaCommandOutputResultIndex OBJECT-TYPE
        SYNTAX  INTEGER {
                displaystring(1),  -- output result is display string
                integer(2),        -- output result is integer
                counter(3),        -- output result is counter
                gauge(4)           -- output result is gauge
                }
        ACCESS  read-write
        STATUS  mandatory
        DESCRIPTION
                "Index to point to command output result type.
                 The results of the command execution are converted
                 to the type set, displaystring, integer, counter,
                 or gauge."
        ::= { smSiaCommandEntry 10 }

smSiaCommandOutputRowIndex OBJECT-TYPE
        SYNTAX  INTEGER (0..4294967295)
        ACCESS  read-write
        STATUS  mandatory
        DESCRIPTION
                "Index for the row to be returned. New line is
                 the delimiter for row.  A value of zero returns
                 all rows.  This allows the parsing of the output
                 from the command execution by row."
        ::= { smSiaCommandEntry 11 }

smSiaCommandOutputColumnIndex OBJECT-TYPE
        SYNTAX  INTEGER (0..4294967295)
        ACCESS  read-write
        STATUS  mandatory
        DESCRIPTION
                "Index for the column to be returned. White space
                 is the delimiter for the column.  A value of zero
                 returns all columns.  This allows the parsing of the
                 output from the command execution by column."
        ::= { smSiaCommandEntry 12 }

smSiaCommandDisplayStringResult OBJECT-TYPE
        SYNTAX  DisplayString
        ACCESS  read-write
        STATUS  mandatory
        DESCRIPTION
                "Command output for ASCII."
        ::= { smSiaCommandEntry 13 }

smSiaCommandIntegerResult OBJECT-TYPE
        SYNTAX  INTEGER
        ACCESS  read-write
        STATUS  mandatory
        DESCRIPTION
                "Command result for integer.  For each get/set request the
                 response is saved as a signed integer.  The range is
                 -2147483648 to 2147483647."
        ::= { smSiaCommandEntry 14 }

smSiaCommandCounterResult OBJECT-TYPE
        SYNTAX  Counter
        ACCESS  read-write
        STATUS  mandatory
        DESCRIPTION
                "Command result for counter.  For each get/set request the
                 command response is saved as an unsigned integer.
                 The range is 0 to 4294967295."
        ::= { smSiaCommandEntry 15 }

smSiaCommandGaugeResult OBJECT-TYPE
        SYNTAX  Gauge
        ACCESS  read-write
        STATUS  mandatory
        DESCRIPTION
                "Command result for gauge.  For each get/set request the
                 command response is saved as an unsigned integer.
                 The range is 0 to 4294967295."
        ::= { smSiaCommandEntry 16 }

smSiaCommandExecutionReturnCode OBJECT-TYPE
        SYNTAX  INTEGER
        ACCESS  read-only
        STATUS  mandatory
        DESCRIPTION
                "Return code from the command execution.  This
                 value is the exit status from the command execution.
                 NOTE: because of the 'wait' system call, only the
                 lower 8 bits of the exit status is returned, so
                 negative exit codes are lost. Therefore, all return
                 codes are 0 - 255."
        ::= { smSiaCommandEntry 17 }

smSiaCommandStandardError OBJECT-TYPE
        SYNTAX  DisplayString
        ACCESS  read-only
        STATUS  mandatory
        DESCRIPTION
                "Standard error output from the command execution."
        ::= { smSiaCommandEntry 18 }


--
--  The System Information Agent Administration Table
--  This table is for the convenience of the end user.  It may be
--  used to store any desired administrative information
--

smSiaAdministrationTable OBJECT-TYPE
        SYNTAX  SEQUENCE OF SmSiaAdministrationEntry
        ACCESS  not-accessible
        STATUS  mandatory
        DESCRIPTION
                "Table of user information."
        ::= { smSiaAdministration 1 }

smSiaAdministrationEntry OBJECT-TYPE
        SYNTAX  SmSiaAdministrationEntry
        ACCESS  not-accessible
        STATUS  mandatory
        DESCRIPTION
                "Each entry contains objects for a particular
                 administrative community."
	INDEX { smSiaAdministrationFieldName }
        ::= { smSiaAdministrationTable 1 }

SmSiaAdministrationEntry ::= SEQUENCE {
	smSiaAdministrationFieldState
	INTEGER,
	smSiaAdministrationFieldName
	DisplayString,
	smSiaAdministrationFieldOwner
	DisplayString,
	smSiaAdministrationFieldDescription
	DisplayString,
	smSiaAdministrationFieldValue
	DisplayString
}

smSiaAdministrationFieldState OBJECT-TYPE
        SYNTAX  INTEGER {
                valid(1),    -- Valid information
                invalid(2),  -- used to delete an entry
                outDated(3)  -- Obsolete data
                }
        ACCESS  read-write
        STATUS  mandatory
        DESCRIPTION
                "Indication that administrative information is either
                 valid (1), invalid (2), or outdated (3).
                 Note:  Setting state to invalid will delete the row."
        ::= { smSiaAdministrationEntry 1 }

smSiaAdministrationFieldName OBJECT-TYPE
        SYNTAX  DisplayString
        ACCESS  read-write
        STATUS  mandatory
        DESCRIPTION
          "Name of administrative information.  There should be a
           corporate-wide policy on naming information in order to avoid
           possible naming conflicts."
        ::= { smSiaAdministrationEntry 2 }

smSiaAdministrationFieldOwner OBJECT-TYPE
        SYNTAX  DisplayString
        ACCESS  read-write
        STATUS  mandatory
        DESCRIPTION
           "Owner of this piece of administrative information."
        ::= { smSiaAdministrationEntry 3 }

smSiaAdministrationFieldDescription OBJECT-TYPE
        SYNTAX  DisplayString
        ACCESS  read-write
        STATUS  mandatory
        DESCRIPTION
           "Description of the administrative information."
        ::= { smSiaAdministrationEntry 4 }

smSiaAdministrationFieldValue OBJECT-TYPE
        SYNTAX  DisplayString
        ACCESS  read-write
        STATUS  mandatory
        DESCRIPTION
                "The actual administrative information."
        ::= { smSiaAdministrationEntry 5 }


--
--  The File Monitor Table
--

smSiaFileMonitorTable OBJECT-TYPE
        SYNTAX  SEQUENCE OF SmSiaFileMonitorEntry
        ACCESS  not-accessible
        STATUS  mandatory
        DESCRIPTION
                "File Monitor table."
        ::= { smSiaFileMonitor 1 }

smSiaFileMonitorEntry OBJECT-TYPE
        SYNTAX  SmSiaFileMonitorEntry
        ACCESS  not-accessible
        STATUS  mandatory
        DESCRIPTION
                "Each entry contains objects for a particular file."
	INDEX { smSiaFileMonitorName }
        ::= { smSiaFileMonitorTable 1 }

SmSiaFileMonitorEntry ::= SEQUENCE {
    smSiaFileMonitorState
        INTEGER,
    smSiaFileMonitorName
        DisplayString,
    smSiaFileMonitorType
        INTEGER,
    smSiaFileMonitorTrapState
        INTEGER,
    smSiaFileMonitorCaseState
        INTEGER,
    smSiaFileMonitorDescription
        DisplayString,
    smSiaFileMonitorOwnerID
        DisplayString,
    smSiaFileMonitorFullPathName
        DisplayString,
    smSiaFileMonitorForString
        DisplayString,
    smSiaFileMonitorActivationState
        INTEGER,
    smSiaFileMonitorActivationTime
        DisplayString,
    smSiaFileMonitorActivationDayOfWeek
        DisplayString,
    smSiaFileMonitorDeactivationTime
        DisplayString,
    smSiaFileMonitorDeactivationDayOfWeek
        DisplayString,
    smSiaFileMonitorPollTime
        DisplayString,
    smSiaFileMonitorResetToStartOfFile
        INTEGER,
    smSiaFileMonitorCurrentLineCountOfFile
        INTEGER,
    smSiaFileMonitorFoundStringCount
        INTEGER,
    smSiaFileMonitorFoundStringAtLineNumber
        INTEGER,
    smSiaFileMonitorStringFound
        DisplayString,
    smSiaFileMonitorBytePositionWithinLine
        INTEGER,
    smSiaFileMonitorCompleteLineStringFound
        DisplayString,
    smSiaFileMonitorFoundStringBytePositionWithinFile
        INTEGER,
    smSiaFileMonitorTimeLastFound
        DisplayString,
    smSiaFileMonitorCommandToExecuteTypeMet
        DisplayString,
    smSiaFileMonitorCommandToExecuteBeforeMonitor
        DisplayString,
    smSiaFileMonitorMode
        DisplayString,
    smSiaFileMonitorUserID
        DisplayString,
    smSiaFileMonitorGroupID
        DisplayString,
    smSiaFileMonitorSize
        INTEGER,
    smSiaFileMonitorTimeLastDataModification
        DisplayString,
    smSiaFileMonitorTimeLastFileStatusChange
        DisplayString,
    smSiaFileMonitorReturnCode
        INTEGER,
    smSiaFileMonitorMessages
        DisplayString
}

smSiaFileMonitorState OBJECT-TYPE
        SYNTAX  INTEGER {
                enabled(3),            -- enabled file monitor with traps
                enabledFromBegin(4),   -- enabled file monitor search always
                                       -- from the beginning of the file
                disabled(1),           -- disabled file monitor
                invalid(2)             -- an invalidated file monitor
                }
        ACCESS  read-write
        STATUS  mandatory
        DESCRIPTION
                "State of file monitor entry - disabled (1),
                 invalid (2), enabled (3), enabledFromBegin (4)."
         ::= { smSiaFileMonitorEntry 1 }

smSiaFileMonitorName OBJECT-TYPE
        SYNTAX  DisplayString
        ACCESS  read-write
        STATUS  mandatory
        DESCRIPTION
                "File Monitor name for use as a label and row instance.  The
                 selection of a row in the table uses the file monitor name as
                 the instance for the row selection.  The file monitor name is
                 appended to the row object ID to uniquely identify the
                 instance of this variable.  For example, the instance of
                 smSiaFileMonitorState is smSiaFileMonitorState.smSiaFileMonitorName,
                 where each octet in smSiaFileMonitorName is a value in dot
                 notation for the variable."
        ::= { smSiaFileMonitorEntry 2 }

smSiaFileMonitorType OBJECT-TYPE
        SYNTAX  INTEGER {
                string(1),        -- search for string in file
                dataChange(2),    -- data modification to file
                statusChange(3),  -- file permissions, owner, or group
                                  -- changed for the file
                strDataStatus(4), -- monitor string, dataChange, and
                                  -- statusChange types (1-3) above
                notExist(5),      -- file does not exist
                exist(6),         -- file exists
                all(7),           -- monitor all types (1-6) above
                notString(8)      -- string not found in file
                }
        ACCESS  read-write
        STATUS  mandatory
        DESCRIPTION
                "Type of file monitor entry - string (1), dataChange (2),
                 statusChange (3), strDataStatus (4), notExist (5), exist (6),
                 all (7), notString(8)."
         ::= { smSiaFileMonitorEntry 3 }

smSiaFileMonitorTrapState OBJECT-TYPE
        SYNTAX  INTEGER {
                send(1),  -- send traps
                noSend(2)  -- do not send traps
                }
        ACCESS  read-write
        STATUS  mandatory
        DESCRIPTION
                "Trap state for file monitor entry - send (1) or
                 noSend (2).  Not supported for Systems Monitor Version 1.
                 Type of Traps:
                   generic 6 specific 21 : String found
                   MIB variable binding: v1 = Entry name
                       v2 = Entry description
                       v3 = Full path filename
                       v4 = time string found
                       v5 = file size
                       v6 = previous file size
                       v7 = line count of file
                       v8 = search for string
                       v9 = Found string count
                      v10 = Actual string found
                      v11 = Line number string found
                      v12 = Character position in line string was found
                      v13 = complete line string was found
                      v14 = Character position in file string was found

                   generic 6 specific 22 : File data modified
                   MIB variable binding: v1 = Entry name
                       v2 = Entry description
                       v3 = Full path filename
                       v4 = Time of data modification
                       v5 = Size of file
                       v6 = previous size of file

                   generic 6 specific 23 : File status changed
                   MIB variable binding: v1 = Entry name
                       v2 = Entry description
                       v3 = Full path filename
                       v4 = Time of status change
                       v5 = mode of of file
                       v6 = userID of file
                       v7 = groupID of file
                       v8 = previous mode of of file
                       v9 = previous userID of file
                       v10 = previous groupID of file

                   generic 6 specific 24 : File does not exist
                   MIB variable binding: v1 = Entry name
                       v2 = Entry description
                       v3 = Full path filename

                   generic 6 specific 25 : File exists
                   MIB variable binding: v1 = Entry name
                       v2 = Entry description
                       v3 = Full path filename
                       v4 = Time file creation
                       v5 = mode of of file
                       v6 = userID of file
                       v7 = groupID of file

                   generic 6 specific 26 : String not found
                   MIB variable binding: v1 = Entry name
                       v2 = Entry description
                       v3 = Full path filename
                       v4 = search for string"

        ::= { smSiaFileMonitorEntry 4 }

smSiaFileMonitorCaseState OBJECT-TYPE
        SYNTAX  INTEGER {
                case(1),  -- case sensitive search
                ignoreCase(2)  -- ignore case on search
                }
        ACCESS  read-write
        STATUS  mandatory
        DESCRIPTION
                "Case state for string search: case (1) or
                 ignoreCase (2).
                 On Solaris 2.4, search is always case-sensitive."
         ::= { smSiaFileMonitorEntry 5 }

smSiaFileMonitorDescription OBJECT-TYPE
        SYNTAX  DisplayString
        ACCESS  read-write
        STATUS  mandatory
        DESCRIPTION
                "File Monitor description for this file monitor entry."
        ::= { smSiaFileMonitorEntry 6 }

smSiaFileMonitorOwnerID OBJECT-TYPE
        SYNTAX  DisplayString
        ACCESS  read-write
        STATUS  mandatory
        DESCRIPTION
                "Owner ID (IP address or hostname) who generated the
                 file monitor entry.  This must be initialized by the user."
         ::= { smSiaFileMonitorEntry 7 }

smSiaFileMonitorFullPathName OBJECT-TYPE
        SYNTAX  DisplayString
        ACCESS  read-write
        STATUS  mandatory
        DESCRIPTION
                "Full path name of file to monitor.
                 If the file already exists then the monitoring starts at
                 the last byte position in the file.  If the file is created
                 after the monitoring is enabled then searching for the string
                 is started at the beginning of the file.  If no string
                 is specified then a met condition occurs, whenever,
                 the file is modified or its status changes.  Status changes
                 are when the user, group, or mode is modified."
         ::= { smSiaFileMonitorEntry 8 }

smSiaFileMonitorForString OBJECT-TYPE
        SYNTAX  DisplayString
        ACCESS  read-write
        STATUS  mandatory
        DESCRIPTION
                "String to monitor within a file.  The string or pattern
                 can be any limited regular expression (RE) in the  style
                 of the ed or egrep command.  If the anchor symbols (^ or $)
                 are used in the regular expression then searching is done
                 only when a line is terminated by a new line (\n) character.

                 On Solaris 2.4, regular expressions are not supported."
         ::= { smSiaFileMonitorEntry 9 }

smSiaFileMonitorActivationState OBJECT-TYPE
        SYNTAX  INTEGER {
                active(2),      -- file monitor is active
                notEnabled(1),  -- file monitor not enabled in FileMonitorState
                inactive(3)     -- file monitor is not active
                }
        ACCESS  read-only
        STATUS  mandatory
        DESCRIPTION
                "This field indicates whether or not the entry is active
                 in file monitoring.  When the file monitor entry is
                 active, it is monitoring the file.  When the file monitor
                 entry is inactive, it is not monitoring the file,
                 but will start monitoring when the activation time arrives.

                 The activation state can be inactive only if
                 activation/deactivation days are specified.  Otherwise,
                 the activation state is activated when the smSiaFileMonitorState
                 field is set to enabled.  If this field is notEnabled, the
                 smSiaFileMonitorState field is not set to enabled."
         ::= { smSiaFileMonitorEntry 10 }

smSiaFileMonitorActivationTime OBJECT-TYPE
        SYNTAX  DisplayString
        ACCESS  read-write
        STATUS  mandatory
        DESCRIPTION
                "This field specifies the time to activate the file monitor
                 (ie. change the activation state from inactive to active).
                 The format should be HH:MM where HH represents the hour
                 (integer between 0 and 23) and MM represents the minute
                 (integer between 0 and 59) to activate the file monitor.
                 A value all blanks will be interpreted as 00:00."
         ::= { smSiaFileMonitorEntry 11 }

smSiaFileMonitorActivationDayOfWeek OBJECT-TYPE
        SYNTAX  DisplayString
        ACCESS  read-write
        STATUS  mandatory
        DESCRIPTION
                "This field specifies the days of the week to activate
                 the file monitor at the time specified in the ActivationTime
                 field (ie. change the activation state from inactive to
                 active).
                 The day of the week may be one of three literals:
                     none      -  Doesn't activate
                     weekdays  -  Activates file monitor entry on MTWThF
                     all       -  Activates file monitor entry every day
                                    SuMTWThFS

                 Alternatively, the days of the week may be specified as a
                 list of numbers between 0 and 6 (Sunday = 0, Monday = 1, ...,
                 Saturday = 6).  The expression '1,3,5' would activate the
                 file monitor entry at the specified time on MWF."
         ::= { smSiaFileMonitorEntry 12 }

smSiaFileMonitorDeactivationTime OBJECT-TYPE
        SYNTAX  DisplayString
        ACCESS  read-write
        STATUS  mandatory
        DESCRIPTION
                "This field specifies the time to deactivate the file monitor
                 (ie. change the activation state from active to inactive).
                 The format should be HH:MM where HH represents the hour
                 (integer between 0 and 23) and MM represents the minute
                 (integer between 0 and 59) to deactivate the file monitor.
                 A value of all blanks will be interpreted as 00:00."
         ::= { smSiaFileMonitorEntry 13 }

smSiaFileMonitorDeactivationDayOfWeek OBJECT-TYPE
        SYNTAX  DisplayString
        ACCESS  read-write
        STATUS  mandatory
        DESCRIPTION
                "This field specifies the days of the week to deactivate
                 the file monitor at the time specified in the
                 DeactivationTime field (ie. change the activation state
                 from active to inactive).
                 The day of the week may be one of three literals:
                   none      -  Doesn't deactivate
                   weekdays  -  Dectivates file monitor entry on MTWThF
                   all       -  Deactivates file monitor entry every day
                                SuMTWThFS

                 Alternatively, the days of the week may be specified as a
                 list of numbers between 0 and 6 (Sunday = 0, Monday = 1, ...,
                 Saturday = 6).  The expression '1,3,5' would deactivate the
                 file monitor entry at the specified time on MWF."
         ::= { smSiaFileMonitorEntry 14 }

smSiaFileMonitorPollTime OBJECT-TYPE
        SYNTAX  DisplayString
        ACCESS  read-write
        STATUS  mandatory
        DESCRIPTION
                "File Monitor polling time.  Polling units are decimal values
                 appended by the unit: d - day, h - hour, m - minute, or
                 s - second.  If no unit is appended, the value is minutes.
                 Multiple values/units are allowed (i.e. 1h45m = 1 hour,
                 45 minutes).
                 The default poll time is 10 seconds."
         ::= { smSiaFileMonitorEntry 15 }

smSiaFileMonitorResetToStartOfFile OBJECT-TYPE
        SYNTAX  INTEGER {
                false(1),
                true(2)
                }
        ACCESS  read-write
        STATUS  mandatory
        DESCRIPTION
                "Setting to true causes file monitoring to reset
                 to the beginning of the file.  The value of this
                 variable returns to false once the reset has occurred."
         ::= { smSiaFileMonitorEntry 16 }

smSiaFileMonitorCurrentLineCountOfFile OBJECT-TYPE
        SYNTAX  INTEGER (0..4294967295)
        ACCESS  read-only
        STATUS  mandatory
        DESCRIPTION
                "Current monitoring line count of the file.
                 Line count starts at one."
        ::= { smSiaFileMonitorEntry 17 }

smSiaFileMonitorFoundStringCount OBJECT-TYPE
        SYNTAX  INTEGER (0..4294967295)
        ACCESS  read-only
        STATUS  mandatory
        DESCRIPTION
                "Count of number of times string found within file."
         ::= { smSiaFileMonitorEntry 18 }

smSiaFileMonitorStringFound OBJECT-TYPE
        SYNTAX  DisplayString
        ACCESS  read-only
        STATUS  mandatory
        DESCRIPTION
                "String found in the file."
        ::= { smSiaFileMonitorEntry 19 }

smSiaFileMonitorFoundStringAtLineNumber OBJECT-TYPE
        SYNTAX  INTEGER (0..4294967295)
        ACCESS  read-only
        STATUS  mandatory
        DESCRIPTION
                "Line number within file string was found."
        ::= { smSiaFileMonitorEntry 20 }

smSiaFileMonitorBytePositionWithinLine OBJECT-TYPE
        SYNTAX  INTEGER (0..4294967295)
        ACCESS  read-only
        STATUS  mandatory
        DESCRIPTION
                "Character position within line number in which string
                 was found.  Character position starts at one."
         ::= { smSiaFileMonitorEntry 21 }

smSiaFileMonitorCompleteLineStringFound OBJECT-TYPE
        SYNTAX  DisplayString
        ACCESS  read-only
        STATUS  mandatory
        DESCRIPTION
                "Complete line in which string was found in the file."
        ::= { smSiaFileMonitorEntry 22 }

smSiaFileMonitorFoundStringBytePositionWithinFile OBJECT-TYPE
        SYNTAX  INTEGER (0..4294967295)
        ACCESS  read-only
        STATUS  mandatory
        DESCRIPTION
                "Character position within file in which string was found.
                 Character position starts at one."
        ::= { smSiaFileMonitorEntry 23 }

smSiaFileMonitorTimeLastFound OBJECT-TYPE
        SYNTAX  DisplayString
        ACCESS  read-only
        STATUS  mandatory
        DESCRIPTION
                "Time last found.  Format is the output of the
                 date command."
        ::= { smSiaFileMonitorEntry 24 }

smSiaFileMonitorCommandToExecuteTypeMet OBJECT-TYPE
        SYNTAX  DisplayString
        ACCESS  read-write
        STATUS  mandatory
        DESCRIPTION
                "Command to execute if the type of the file monitor
                 condition is met.  This command is run once for each
                 condtion that is met and each time a string is found
                 in the file.
                 Environment variables which are available on
                 file monitor execution are:

                   SM6K_HOSTNAME = {hostname running subagent}
                   SM6K_DOMAIN_NAME = {fully qualified hostname}
                   SM6K_HOST_ADDRESS = {ip address}
                   SM6K_INSTANCE_NAME = {instance string of row}
                   SM6K_INSTANCE_ID = {instance ASCII octet value of row}
                   SM6K_FILE_MONITOR_REASON = File_Monitor_Found_String,
                                              File_Monitor_Data_Change,
                                              File_Monitor_Status_Change,
                                              File_Monitor_Not_Exist,
                                              File_Monitor_Exist
                   SM6K_FILE_MONITOR_TYPE = {enumerated value for type}
                   SM6K_FILE_MONITOR_DESCRIPTION = {string from description field}
                   SM6K_FILE_MONITOR_OWNERID = {string from ownerid filed}
                   SM6K_FILE_MONITOR_FULL_PATH_NAME = {file name for monitor}
                   SM6K_FILE_MONITOR_FOR_STRING = {search string}
                   SM6K_FILE_MONITOR_POLL_TIME = {poll time}
                   SM6K_FILE_MONITOR_CURRENT_LINE_COUNT_OF_FILE = {line count}
                   SM6K_FILE_MONITOR_FOUND_STRING_COUNT = {string count found}
                   SM6K_FILE_MONITOR_FOUND_STRING_AT_LINE_NUMBER = {line number found}
                   SM6K_FILE_MONITOR_BYTE_POSITION_WITHIN_LINE = {position in line}
                   SM6K_FILE_MONITOR_COMPLETE_LINE_STRING_FOUND = {complete line}
                   SM6K_FILE_MONITOR_BYTE_POSITION_WITHIN_FILE = {byte count}
                   SM6K_FILE_MONITOR_STRING_FOUND = {string found}
                   SM6K_FILE_MONITOR_TIME_LAST_FOUND = {time last found}
                   SM6K_FILE_MONITOR_SIZE = {size of file}
                   SM6K_FILE_MONITOR_MODE = {mode of file}
                   SM6K_FILE_MONITOR_USERID = {userID of file}
                   SM6K_FILE_MONITOR_GROUPID = {groupID of file}
                   SM6K_FILE_MONITOR_OLD_SIZE = {previous size of file}
                   SM6K_FILE_MONITOR_OLD_MODE = {previous mode of file}
                   SM6K_FILE_MONITOR_OLD_USERID = {previous userID of file}
                   SM6K_FILE_MONITOR_OLD_GROUPID = {previous groupID of file}"

        ::= { smSiaFileMonitorEntry 25 }

smSiaFileMonitorCommandToExecuteBeforeMonitor OBJECT-TYPE
        SYNTAX  DisplayString
        ACCESS  read-write
        STATUS  mandatory
        DESCRIPTION
                "Command to execute before monitoring a file for any
                 of the types.  This MIB variable can be used to
                 generate the file prior to monitoring it.
                 Environment variables which are available on
                 file monitor execution before monitoring are:

                   SM6K_HOSTNAME = {hostname running subagent}
                   SM6K_DOMAIN_NAME = {fully qualified hostname}
                   SM6K_HOST_ADDRESS = {ip address}
                   SM6K_INSTANCE_NAME = {instance string of row}
                   SM6K_INSTANCE_ID = {instance ASCII octet value of row}
                   SM6K_FILE_MONITOR_REASON = File_Monitor_Before_Monitor
                   SM6K_FILE_MONITOR_TYPE = {enumerated value for type}
                   SM6K_FILE_MONITOR_DESCRIPTION = {string from description field}
                   SM6K_FILE_MONITOR_OWNERID = {string from ownerid filed}
                   SM6K_FILE_MONITOR_FULL_PATH_NAME = {file name for monitor}
                   SM6K_FILE_MONITOR_FOR_STRING = {search string}
                   SM6K_FILE_MONITOR_POLL_TIME = {poll time}
                   SM6K_FILE_MONITOR_CURRENT_LINE_COUNT_OF_FILE = {line count}
                   SM6K_FILE_MONITOR_FOUND_STRING_COUNT = {string count found}
                   SM6K_FILE_MONITOR_FOUND_STRING_AT_LINE_NUMBER = {line number found}
                   SM6K_FILE_MONITOR_BYTE_POSITION_WITHIN_LINE = {position in line}
                   SM6K_FILE_MONITOR_COMPLETE_LINE_STRING_FOUND = {complete line}
                   SM6K_FILE_MONITOR_FOUND_STRING_AT_BYTE_POSITION_WITHIN_FILE = {byte count}
                   SM6K_FILE_MONITOR_STRING_FOUND = {string found}
                   SM6K_FILE_MONITOR_TIME_LAST_FOUND = {time last found}
                   SM6K_FILE_MONITOR_SIZE = {size of file}
                   SM6K_FILE_MONITOR_MODE = {mode of file}
                   SM6K_FILE_MONITOR_USERID = {userID of file}
                   SM6K_FILE_MONITOR_GROUPID = {groupID of file}
                   SM6K_FILE_MONITOR_OLD_SIZE = {previous size of file}
                   SM6K_FILE_MONITOR_OLD_MODE = {previous mode of file}
                   SM6K_FILE_MONITOR_OLD_USERID = {previous userID of file}
                   SM6K_FILE_MONITOR_OLD_GROUPID = {previous groupID of file}

                  This MIB variable can be used to generate the file, modifiy the file
                  or translate the file prior to the search"
        ::= { smSiaFileMonitorEntry 26 }

smSiaFileMonitorMode OBJECT-TYPE
        SYNTAX  DisplayString
        ACCESS  read-write
        STATUS  mandatory
        DESCRIPTION
                "File mode for the file.  The mode can be modified by
                 setting the three octal digits."
         ::= { smSiaFileMonitorEntry 27 }

smSiaFileMonitorUserID OBJECT-TYPE
        SYNTAX  DisplayString
        ACCESS  read-write
        STATUS  mandatory
        DESCRIPTION
                "User ID that owns the file.  The user/owner can be modified
                 by setting a new owner/user."
         ::= { smSiaFileMonitorEntry 28 }

smSiaFileMonitorGroupID OBJECT-TYPE
        SYNTAX  DisplayString
        ACCESS  read-write
        STATUS  mandatory
        DESCRIPTION
                "Group ID for the file.  The group ID can be modified by setting
                 a new group."
         ::= { smSiaFileMonitorEntry 29 }

smSiaFileMonitorSize OBJECT-TYPE
        SYNTAX  INTEGER (0..4294967295)
        ACCESS  read-only
        STATUS  mandatory
        DESCRIPTION
                "Size of file in bytes.  If the size of the file decreases or
                 the file wraps then string searching resets to the first byte of
                 the file."
         ::= { smSiaFileMonitorEntry 30 }

smSiaFileMonitorTimeLastDataModification OBJECT-TYPE
        SYNTAX  DisplayString
        ACCESS  read-only
        STATUS  mandatory
        DESCRIPTION
                "Time last data modification to file.  This
                 is updated when the file data is modified.
                 Format is the output of the date command."
         ::= { smSiaFileMonitorEntry 31 }

smSiaFileMonitorTimeLastFileStatusChange OBJECT-TYPE
        SYNTAX  DisplayString
        ACCESS  read-only
        STATUS  mandatory
        DESCRIPTION
                "Time last status change on the file. This is
                 updated when the user, group, or mode is changed.
                 Format is the output of the date command."
         ::= { smSiaFileMonitorEntry 32 }

smSiaFileMonitorReturnCode OBJECT-TYPE
        SYNTAX  INTEGER
        ACCESS  read-only
        STATUS  mandatory
        DESCRIPTION
                "Return code from file monitor operations.
                 The value is zero if successful, non-zero if error."
         ::= { smSiaFileMonitorEntry 33 }

smSiaFileMonitorMessages OBJECT-TYPE
        SYNTAX  DisplayString
        ACCESS  read-only
        STATUS  mandatory
        DESCRIPTION
                "Messages from file monitor operations."
        ::= { smSiaFileMonitorEntry 34 }

-- End definition of MIB Subtree

END
