-- *****************************************************************************
-- Unisphere-Data-Internet-CONF
--
-- SNMP Agent Capabilities definitions for the basic Internet MIBs.
--
-- Copyright (c) 2001, 2002 Unisphere Networks, Inc.  All rights reserved.
-- *****************************************************************************

Unisphere-Data-Internet-CONF DEFINITIONS ::= BEGIN

IMPORTS
    MODULE-IDENTITY
        FROM SNMPv2-SMI
    AGENT-CAPABILITIES
        FROM SNMPv2-CONF
    usDataAgents
        FROM Unisphere-Data-Agents
    ipRouteEntry, ipRouteDest, ipRouteIfIndex, ipRouteMetric1, ipRouteMetric2,
    ipRouteMetric3, ipRouteMetric4, ipRouteNextHop, ipRouteType, ipRouteAge,
    ipRouteMask, ipRouteMetric5
        FROM RFC1213-MIB
    ipGroup, icmpGroup, ipNetToMediaIfIndex, ipNetToMediaNetAddress
        FROM IP-MIB
    ipForwardCidrRouteGroup, ipCidrRouteIfIndex, ipCidrRouteType,
    ipCidrRouteInfo, ipCidrRouteNextHopAS, ipCidrRouteMetric1,
    ipCidrRouteMetric2, ipCidrRouteMetric3, ipCidrRouteMetric4,
    ipCidrRouteMetric5, ipCidrRouteStatus
        FROM IP-FORWARD-MIB
    tcpGroup
        FROM TCP-MIB
    udpGroup
        FROM UDP-MIB
    usdIpInterfaceGroup, usdIpAddressGroup, usdIpRouteGroup, usdIpGlobalGroup,
    usdIpInterfaceGroup2, usdIpAddressGroup2, usdIpInterfaceGroup3,
    usdIpInterfaceGroup4
        FROM Unisphere-Data-IP-MIB
    usdHostGroup
        FROM Unisphere-Data-HOST-MIB;

usdInternetAgent MODULE-IDENTITY
    LAST-UPDATED "200204031404Z"  -- 03-Apr-02 09:04 AM EST
    ORGANIZATION "Unisphere Networks, Inc."
    CONTACT-INFO
        "       Unisphere Networks, Inc.
        Postal: 10 Technology Park Drive
                Westford, MA  01886
                USA
        Tel:    +1 978 589 5800
        E-mail: mib@UnisphereNetworks.com"
    DESCRIPTION
        "The agent capabilities definitions for the basic layer 3 and 4 Internet
        component of the SNMP agent in the Unisphere Routing Switch family of
        products."
    -- Revision History
    REVISION    "200204031404Z"  -- 03-Apr-02 09:04 AM EST  - RX 4.0
    DESCRIPTION
        "Obsoleted the QoS related objects in the Unisphere-Data-IP-MIB."
    REVISION    "200203262146Z"  -- 26-Mar-02 04:46 PM EST  - RX 3.2
    DESCRIPTION
        "The initial release of this management information module."
    ::= { usDataAgents 21 }


-- *****************************************************************************
-- Internet protocol agent capabilities
-- *****************************************************************************
usdInternetAgentV1 AGENT-CAPABILITIES
    PRODUCT-RELEASE
        "Version 1 of the Internet component of the Unisphere Routing Switch
        SNMP agent.  This version of the Internet component was supported in the
        Unisphere 2.x system releases."
    STATUS      obsolete
    DESCRIPTION
        "The MIBs supported by the SNMP agent for the Internet application in
        the Unisphere Routing Switch.  These capabilities became obsolete when
        the IP global objects were added to the Unisphere-Data-IP-MIB."
    SUPPORTS    IP-MIB
        INCLUDES  {
            ipGroup,
            icmpGroup }
        VARIATION   ipNetToMediaIfIndex
            ACCESS      read-only
            DESCRIPTION
                "Allowing create/write access on an auxiliary object is absurd."
        VARIATION   ipNetToMediaNetAddress
            ACCESS      read-only
            DESCRIPTION
                "Allowing create/write access on an auxiliary object is absurd."
    SUPPORTS    IP-FORWARD-MIB
        INCLUDES  {
            ipForwardCidrRouteGroup }
        VARIATION   ipCidrRouteIfIndex
            ACCESS      read-only
            DESCRIPTION
                "An ipCidrRouteEntry cannot be created or modified."
        VARIATION   ipCidrRouteType
            ACCESS      read-only
            DESCRIPTION
                "An ipCidrRouteEntry cannot be created or modified."
        VARIATION   ipCidrRouteInfo
            ACCESS      read-only
            DESCRIPTION
                "An ipCidrRouteEntry cannot be created or modified."
        VARIATION   ipCidrRouteNextHopAS
            ACCESS      read-only
            DESCRIPTION
                "An ipCidrRouteEntry cannot be created or modified."
        VARIATION   ipCidrRouteMetric1
            ACCESS      read-only
            DESCRIPTION
                "An ipCidrRouteEntry cannot be created or modified."
        VARIATION   ipCidrRouteMetric2
            ACCESS      read-only
            DESCRIPTION
                "An ipCidrRouteEntry cannot be created or modified."
        VARIATION   ipCidrRouteMetric3
            ACCESS      read-only
            DESCRIPTION
                "An ipCidrRouteEntry cannot be created or modified."
        VARIATION   ipCidrRouteMetric4
            ACCESS      read-only
            DESCRIPTION
                "An ipCidrRouteEntry cannot be created or modified."
        VARIATION   ipCidrRouteMetric5
            ACCESS      read-only
            DESCRIPTION
                "An ipCidrRouteEntry cannot be created or modified."
        VARIATION   ipCidrRouteStatus
            ACCESS      read-only
            DESCRIPTION
                "An ipCidrRouteEntry cannot be created or modified."
    SUPPORTS    TCP-MIB
        INCLUDES  {
            tcpGroup }
    SUPPORTS    UDP-MIB
        INCLUDES  {
            udpGroup }
    SUPPORTS    Unisphere-Data-IP-MIB
        INCLUDES  {
            usdIpInterfaceGroup,
            usdIpAddressGroup,
            usdIpRouteGroup }
    SUPPORTS    Unisphere-Data-HOST-MIB
        INCLUDES  {
            usdHostGroup }
    ::= { usdInternetAgent 1 }

usdInternetAgentV2 AGENT-CAPABILITIES
    PRODUCT-RELEASE
        "Version 2 of the Internet component of the Unisphere Routing Switch
        SNMP agent.  This version of the Internet component was supported in the
        Unisphere RX 3.0 and RX 3.1 system releases."
    STATUS      obsolete
    DESCRIPTION
        "The MIBs supported by the SNMP agent for the Internet application in
        the Unisphere Routing Switch.  These capabilities became obsolete when
        support was added for the RFC1213-MIB.ipRouteTable and the
        Unisphere-Data-IP-MIB.rsIpIfAssocTable."
    SUPPORTS    IP-MIB
        INCLUDES  {
            ipGroup,
            icmpGroup }
        VARIATION   ipNetToMediaIfIndex
            ACCESS      read-only
            DESCRIPTION
                "Allowing create/write access on an auxiliary object is absurd."
        VARIATION   ipNetToMediaNetAddress
            ACCESS      read-only
            DESCRIPTION
                "Allowing create/write access on an auxiliary object is absurd."
    SUPPORTS    IP-FORWARD-MIB
        INCLUDES  {
            ipForwardCidrRouteGroup }
        VARIATION   ipCidrRouteIfIndex
            ACCESS      read-only
            DESCRIPTION
                "An ipCidrRouteEntry cannot be created or modified."
        VARIATION   ipCidrRouteType
            ACCESS      read-only
            DESCRIPTION
                "An ipCidrRouteEntry cannot be created or modified."
        VARIATION   ipCidrRouteInfo
            ACCESS      read-only
            DESCRIPTION
                "An ipCidrRouteEntry cannot be created or modified."
        VARIATION   ipCidrRouteNextHopAS
            ACCESS      read-only
            DESCRIPTION
                "An ipCidrRouteEntry cannot be created or modified."
        VARIATION   ipCidrRouteMetric1
            ACCESS      read-only
            DESCRIPTION
                "An ipCidrRouteEntry cannot be created or modified."
        VARIATION   ipCidrRouteMetric2
            ACCESS      read-only
            DESCRIPTION
                "An ipCidrRouteEntry cannot be created or modified."
        VARIATION   ipCidrRouteMetric3
            ACCESS      read-only
            DESCRIPTION
                "An ipCidrRouteEntry cannot be created or modified."
        VARIATION   ipCidrRouteMetric4
            ACCESS      read-only
            DESCRIPTION
                "An ipCidrRouteEntry cannot be created or modified."
        VARIATION   ipCidrRouteMetric5
            ACCESS      read-only
            DESCRIPTION
                "An ipCidrRouteEntry cannot be created or modified."
        VARIATION   ipCidrRouteStatus
            ACCESS      read-only
            DESCRIPTION
                "An ipCidrRouteEntry cannot be created or modified."
    SUPPORTS    TCP-MIB
        INCLUDES  {
            tcpGroup }
    SUPPORTS    UDP-MIB
        INCLUDES  {
            udpGroup }
    SUPPORTS    Unisphere-Data-IP-MIB
        INCLUDES  {
            usdIpInterfaceGroup2,
            usdIpAddressGroup2,
            usdIpRouteGroup,
            usdIpGlobalGroup }
    SUPPORTS    Unisphere-Data-HOST-MIB
        INCLUDES  {
            usdHostGroup }
    ::= { usdInternetAgent 2 }

usdInternetAgentV3 AGENT-CAPABILITIES
    PRODUCT-RELEASE
        "Version 3 of the Internet component of the Unisphere Routing Switch
        SNMP agent.  This version of the Internet component was supported in the
        Unisphere RX 3.2 and subsequent 3.x system releases."
    STATUS      obsolete
    DESCRIPTION
        "The MIBs supported by the SNMP agent for the Internet application in
        the Unisphere Routing Switch.  These capabilities became obsolete when
        the QoS related objects in the Unisphere-Data-IP-MIB were obsoleted."
    SUPPORTS    RFC1213-MIB
    --  The RFC1213-MIB is based on SMIv1 and has no conformance groups.
    --  Therefore, we list capabilities by OID subtree "groups".
        INCLUDES  {
            ipRouteEntry }
        VARIATION   ipRouteDest
            ACCESS      read-only
            DESCRIPTION
                "Allowing write access on an auxiliary object is absurd."
        VARIATION   ipRouteIfIndex
            ACCESS      read-only
            DESCRIPTION
                "The ipRouteTable is read-only in this agent."
        VARIATION   ipRouteMetric1
            ACCESS      read-only
            DESCRIPTION
                "The ipRouteTable is read-only in this agent."
        VARIATION   ipRouteMetric2
            ACCESS      read-only
            DESCRIPTION
                "The ipRouteTable is read-only in this agent."
        VARIATION   ipRouteMetric3
            ACCESS      read-only
            DESCRIPTION
                "The ipRouteTable is read-only in this agent."
        VARIATION   ipRouteMetric4
            ACCESS      read-only
            DESCRIPTION
                "The ipRouteTable is read-only in this agent."
        VARIATION   ipRouteNextHop
            ACCESS      read-only
            DESCRIPTION
                "The ipRouteTable is read-only in this agent."
        VARIATION   ipRouteType
            ACCESS      read-only
            DESCRIPTION
                "The ipRouteTable is read-only in this agent."
        VARIATION   ipRouteAge
            ACCESS      read-only
            DESCRIPTION
                "The ipRouteTable is read-only in this agent."
        VARIATION   ipRouteMask
            ACCESS      read-only
            DESCRIPTION
                "The ipRouteTable is read-only in this agent."
        VARIATION   ipRouteMetric5
            ACCESS      read-only
            DESCRIPTION
                "The ipRouteTable is read-only in this agent."
    SUPPORTS    IP-MIB
        INCLUDES  {
            ipGroup,
            icmpGroup }
        VARIATION   ipNetToMediaIfIndex
            ACCESS      read-only
            DESCRIPTION
                "Allowing create/write access on an auxiliary object is absurd."
        VARIATION   ipNetToMediaNetAddress
            ACCESS      read-only
            DESCRIPTION
                "Allowing create/write access on an auxiliary object is absurd."
    SUPPORTS    IP-FORWARD-MIB
        INCLUDES  {
            ipForwardCidrRouteGroup }
        VARIATION   ipCidrRouteIfIndex
            ACCESS      read-only
            DESCRIPTION
                "An ipCidrRouteEntry cannot be created or modified."
        VARIATION   ipCidrRouteType
            ACCESS      read-only
            DESCRIPTION
                "An ipCidrRouteEntry cannot be created or modified."
        VARIATION   ipCidrRouteInfo
            ACCESS      read-only
            DESCRIPTION
                "An ipCidrRouteEntry cannot be created or modified."
        VARIATION   ipCidrRouteNextHopAS
            ACCESS      read-only
            DESCRIPTION
                "An ipCidrRouteEntry cannot be created or modified."
        VARIATION   ipCidrRouteMetric1
            ACCESS      read-only
            DESCRIPTION
                "An ipCidrRouteEntry cannot be created or modified."
        VARIATION   ipCidrRouteMetric2
            ACCESS      read-only
            DESCRIPTION
                "An ipCidrRouteEntry cannot be created or modified."
        VARIATION   ipCidrRouteMetric3
            ACCESS      read-only
            DESCRIPTION
                "An ipCidrRouteEntry cannot be created or modified."
        VARIATION   ipCidrRouteMetric4
            ACCESS      read-only
            DESCRIPTION
                "An ipCidrRouteEntry cannot be created or modified."
        VARIATION   ipCidrRouteMetric5
            ACCESS      read-only
            DESCRIPTION
                "An ipCidrRouteEntry cannot be created or modified."
        VARIATION   ipCidrRouteStatus
            ACCESS      read-only
            DESCRIPTION
                "An ipCidrRouteEntry cannot be created or modified."
    SUPPORTS    TCP-MIB
        INCLUDES  {
            tcpGroup }
    SUPPORTS    UDP-MIB
        INCLUDES  {
            udpGroup }
    SUPPORTS    Unisphere-Data-IP-MIB
        INCLUDES  {
            usdIpInterfaceGroup3,
            usdIpAddressGroup2,
            usdIpRouteGroup,
            usdIpGlobalGroup }
    SUPPORTS    Unisphere-Data-HOST-MIB
        INCLUDES  {
            usdHostGroup }
    ::= { usdInternetAgent 3 }

usdInternetAgentV4 AGENT-CAPABILITIES
    PRODUCT-RELEASE
        "Version 4 of the Internet component of the Unisphere Routing Switch
        SNMP agent.  This version of the Internet component is supported in the
        Unisphere RX 4.0 and subsequent system releases."
    STATUS      current
    DESCRIPTION
        "The MIBs supported by the SNMP agent for the Internet application
        in the Unisphere Routing Switch."
    SUPPORTS    RFC1213-MIB
    --  The RFC1213-MIB is based on SMIv1 and has no conformance groups.
    --  Therefore, we list capabilities by OID subtree "groups".
        INCLUDES  {
            ipRouteEntry }
        VARIATION   ipRouteDest
            ACCESS      read-only
            DESCRIPTION
                "Allowing write access on an auxiliary object is absurd."
        VARIATION   ipRouteIfIndex
            ACCESS      read-only
            DESCRIPTION
                "The ipRouteTable is read-only in this agent."
        VARIATION   ipRouteMetric1
            ACCESS      read-only
            DESCRIPTION
                "The ipRouteTable is read-only in this agent."
        VARIATION   ipRouteMetric2
            ACCESS      read-only
            DESCRIPTION
                "The ipRouteTable is read-only in this agent."
        VARIATION   ipRouteMetric3
            ACCESS      read-only
            DESCRIPTION
                "The ipRouteTable is read-only in this agent."
        VARIATION   ipRouteMetric4
            ACCESS      read-only
            DESCRIPTION
                "The ipRouteTable is read-only in this agent."
        VARIATION   ipRouteNextHop
            ACCESS      read-only
            DESCRIPTION
                "The ipRouteTable is read-only in this agent."
        VARIATION   ipRouteType
            ACCESS      read-only
            DESCRIPTION
                "The ipRouteTable is read-only in this agent."
        VARIATION   ipRouteAge
            ACCESS      read-only
            DESCRIPTION
                "The ipRouteTable is read-only in this agent."
        VARIATION   ipRouteMask
            ACCESS      read-only
            DESCRIPTION
                "The ipRouteTable is read-only in this agent."
        VARIATION   ipRouteMetric5
            ACCESS      read-only
            DESCRIPTION
                "The ipRouteTable is read-only in this agent."
    SUPPORTS    IP-MIB
        INCLUDES  {
            ipGroup,
            icmpGroup }
        VARIATION   ipNetToMediaIfIndex
            ACCESS      read-only
            DESCRIPTION
                "Allowing create/write access on an auxiliary object is absurd."
        VARIATION   ipNetToMediaNetAddress
            ACCESS      read-only
            DESCRIPTION
                "Allowing create/write access on an auxiliary object is absurd."
    SUPPORTS    IP-FORWARD-MIB
        INCLUDES  {
            ipForwardCidrRouteGroup }
        VARIATION   ipCidrRouteIfIndex
            ACCESS      read-only
            DESCRIPTION
                "An ipCidrRouteEntry cannot be created or modified."
        VARIATION   ipCidrRouteType
            ACCESS      read-only
            DESCRIPTION
                "An ipCidrRouteEntry cannot be created or modified."
        VARIATION   ipCidrRouteInfo
            ACCESS      read-only
            DESCRIPTION
                "An ipCidrRouteEntry cannot be created or modified."
        VARIATION   ipCidrRouteNextHopAS
            ACCESS      read-only
            DESCRIPTION
                "An ipCidrRouteEntry cannot be created or modified."
        VARIATION   ipCidrRouteMetric1
            ACCESS      read-only
            DESCRIPTION
                "An ipCidrRouteEntry cannot be created or modified."
        VARIATION   ipCidrRouteMetric2
            ACCESS      read-only
            DESCRIPTION
                "An ipCidrRouteEntry cannot be created or modified."
        VARIATION   ipCidrRouteMetric3
            ACCESS      read-only
            DESCRIPTION
                "An ipCidrRouteEntry cannot be created or modified."
        VARIATION   ipCidrRouteMetric4
            ACCESS      read-only
            DESCRIPTION
                "An ipCidrRouteEntry cannot be created or modified."
        VARIATION   ipCidrRouteMetric5
            ACCESS      read-only
            DESCRIPTION
                "An ipCidrRouteEntry cannot be created or modified."
        VARIATION   ipCidrRouteStatus
            ACCESS      read-only
            DESCRIPTION
                "An ipCidrRouteEntry cannot be created or modified."
    SUPPORTS    TCP-MIB
        INCLUDES  {
            tcpGroup }
    SUPPORTS    UDP-MIB
        INCLUDES  {
            udpGroup }
    SUPPORTS    Unisphere-Data-IP-MIB
        INCLUDES  {
            usdIpInterfaceGroup4,
            usdIpAddressGroup2,
            usdIpRouteGroup,
            usdIpGlobalGroup }
    SUPPORTS    Unisphere-Data-HOST-MIB
        INCLUDES  {
            usdHostGroup }
    ::= { usdInternetAgent 4 }

END
