XYPLEX-LAT-MIB DEFINITIONS ::= BEGIN
            
                    IMPORTS
                            enterprises, Counter, Gauge, TimeTicks
                                    FROM RFC1155-SMI
                            DisplayString
                                    FROM SNMPv2-TC
                            OBJECT-TYPE
                                    FROM RFC-1212;
            
            xyplex          OBJECT IDENTIFIER ::= { enterprises 33 }
            lat             OBJECT IDENTIFIER ::= { xyplex 3 }
            
            -- This MIB module uses the extended OBJECT-TYPE macro as
            -- defined in [9]
            
            -- This is a MIB module for all Xyplex systems that
            -- implement LAT


























            
            

            
            
            
            
            -- the LAT group
            
            -- Implementation of this group is mandatory for all Xyplex
            -- systems that implement LAT
            
            latAnnounceServices OBJECT-TYPE
                SYNTAX INTEGER { disabled(1), enabled(2) }
                ACCESS read-write
                STATUS mandatory
                DESCRIPTION
                    "Control for automatic, periodic announcement of 
                    local services to the network.  Corresponds directly 
                    to SERVER ANNOUNCEMENTS and the presence of the 
                    label 'Announcements' following the label 'Enabled 
                    Characteristics:' in the SERVER CHARACTERISTICS 
                    display."
                ::= { lat 1 }
            
            latCircuitTimer OBJECT-TYPE
                SYNTAX INTEGER (30..200)
                ACCESS read-write
                STATUS mandatory
                DESCRIPTION
                    "Number of milleseconds to collect port input data 
                    before sending it to the host.  Corresponds directly 
                    to SERVER CIRCUIT TIMER and the value labeled 
                    'Circuit Timer:' in the SERVER CHARACTERISTICS 
                    display."
                ::= { lat 2 }
            
            latIdentificationLengthLimit OBJECT-TYPE
                SYNTAX INTEGER (0..63)
                ACCESS read-write
                STATUS mandatory
                DESCRIPTION
                    "Maximum number of characters to store in the 
                    instances of latVisibleServiceIdentification.  
                    Corresponds directly to SERVER IDENTIFICATION SIZE 
                    and the value labeled 'Identification Size:' in the 
                    SERVER CHARACTERISTICS display."
                ::= { lat 3 }
            
            latKeepaliveTimer OBJECT-TYPE
                SYNTAX INTEGER (10..180)
                ACCESS read-write
                STATUS mandatory

            
            

            
            
            
            
                DESCRIPTION
                    "Number of seconds of inactivity before sending a 
                    null message to the host.  Corresponds directly to 
                    SERVER KEEPALIVE TIMER and the value labeled 
                    'Keepalive Timer:' in the SERVER CHARACTERISTICS 
                    display."
                ::= { lat 4 }
            
            latMulticastTimer OBJECT-TYPE
                SYNTAX INTEGER (10..180)
                ACCESS read-write
                STATUS mandatory
                DESCRIPTION
                    "Number of seconds between transmission of local 
                    service announcements.  Corresponds directly to 
                    SERVER MULTICAST TIMER and the value labeled 
                    'Multicast Timer:' in the SERVER CHARACTERISTICS 
                    display."
                ::= { lat 5 }
            
            latNodeLimit OBJECT-TYPE
                SYNTAX INTEGER (0..1000)
                ACCESS read-write
                STATUS mandatory
                DESCRIPTION
                    "Maximum number of service nodes to keep in the node 
                    table.  Corresponds directly to SERVER NODE LIMIT 
                    and the value labeled 'Node Limit:' in the SERVER 
                    CHARACTERISTICS display."
                ::= { lat 6 }
            
            latNumber OBJECT-TYPE
                SYNTAX INTEGER (0..32767)
                ACCESS read-write
                STATUS mandatory
                DESCRIPTION
                    "An arbitrary number assigned and used for 
                    administrative purposes.  Corresponds directly to 
                    SERVER NUMBER and the value labeled 'Number:' in the 
                    SERVER CHARACTERISTICS display."
                ::= { lat 7 }
            
            latRetransmitLimit OBJECT-TYPE
                SYNTAX INTEGER (4..120)
                ACCESS read-write
                STATUS mandatory

            
            

            
            
            
            
                DESCRIPTION
                    "Maximum number of times to retransmit an 
                    unacknowledged message.  Corresponds directly to 
                    SERVER RETRANSMIT LIMIT and the value labeled 
                    'Retransmit Limit:' in the SERVER CHARACTERISTICS 
                    display."
                ::= { lat 8 }
            
            latLocalServiceGroups OBJECT-TYPE
                SYNTAX OCTET STRING (SIZE (32))
                ACCESS read-write
                STATUS mandatory
                DESCRIPTION
                    "The list of group numbers allowed to use local 
                    services, where a group number is in the range 
                    0-255.  The OCTET STRING contains a bitmap, with one 
                    bit for each group.  Corresponding bit numbers start 
                    with 0 as the high-order bit of the first octet.  
                    Corresponds directly to SERVER SERVICE GROUPS and 
                    the value labeled 'Service Groups:' in the SERVER 
                    CHARACTERISTICS display."
                ::= { lat 9 }
            
            latGroupPurge OBJECT-TYPE
                SYNTAX INTEGER { disabled(1), enabled(2) }
                ACCESS read-write
                STATUS mandatory
                DESCRIPTION
                    "Control for automatic deletion of all node table 
                    entries when latServiceGroups or 
                    latPortCurrentGroups is changed.  Corresponds 
                    directly to SERVER PURGE GROUP and the presence of 
                    the label 'Purge Group' following the label 'Enabled 
                    Characteristics:' in the SERVER CHARACTERISTICS 
                    display."
                ::= { lat 10 }
            
            latNodePurge OBJECT-TYPE
                SYNTAX INTEGER { disabled(1), enabled(2) }
                ACCESS read-write
                STATUS mandatory
                DESCRIPTION
                    "Control for automatic deletion of all node table 
                    entries with status 'reachable' when the number of 
                    entries exceeds latNodeLimit.  Corresponds directly 
                    to SERVER PURGE NODE and the presence of the label 

            
            

            
            
            
            
                            'Purge Node' following the label 'Enabled 
                    Characteristics:' in the SERVER CHARACTERISTICS 
                    display."
                ::= { lat 11 }
            
            latNodesRejected OBJECT-TYPE
                SYNTAX Counter
                ACCESS read-only
                STATUS mandatory
                DESCRIPTION
                    "Number of nodes not added to the node table because 
                    there was no room.  Corresponds directly to the 
                    value labeled 'Discarded Nodes:' in the SERVER 
                    STATUS display."
                ::= { lat 12 }
            
            latInMessages OBJECT-TYPE
                SYNTAX Counter
                ACCESS read-only
                STATUS mandatory
                DESCRIPTION
                    "Number of LAT messages received.  Corresponds 
                    directly to the value labeled 'Messages Received:' 
                    in the SERVER COUNTERS display."
                ::= { lat 13 }
            
            latOutMessages OBJECT-TYPE
                SYNTAX Counter
                ACCESS read-only
                STATUS mandatory
                DESCRIPTION
                    "Number of LAT messages sent.  Corresponds directly 
                    to the value labeled 'Messages Transmitted:' in the 
                    SERVER COUNTERS display."
                ::= { lat 14 }
            
            latInSessionsAccepted OBJECT-TYPE
                SYNTAX Counter
                ACCESS read-only
                STATUS mandatory
                DESCRIPTION
                    "Number of incoming LAT session connection attempts 
                    accepted.  Corresponds directly to the value labeled 
                    'Solicitations Accepted:' in the SERVER COUNTERS 
                    display."
                ::= { lat 15 }

            
            

            
            
            
            
            
            latInSessionsRejected OBJECT-TYPE
                SYNTAX Counter
                ACCESS read-only
                STATUS mandatory
                DESCRIPTION
                    "Number of incoming LAT session connection attempts 
                    rejected.  Corresponds directly to the value labeled 
                    'Solicitations Rejected:' in the SERVER COUNTERS 
                    display."
                ::= { lat 16 }
            
            latAddressChange OBJECT-TYPE
                SYNTAX Counter
                ACCESS read-only
                STATUS mandatory
                DESCRIPTION
                    "Number of times a service announcement contained a 
                    node name already in the visible service table but 
                    with a different address.  Corresponds directly to 
                    the value labeled 'Multiple Node Addresses:' in the 
                    SERVER COUNTERS display."
                ::= { lat 17 }
            
            latInDuplicates OBJECT-TYPE
                SYNTAX Counter
                ACCESS read-only
                STATUS mandatory
                DESCRIPTION
                    "Number of duplicate LAT messages received.  
                    Corresponds directly to the value labeled 
                    'Duplicates Received:' in the SERVER COUNTERS 
                    display."
                ::= { lat 18 }
            
            latOutRetransmits OBJECT-TYPE
                SYNTAX Counter
                ACCESS read-only
                STATUS mandatory
                DESCRIPTION
                    "Number of LAT messages retransmitted due to no 
                    acknowledgement.  Corresponds directly to the value 
                    labeled 'Messages Re-transmitted:' in the SERVER 
                    COUNTERS display."
                ::= { lat 19 }
            

            
            

            
            
            
            
            latInBadMessages OBJECT-TYPE
                SYNTAX Counter
                ACCESS read-only
                STATUS mandatory
                DESCRIPTION
                    "Number of LAT messages received with invalid 
                    format.  Corresponds directly to the value labeled 
                    'Illegal Messages Rcv'd:' in the SERVER COUNTERS 
                    display."
                ::= { lat 20 }
            
            latInBadSlots OBJECT-TYPE
                SYNTAX Counter
                ACCESS read-only
                STATUS mandatory
                DESCRIPTION
                    "Number of LAT messages received with invalid slot 
                    format.  Corresponds directly to the value labeled 
                    'Illegal Slots Rcv'd:' in the SERVER COUNTERS 
                    display."
                ::= { lat 21 }
            
            latInBadMulticasts OBJECT-TYPE
                SYNTAX Counter
                ACCESS read-only
                STATUS mandatory
                DESCRIPTION
                    "Number of multicast LAT messages received with 
                    invalid format.  Corresponds directly to the value 
                    labeled 'Illegal Multicasts Rcv'd:' in the SERVER 
                    COUNTERS display."
                ::= { lat 22 }














            
            

            
            
            
            
            -- the LAT Port table
            
            latPortTable OBJECT-TYPE
                SYNTAX SEQUENCE OF LatPortEntry
                ACCESS not-accessible
                STATUS mandatory
                DESCRIPTION
                    "A list of LAT character port entries."
                ::= { lat 23 }
            
            latPortEntry OBJECT-TYPE
                SYNTAX LatPortEntry
                ACCESS not-accessible
                STATUS mandatory
                DESCRIPTION
                    "LAT parameter values for a port."
                INDEX { latPortIndex }
                ::= { latPortTable 1 }
            
            LatPortEntry ::=
                SEQUENCE {
                    latPortIndex
                        INTEGER,
                    latPortAuthorizedGroups
                        OCTET STRING,
                    latPortAutoPrompt
                        INTEGER,
                    latPortCurrentGroups
                        OCTET STRING,
                    latPortRemoteModification
                        INTEGER
                }
            
            latPortIndex OBJECT-TYPE
                SYNTAX INTEGER
                ACCESS read-only
                STATUS mandatory
                DESCRIPTION
                    "An index value that uniquely identifies a port.  
                    The port identified by a particular value of this 
                    index is the same port as identified by 
                    charPortIndex in the Character MIB [11]."
                ::= { latPortEntry 1 }
            
            latPortAuthorizedGroups OBJECT-TYPE
                SYNTAX OCTET STRING (SIZE (32))

            
            

            
            
            
            
                ACCESS read-write
                STATUS mandatory
                DESCRIPTION
                    "The list of group numbers to which the port is 
                    allowed to set access, where a group number is in 
                    the range 0-255.  The OCTET STRING contains a 
                    bitmap, with one bit for each group.  Corresponding 
                    bit numbers start with 0 as the high-order bit of 
                    the first octet.  Corresponds directly to PORT 
                    AUTHORIZED GROUPS and the value labeled 'Authorized 
                    Groups:' in the PORT CHARACTERISTICS display."
                ::= { latPortEntry 2 }
            
            latPortAutoPrompt OBJECT-TYPE
                SYNTAX INTEGER { disabled(1), enabled(2) }
                ACCESS read-write
                STATUS mandatory
                DESCRIPTION
                    "Control for automatic stimulation of a host prompt 
                    upon forming a new session.  Corresponds directly to 
                    PORT AUTOPROMPT and the presence of the label 
                    'Autoprompt' following the label 'Enabled 
                    Characteristics:' in the PORT CHARACTERISTICS 
                    display."
                ::= { latPortEntry 3 }
            
            latPortCurrentGroups OBJECT-TYPE
                SYNTAX OCTET STRING (SIZE (32))
                ACCESS read-write
                STATUS mandatory
                DESCRIPTION
                    "The list of group numbers to which the port 
                    currently has set access, where a group number is in 
                    the range 0-255.  The OCTET STRING contains a 
                    bitmap, with one bit for each group.  Corresponding 
                    bit numbers start with 0 as the high-order bit of 
                    the first octet.  Corresponds directly to PORT 
                    GROUPS and the value labeled 'Groups:' in the PORT 
                    CHARACTERISTICS display."
                ::= { latPortEntry 4 }
            
            latPortRemoteModification OBJECT-TYPE
                SYNTAX INTEGER { disabled(1), enabled(2) }
                ACCESS read-write
                STATUS mandatory
                DESCRIPTION

            
            

            
            
            
            
                    "Control to allow the remote system to modify 
                    certain physical port characteristics.  Corresponds 
                    directly to PORT REMOTE MODIFICATION and the 
                    presence of the label 'Remote Modification' 
                    following the label 'Enabled Characteristics:' in 
                    the PORT CHARACTERISTICS display."
                ::= { latPortEntry 5 }







































            
            

            
            
            
            
            -- The LAT Offered Service table
            
            latOfferedServiceTable OBJECT-TYPE
                SYNTAX SEQUENCE OF LatOfferedServiceEntry
                ACCESS not-accessible
                STATUS mandatory
                DESCRIPTION
                    "A list of offered service entries."
                ::= { lat 24 }
            
            latOfferedServiceEntry OBJECT-TYPE
                SYNTAX LatOfferedServiceEntry
                ACCESS not-accessible
                STATUS mandatory
                DESCRIPTION
                    "Parameter values for an offered service entry."
                INDEX { latOfferedServiceName }
                ::= { latOfferedServiceTable 1 }
            
            LatOfferedServiceEntry ::=
                SEQUENCE {
                    latOfferedServiceName
                        DisplayString,
                    latOfferedServiceStatus
                        INTEGER,
                    latOfferedServiceAllowConnections
                        INTEGER,
                    latOfferedServiceIdentification
                        DisplayString,
                    latOfferedServicePassword
                        DisplayString,
                    latOfferedServicePortMap
                        OCTET STRING,
                    latOfferedServiceQueuing
                        INTEGER
                }
            
            latOfferedServiceName OBJECT-TYPE
                SYNTAX DisplayString (SIZE (1..16))
                ACCESS read-write
                STATUS mandatory
                DESCRIPTION
                    "The name of an offered service.  Corresponds 
                    directly to the name in a SERVICE command and the 
                    value labeled 'Service:' in the SERVICE 
                    CHARACTERISTICS display."

            
            

            
            
            
            
                ::= { latOfferedServiceEntry 1 }
            
            latOfferedServiceStatus OBJECT-TYPE
                SYNTAX INTEGER { invalid(1), valid(2) }
                ACCESS read-write
                STATUS mandatory
                DESCRIPTION
                    "The status of the entry.  Set to 'invalid' to 
                    remove the entry, which corresponds directly to the 
                    CLEAR SERVICE command.  Actual removal of the entry 
                    is implementation specific."
                DEFVAL { valid }
                ::= { latOfferedServiceEntry 2 }
            
            latOfferedServiceAllowConnections OBJECT-TYPE
                SYNTAX INTEGER { disabled(1), enabled(2) }
                ACCESS read-write
                STATUS mandatory
                DESCRIPTION
                    "Control for allowing incoming connections to the 
                    service.  Corresponds directly to SERVICE 
                    CONNECTIONS and the presence of the label 
                    'Connections' following the label 'Enabled 
                    Characteristics:' in the SERVICE CHARACTERISTICS 
                    display."
                ::= { latOfferedServiceEntry 3 }
            
            latOfferedServiceIdentification OBJECT-TYPE
                SYNTAX DisplayString (SIZE (0..63))
                ACCESS read-write
                STATUS mandatory
                DESCRIPTION
                    "Text to identify a service.  Corresponds directly 
                    to SERVICE IDENTIFICATION and the value labeled 
                    'Identification:' in the SERVICE CHARACTERISTICS 
                    display."
                ::= { latOfferedServiceEntry 4 }
            
            latOfferedServicePassword OBJECT-TYPE
                SYNTAX DisplayString (SIZE (0..16))
                ACCESS read-write
                STATUS mandatory
                DESCRIPTION
                    "The password a user must supply to use the service.  
                    Corresponds directly to SERVICE PASSWORD and the 
                    presence of the label 'Password' following the label 

            
            

            
            
            
            
                            'Enabled Characteristics:' in the SERVICE 
                    CHARACTERISTICS display.
            
                    When setting this value, the management system must 
                    supply eight octets, filling with zeros from the 
                    first octet.  That is, the value '1ab42' would be 
                    expressed as '0.0.0.0.0.1.ab.42'.  Setting the value 
                    to zero disables the password check.
            
                    When returning this value, the agent always returns 
                    a zero length OCTET STRING."
                ::= { latOfferedServiceEntry 5 }
            
            latOfferedServicePortMap OBJECT-TYPE
                SYNTAX OCTET STRING
                ACCESS read-write
                STATUS mandatory
                DESCRIPTION
                    "The list of character ports offer the service.  The 
                    OCTET STRING contains a bitmap, with one bit for 
                    each port, and enough octets for all the ports on 
                    the system.  Port numbers are as defined for 
                    charPortIndex in the Character MIB [11].  
                    Corresponding bit numbers start with 1 as the 
                    high-order bit of the first octet.  Corresponds 
                    directly to port-list portion of SERVICE PORTS and 
                    the value labeled 'Ports:' in the SERVICE 
                    CHARACTERISTICS display."
                ::= { latOfferedServiceEntry 6 }
            
            latOfferedServiceQueuing OBJECT-TYPE
                SYNTAX INTEGER { disabled(1), enabled(2) }
                ACCESS read-write
                STATUS mandatory
                DESCRIPTION
                    "Control for allowing queuing of incoming 
                    connections to the service when the service is busy.  
                    Corresponds directly to SERVICE QUEUE and the 
                    presence of the label 'Queuing' following the label 
                    'Enabled Characteristics:' in the SERVICE 
                    CHARACTERISTICS display."
                ::= { latOfferedServiceEntry 7 }




            
            

            
            
            
            
            -- The LAT Visible Service table
            
            latVisibleServiceTable OBJECT-TYPE
                SYNTAX SEQUENCE OF LatVisibleServiceEntry
                ACCESS not-accessible
                STATUS mandatory
                DESCRIPTION
                    "A list of visible service entries."
                ::= { lat 25 }
            
            latVisibleServiceEntry OBJECT-TYPE
                SYNTAX LatVisibleServiceEntry
                ACCESS not-accessible
                STATUS mandatory
                DESCRIPTION
                    "Parameter values for a visible service entry."
                INDEX { latVisibleServiceName }
                ::= { latVisibleServiceTable 1 }
            
            LatVisibleServiceEntry ::=
                SEQUENCE {
                    latVisibleServiceName
                        DisplayString,
                    latVisibleServiceStatus
                        INTEGER,
                    latVisibleServiceNode
                        DisplayString,
                    latVisibleServiceConnectedSessions
                        Gauge,
                    latVisibleServiceIdentification
                        DisplayString,
                    latVisibleServiceRating
                        Gauge
                }
            
            latVisibleServiceName OBJECT-TYPE
                SYNTAX DisplayString (SIZE (1..16))
                ACCESS read-only
                STATUS mandatory
                DESCRIPTION
                    "The name of a visible service.  Corresponds 
                    directly to the name in a SERVICE command and the 
                    value labeled 'Service Name' in the SERVICE SUMMARY 
                    display."
                ::= { latVisibleServiceEntry 1 }
            

            
            

            
            
            
            
            latVisibleServiceStatus OBJECT-TYPE
                SYNTAX INTEGER { available(1), unavailable(2), 
                                 unknown(3), unreachable(4), 
                                 reachable(5), connected(6) }
                ACCESS read-only
                STATUS mandatory
                DESCRIPTION
                    "Status of communication with the service.  
                    Corresponds directly to the value labeled 'Status' 
                    in the SERVICE SUMMARY display."
                ::= { latVisibleServiceEntry 2 }
            
            latVisibleServiceNode OBJECT-TYPE
                SYNTAX DisplayString (SIZE (1..16))
                ACCESS read-only
                STATUS mandatory
                DESCRIPTION
                    "Name of a node offering the service.  Corresponds 
                    directly to the value labeled Node Name in the 
                    SERVICE STATUS display."
                ::= { latVisibleServiceEntry 3 }
            
            latVisibleServiceConnectedSessions OBJECT-TYPE
                SYNTAX Gauge
                ACCESS read-only
                STATUS mandatory
                DESCRIPTION
                    "Number of connected sessions to the service.  
                    Corresponds directly to the number with the value 
                    'Connected', labeled 'Status' in the SERVICE SUMMARY 
                    display."
                ::= { latVisibleServiceEntry 4 }
            
            latVisibleServiceIdentification OBJECT-TYPE
                SYNTAX DisplayString (SIZE (0..63))
                ACCESS read-only
                STATUS mandatory
                DESCRIPTION
                    "Text to identify a service.  The length is subject 
                    to limitation by latIdentificationLengthLimit.    
                    Corresponds directly to the value labeled 
                    'Identification:' in the SERVICE SUMMARY display."
                ::= { latVisibleServiceEntry 5 }
            
            latVisibleServiceRating OBJECT-TYPE
                SYNTAX Gauge

            
            

            
            
            
            
                ACCESS read-only
                STATUS mandatory
                DESCRIPTION
                    "Relative capacity of the service to accept 
                    additional sessions.  Corresponds directly to value 
                    labeled Rating in the SERVICE STATUS display."
                ::= { latVisibleServiceEntry 6 }







































            
            

            
            
            
            
            -- The LAT Node table
            
            latNodeTable OBJECT-TYPE
                SYNTAX SEQUENCE OF LatNodeEntry
                ACCESS not-accessible
                STATUS mandatory
                DESCRIPTION
                    "A list of node entries."
                ::= { lat 26 }
            
            latNodeEntry OBJECT-TYPE
                SYNTAX LatNodeEntry
                ACCESS not-accessible
                STATUS mandatory
                DESCRIPTION
                    "Parameter values for a node entry."
                INDEX { latNodeName }
                ::= { latNodeTable 1 }
            
            LatNodeEntry ::=
                SEQUENCE {
                    latNodeName
                        DisplayString,
                    latNodeStatus
                        INTEGER,
                    latNodeConnectedSessions
                        Gauge,
                    latNodeAddress
                        OCTET STRING,
                    latNodeDataLinkFrame
                        INTEGER,
                    latNodeIdentification
                        DisplayString,
                    latNodeGroups
                        OCTET STRING,
                    latNodeServiceNumber
                        Gauge,
                    latNodeZero
                        INTEGER,
                    latNodeZeroTime
                        TimeTicks,
                    latNodeInMessages
                        Counter,
                    latNodeOutMessages
                        Counter,
                    latNodeInSlots

            
            

            
            
            
            
                        Counter,
                    latNodeOutSlots
                        Counter,
                    latNodeInBytes
                        Counter,
                    latNodeOutBytes
                        Counter,
                    latNodeAddressChange
                        Counter,
                    latNodeInDuplicates
                        Counter,
                    latNodeOutRetransmits
                        Counter,
                    latNodeInBadMessages
                        Counter,
                    latNodeInBadSlots
                        Counter,
                    latNodeInSessionsAccepted
                        Counter,
                    latNodeInSessionsRejected
                        Counter
                }
            
            latNodeName OBJECT-TYPE
                SYNTAX DisplayString (SIZE (1..16))
                ACCESS read-only
                STATUS mandatory
                DESCRIPTION
                    "The name of a node.  Corresponds directly to the 
                    value labeled 'Node:' in the NODE STATUS display."
                ::= { latNodeEntry 1 }
            
            latNodeStatus OBJECT-TYPE
                SYNTAX INTEGER { available(1), unavailable(2), 
                                 unknown(3), unreachable(4), 
                                 reachable(5), connected(6) }
                ACCESS read-only
                STATUS mandatory
                DESCRIPTION
                    "Status of communication with the node.  Corresponds 
                    directly to the value labeled 'Status' in the NODE 
                    STATUS display."
                ::= { latNodeEntry 2 }
            
            latNodeConnectedSessions OBJECT-TYPE
                SYNTAX Gauge

            
            

            
            
            
            
                ACCESS read-only
                STATUS mandatory
                DESCRIPTION
                    "Number of connected sessions to the node.  
                    Corresponds directly to the number with the value 
                    'Connected', labeled 'Status' in the NODE STATUS 
                    display."
                ::= { latNodeEntry 3 }
            
            latNodeAddress OBJECT-TYPE
                SYNTAX OCTET STRING (SIZE (6))
                ACCESS read-only
                STATUS mandatory
                DESCRIPTION
                    "Ethernet address of the node.  Corresponds directly 
                    to the value labeled 'Address:' in the NODE STATUS 
                    display."
                ::= { latNodeEntry 4 }
            
            latNodeDataLinkFrame OBJECT-TYPE
                SYNTAX INTEGER
                ACCESS read-only
                STATUS mandatory
                DESCRIPTION
                    "Maximum Ethernet frame used by the node.  
                    Corresponds directly to the value labeled 'Data Link 
                    Frame Size:' in the NODE STATUS display."
                ::= { latNodeEntry 5 }
            
            latNodeIdentification OBJECT-TYPE
                SYNTAX DisplayString (SIZE (0..63))
                ACCESS read-only
                STATUS mandatory
                DESCRIPTION
                    "Text that identifies the node.  The size is subject 
                    to limitation by latIdentificationLengtLimit.  
                    Corresponds directly to the value labeled 
                    'Identification' in the NODE STATUS display."
                ::= { latNodeEntry 6 }
            
            latNodeGroups OBJECT-TYPE
                SYNTAX OCTET STRING (SIZE (32))
                ACCESS read-write
                STATUS mandatory
                DESCRIPTION
                    "The list of group numbers to which the node 

            
            

            
            
            
            
                            belongs, where a group number is in the range 0-255.  
                    The OCTET STRING contains a bitmap, with one bit for 
                    each group.  Corresponding bit numbers start with 0 
                    as the high-order bit of the first octet.  
                    Corresponds directly to the value labeled 'Node 
                    Groups:' in the NODE STATUS display."
                ::= { latNodeEntry 7 }
            
            latNodeServiceNumber OBJECT-TYPE
                SYNTAX Gauge
                ACCESS read-only
                STATUS mandatory
                DESCRIPTION
                    "Number of entries for the node in the node service 
                    table.  Corresponds indirectly to the list of 
                    services in the NODE STATUS display."
                ::= { latNodeEntry 8 }
            
            latNodeZero OBJECT-TYPE
                SYNTAX INTEGER { ready(1), execute(2) }
                ACCESS read-write
                STATUS mandatory
                DESCRIPTION
                    "Control to zero counters kept for the node.  In 
                    response to a get-request or get-next-request, the 
                    agent always returns 'ready' for this value.  
                    Setting the value to 'ready' has no effect.  Setting 
                    it to 'execute' causes all the system's counters to 
                    be zeroed.  Corresponds to the ZERO NODE command."
                ::= { latNodeEntry 9 }
            
            latNodeZeroTime OBJECT-TYPE
                SYNTAX TimeTicks
                ACCESS read-only
                STATUS mandatory
                DESCRIPTION
                    "The number of hundredths of a second since the most 
                    recent zeroing of the counters kept for the node, 
                    such as through execution of sysZeroAll or 
                    latNodeZero.  Corresponds directly to the value 
                    labeled 'Seconds Since Zeroed:' in the NODE COUNTERS 
                    display."
                ::= { latNodeEntry 10 }
            
            latNodeInMessages OBJECT-TYPE
                SYNTAX Counter

            
            

            
            
            
            
                ACCESS read-only
                STATUS mandatory
                DESCRIPTION
                    "The number of LAT messages received from the node.  
                    Corresponds directly to the value labeled 'Messages 
                    Received:' in the NODE COUNTERS display."
                ::= { latNodeEntry 11 }
            
            latNodeOutMessages OBJECT-TYPE
                SYNTAX Counter
                ACCESS read-only
                STATUS mandatory
                DESCRIPTION
                    "The number of LAT messages sent to the node.  
                    Corresponds directly to the value labeled 'Messages 
                    Transmitted:' in the NODE COUNTERS display."
                ::= { latNodeEntry 12 }
            
            latNodeInSlots OBJECT-TYPE
                SYNTAX Counter
                ACCESS read-only
                STATUS mandatory
                DESCRIPTION
                    "The number of LAT slots received from the node.  
                    Corresponds directly to the value labeled 'Slots 
                    Received:' in the NODE COUNTERS display."
                ::= { latNodeEntry 13 }
            
            latNodeOutSlots OBJECT-TYPE
                SYNTAX Counter
                ACCESS read-only
                STATUS mandatory
                DESCRIPTION
                    "The number of LAT slots sent to the node.  
                    Corresponds directly to the value labeled 'Slots 
                    Transmitted:' in the NODE COUNTERS display."
                ::= { latNodeEntry 14 }
            
            latNodeInBytes OBJECT-TYPE
                SYNTAX Counter
                ACCESS read-only
                STATUS mandatory
                DESCRIPTION
                    "The total number of bytes received from the node, 
                    including Ethernet overhead.  Corresponds directly 
                    to the value labeled 'Bytes Received:' in the NODE 

            
            

            
            
            
            
                            COUNTERS display."
                ::= { latNodeEntry 15 }
            
            latNodeOutBytes OBJECT-TYPE
                SYNTAX Counter
                ACCESS read-only
                STATUS mandatory
                DESCRIPTION
                    "The total number of bytes sent to the node, 
                    including Ethernet overhead.  Corresponds directly 
                    to the value labeled 'Bytes Transmitted:' in the 
                    NODE COUNTERS display."
                ::= { latNodeEntry 16 }
            
            latNodeAddressChange OBJECT-TYPE
                SYNTAX Counter
                ACCESS read-only
                STATUS mandatory
                DESCRIPTION
                    "The number of times a LAT message multicast by the 
                    node had a different Ethernet address from the 
                    previous time.  Corresponds directly to the value 
                    labeled 'Multiple Node Addresses:' in the NODE 
                    COUNTERS display."
                ::= { latNodeEntry 17 }
            
            latNodeInDuplicates OBJECT-TYPE
                SYNTAX Counter
                ACCESS read-only
                STATUS mandatory
                DESCRIPTION
                    "The number of duplicate LAT message received from 
                    the node.  Corresponds directly to the value labeled 
                    'Duplicates Received:' in the NODE COUNTERS 
                    display."
                ::= { latNodeEntry 18 }
            
            latNodeOutRetransmits OBJECT-TYPE
                SYNTAX Counter
                ACCESS read-only
                STATUS mandatory
                DESCRIPTION
                    "The number of LAT message retransmitted to the node 
                    due to lack of acknowledgement.  Corresponds 
                    directly to the value labeled 'Messages 
                    Re-transmitted:' in the NODE COUNTERS display."

            
            

            
            
            
            
                ::= { latNodeEntry 19 }
            
            latNodeInBadMessages OBJECT-TYPE
                SYNTAX Counter
                ACCESS read-only
                STATUS mandatory
                DESCRIPTION
                    "The number of LAT message received from the node 
                    with invalid format.  Corresponds directly to the 
                    value labeled 'Illegal Messages Received:' in the 
                    NODE COUNTERS display."
                ::= { latNodeEntry 20 }
            
            latNodeInBadSlots OBJECT-TYPE
                SYNTAX Counter
                ACCESS read-only
                STATUS mandatory
                DESCRIPTION
                    "The number of LAT slots received from the node with 
                    invalid format.  Corresponds directly to the value 
                    labeled 'Illegal Slots Received:' in the NODE 
                    COUNTERS display."
                ::= { latNodeEntry 21 }
            
            latNodeInSessionsAccepted OBJECT-TYPE
                SYNTAX Counter
                ACCESS read-only
                STATUS mandatory
                DESCRIPTION
                    "The number of LAT session connection attempts 
                    received from the node and accepted.  Corresponds 
                    directly to the value labeled 'Solicitations 
                    Accepted:' in the NODE COUNTERS display."
                ::= { latNodeEntry 22 }
            
            latNodeInSessionsRejected OBJECT-TYPE
                SYNTAX Counter
                ACCESS read-only
                STATUS mandatory
                DESCRIPTION
                    "The number of LAT session connection attempts 
                    received from the node and rejected.  Corresponds 
                    directly to the value labeled 'Solicitations 
                    Rejected:' in the NODE COUNTERS display."
                ::= { latNodeEntry 23 }
            

            
            

            
            
            
            
END
