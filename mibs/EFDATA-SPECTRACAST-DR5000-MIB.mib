EFDATA-SPECTRACAST-DR5000-MIB DEFINITIONS ::= BEGIN

-- generic definitions of types and Efdata client MIB
-- placement on general SNMP tree

         IMPORTS
			Counter FROM RFC1155-SMI
                 enterprises, IpAddress, OBJECT-TYPE
                         FROM SNMPv2-SMI
                 DisplayString
                         FROM RFC1213-MIB;
                         
         efdata  OBJECT IDENTIFIER ::= { enterprises 6247 }
         spectracast  OBJECT IDENTIFIER ::= { efdata 3 }
	 dr5000	OBJECT IDENTIFIER ::= { spectracast 2 }
         general  OBJECT IDENTIFIER ::= { dr5000 1 }

	MPEG-PID-mode ::= INTEGER { manual(1), automatic(2) }

	FLAG ::= INTEGER	{ on(1), off(2) } 

-- lns definitions

	softwareVersion OBJECT-TYPE
	SYNTAX  DisplayString
              	ACCESS  read-only
        		STATUS  mandatory
	   	DESCRIPTION "Software Version (read only)."
	::={ general 1 }

	hardwareVersion OBJECT-TYPE
	SYNTAX  DisplayString
              	ACCESS  read-only
        	STATUS  mandatory
	   	DESCRIPTION "Hardware Version (read only)."
	::={ general 2 }
	
	macAddress OBJECT-TYPE
		SYNTAX 	DisplayString
			ACCESS  read-only
			STATUS  mandatory
		DESCRIPTION
		"MAC address (read only)."
	::={ general 3 } 

	multicastRoutingStatus OBJECT-TYPE
		SYNTAX DisplayString
			ACCESS  read-only
			STATUS  mandatory
		DESCRIPTION
		"Multicast routing status (read only)."
	::={ general 4 }


        rfparameters  OBJECT IDENTIFIER ::= { dr5000 2 }

	rf-Input OBJECT-TYPE
		SYNTAX  DisplayString
			ACCESS  read-write
			STATUS  mandatory
		DESCRIPTION 
		"RF Input frequency (MHz) (read-write)."
	::={ rfparameters 1 }

	lnb-Frequency OBJECT-TYPE
		SYNTAX  DisplayString
			ACCESS  read-write
			STATUS  mandatory
		DESCRIPTION 
		"LNB frequency (GHz) (read-write)."
	::={ rfparameters 2 }

	symbolRate    OBJECT-TYPE
		SYNTAX  DisplayString
			ACCESS  read-write	
			STATUS  mandatory
		DESCRIPTION
		"Symbol rate (Msps) (read-write)."
	::={ rfparameters 3 }

	polarity	 OBJECT-TYPE
		SYNTAX  INTEGER
			{
				disabled(0),
				vertical(14),
				horizontal(18)
			}
			ACCESS  read-write	
			STATUS  mandatory
		DESCRIPTION
		"Polarity may take values: Disabled(0), Vertical(14) or Horizontal(18) (read-write)."
	::={ rfparameters 4 }

	frequencyRange OBJECT-TYPE
		SYNTAX  INTEGER
			{
				low(0),
				high(1)
			}
			ACCESS  read-write
			STATUS  mandatory
		DESCRIPTION
		"Frequency range may take values: Low(0) or High(1) (read-write)."
	::= { rfparameters 5 }


        dvbparameters  OBJECT IDENTIFIER ::= { dr5000 3 }

	pids-number    OBJECT-TYPE
		SYNTAX  INTEGER
			ACCESS  read-only
			STATUS  mandatory
		DESCRIPTION
		"Number of PIDs in the list (read only)."
	::={ dvbparameters 1 }

	pidTable  OBJECT-TYPE
		SYNTAX  SEQUENCE OF PIDentry
			ACCESS not-accessible 
			STATUS  mandatory
		DESCRIPTION
		"List of PID entries. The number of entries is given by PIDs-number value."
	::= { dvbparameters 2 }

	pidEntry OBJECT-TYPE
		SYNTAX PIDentry
			ACCESS not-accessible
			STATUS mandatory
		DESCRIPTION
		"PID entry containing objects for the particular PID."
		INDEX { pidindex }
	::= { pidTable 1 }

	PIDentry ::=
		SEQUENCE {
			pidindex INTEGER,
			pidvalue INTEGER
		}

	pidindex OBJECT-TYPE
		SYNTAX INTEGER
              	ACCESS  read-only
              	STATUS  mandatory

		DESCRIPTION 
		"Unique ID for each PID, ranges between 1 and PIDs-number (read-only)."
	::= { pidEntry 1 }


	pidvalue OBJECT-TYPE
		SYNTAX INTEGER
		ACCESS read-write
		STATUS mandatory
		DESCRIPTION 
		"Unique PID value (read-write)."
	::= { pidEntry 2 }


	ccuparameters  OBJECT IDENTIFIER ::= { dr5000 4 }

	ccuConnectionMode	OBJECT-TYPE
		SYNTAX INTEGER
			{	
				manual(0),
				duplex(1),
				simplex(2)
			}
		ACCESS read-write
		STATUS mandatory
		DESCRIPTION
		"CCU connection mode, may take values: Manual(0), Duplex(1) or Simplex(2) (read-write)."
	::={ ccuparameters 1 }

	ccuIpAddress OBJECT-TYPE
		SYNTAX IpAddress
		ACCESS read-write
		STATUS mandatory
		DESCRIPTION
		"CCU IP Address (read-write)."
	::={ ccuparameters 2 }

	ccuUserName OBJECT-TYPE
		SYNTAX 	DisplayString
		ACCESS 	write-only
		STATUS 	mandatory
		DESCRIPTION
		"User name for connecting to the CCU (write only)."
	::={ ccuparameters 3 }	

	ccuPassword	OBJECT-TYPE
		SYNTAX	DisplayString
		ACCESS	write-only
		STATUS	mandatory
		DESCRIPTION
		"Password for connecting to the CCU (write only)."
	::={ ccuparameters 4 }

	encryptedMulticast	OBJECT-TYPE
		SYNTAX	INTEGER
			{
				disabled(0),
				enabled(1)
			}
		ACCESS	read-write
		STATUS	mandatory
		DESCRIPTION
		"Set to Enabled in order to receive encrypted multicast."
	::={ ccuparameters 5 }


	dialupparameters  OBJECT IDENTIFIER ::= { dr5000 5 }

	connectionMode	OBJECT-TYPE
		SYNTAX 	INTEGER
			{
				manual(0),
				automatic(1)		
			}
		ACCESS	read-write
		STATUS	mandatory
		DESCRIPTION
		"Connection Mode, may take values: Manual(0) or Automatic(1) (read-write)."
	::={ dialupparameters 1 }

	phoneNumber	OBJECT-TYPE
		SYNTAX	INTEGER
		ACCESS	read-write
		STATUS	mandatory
		DESCRIPTION
		"ISP Phone number, accepts only digits (read-write)."
	::={ dialupparameters 2 }

	userName	OBJECT-TYPE
		SYNTAX	DisplayString
		ACCESS	write-only
		STATUS	mandatory
		DESCRIPTION
		"User name for dialup connection (write only)."
	::={ dialupparameters 3 }

	password	OBJECT-TYPE
		SYNTAX	DisplayString
		ACCESS	write-only
		STATUS	mandatory
		DESCRIPTION
		"Password for dialup connection (write only)."
	::={ dialupparameters 4 }

	dialTone	OBJECT-TYPE
		SYNTAX	INTEGER
			{
				tone(0),
				pulse(1)
			}
		ACCESS	read-write
		STATUS	mandatory
		DESCRIPTION
		"Dialing mode, may take values: Tone(0)) or Pulse(1) (read-write)."
	::={ dialupparameters 5 }

	speed	OBJECT-TYPE
		SYNTAX	INTEGER
		ACCESS	read-write
		STATUS	mandatory
		DESCRIPTION
		"Modem connection speed, may take values: 9600, 19200, 38400, 57600 or 115200 (read-write)."
	::={ dialupparameters 7 }

	idleTimeOut OBJECT-TYPE
		SYNTAX	INTEGER
		ACCESS	read-write
		STATUS	mandatory
		DESCRIPTION
		"Dial on demand time out in minutes.
		 Set to 0 in order to disable dial on demand (read-write)."
	::={ dialupparameters 8 }

	authentication	OBJECT-TYPE
		SYNTAX INTEGER
		{
			pap(0),
			chap(1)
		}
		ACCESS	read-write
		STATUS	mandatory
		DESCRIPTION
		"Authentication mode, may take values: PAP or CHAP (read-write)."
	::={ dialupparameters 9 }


        status  OBJECT IDENTIFIER ::= { dr5000 6 }

	initializationStatus OBJECT-TYPE
		SYNTAX  DisplayString
              	ACCESS  read-only
              	STATUS  mandatory
		DESCRIPTION
		"Card initialization status (read only)."
	::={ status 1 }

	demodulatorStatus OBJECT-TYPE
		SYNTAX  DisplayString
			ACCESS  read-only	
			STATUS  mandatory
		DESCRIPTION 
		"Current demodulator status (read only)."
	::={ status 2 }

	spectralInversion OBJECT-TYPE
		SYNTAX  DisplayString
			ACCESS  read-only
			STATUS  mandatory
		DESCRIPTION
		"Spectral inversion (read only)."
	::={ status 3 }

	ber-before-Err-Correction OBJECT-TYPE
		SYNTAX  DisplayString
			ACCESS  read-only
			STATUS  mandatory
		DESCRIPTION
		"BER before error correction (read only)."
	::={ status 4 }

	fec OBJECT-TYPE
		SYNTAX  DisplayString
			ACCESS  read-only
			STATUS  mandatory
		DESCRIPTION
		"FEC (read only)."
	::={ status 5 }

	agc OBJECT-TYPE
		SYNTAX  DisplayString
			ACCESS  read-only
			STATUS  mandatory
		DESCRIPTION
		"Gain value set by AGC (Db) (read only)."
	::={ status 6 }

	frequencyOffset OBJECT-TYPE
		SYNTAX  DisplayString
			ACCESS  read-only
			STATUS  mandatory
		DESCRIPTION
		"Frequency offset (read only)."
	::={ status 7 }

	eb-N0 OBJECT-TYPE
		SYNTAX  DisplayString
			ACCESS  read-only
			STATUS  mandatory
		DESCRIPTION
		"Eb/N0 (read only)."
	::={ status 8 }

	ccu-connection-status OBJECT-TYPE
		SYNTAX	INTEGER
		{
			disconnected(0),
			connected(1),
			tryingtoconnect(2),
			waitingfordialup(3),
			waitingforrflock(4)
		}
		ACCESS	read-only
		STATUS	mandatory
		DESCRIPTION
		"CCU connection status, may take values Disconnected(0), Connected(1), Trying to Connect(2),
		 Waiting for Dialup(3), or Waiting for RF Lock(4) (read only)."
	::={ status 9 }

	dialup-connection-status OBJECT-TYPE
		SYNTAX	INTEGER
		{
			disconnected(0),
			connected(1),
			tryingtoconnect(2),
			idle(10)
		}
		ACCESS	read-only
		STATUS	mandatory
		DESCRIPTION
		"Dialup connection status, may take values Disconnected(0), Connected(1), Trying to Connect(2)
		 or Idle(10) (read only)."
	::={ status 10 } 


        flowStatistics  OBJECT IDENTIFIER ::= { dr5000 7 }
  
	totalThroughput OBJECT-TYPE
		SYNTAX  DisplayString
              	ACCESS  read-only
              	STATUS  mandatory
		DESCRIPTION
		"Total throughput in bytes/sec. (read only)."
	::={ flowStatistics 1 }

	unicastThroughput OBJECT-TYPE
		SYNTAX  DisplayString
              	ACCESS  read-only
              	STATUS  mandatory
		DESCRIPTION
		"Unicast throughput in bytes/sec. (read only)."
	::={ flowStatistics 2 }

	multicastThroughput OBJECT-TYPE
		SYNTAX  DisplayString
              	ACCESS  read-only
              	STATUS  mandatory
		DESCRIPTION
		"Multicast throughput in bytes/sec. (read only)."
	::={ flowStatistics 3 }

	totalPackets OBJECT-TYPE
		SYNTAX  DisplayString
			ACCESS  read-only
			STATUS  mandatory
		DESCRIPTION
		"Total packets received since reset (read only)."
	::={ flowStatistics 4 }

	badPackets OBJECT-TYPE
		SYNTAX  DisplayString
			ACCESS  read-only
			STATUS  mandatory
		DESCRIPTION
		"Bad RS packets (read only)."
	::={ flowStatistics 5 }

	correctedPackets OBJECT-TYPE
		SYNTAX  DisplayString
			ACCESS  read-only
			STATUS  mandatory
		DESCRIPTION
		"Corrected RS packets (read only)."
	::={ flowStatistics 6 }

	resetFlowStatistics OBJECT-TYPE
		SYNTAX  INTEGER
		{
			false(0),
			true(1)
		}
			ACCESS read-write
			STATUS mandatory
		DESCRIPTION
		"Set to True in order to reset flow statistics."
	::={ flowStatistics 7 }

	maintenance  OBJECT IDENTIFIER ::= { dr5000 8 }
	
	
	driverRestart OBJECT-TYPE
		SYNTAX  INTEGER
		{
			false(0),
			true(1)
		}
			ACCESS read-write
			STATUS mandatory
		DESCRIPTION 
		"Set to True in order to restart the Driver."
	::={ maintenance 1 }

	dialupConnect	OBJECT-TYPE
		SYNTAX	INTEGER
		{
			false(0),
			true(1)
		}
		ACCESS	read-write
		STATUS mandatory
		DESCRIPTION
		"Set to True in order to dial your ISP."
	::={ maintenance 2 }

	dialupDisconnect	OBJECT-TYPE
		SYNTAX	INTEGER
		{
			false(0),
			true(1)
		}
		ACCESS	read-write
		STATUS	mandatory
		DESCRIPTION
		"Set to true in order to disconnect from your ISP."
	::={ maintenance 3 }

	ccuconnect	OBJECT-TYPE
		SYNTAX	INTEGER
		{
			false(0),
			true(1)
		}
		ACCESS	read-write
		STATUS	mandatory
		DESCRIPTION
		"Set to True in order to connect to the CCU."
	::={ maintenance 4 }

	ccudisconnect	OBJECT-TYPE
		SYNTAX	INTEGER
		{
			false(0),
			true(1)
		}
		ACCESS	read-write
		STATUS	mandatory
		DESCRIPTION
		"Set to True in order to disconnect from the CCU."
	::={ maintenance 5 }
	
	upgrade		OBJECT-TYPE
		SYNTAX	DisplayString
		ACCESS	write-only
		STATUS	mandatory
		DESCRIPTION
		"Set to the upgrade file name, and upgrade the system.
		 After upgrade finishes the system reboots automatically (write only)."
	::={ maintenance 6 }


	snmpVariables  OBJECT IDENTIFIER ::= { dr5000 9 }
	
	enableTraps OBJECT-TYPE
		SYNTAX  INTEGER
		{
			disable(0),
			enable(1)
		}
			ACCESS read-write
			STATUS mandatory
		DESCRIPTION 
		"Set to True in order to start getting traps."
	::={ snmpVariables 1 }

	snmpManagerIP OBJECT-TYPE
		SYNTAX  IpAddress
		ACCESS read-write
		STATUS mandatory
		DESCRIPTION 
		"IP address of SNMP manager where traps have to be sent to (read-write)."
	::={ snmpVariables 2 }

	trapPeriod OBJECT-TYPE
		SYNTAX  INTEGER
		ACCESS read-write
		STATUS mandatory
		DESCRIPTION 
		"Trap sending period in seconds (read-write)."
	::={ snmpVariables 3 }

	trapList  OBJECT IDENTIFIER ::= { snmpVariables 4 }

	multicastDaemon  OBJECT IDENTIFIER ::= { trapList 1 }
	
	multicastTrapEnable OBJECT-TYPE
		SYNTAX  INTEGER
		{
			disable(0),
			enable(1)
		}
			ACCESS read-write
			STATUS mandatory
		DESCRIPTION 
		"Use multicast daemon status trap. A trap message is sent when multicast
		 daemon goes down (read-write)."
	::={ multicastDaemon 1 }

	demodulator  OBJECT IDENTIFIER ::= { trapList 2 }
	
	demodulatorTrapEnable OBJECT-TYPE
		SYNTAX  INTEGER
		{
			disable(0),
			enable(1)
		}
			ACCESS read-write
			STATUS mandatory
		DESCRIPTION 
		"Use demodulator status trap. A trap message is sent when the demodulator 
		loses data lock (read-write)."
	::={ demodulator 1 }
	
	ccuConnection  OBJECT IDENTIFIER ::= { trapList 3 }
	
	ccuTrapEnable OBJECT-TYPE
		SYNTAX  INTEGER
		{
			disable(0),
			enable(1)
		}
			ACCESS read-write
			STATUS mandatory
		DESCRIPTION 
		"Use CCU connection status trap. A trap message is sent when CCU status changes from
		 Connected to any other one (read-write)."
	::={ ccuConnection 1 }
	
	dialup  OBJECT IDENTIFIER ::= { trapList 4 }
	
	dialupTrapEnable OBJECT-TYPE
		SYNTAX  INTEGER
		{
			disable(0),
			enable(1)
		}
			ACCESS read-write
			STATUS mandatory
		DESCRIPTION 
		"Use dialup connection status trap. A trap message is sent when dialup status changes
		 from Connected to any other one except Idle (read-write)."
	::={ dialup 1 }
	
	berLevel  OBJECT IDENTIFIER ::= { trapList 5 }
	
	berTrapEnable OBJECT-TYPE
		SYNTAX  INTEGER
		{
			disable(0),
			enable(1)
		}
			ACCESS read-write
			STATUS mandatory
		DESCRIPTION 
		"Use BER level trap. A trap message is sent when BER value is greater
		 then BER trap threshold (read-write)."
	::={ berLevel 1 }

	berThreshold OBJECT-TYPE
		SYNTAX  OCTET STRING 
		ACCESS read-write
		STATUS mandatory
		DESCRIPTION 
		"BER level threshold value (read-write)."
	::={ berLevel 2 }

	freqOffset  OBJECT IDENTIFIER ::= { trapList 6 }
	
	freqOffsetTrapEnable OBJECT-TYPE
		SYNTAX  INTEGER
		{
			disable(0),
			enable(1)
		}
			ACCESS read-write
			STATUS mandatory
		DESCRIPTION 
		"Use frequency offset trap. A trap message is sent when absolute frequency offset is greater 
		then frequency offset trap threshold (read-write)."
	::={ freqOffset 1 }

	freqOffsetThreshold OBJECT-TYPE
		SYNTAX  OCTET STRING 
		ACCESS read-write
		STATUS mandatory
		DESCRIPTION 
		"Frequency offset threshold value (read-write)."
	::={ freqOffset 2 }

	agcLevel  OBJECT IDENTIFIER ::= { trapList 7 }
	
	agcTrapEnable OBJECT-TYPE
		SYNTAX  INTEGER
		{
			disable(0),
			enable(1)
		}
			ACCESS read-write
			STATUS mandatory
		DESCRIPTION 
		"Use AGC level trap.  A trap message is sent when gain value is greater 
		then AGC trap threshold (read-write)."
	::={ agcLevel 1 }

	agcThreshold OBJECT-TYPE
		SYNTAX  OCTET STRING 
		ACCESS read-write
		STATUS mandatory
		DESCRIPTION 
		"AGC threshold value (read-write)"
	::={ agcLevel 2 }

END
