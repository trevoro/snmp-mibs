-- $Id: it-rmon-mib.mib,v 1.3 2001/07/25 15:15:02 sse Exp $
        ITOUCH-RMON-MIB DEFINITIONS ::= BEGIN

                IMPORTS
                        Counter             FROM RFC1155-SMI
                        Gauge               FROM RFC1155-SMI
                        OBJECT-TYPE         FROM RFC-1212
                        TRAP-TYPE           FROM RFC-1215
                        iTouch              FROM ITOUCH-MIB
                        DateTime            FROM ITOUCH-MIB
                        DisplayString       FROM RFC1213-MIB
                        alarmIndex          FROM RFC1271-MIB
                        etherStatsIndex     FROM RFC1271-MIB;

        xRmon           OBJECT IDENTIFIER ::= { iTouch 31 }

        -- The individual Groups within the RMON MIB

        xRmonMonitor    OBJECT IDENTIFIER ::= { xRmon 1 }
        xRmonMB         OBJECT IDENTIFIER ::= { xRmon 2 }
        -- xRmonMapTable OBJECT IDENTIFIER ::= { xRmon 3 }

            -- This is a MIB module for all iTouch Communications systems
            -- that implement RMON.

            -- Copyright 2000 iTouch Communications, Inc. All Rights Reserved.
            -- Reproduction of this document is authorized on
            -- condition that this copyright notice is included.
            -- This MIB document embodies iTouch Communications, Inc.'s 
            -- proprietary intellectual property.  iTouch Communications, Inc.
            -- retains all title and ownership in this MIB, including any
            -- revisions.
            --
            -- It is iTouch Communications, Inc.'s intent to encourage the
            -- widespread use of this MIB in connection with the management of
            -- iTouch Communications, Inc. products. iTouch Communications,
            -- Inc. grants vendors,end-users, and other interested parties a
            -- non-exclusive license to use this MIB in connection with the
            -- management of iTouch Communications, Inc. products.
            --
            -- This MIB document is supplied "AS IS," and iTouch 
            -- Communications, Inc. makes no warranty, either express or
            -- implied, as to the use operation, condition, or performance of
            -- the MIB.

        -- DESCRIPTION fields for many objects are written in the
        -- form of 'help text', rather than as complete 'mib style'
        -- functional descriptions.

        -- The RMON Monitor group

        -- Implementation of this group is mandatory for all iTouch
        -- systems that implement RMON for fault management.

        xRmonMonitorRemote OBJECT-TYPE
            SYNTAX INTEGER (0..65535)
            ACCESS read-only
            STATUS mandatory
            DESCRIPTION "
                Once an alarm is 'completed', monitoring for that
                variable may be distributed within an enclosure to
                another processor.  Factors affecting this decision
                include variable type, slot number, and processor
                type.  Furthermore, alarms which have identical
                parameters (variable, interval, thresholds, etc.)
                are viewed by the monitoring processor as a single
                'object' to monitor.

                Alarm variables falling into this category are a
                subset of the repeater MIB and iTouch repeater MIB
                objects.

                This field represents the number of 'objects' this
                system CPU is monitoring on behalf of alarms which
                were distributed to it by a management processor."
            ::= { xRmonMonitor 1 }

        xRmonMonitorLocal OBJECT-TYPE
            SYNTAX INTEGER (0..65535)
            ACCESS read-only
            STATUS mandatory
            DESCRIPTION "
                Once an alarm is 'completed', monitoring for that
                variable may be distributed within an enclosure to
                another processor.  Factors affecting this decision
                include variable type, slot number, and processor
                type.  Furthermore, alarms which have identical
                parameters (variable, interval, thresholds, etc.)
                are viewed by the monitoring processor as a single
                'object' to monitor.

                Alarm variables falling into this category are a
                subset of the repeater MIB and iTouch repeater MIB
                objects.

                This field represents the number of 'objects' this
                system CPU is monitoring, objects it did not
                distribute to another processor."
            ::= { xRmonMonitor 2 }

        xRmonLogClear OBJECT-TYPE
            SYNTAX INTEGER { ready(1), execute(2) }
            ACCESS read-write
            STATUS mandatory
            DESCRIPTION "
                Set this field to 'execute' to delete all RMON log
                table entries.  Setting to 'ready' has no effect."
            ::= { xRmonMonitor 3 }

        xRmonLogTotal OBJECT-TYPE
            SYNTAX Counter
            ACCESS read-only
            STATUS mandatory
            DESCRIPTION "
                This field reports the total number of RMON log
                entries created since the system was initialized.
                Clearing the log table does not change this value."
            ::= { xRmonMonitor 4 }

        xRmonLogLastDateTime OBJECT-TYPE
            SYNTAX DateTime
            ACCESS read-only
            STATUS mandatory
            DESCRIPTION "
                The local date and time of the system at the time
                an RMON log entry was last created."
            ::= { xRmonMonitor 5 }

        xRmonTrapType OBJECT-TYPE
            SYNTAX INTEGER { standardFormat(1), iTouchFormat(2) }
            ACCESS read-write
            STATUS mandatory
            DESCRIPTION "
                Use this field to specify the type of SNMP trap to
                generate when an alarm event occurs.

                The value 'standardFormat' formats the trap as a
                standard, RMON-compliant rising and falling event
                trap.

                The value 'iTouchFormat' formats the trap as a
                DisplayString containing a human-readable summary
                of the event.  The text of the string is very
                similar to that of the log descriptions."
            DEFVAL { standardFormat }
            ::= { xRmonMonitor 6 }

        xRmonRepeaterManagement OBJECT-TYPE
            SYNTAX INTEGER { disabled(1), enabled(2) }
            ACCESS read-write
            STATUS mandatory
            DESCRIPTION "
                This field enables and disables RMON monitoring of
                certain repeater related variables in the chassis.

                Set this field to 'enabled' to allow this slot to
                activate alarms and report traps for variables from
                the standard repeater MIB (snmpDot3RptrMgt
                1.3.6.1.2.1.22) and the iTouch repeater MIB
                (xRepeater 1.3.6.1.4.1.33.17).

                When you set this field to 'disabled', alarms may
                still be created for these repeater variables, but
                no monitoring will take place for them.  The alarm
                state will be 'held' during this time.

                Only one slot in a chassis may have this field set
                to 'enabled' at any given time.  Setting 'enabled'
                in any one slot automatically sets it to 'disabled'
                in every other slot.  Repeater variable monitoring
                in those slots will cease and the corresponding
                alarm states will be 'held'."
            DEFVAL { disabled }
            ::= { xRmonMonitor 7 }

        xRmonAlarmActivate OBJECT-TYPE
            SYNTAX INTEGER {
                noAction(1),
                activateAll(2),
                deactivateAll(3)
            }
            ACCESS read-write
            STATUS mandatory
            DESCRIPTION "
                Use this field to change the states of all completed
                alarms to 'active' or 'inactive'.

                Select 'activateAll' to make all completed alarms
                not in the 'active' state become 'active' again.
                This is useful for alarms whose error states are not
                automatically cleared by the system.  Alarms whose
                error conditions have not cleared will remain in
                their current states.

                Select 'deactivateAll' to make all completed alarms
                that are in the 'active' state become 'inactive'.
                This is a convenient way to suppress alarm activity
                while making other configuration changes without
                actually deleting the alarms.

                Alarms which are incomplete (e.g., 'creating' state)
                are not affected by these actions.

                If you want to alter the state of a single alarm,
                modify the table entry for that alarm.

                Selecting noAction has no effect."
            ::= { xRmonMonitor 8 }

        xRmonAlarmClear OBJECT-TYPE
            SYNTAX INTEGER { noAction(1), deleteAll(2) }
            ACCESS read-write
            STATUS mandatory
            DESCRIPTION "
                Set this field to 'deleteAll' to delete all alarm
                table entries and their associated event entries.
                Setting to 'noAction' has no effect."
            ::= { xRmonMonitor 9 }

        -- The xRmonAlarmCount group

        -- These counters reflect the number of alarms in each of
        -- several different states.

        xRmonAlarmCount   OBJECT IDENTIFIER ::= { xRmonMonitor 10 }

        xRmonAlarmsIncomplete OBJECT-TYPE
            SYNTAX INTEGER
            ACCESS read-only
            STATUS mandatory
            DESCRIPTION "
                This value represents the number of alarms that are
                not completed.  Completing these alarms will make
                them active."
            ::= { xRmonAlarmCount 1 }

        xRmonAlarmsActive OBJECT-TYPE
            SYNTAX INTEGER
            ACCESS read-only
            STATUS mandatory
            DESCRIPTION "
                This value represents the number of alarms whose
                state is 'active'.  These are completed alarms
                which are actively monitored."
            ::= { xRmonAlarmCount 2 }

        xRmonAlarmsHeld OBJECT-TYPE
            SYNTAX INTEGER
            ACCESS read-only
            STATUS mandatory
            DESCRIPTION "
                This value represents the number of alarms whose
                state is 'held'.  These are completed alarms
                which will not be actively monitored because the
                Repeater Management feature for this processor is
                currently disabled.  Enabling the feature will
                activate all alarms in this state."
            ::= { xRmonAlarmCount 3 }

        xRmonAlarmsOther OBJECT-TYPE
            SYNTAX INTEGER
            ACCESS read-only
            STATUS mandatory
            DESCRIPTION "
                This value represents the number of completed alarms
                that are not 'active' and not 'held'.  Monitoring is
                not active for these alarms."
            ::= { xRmonAlarmCount 4 }

        xRmonAlarmInitAction OBJECT-TYPE
            SYNTAX INTEGER {
                activateUponInit(1),
                inactiveUponInit(2)
            }
            ACCESS read-write
            STATUS mandatory
            DESCRIPTION "
                Use this field to specify whether all alarms read
                from the parameter file should be placed in the
                'active' state or the 'inactive' state upon system
                initialization.

                Selecting 'activateUponInit' (the default) will
                activate all alarms read from the parameter file
                when the system initializes.

                Selecting 'inactiveUponInit' will place all alarms
                in the 'inactive' state when the system initializes.

                Modifying this value does not affect the present
                state of any alarm."
            ::= { xRmonMonitor 11 }

        -- The RMON MB group

        -- Implementation of the iTouch RMON MB group is optional.

        -- The MB group requires implementation of the RMON alarm
        -- and event groups.

        -- The MB group implements a more user-friendly interface to
        -- create RMON alarms and view alarm and log entries using
        -- applications that cannot interpret complex RMON tables.
        -- It offers an alternate interface for creating alarmTable
        -- and eventTable entries.  It also interprets the alarm and
        -- log tables, presenting them as more readable strings.


        -- The RMON MB Configuration Group

        -- The following objects provide access to the creation and
        -- viewing of a single, complete RMON alarmTable entry,
        -- including associated eventTable entries.  RMON alarms not
        -- created using these objects may also be viewed, within
        -- the limits stated below.

        -- Note that these objects, mbAlarmIndex in particular,
        -- cannot be shared among SNMP clients.  Only one such client
        -- should be attempting to create, modify, or view an alarm
        -- at any given time.  Failure to adhere to this convention
        -- may result in unexpected alarm parameter settings.

        -- Similarly, when creating a new alarm sets of these objects
        -- should not be combined in the same SET PDU with RMON alarm
        -- group objects for the same alarmIndex.

        xRmonMBConfig   OBJECT IDENTIFIER ::= { xRmonMB 1 }

        -- If the alarm specified by mbAlarmIndex is deleted through the
        -- standard RMON alarmStatus object, this entry becomes zero.
        -- Setting this object to 0 makes all remaining objects in this
        -- group invisible to SNMP.  GET-NEXT will skip over them and
        -- GET/SET return noSuchName errors.

        mbAlarmIndex OBJECT-TYPE
            SYNTAX INTEGER (0..65535)
            ACCESS read-write
            STATUS mandatory
            DESCRIPTION "
                This field can be either the index of an existing
                alarm (as seen in the alarm summary view) or a new
                number to create a new alarm.

                Specify the index of an existing alarm to fill the
                remaining fields with the corresponding settings
                from that alarm.  To modify the settings of a
                completed alarm, set its status to underCreation.

                Specify an index which does not exist to create a
                new alarm.  The initial settings of the remaining
                fields are taken from the alarm you were previously
                viewing, if any.  This makes it easier to 'copy' an
                alarm definition when you want to change only a few
                of the settings, such as the alarm variable or keys.

                Specify a value of 0 to clear the remaining fields."
            DEFVAL { 0 }
            ::= { xRmonMBConfig 1 }

        mbAlarmInterval OBJECT-TYPE
            SYNTAX INTEGER
            ACCESS read-write
            STATUS mandatory
            DESCRIPTION "
                The interval in seconds over which the variable is
                sampled and compared with the rising and falling
                thresholds.  If the monitored variable exceeds the
                limit 2^31-1 (4294967295), the alarm value field may
                roll over to 0 and cause or suppress the generation
                of an alarm event during that interval.

                You may not modify this field once the alarm is
                completed (see alarm status field)."
            DEFVAL { 10 }
            ::= { xRmonMBConfig 2 }

        mbAlarmVariable OBJECT-TYPE
            SYNTAX OBJECT IDENTIFIER
            ACCESS read-write
            STATUS mandatory
            DESCRIPTION "
                This value shows the SNMP object identifier of the
                variable being sampled.  Only variables that have an
                SNMP 'SYNTAX' of INTEGER, Counter, Gauge, or
                TimeTicks may be sampled.

                When you specify an object identifier in this field,
                the quick list, key prompt, and key value fields are
                filled for you with the appropriate values.  If you
                specify an object not found in the quick list, that
                field is set to 'unlistedAlarmVariable'.  The key
                values will be set to zero in this case.

                If you specify an alarm variable and keys using the
                quick list and key fields, an SNMP object identifier
                is built for you and placed in this field.

                You may not modify this field at the same time that
                you modify the quick list field or either of the
                key values.

                You may not modify this field once the alarm is
                completed (see alarm status field)."
            ::= { xRmonMBConfig 3 }

        mbAlarmInterpretation OBJECT-TYPE
            SYNTAX INTEGER {
                unlistedAlarmVariable(1),
                portReadableFrames(2),
                portReadableOctets(3),
                portTotalFrames(4),
                portTotalOctets(5),
                portBroadcastFrames(6),
                portMulticastFrames(7),
                portFrames64Octets(8),
                portFrames65to127Octets(9),
                portFrames128to255Octets(10),
                portFrames256to511Octets(11),
                portFrames512to1023Octets(12),
                portFrames1024to1518Octets(13),
                portPercentUtilization(14),
                portTrafficRatio(15),
                portCollisionRatio(16),
                portErrorRatio(17),
                portBroadcastRatio(18),
                portMulticastRatio(19),
                portUnicastRatio(20),
                 portAlignmentErrors(21),
                portAutoPartitions(22),
                portCollisions(23),
                portCRCAlignErrors(24),
                portCRCErrors(25),
                portDataRateMismatches(26),
                portFrameTooLongErrors(27),
                portLateCollisionErrors(28),
                portManchesterCodeViolations(29),
                portRunts(30),
                portShortPacketErrors(31),
                portStartOfFrameMissing(32),
                portVeryLongFrameErrors(33),
                portTotalErrors(34),
                portAccessState(35),
                portAccessAddressViolations(36),
                portGlobalAddressChanges(37),
                portSourceAddressChanges(38),
                portAdminStatus(39),
                portAutoPartitionState(40),
                portOperStatus(41),
                portPulseStatus(43),
                portPulseLosses(44),
                portSecondsSinceCountersZeroed(45),
                repeaterTotalFrames(46),
                repeaterTotalOctets(47),
                repeaterPercentUtilization(48),
                repeaterCollisions(49),
                repeaterFifoOverflows(50),
                repeaterJabbers(51),
                repeaterSQEErrors(52),
                repeaterSecondsSinceCountersZeroed(53),
                slotTotalFrames(54),
                slotTotalOctets(55),
                slotTotalErrors(56),
                slotCpuUtilization(57),
                slotMemoryUtilization(58),
                slotAlarmCount(59),
                slotFifoErrors(60),
                slotOperStatus(61),
                slotOperStatusChange(62),
                slotSecurityLockState(63),
                slotIOCardOperStatus(64),
                redundancyGroupPathChanges(67),
                redundancyGroupRollbackAttempts(68),
                redundancySecondsSinceCountersZeroed(69),
                redundancyPathTestAttempts(70),
                redundancyPathTestStatus(71),
                systemCurrentPctCPU(72),
                systemCurrentPctMemory(73),
                systemCurrentProcesses(74),
                systemCurrentTimers(75),
                systemCurrentPackets(76),
                systemCurrentIPCs(77),
                systemCurrentFreeMemory(78),
                systemWorstPctCPU(82),
                systemWorstPctMemory(83),
                systemWorstProcesses(84),
                systemWorstTimers(85),
                systemWorstPackets(86),
                systemWorstIPCs(87),
                systemWorstFreeMemory(88),
                systemUpTime(92),
                chassisSlotOperStatus(93),
                chassisSlotSecondsSinceReset(94),
                chassisSlotIOCardOperStatus(95),
                chassisSlotPlus5Status(96),
                chassisSlotPlus12Status(97),
                chassisSlotMinus12Status(98),
                chassisSlotPlus5Watts(99),
                chassisSlotPlus12Watts(100),
                chassisSlotMinus12Watts(101),
                powerSupplyRedundancyStatus(102),
                powerSupplyPlus5Status(103),
                powerSupplyPlus12Status(104),
                powerSupplyMinus12Status(105),
                powerSupplyThermalWarningStatus(106),
                powerSupplyThermalShutdownStatus(107),
                powerSupplyFanStatus(108),
                powerSupplyHardwareInhibitStatus(109),
                powerSupplyPlus5Volts(110),
                powerSupplyPlus12Volts(111),
                powerSupplyMinus12Volts(112),
                powerSupplyWatts(113),
                powerSupplyWattsMax(114),
                powerSupplyChassisWatts(115),
                powerSupplyChassisWattsMax(116),
                powerSupplyHardwareType(117)
            }
            ACCESS read-write
            STATUS mandatory
            DESCRIPTION "
                Use this field when you want to select an alarm
                variable without specifying its entire SNMP object
                identifier.  First, modify this field by selecting
                a variable from the list.  Then, read the key prompt
                fields.  They will direct you to specify key values
                appropriate to the selected variable.  The SNMP
                object identifier will be built for you when you
                are done.

                You may not modify this field at the same time that
                you modify the object identifier field.

                You may not modify this field once the alarm is
                completed (see alarm status field)."
            ::= { xRmonMBConfig 4 }

        mbAlarmKey1Meaning OBJECT-TYPE
            SYNTAX DisplayString (SIZE (0..47))
            ACCESS read-only
            STATUS mandatory
            DESCRIPTION "
                This field describes how its adjacent key value
                field will be interpreted when building a complete
                SNMP object identifier for the alarm variable.  The
                value of this field changes as you select different
                items from the quick list or specify different SNMP
                object identifiers.

                This object has the value 'not applicable' if its key
                value is not necessary or the object is unknown."
            ::= { xRmonMBConfig 5 }

        mbAlarmKey1 OBJECT-TYPE
            SYNTAX INTEGER
            ACCESS read-write
            STATUS mandatory
            DESCRIPTION "
                Specify a value here according the the instructions
                given in its adjacent prompt field.  That prompt
                explains how this field will be used.

                You may still modify this field even though the
                prompt field indicates that it is not applicable to
                the selected variable.  It will be ignored.

                You may not modify this field at the same time that
                you modify the object identifier field.

                You may not modify this field once the alarm is
                completed (see alarm status field)."
            ::= { xRmonMBConfig 6 }

        mbAlarmKey2Meaning OBJECT-TYPE
            SYNTAX DisplayString (SIZE (0..47))
            ACCESS read-only
            STATUS mandatory
            DESCRIPTION "
                This field describes how its adjacent key value
                field will be interpreted when building a complete
                SNMP object identifier for the alarm variable.  The
                value of this field changes as you select different
                items from the quick list or specify different SNMP
                object identifiers.

                This object has the value 'not applicable' if its key
                value is not necessary or the object is unknown."
            ::= { xRmonMBConfig 7 }

        mbAlarmKey2 OBJECT-TYPE
            SYNTAX INTEGER
            ACCESS read-write
            STATUS mandatory
            DESCRIPTION "
                Specify a value here according the the instructions
                given in its adjacent prompt field.  That prompt
                explains how this field will be used.

                In some cases, the value zero has a special meaning.
                This often occurs when you are prompted to enter a
                port number.  Zero indicates you want each port in
                the indicated slot to be monitored by this alarm.
                Only one alarm will exist, but it will generate an
                event each time any of the ports meets its criteria.

                You may still modify this field even though the
                prompt field indicates that it is not applicable to
                the selected variable.  It will be ignored.

                You may not modify this field at the same time that
                you modify the object identifier field.

                You may not modify this field once the alarm is
                completed (see alarm status field)."
            ::= { xRmonMBConfig 8 }

        mbAlarmSampleType OBJECT-TYPE
            SYNTAX INTEGER { absoluteValue(1), changeInValue(2) }
            ACCESS read-write
            STATUS mandatory
            DESCRIPTION "
                Use this field to select the method of calculating
                the value to be compared against the thresholds.

                When you set this to 'absoluteValue', the variable
                you specified is compared directly with the alarm
                thresholds at the end of each monitoring interval.

                When you set this to 'changeInValue', the change in
                the value of the variable over the interval is
                compared with the thresholds.  This is useful for
                detecting changes in rates of activity.

                You may not modify this field once the alarm is
                completed (see alarm status field)."
            ::= { xRmonMBConfig 9 }

        mbAlarmValue OBJECT-TYPE
            SYNTAX INTEGER
            ACCESS read-only
            STATUS mandatory
            DESCRIPTION "
                This field shows the value of the alarm variable at
                the end of the most recent monitoring interval.  If
                the alarm sample type is 'changeInValue', it instead
                shows the change in value over that interval.

                This field is zero any time the alarm is not active,
                or when the alarm is a wildcard (that is, a port or
                repeater number of 0 was specified for key 2 value).

                The value of this field has meaning after the alarm
                configuration is complete and monitoring begins."
            ::= { xRmonMBConfig 10 }

        -- The alarmStartupAlarm feature is not offered through this
        -- interface.  When creating alarms, risingOrFallingAlarm(3)
        -- is supplied.

        mbAlarmRisingThreshold OBJECT-TYPE
            SYNTAX INTEGER
            ACCESS read-write
            STATUS mandatory
            DESCRIPTION "
                This is the rising threshold value for the alarm.

                When the current alarm value, specified by the alarm
                sample type, is greater than or equal to this
                threshold, and the value at the previous sampling
                interval was less than this threshold, a single
                rising alarm event will be generated.

                Another rising alarm event will not be generated
                until the sampled value falls below the falling
                threshold value.

                You may not modify this field once the alarm is
                completed (see alarm status field)."
            ::= { xRmonMBConfig 11 }

        mbAlarmFallingThreshold OBJECT-TYPE
            SYNTAX INTEGER
            ACCESS read-write
            STATUS mandatory
            DESCRIPTION "
                This is the falling threshold value for the alarm.

                When the current alarm value, specified by the alarm
                sample type, is less than or equal to this
                threshold, and the value at the previous sampling
                interval was greater than this threshold, a single
                rising alarm event will be generated.

                Another rising alarm event will not be generated
                until the sampled value falls below the falling
                threshold value.

                You may not modify this field once the alarm is
                completed (see alarm status field)."
            ::= { xRmonMBConfig 12 }

        -- The alarmRisingEventIndex and alarmFallingEventIndex
        -- values are not accessible through this interface.  Instead,
        -- the value of mbAlarmRisingEventType indicates the event
        -- action.  A set to one of these entries will create an
        -- event entry unique to this alarm.  Choosing noAction(1)
        -- places a zero in the corresponding event index entry.
        -- Deleting an alarm will delete all of its event entries.

        mbAlarmRisingEventType OBJECT-TYPE
            SYNTAX INTEGER {
                noAction(1),
                logOnly(2),
                trapOnly(3),
                logAndTrap(4)
            }
            ACCESS read-write
            STATUS mandatory
            DESCRIPTION "
                Use this field to indicate the type of notification
                to make when the alarm variable exceeds its rising
                threshold.  The default action is to generate both
                a log entry and a trap.

                Set this field to noAction to suppress notification
                of rising threshold events.

                Set this field to logOnly to generate an RMON alarm
                log entry.  These log entries may be viewed through
                the RMON alarm log view.

                Set this field to trapOnly to generate an SNMP trap.
                Refer to the RMON alarm summary to specify whether
                traps are generated in standard RMON format or in
                iTouch format.

                Choosing logAndTrap invokes both these actions.

                You may not modify this field once the alarm is
                completed (see alarm status field)."
            DEFVAL { logAndTrap }
            ::= { xRmonMBConfig 13 }

        mbAlarmFallingEventType OBJECT-TYPE
            SYNTAX INTEGER {
                noAction(1),
                logOnly(2),
                trapOnly(3),
                logAndTrap(4)
            }
            ACCESS read-write
            STATUS mandatory
            DESCRIPTION "
                Use this field to indicate the type of notification
                to make when the alarm variable exceeds its falling
                threshold.  The default action is to generate both
                a log entry and a trap.

                Set this field to noAction to suppress notification
                of falling threshold events.

                Set this field to logOnly to generate an RMON alarm
                log entry.  These log entries may be viewed through
                the RMON alarm log view.

                Set this field to trapOnly to generate an SNMP trap.
                Refer to the RMON alarm summary to specify whether
                traps are generated in standard RMON format or in
                iTouch format.

                Choosing logAndTrap invokes both these actions.

                You may not modify this field once the alarm is
                completed (see alarm status field)."
            DEFVAL { logAndTrap }
            ::= { xRmonMBConfig 14 }

        -- The alarmOwner feature is not offered through this
        -- interface.  When creating alarms, a value of
        -- 'RMON monitor' is supplied.

        mbAlarmSummary OBJECT-TYPE
            SYNTAX DisplayString (SIZE (0..255))
            ACCESS read-only
            STATUS mandatory
            DESCRIPTION "
                As you make changes to the to alarm settings, this
                field is filled with an easily readable summary of
                the alarm parameters.  This is to make it easy for
                you to confirm that monitoring will behave as you
                expected once the alarm status is 'active'."
            ::= { xRmonMBConfig 15 }

        -- mbAlarmStatus is identical to mbAlarmCondition

        mbAlarmStatus OBJECT-TYPE
            SYNTAX INTEGER {
                underCreation(1),
                active(2),
                inactive(3),
                delete(4),
                held(5),
                noHubCard(6),
                oldFirmware(7),
                slotTimeout(8),
                slotFailed(9),
                monitorStopped(10),
                unknownVariable(11),
                keysMissing(12),
                noResources(13),
                loading(14),
                activating(15),
                deactivating(16),
                unsupported(17),
                unknownAlarm(18),
                inconsistency(19),
                invalidFlags(20),
                invalidSlot(21),
                inaccessible(22),
                otherError(23)
            }
            ACCESS read-write
            STATUS mandatory
            DESCRIPTION "
Describes the current operational state of the
alarm and allows you to make limited changes in
the state of the alarm for purposes of managing
its state.

You may set this field to one of: underCreation,
active, inactive, and delete.  All other values
report current status.

underCreation: Alarm configuration is incomplete.
You may modify alarm parameters.  No monitoring
is taking place for the alarm.  An alarm is saved
in a parameter file after configuration complete.
Select this state before changing a previously
completed alarm.

active: Alarm configuration is complete and active
monitoring of the alarm variable is in progress.
Select this state to complete an alarm or to begin
active monitioring of the alarm variable.

inactive: No monitoring of the alarm variable is
actively taking place.  Select this state when you
want to temporarily suppress monitoring for the
alarm.  Select 'active' to begin monitoring again.

delete: Select this state when you want to delete
this alarm and all log entries associated with it.

held: Active monitoring of the alarm variable is not
taking place because this system does not have RMON
Repeater Management set to 'enabled'.  Once you do
this, alarm monitoring begins automatically.

noHubCard: The target slot does not contain a
management card or repeater I/O card capable of
monitoring.  Monitoring will begin automatically
once the target slot is loaded with a supported
configuration.

oldFirmware: The I/O card in the target slot does
not contain monitoring firmware.  Monitoring will
begin automatically once that card has been loaded
with current scm firmware.

slotTimeout: The target slot did not respond to
attempts to activate the alarm.  May happen if the
management card in the target slot does not contain
monitoring software.  Monitoring begins automatically
once the target slot has been repaired or loaded
with current software.

slotFailed: Active monitoring of the alarm
variable stopped because the target slot was not
operating properly.  Monitoring automatically
resumes once the target slot has recovered.

monitorStopped: Active monitoring of the alarm
variable stopped due to some error.  This can
occur if the variable no longer exists because a
related configuration change has made it invalid.
Correct the condition and re-activate the alarm.

unknownVariable: The alarm variable specified by the
object ID is not recognized in the currently running
system.  Correct the entry.

keysMissing: One or more required key values are not
specified in the alarm variable object ID.  Correct
the entry.

noResources: Not enough system resources exist to
activate this alarm.  Reduce the use of packet buffers
or available memory and re-activate the alarm.

loading: The alarm is being read from a parameter
file and will soon be activated.  This condition
is transient.

activating: Monitoring of the alarm variable will
begin soon.  This condition is transient.

deactivating: Monitoring of the alarm variable will
stop soon.  This condition is transient.

unsupported: Monitoring for the alarm variable is
not supported by the target slot.  Monitoring will
begin once that card is loaded with current scm
firmware or software.

unknownAlarm: Monitoring stopped because the target
slot reset.  Monitoring will continue shortly.

inconsistency: Internal system error.

invalidFlags: Internal system error.

invalidSlot: Alarm specified for a slot which does
not exist in the chassis.  Modify and re-activate.

inaccessible: Monitoring of the alarm variable could
not begin.  This can occur if the key values are
invalid for the variable.  Correct and re-activate
the alarm.

otherError: An unspecified error has occurred."
            ::= { xRmonMBConfig 16 }

        -- The eventDescription field is set to contain a description
        -- of the alarm similar to the mbAlarmSummary field.

        -- The eventCommunity feature is not offered through this
        -- interface.  When creating events, a value of null is used.

        -- eventLastTimeSent is not reported through this interface
        -- because event entries created by it are shared among all
        -- alarms.

        -- The eventOwner feature is not offered through this
        -- interface.  When creating events, a value of
        -- 'RMON monitor' is supplied.

        -- The eventStatus feature is not offered through this
        -- interface.  Failure to create an event results in a
        -- mbAlarmRising/FallingEventType of noAction(1).


        -- The RMON MB Group Alarm View Table

        -- This table provides a human-readable interpretation of
        -- all RMON alarm group alarmTable entries, ordered by
        -- increasing value of alarmIndex.

        -- Though this table is indexed by alarmIndex, a separate
        -- index is supplied within the table to allow

        mbAlarmTable OBJECT-TYPE
            SYNTAX SEQUENCE OF MbAlarmEntry
            ACCESS not-accessible
            STATUS mandatory
            DESCRIPTION
                "A list of RMON alarms.  This table is indexed by
                alarmIndex to provide an intuitive mapping between
                alarms and descriptions."
            ::= { xRmonMB 2 }

        mbAlarmEntry OBJECT-TYPE
            SYNTAX MbAlarmEntry
            ACCESS not-accessible
            STATUS mandatory
            DESCRIPTION
                "A description of an RMON alarm which summarizes the
                actual RMON alarm and event parameters corresponding
                to this entry."
            INDEX { alarmIndex }
            ::= { mbAlarmTable 1 }

        MbAlarmEntry ::= SEQUENCE {
            mbAlarmCondition            INTEGER,
            mbAlarmDescription          DisplayString
        }

        -- mbAlarmCondition is identical to mbAlarmStatus

        mbAlarmCondition OBJECT-TYPE
            SYNTAX INTEGER {
                underCreation(1),
                active(2),
                inactive(3),
                delete(4),
                held(5),
                noHubCard(6),
                oldFirmware(7),
                slotTimeout(8),
                slotFailed(9),
                monitorStopped(10),
                unknownVariable(11),
                keysMissing(12),
                noResources(13),
                loading(14),
                activating(15),
                deactivating(16),
                unsupported(17),
                unknownAlarm(18),
                inconsistency(19),
                invalidFlags(20),
                invalidSlot(21),
                inaccessible(22),
                otherError(23)
            }
            ACCESS read-write
            STATUS mandatory
            DESCRIPTION "
Describes the current operational state of the
alarm and allows you to make limited changes in
the state of the alarm for purposes of managing
its state.

You may set this field to one of: underCreation,
active, inactive, and delete.  All other values
report current status.

underCreation: Alarm configuration is incomplete.
You may modify alarm parameters.  No monitoring
is taking place for the alarm.  An alarm is saved
in a parameter file after configuration complete.
Select this state before changing a previously
completed alarm.

active: Alarm configuration is complete and active
monitoring of the alarm variable is in progress.
Select this state to complete an alarm or to begin
active monitioring of the alarm variable.

inactive: No monitoring of the alarm variable is
actively taking place.  Select this state when you
want to temporarily suppress monitoring for the
alarm.  Select 'active' to begin monitoring again.

delete: Select this state when you want to delete
this alarm and all log entries associated with it.

held: Active monitoring of the alarm variable is not
taking place because this system does not have RMON
Repeater Management set to 'enabled'.  Once you do
this, alarm monitoring begins automatically.

noHubCard: The target slot does not contain a
management card or repeater I/O card capable of
monitoring.  Monitoring will begin automatically
once the target slot is loaded with a supported
configuration.

oldFirmware: The I/O card in the target slot does
not contain monitoring firmware.  Monitoring will
begin automatically once that card has been loaded
with current scm firmware.

slotTimeout: The target slot did not respond to
attempts to activate the alarm.  May happen if the
management card in the target slot does not contain
monitoring software.  Monitoring begins automatically
once the target slot has been repaired or loaded
with current software.

slotFailed: Active monitoring of the alarm
variable stopped because the target slot was not
operating properly.  Monitoring automatically
resumes once the target slot has recovered.

monitorStopped: Active monitoring of the alarm
variable stopped due to some error.  This can
occur if the variable no longer exists because a
related configuration change has made it invalid.
Correct the condition and re-activate the alarm.

unknownVariable: The alarm variable specified by the
object ID is not recognized in the currently running
system.  Correct the entry.

keysMissing: One or more required key values are not
specified in the alarm variable object ID.  Correct
the entry.

noResources: Not enough system resources exist to
activate this alarm.  Allocate more packet buffers
or increase free memory and re-activate the alarm.

loading: The alarm is being read from a parameter
file and will soon be activated.  This condition
is transient.

activating: Monitoring of the alarm variable will
begin soon.  This condition is transient.

deactivating: Monitoring of the alarm variable will
stop soon.  This condition is transient.

unsupported: Monitoring for the alarm variable is
not supported by the target slot.  Monitoring will
begin once that card is loaded with current scm
firmware or software.

unknownAlarm: Monitoring stopped because the target
slot reset.  Monitoring will continue shortly.

inconsistency: Internal system error.

invalidFlags: Internal system error.

invalidSlot: Alarm specified for a slot which does
not exist in the chassis.  Modify and re-activate.

inaccessible: Monitoring of the alarm variable could
not begin.  This can occur if the key values are
invalid for the variable.  Correct and re-activate
the alarm.

otherError: An unspecified error has occurred."
            ::= { mbAlarmEntry 1 }

        mbAlarmDescription OBJECT-TYPE
            SYNTAX DisplayString (SIZE (0..255))
            ACCESS read-only
            STATUS mandatory
            DESCRIPTION "
                An easily-readable summary of an RMON alarm.

                The general format is:  '<action> when <condition>
                <variable> <key2tag> <key1tag> is >= <r> or <= <f>
                <interval>.'

                <action> is from: 'Do nothing', 'Create log record',
                'Generate trap', 'Create log and trap', or 'Various
                actions', based on the alarm rising and falling
                event types.

                <condition> is one of 'value of' or 'change in',
                according to the alarm sample type.

                <variable>, if recognized, describes the quick list
                selection.  If unlisted, the object identifier is
                substituted.

                <key1tag> and <key2tag> appear only if <variable> is
                recognized and represent phrases like 'slot',
                'port', and 'any port'.

                <r> and <f> represent the rising and falling
                threshold values, respectively.

                The <interval> phrase describes the units per N
                seconds or the length of the sample interval in
                seconds."
            ::= { mbAlarmEntry 2 }


        -- The RMON MB Group Log View Table

        -- This table provides a human-readable interpretation of
        -- all RMON event group logTable entries, ordered by time
        -- of creation, most recent first.

        mbLogTable OBJECT-TYPE
            SYNTAX SEQUENCE OF MbLogEntry
            ACCESS not-accessible
            STATUS mandatory
            DESCRIPTION
                "A list of RMON logTable entries."
            ::= { xRmonMB 3 }

        mbLogEntry OBJECT-TYPE
            SYNTAX MbLogEntry
            ACCESS not-accessible
            STATUS mandatory
            DESCRIPTION
                "A human-readable description of an RMON event."
            INDEX { mbLogIndex }
            ::= { mbLogTable 1 }

        MbLogEntry ::= SEQUENCE {
            mbLogIndex                INTEGER,
            mbLogDescription          DisplayString
        }

        mbLogIndex OBJECT-TYPE
            SYNTAX INTEGER
            ACCESS read-only
            STATUS mandatory
            DESCRIPTION "
                An index uniquely identifying an entry in this log
                table. Each such entry describes, in human-readable
                format, an RMON event occurring for an alarm.  All
                RMON log table entries are shown, ordered most
                recent first."
            ::= { mbLogEntry 1 }

        mbLogDescription OBJECT-TYPE
            SYNTAX DisplayString (SIZE (0..255))
            ACCESS read-only
            STATUS mandatory
            DESCRIPTION "
                An easily-readable summary of an RMON log entry.

                The general format is: '<time>: alarm <index>
                <condition> <variable> <key2tag> <key1tag> is
                <limit> <interval>.'

                <time> is the date and time the entry was created.

                <index> is the alarm index causing the report.

                <condition> is one of 'value of <V> for' or 'change
                of <V> for', according to the alarm sample type.
                <V> is the actual value triggering the report.

                <variable>, if recognized, describes the quick list
                selection.  If unlisted, the object identifier is
                substituted.

                <key1tag> and <key2tag> appear only if <variable> is
                recognized and represent phrases like 'slot',
                'port', and 'any port'.

                <limit> is one of '>= <r>' or '<= <f>' where <r> and
                <f> represent the rising and falling threshold
                values, respectively.

                The <interval> phrase describes the units per N
                seconds or the length of the sample interval in
                seconds."
            ::= { mbLogEntry 2 }


        -- The RMON Resource Table

        -- Standard RMON does not place limits on the number of rows
        -- in its tables.  This table provides controls to specify
        -- and monitor the lengths of some RMON tables.

        mbResourceTable OBJECT-TYPE
            SYNTAX SEQUENCE OF MbResourceEntry
            ACCESS not-accessible
            STATUS mandatory
            DESCRIPTION
                "A list of RMON resource entries."
            ::= { xRmonMB 4 }

        mbResourceEntry OBJECT-TYPE
            SYNTAX MbResourceEntry
            ACCESS not-accessible
            STATUS mandatory
            DESCRIPTION
                "Values to control and monitor RMON resources."
            INDEX { mbResourceType }
            ::= { mbResourceTable 1 }

        MbResourceEntry ::= SEQUENCE {
            mbResourceType         INTEGER,
            mbResourceCurrent      Gauge,
            mbResourceWorst        Gauge,
            mbResourceMaximum      INTEGER,
            mbResourceOperMaximum  INTEGER
        }

        mbResourceType OBJECT-TYPE
            SYNTAX INTEGER { rmonAlarms(1),
                             rmonEvents(2),
                             rmonLogEntries(3),
                             rmonStatistics(4)
            }
            ACCESS read-only
            STATUS mandatory
            DESCRIPTION
                "Identification of an RMON resource type.  Typically
                each type corresponds to an RMON table whose size is
                to be controlled and monitored."
            ::= { mbResourceEntry 1 }

        mbResourceCurrent OBJECT-TYPE
            SYNTAX Gauge
            ACCESS read-only
            STATUS mandatory
            DESCRIPTION "
                The number of entries currently allocated by RMON."
            ::= { mbResourceEntry 2 }

        mbResourceWorst OBJECT-TYPE
            SYNTAX Gauge
            ACCESS read-only
            STATUS mandatory
            DESCRIPTION "
                The highest number of entries ever allocated by
                RMON since system initialization."
            ::= { mbResourceEntry 3 }

        mbResourceMaximum OBJECT-TYPE
            SYNTAX INTEGER
            ACCESS read-write
            STATUS mandatory
            DESCRIPTION "
                The desired maximum possible number of resources of
                this type RMON is permitted to use at any one time.

                Changes to alarm, event, and log entry resource
                settings take effect immediately.

                Changes to the statistics resource takes place after
                the system is initialized.

                For alarms and events, this value may not be set
                less than the current number of entries in use."
            ::= { mbResourceEntry 4 }

        mbResourceOperMaximum OBJECT-TYPE
            SYNTAX INTEGER
            ACCESS read-only
            STATUS mandatory
            DESCRIPTION "
                The actual maximum number of resources of this type
                RMON will attempt to use at any one time.  This is
                the limit in effect for the current system."
            ::= { mbResourceEntry 5 }


        -- The RMON Map Table

        -- This table is used to define RMON EtherStats tables
        -- for repeater ports.  ifTable entries are created that
        -- correspond to etherStatsTables for repeater ports.
        -- Entries created through this interface will have an
        -- owner string of 'RMON monitor'.

        xRmonMapTable OBJECT-TYPE
            SYNTAX SEQUENCE OF XRmonMapEntry
            ACCESS not-accessible
            STATUS mandatory
            DESCRIPTION
                "A list of RMON map entries."
            ::= { xRmon 3 }

        xRmonMapEntry OBJECT-TYPE
            SYNTAX XRmonMapEntry
            ACCESS not-accessible
            STATUS mandatory
            DESCRIPTION
                "Values to create RMON statistics tables for
                repeater ports."
            INDEX { etherStatsIndex }
            ::= { xRmonMapTable 1 }

        XRmonMapEntry ::= SEQUENCE {
            xRmonMapSlot           INTEGER,
            xRmonMapPort           INTEGER,
            xRmonMapIfIndex        INTEGER
        }

        xRmonMapSlot OBJECT-TYPE
            SYNTAX INTEGER
            ACCESS read-write
            STATUS mandatory
            DESCRIPTION "
                The slot the statistics will come from."
            ::= { xRmonMapEntry 1 }

        xRmonMapPort OBJECT-TYPE
            SYNTAX INTEGER
            ACCESS read-write
            STATUS mandatory
            DESCRIPTION "
                The port the statistics will come from."
            ::= { xRmonMapEntry 2 }

        xRmonMapIfIndex OBJECT-TYPE
            SYNTAX INTEGER
            ACCESS read-only
            STATUS mandatory
            DESCRIPTION "
                The interface index (ifIndex) corresponding to
                this statistics table."
            ::= { xRmonMapEntry 3 }

        -- ITouch RMON Traps

        iTouchAlarm TRAP-TYPE
            ENTERPRISE xRmon
            VARIABLES { mbLogDescription }
            DESCRIPTION
                "The SNMP trap that is generated when xRmonTrapType
                is set to iTouchFormat(2).  These traps, like the
                RMON standardFormat(1) traps, occur when an alarm
                variable crosses its rising or falling threshold
                and generates an event configured to send SNMP traps.

                The format of the DisplayString embodied by the
                trap PDU is identical to that of mbLogDescription.
                The actual object identifier is not significant."
            ::= 1


END
