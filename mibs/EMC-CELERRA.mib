--------------------------------------------------------------------------
-- Copyright (c) 1998, All rights reserved by
--
-- EMC Corporation
-- 171 South Street
-- Hopkinton, MA 01748 USA
--
-- This software is furnished under a license and may be used and copied
-- inclusion of the above copyright notice. This software or  any  other
-- only  in  accordance  with  the  terms  of such  license and with the
-- copies thereof may not be provided or otherwise made available to any
-- other person. No title to and ownership of  the  software  is  hereby
-- transferred.
--
-- The information in this software is subject to change without notice
-- and should not be construed as a commitment by EMC Corporation.
--
-- EMC Corporation assumes no responsibility for the use or reliability
-- of this software.
--
----------------------------------------------------------------------------
--
--
-- EMC Celerra Management Information Base description
--
----------------------------------------------------------------------------
----------------------------------------------------------------------------
--
-- Author Identification
--
-- gma      Gary Ma, EMC
--
----------------------------------------------------------------------------
--
--  000  gma   11-05-98   Created Original Module
--
----------------------------------------------------------------------------

EMC-CELERRA DEFINITIONS ::= BEGIN

   IMPORTS
       enterprises, Opaque
	  FROM RFC1155-SMI
       DisplayString 
          FROM RFC1213-MIB
       OBJECT-TYPE
          FROM RFC-1212
       TRAP-TYPE
          FROM RFC-1215;
--     emc
--        FROM EMC-MIB;


       emc OBJECT IDENTIFIER ::= { enterprises 1139  }
       emcCelerra OBJECT IDENTIFIER ::= { emc 2 }

-------------------------------------------------------------------
--
--       Celerra Event Group
--
-------------------------------------------------------------------

       celEventTable OBJECT-TYPE
          SYNTAX SEQUENCE OF CelEvent
          ACCESS not-accessible
          STATUS mandatory
          DESCRIPTION
                   "A table containing information
		    about an particular event."
          ::= { emcCelerra 1}

       celEvent OBJECT-TYPE
          SYNTAX CelEvent
          ACCESS not-accessible
          STATUS mandatory
          DESCRIPTION
                   "Information about an particular event."
          INDEX {celEventFacility,
                 celEventID}
          ::= { celEventTable 1}

       CelEvent ::= SEQUENCE { celEventFacility INTEGER,
                               celEventID INTEGER,
                               celEventSeverity INTEGER,
                               celEventDescr DisplayString}

                              
       celEventFacility OBJECT-TYPE
          SYNTAX INTEGER
          ACCESS read-only
          STATUS mandatory
          DESCRIPTION
                 "The number representing the facility which generates
                  the event. For now, the value could be:
                  first 128 - default Dart facility
                  129 - master control 
                  130 - event log
                  131 - box monitor
                  132 - video service
                  133 - callhome application
                  134 - AAF backup control station."
          ::= { celEvent 1 }

       celEventID OBJECT-TYPE
          SYNTAX INTEGER
          ACCESS read-only
          STATUS mandatory
          DESCRIPTION
                  "The event id which identifies the particular event
                  within a facility."
          ::= { celEvent 2 }

       celEventSeverity OBJECT-TYPE
          SYNTAX INTEGER
          ACCESS read-only
          STATUS mandatory
          DESCRIPTION
                   "Severity of the event."
          ::= { celEvent 3 }

       celEventDescr OBJECT-TYPE
          SYNTAX DisplayString
          ACCESS read-only
          STATUS mandatory
          DESCRIPTION
                   "text description of the event."
          ::= { celEvent 4 }
       
----------------------------
--
--     Trap definitions
--
----------------------------

       celReboot TRAP-TYPE
          ENTERPRISE emcCelerra
          VARIABLES { celEvent }
          DESCRIPTION
                   "Trap message will be sent in the event of a Data Mover
                    Reboots. The trap message includes the facility, event id,
                    serverity and a text description of the event."
          ::= 1

       celMasterCtlFault TRAP-TYPE
          ENTERPRISE emcCelerra
          VARIABLES { celEvent }
          DESCRIPTION
                   "Trap message will be sent in the event of Master Control
                    serious fault. 
                    unexpected daemon exit or control station heartbeat 
                    missing."
          ::= 2

       celHWFailure TRAP-TYPE
          ENTERPRISE emcCelerra
          VARIABLES { celEvent }
          DESCRIPTION
                   "Trap message will be sent in the event of celerra hardware
                    failure."
          ::= 3

       celSlotStale TRAP-TYPE
          ENTERPRISE emcCelerra
          VARIABLES { celEvent }
          DESCRIPTION
                   "Trap message will be sent in the event of celerra stale
                    reason code."
          ::= 4

       celSlotPanicked TRAP-TYPE
          ENTERPRISE emcCelerra
          VARIABLES { celEvent }
          DESCRIPTION
                   "Trap message will be sent in the event of panicked 
                    slot."
          ::= 5

       celIntfFailure TRAP-TYPE
          ENTERPRISE emcCelerra
          VARIABLES { celEvent }
          DESCRIPTION
                   "Trap message will be sent in the event of both interfaces
                    failure."
          ::= 6

       celAAF  TRAP-TYPE
          ENTERPRISE emcCelerra
          VARIABLES { celEvent }
          DESCRIPTION
                   "Trap message will be sent in the event of AAF."
          ::= 7

END
