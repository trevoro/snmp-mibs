SGTE-MIB DEFINITIONS ::= BEGIN

-- Title   : SGTE.MIB
-- Version : 1.0
-- Date    : 16/07/02

IMPORTS
     enterprises
          FROM RFC1155-SMI
     OBJECT-TYPE
          FROM RFC-1212
     DisplayString
          FROM RFC1213-MIB
     TRAP-TYPE
          FROM RFC-1215;

sgte OBJECT IDENTIFIER ::= { enterprises 13743 }

sEci48VP OBJECT IDENTIFIER ::= { sgte 1 }

cIDENTIFICATION OBJECT IDENTIFIER ::= { sEci48VP 1 }

iNomEquipement OBJECT-TYPE
     SYNTAX DisplayString (SIZE (255))
     ACCESS read-only
     STATUS optional
     DESCRIPTION
     "Designation de l'entite"
     ::= { cIDENTIFICATION 1 }

iNomConstructeur OBJECT-TYPE
     SYNTAX DisplayString (SIZE (255))
     ACCESS read-only
     STATUS optional
     DESCRIPTION
     "Nom du constructeur"
     ::= { cIDENTIFICATION 2 }

iMarqueCommerciale OBJECT-TYPE
     SYNTAX DisplayString (SIZE (255))
     ACCESS read-only
     STATUS optional
     DESCRIPTION
     "Marque commerciale"
     ::= { cIDENTIFICATION 3 }

iVersionLogiciel OBJECT-TYPE
     SYNTAX DisplayString (SIZE (255))
     ACCESS read-only
     STATUS optional
     DESCRIPTION
     "Version du Logiciel"
     ::= { cIDENTIFICATION 4 }

iCaracterisationFine OBJECT-TYPE
     SYNTAX DisplayString (SIZE (255))
     ACCESS read-only
     STATUS optional
     DESCRIPTION
     "Caracterisation plus fine du materiel"
     ::= { cIDENTIFICATION 5 }

cMESURES OBJECT IDENTIFIER ::= { sEci48VP 2 }

mTensionUtilisation OBJECT-TYPE
     SYNTAX DisplayString (SIZE (255))
     ACCESS read-only
     STATUS optional
     DESCRIPTION
     "Tension Utilisation"
     ::= { cMESURES 1 }

mTensionBatterie OBJECT-TYPE
     SYNTAX DisplayString (SIZE (255))
     ACCESS read-only
     STATUS optional
     DESCRIPTION
     "Tension Batterie"
     ::= { cMESURES 2 }

mCourantUtilisation OBJECT-TYPE
     SYNTAX DisplayString (SIZE (255))
     ACCESS read-only
     STATUS optional
     DESCRIPTION
     "Courant Utilisation"
     ::= { cMESURES 3 }

mCourantBatterie1A OBJECT-TYPE
     SYNTAX DisplayString (SIZE (255))
     ACCESS read-only
     STATUS optional
     DESCRIPTION
     "Courant Batterie 1A"
     ::= { cMESURES 4 }

mCourantBatterie2A OBJECT-TYPE
     SYNTAX DisplayString (SIZE (255))
     ACCESS read-only
     STATUS optional
     DESCRIPTION
     "Courant Batterie 2A"
     ::= { cMESURES 5 }

mCourantBatterie3A OBJECT-TYPE
     SYNTAX DisplayString (SIZE (255))
     ACCESS read-only
     STATUS optional
     DESCRIPTION
     "Courant Batterie 3A"
     ::= { cMESURES 6 }

mCourantBatterie1B OBJECT-TYPE
     SYNTAX DisplayString (SIZE (255))
     ACCESS read-only
     STATUS optional
     DESCRIPTION
     "Courant Batterie 1B"
     ::= { cMESURES 7 }

mCourantBatterie2B OBJECT-TYPE
     SYNTAX DisplayString (SIZE (255))
     ACCESS read-only
     STATUS optional
     DESCRIPTION
     "Courant Batterie 2B"
     ::= { cMESURES 8 }

mCourantBatterie3B OBJECT-TYPE
     SYNTAX DisplayString (SIZE (255))
     ACCESS read-only
     STATUS optional
     DESCRIPTION
     "Courant Batterie 3B"
     ::= { cMESURES 9 }

mCourantRedresseur OBJECT-TYPE
     SYNTAX INTEGER (0..255)
     ACCESS read-only
     STATUS optional
     DESCRIPTION
     "Courant Nominal d'un Redresseur"
     ::= { cMESURES 10 }

mTauxCharge OBJECT-TYPE
     SYNTAX DisplayString (SIZE (255))
     ACCESS read-only
     STATUS optional
     DESCRIPTION
     "Taux de Charge"
     ::= { cMESURES 11 }

mEtape OBJECT-TYPE
     SYNTAX DisplayString (SIZE (255))
     ACCESS read-only
     STATUS optional
     DESCRIPTION
     "Numero de l'etape active"
     ::= { cMESURES 12 }

mTensionDebutTestBatt OBJECT-TYPE
     SYNTAX DisplayString (SIZE (255))
     ACCESS read-only
     STATUS optional
     DESCRIPTION
     "Tension Batterie en debut de test"
     ::= { cMESURES 13 }

mTensionFinTestBatt OBJECT-TYPE
     SYNTAX DisplayString (SIZE (255))
     ACCESS read-only
     STATUS optional
     DESCRIPTION
     "Tension Batterie en fin de test"
     ::= { cMESURES 14 }

mCourantBatterie1ADebutTestBatt OBJECT-TYPE
     SYNTAX INTEGER (-32768..32767)
     ACCESS read-only
     STATUS optional
     DESCRIPTION
     "Courant Batterie 1A en debut de test"
     ::= { cMESURES 15 }

mCourantBatterie1AFinTestBatt OBJECT-TYPE
     SYNTAX INTEGER (-32768..32767)
     ACCESS read-only
     STATUS optional
     DESCRIPTION
     "Courant Batterie 1A en fin de test"
     ::= { cMESURES 16 }

mCourantBatterie2ADebutTestBatt OBJECT-TYPE
     SYNTAX INTEGER (-32768..32767)
     ACCESS read-only
     STATUS optional
     DESCRIPTION
     "Courant Batterie 2A en debut de test"
     ::= { cMESURES 17 }

mCourantBatterie2AFinTestBatt OBJECT-TYPE
     SYNTAX INTEGER (-32768..32767)
     ACCESS read-only
     STATUS optional
     DESCRIPTION
     "Courant Batterie 2A en fin de test"
     ::= { cMESURES 18 }

mCourantBatterie3ADebutTestBatt OBJECT-TYPE
     SYNTAX INTEGER (-32768..32767)
     ACCESS read-only
     STATUS optional
     DESCRIPTION
     "Courant Batterie 3A en debut de test"
     ::= { cMESURES 19 }

mCourantBatterie3AFinTestBatt OBJECT-TYPE
     SYNTAX INTEGER (-32768..32767)
     ACCESS read-only
     STATUS optional
     DESCRIPTION
     "Courant Batterie 3A en fin de test"
     ::= { cMESURES 20 }

mCourantBatterie1BDebutTestBatt OBJECT-TYPE
     SYNTAX INTEGER (-32768..32767)
     ACCESS read-only
     STATUS optional
     DESCRIPTION
     "Courant Batterie 1B en debut de test"
     ::= { cMESURES 21 }

mCourantBatterie1BFinTestBatt OBJECT-TYPE
     SYNTAX INTEGER (-32768..32767)
     ACCESS read-only
     STATUS optional
     DESCRIPTION
     "Courant Batterie 1B en fin de test"
     ::= { cMESURES 22 }

mCourantBatterie2BDebutTestBatt OBJECT-TYPE
     SYNTAX INTEGER (-32768..32767)
     ACCESS read-only
     STATUS optional
     DESCRIPTION
     "Courant Batterie 2B en debut de test"
     ::= { cMESURES 23 }

mCourantBatterie2BFinTestBatt OBJECT-TYPE
     SYNTAX INTEGER (-32768..32767)
     ACCESS read-only
     STATUS optional
     DESCRIPTION
     "Courant Batterie 2B en fin de test"
     ::= { cMESURES 24 }

mCourantBatterie3BDebutTestBatt OBJECT-TYPE
     SYNTAX INTEGER (-32768..32767)
     ACCESS read-only
     STATUS optional
     DESCRIPTION
     "Courant Batterie 3B en debut de test"
     ::= { cMESURES 25 }

mCourantBatterie3BFinTestBatt OBJECT-TYPE
     SYNTAX INTEGER (-32768..32767)
     ACCESS read-only
     STATUS optional
     DESCRIPTION
     "Courant Batterie 3B en fin de test"
     ::= { cMESURES 26 }

mTemperature OBJECT-TYPE
     SYNTAX DisplayString (SIZE (255))
     ACCESS read-only
     STATUS optional
     DESCRIPTION
     "Temperature"
     ::= { cMESURES 27 }

cETATS OBJECT IDENTIFIER ::= { sEci48VP 3 }

eModifHeure OBJECT-TYPE
     SYNTAX INTEGER (0..1)
     ACCESS read-only
     STATUS optional
     DESCRIPTION
     "Modification de l'heure"
     ::= { cETATS 1 }

eModifParam OBJECT-TYPE
     SYNTAX INTEGER (0..1)
     ACCESS read-only
     STATUS optional
     DESCRIPTION
     "Modification des parametres"
     ::= { cETATS 2 }

eLiaisonJbus OBJECT-TYPE
     SYNTAX INTEGER (0..1)
     ACCESS read-only
     STATUS optional
     DESCRIPTION
     "Defaut de la liaison JBUS"
     ::= { cETATS 3 }

eTestEnCours OBJECT-TYPE
     SYNTAX INTEGER (0..1)
     ACCESS read-only
     STATUS optional
     DESCRIPTION
     "Test Batterie en cours"
     ::= { cETATS 4 }

eUBMin OBJECT-TYPE
     SYNTAX INTEGER (0..1)
     ACCESS read-only
     STATUS optional
     DESCRIPTION
     "U Batterie < Seuil"
     ::= { cETATS 5 }

eTestNonRealise OBJECT-TYPE
     SYNTAX INTEGER (0..1)
     ACCESS read-only
     STATUS optional
     DESCRIPTION
     "Test Batterie non realise"
     ::= { cETATS 6 }

eDefUnRed OBJECT-TYPE
     SYNTAX INTEGER (0..1)
     ACCESS read-only
     STATUS optional
     DESCRIPTION
     "Un redresseur en defaut"
     ::= { cETATS 7 }

eDefPlusRed OBJECT-TYPE
     SYNTAX INTEGER (0..1)
     ACCESS read-only
     STATUS optional
     DESCRIPTION
     "Plusieurs redresseurs en defaut"
     ::= { cETATS 8 }

eAlimSecteur OBJECT-TYPE
     SYNTAX INTEGER (0..1)
     ACCESS read-only
     STATUS optional
     DESCRIPTION
     "Alimentation Absente"
     ::= { cETATS 9 }

eFuseBatt OBJECT-TYPE
     SYNTAX INTEGER (0..1)
     ACCESS read-only
     STATUS optional
     DESCRIPTION
     "Defaut Fusible/Interrupteur Batterie"
     ::= { cETATS 10 }

eFuseDep OBJECT-TYPE
     SYNTAX INTEGER (0..1)
     ACCESS read-only
     STATUS optional
     DESCRIPTION
     "Defaut Fusible Depart"
     ::= { cETATS 11 }

eFuseAux OBJECT-TYPE
     SYNTAX INTEGER (0..1)
     ACCESS read-only
     STATUS optional
     DESCRIPTION
     "Defaut Fusible Auxiliaire"
     ::= { cETATS 12 }

eUMin OBJECT-TYPE
     SYNTAX INTEGER (0..1)
     ACCESS read-only
     STATUS optional
     DESCRIPTION
     "U Utilisation < Seuil"
     ::= { cETATS 13 }

eUMax OBJECT-TYPE
     SYNTAX INTEGER (0..1)
     ACCESS read-only
     STATUS optional
     DESCRIPTION
     "U Utilisation > Seuil"
     ::= { cETATS 14 }

eTauxCharge OBJECT-TYPE
     SYNTAX INTEGER (0..1)
     ACCESS read-only
     STATUS optional
     DESCRIPTION
     "Taux de Charge > Seuil"
     ::= { cETATS 15 }

eTemperature OBJECT-TYPE
     SYNTAX INTEGER (0..1)
     ACCESS read-only
     STATUS optional
     DESCRIPTION
     "Temperature > 45C"
     ::= { cETATS 16 }

eIBatt OBJECT-TYPE
     SYNTAX INTEGER (0..1)
     ACCESS read-only
     STATUS optional
     DESCRIPTION
     "I Batterie <> I Utilisation"
     ::= { cETATS 17 }

eChargeI OBJECT-TYPE
     SYNTAX INTEGER (0..1)
     ACCESS read-only
     STATUS optional
     DESCRIPTION
     "Defaut CHARGE I"
     ::= { cETATS 18 }

eChargeU OBJECT-TYPE
     SYNTAX INTEGER (0..1)
     ACCESS read-only
     STATUS optional
     DESCRIPTION
     "Defaut CHARGE U"
     ::= { cETATS 19 }

eFloating OBJECT-TYPE
     SYNTAX INTEGER (0..1)
     ACCESS read-only
     STATUS optional
     DESCRIPTION
     "Defaut FLOATING"
     ::= { cETATS 20 }

eComptAH OBJECT-TYPE
     SYNTAX INTEGER (0..1)
     ACCESS read-only
     STATUS optional
     DESCRIPTION
     "Decharge > Seuil"
     ::= { cETATS 21 }

eTestBattOK OBJECT-TYPE
     SYNTAX INTEGER (0..1)
     ACCESS read-only
     STATUS optional
     DESCRIPTION
     "Test Batterie correct"
     ::= { cETATS 22 }

eTestBattKO OBJECT-TYPE
     SYNTAX INTEGER (0..1)
     ACCESS read-only
     STATUS optional
     DESCRIPTION
     "Test Batterie mauvais"
     ::= { cETATS 23 }

eTestImpossible OBJECT-TYPE
     SYNTAX INTEGER (0..1)
     ACCESS read-only
     STATUS optional
     DESCRIPTION
     "Test Batterie impossible"
     ::= { cETATS 24 }

eTestRepousse OBJECT-TYPE
     SYNTAX INTEGER (0..1)
     ACCESS read-only
     STATUS optional
     DESCRIPTION
     "Test Batterie repousse"
     ::= { cETATS 25 }

eTestInterrompu OBJECT-TYPE
     SYNTAX INTEGER (0..1)
     ACCESS read-only
     STATUS optional
     DESCRIPTION
     "Test Batterie interrompu"
     ::= { cETATS 26 }
 
eTestMiniKO OBJECT-TYPE
     SYNTAX INTEGER (0..1)
     ACCESS read-only
     STATUS optional
     DESCRIPTION
     "Test mini mauvais"
     ::= { cETATS 27 }

ePuissTestBatt OBJECT-TYPE
     SYNTAX INTEGER (0..1)
     ACCESS read-only
     STATUS optional
     DESCRIPTION
     "Puissance non constante"
     ::= { cETATS 28 }

eDefEprom OBJECT-TYPE
     SYNTAX INTEGER (0..1)
     ACCESS read-only
     STATUS optional
     DESCRIPTION
     "Perte de Parametres"
     ::= { cETATS 29 }

eDetectionCSB OBJECT-TYPE
     SYNTAX INTEGER (0..1)
     ACCESS read-only
     STATUS optional
     DESCRIPTION
     "Detection de la carte CSB"
     ::= { cETATS 30 }

eRAZ OBJECT-TYPE
     SYNTAX INTEGER (0..1)
     ACCESS read-only
     STATUS optional
     DESCRIPTION
     "RAZ de l'ECI"
     ::= { cETATS 31 }

cALARMES OBJECT IDENTIFIER ::= { sEci48VP 4 }

aModifHeure TRAP-TYPE
     ENTERPRISE cALARMES
     DESCRIPTION
     "Modification de l'heure"
     ::= 1

aModifParam TRAP-TYPE
     ENTERPRISE cALARMES
     DESCRIPTION
     "Modification des parametres"
     ::= 2

aLiaisonJbus TRAP-TYPE
     ENTERPRISE cALARMES
     DESCRIPTION
     "Defaut de la liaison JBUS"
     ::= 3

aTestEnCours TRAP-TYPE
     ENTERPRISE cALARMES
     DESCRIPTION
     "Test Batterie en cours"
     ::= 4

aUBMin TRAP-TYPE
     ENTERPRISE cALARMES
     DESCRIPTION
     "U Batterie < Seuil"
     ::= 5

aTestNonRealise TRAP-TYPE
     ENTERPRISE cALARMES
     DESCRIPTION
     "Test Batterie non realise"
     ::= 6

aDefUnRed TRAP-TYPE
     ENTERPRISE cALARMES
     DESCRIPTION
     "Un redresseur en defaut"
     ::= 7

aDefPlusRed TRAP-TYPE
     ENTERPRISE cALARMES
     DESCRIPTION
     "Plusieurs redresseurs en defaut"
     ::= 8

aAlimSecteur TRAP-TYPE
     ENTERPRISE cALARMES
     DESCRIPTION
     "Alimentation Absente"
     ::= 9

aFuseBatt TRAP-TYPE
     ENTERPRISE cALARMES
     DESCRIPTION
     "Defaut Fusible/Interrupteur Batterie"
     ::= 10

aFuseDep TRAP-TYPE
     ENTERPRISE cALARMES
     DESCRIPTION
     "Defaut Fusible Depart"
     ::= 11

aFuseAux TRAP-TYPE
     ENTERPRISE cALARMES
     DESCRIPTION
     "Defaut Fusible Auxiliaire"
     ::= 12

aUMin TRAP-TYPE
     ENTERPRISE cALARMES
     DESCRIPTION
     "U Utilisation < Seuil"
     ::= 13

aUMax TRAP-TYPE
     ENTERPRISE cALARMES
     DESCRIPTION
     "U Utilisation > Seuil"
     ::= 14

aTauxCharge TRAP-TYPE
     ENTERPRISE cALARMES
     DESCRIPTION
     "Taux de Charge > Seuil"
     ::= 15

aTemperature TRAP-TYPE
     ENTERPRISE cALARMES
     DESCRIPTION
     "Temperature > 45C"
     ::= 16

aIBatt TRAP-TYPE
     ENTERPRISE cALARMES
     DESCRIPTION
     "I Batterie <> I Utilisation"
     ::= 17

aChargeI TRAP-TYPE
     ENTERPRISE cALARMES
     DESCRIPTION
     "Defaut CHARGE I"
     ::= 18

aChargeU TRAP-TYPE
     ENTERPRISE cALARMES
     DESCRIPTION
     "Defaut CHARGE U"
     ::= 19

aFloating TRAP-TYPE
     ENTERPRISE cALARMES
     DESCRIPTION
     "Defaut FLOATING"
     ::= 20

aComptAH TRAP-TYPE
     ENTERPRISE cALARMES
     DESCRIPTION
     "Decharge > Seuil"
     ::= 21

aTestBattOK TRAP-TYPE
     ENTERPRISE cALARMES
     DESCRIPTION
     "Test Batterie correct"
     ::= 22

aTestBattKO TRAP-TYPE
     ENTERPRISE cALARMES
     DESCRIPTION
     "Test Batterie mauvais"
     ::= 23

aTestImpossible TRAP-TYPE
     ENTERPRISE cALARMES
     DESCRIPTION
     "Test Batterie impossible"
     ::= 24

aTestRepousse TRAP-TYPE
     ENTERPRISE cALARMES
     DESCRIPTION
     "Test Batterie repousse"
     ::= 25

aTestInterrompu TRAP-TYPE
     ENTERPRISE cALARMES
     DESCRIPTION
     "Test Batterie interrompu"
     ::= 26
 
aTestMiniKO TRAP-TYPE
     ENTERPRISE cALARMES
     DESCRIPTION
     "Test mini mauvais"
     ::= 27

aPuissTestBatt TRAP-TYPE
     ENTERPRISE cALARMES
     DESCRIPTION
     "Puissance non constante"
     ::= 28

aDefEprom TRAP-TYPE
     ENTERPRISE cALARMES
     DESCRIPTION
     "Perte de Parametres"
     ::= 29

aDetectionCSB TRAP-TYPE
     ENTERPRISE cALARMES
     DESCRIPTION
     "Detection de la carte CSB"
     ::= 30

aRAZ TRAP-TYPE
     ENTERPRISE cALARMES
     DESCRIPTION
     "RAZ de l'ECI"
     ::= 31

END
