NGWX400MIB DEFINITIONS ::= BEGIN

IMPORTS
        Counter, TimeTicks, Gauge, enterprises  FROM RFC1155-SMI
        DisplayString                           FROM RFC1213-MIB
        TRAP-TYPE                               FROM RFC-1215
        OBJECT-TYPE                             FROM RFC-1212;

wpcorp           OBJECT IDENTIFIER   ::= { enterprises 922 }
gateways         OBJECT IDENTIFIER   ::= { wpcorp        2 }
ngwx400          OBJECT IDENTIFIER   ::= { gateways      4 }
ngwx400Info      OBJECT IDENTIFIER   ::= { ngwx400       1 }
ngwx400TrapInfo  OBJECT IDENTIFIER   ::= { ngwx400       2 }


-- ====================================== NGWX400 Get/Set Variables =========
ngwx400GatewayName OBJECT-TYPE
       SYNTAX  DisplayString (SIZE (0..255))
       ACCESS  read-only
       STATUS  mandatory
       DESCRIPTION
       "The GroupWise X.400 Gateway name."
   ::= { ngwx400Info 1 }
 
ngwx400Uptime OBJECT-TYPE
       SYNTAX  TimeTicks
       ACCESS  read-only
       STATUS  mandatory
       DESCRIPTION
      "Uptime of the GroupWise X.400 Gateway."
   ::= { ngwx400Info 2 }

ngwx400GroupWiseLink OBJECT-TYPE
       SYNTAX  DisplayString (SIZE (0..5))
       ACCESS  read-only
       STATUS  mandatory
       DESCRIPTION
      "GroupWise X.400 Gateway Link: UP or DOWN"
   ::= { ngwx400Info 3 }

ngwx400FrgnLink OBJECT-TYPE
       SYNTAX  DisplayString (SIZE (0..5))
       ACCESS  read-only
       STATUS  mandatory
       DESCRIPTION
      "GroupWise X.400 Gateway Foreign Link: UP or DOWN"
   ::= { ngwx400Info 4 }

ngwx400OutBytes OBJECT-TYPE
       SYNTAX  Counter
       ACCESS  read-only
       STATUS  mandatory
       DESCRIPTION
      "The number of message bytes sent to GroupWise X.400."
   ::= { ngwx400Info 5 }
 
ngwx400InBytes OBJECT-TYPE
       SYNTAX  Counter
       ACCESS  read-only
       STATUS  mandatory
       DESCRIPTION
      "The number of message bytes received from GroupWise X.400."
   ::= { ngwx400Info 6 }
 
ngwx400OutMsgs OBJECT-TYPE
       SYNTAX  Counter
       ACCESS  read-only
       STATUS  mandatory
       DESCRIPTION
      "The number of messages sent to GroupWise X.400."
   ::= { ngwx400Info 7 }
 
ngwx400InMsgs OBJECT-TYPE
       SYNTAX  Counter
       ACCESS  read-only
       STATUS  mandatory
       DESCRIPTION
      "The number of messages received from X.400."
   ::= { ngwx400Info 8 }
 
ngwx400OutStatuses OBJECT-TYPE
       SYNTAX  Counter
       ACCESS  read-only
       STATUS  mandatory
       DESCRIPTION
      "The number of statuses sent to X.400."
   ::= { ngwx400Info 9 }
 
ngwx400InStatuses OBJECT-TYPE
       SYNTAX  Counter
       ACCESS  read-only
       STATUS  mandatory
       DESCRIPTION
      "The number of statuses received from X.400."
   ::= { ngwx400Info 10 }
 
ngwx400OutErrors OBJECT-TYPE
       SYNTAX  Counter
       ACCESS  read-only
       STATUS  mandatory
       DESCRIPTION
      "The number of failed transfers to X.400."
   ::= { ngwx400Info 11 }
 
ngwx400InErrors OBJECT-TYPE
       SYNTAX  Counter
       ACCESS  read-only
       STATUS  mandatory
       DESCRIPTION
      "The number of failed transfers from X.400."
   ::= { ngwx400Info 12 }
 

-- ================================================== ngwx400TrapInfo ========
-- The ngwx400TrapInfo group
-- These objects are used only in traps produced by NGWX400
 
ngwx400TrapTime OBJECT-TYPE
		SYNTAX  INTEGER
		ACCESS  not-accessible
		STATUS  mandatory
		DESCRIPTION "The time the trap occurred. Seconds since Jan 1, 1970 (GMT)"
	::= { ngwx400TrapInfo 1 }
 
-- ================================================== NGWX400 Traps =========
ngwx400StartTrap TRAP-TYPE
		ENTERPRISE    ngwx400Info
		VARIABLES     {ngwx400TrapTime, ngwx400GatewayName}
		DESCRIPTION   "GroupWise X.400 Gateway start."
		--NMS Trap annotation
		--#TYPE       "GroupWise X.400 Gateway start."
		--#SUMMARY    "GroupWise X.400 Gateway %s has started."
		--#ARGUMENTS  {1}
		--#SEVERITY   INFORMATIONAL
		--#TIMEINDEX  0
		--#STATE      OPERATIONAL
		::= 1

ngwx400StopTrap TRAP-TYPE
		ENTERPRISE    ngwx400Info
		VARIABLES     {ngwx400TrapTime, ngwx400GatewayName}
		DESCRIPTION   "GroupWise X.400 Gateway stop."
		--NMS Trap annotation
		--#TYPE       "GroupWise X.400 Gateway stop."
		--#SUMMARY    "GroupWise X.400 Gateway %s has stopped."
		--#ARGUMENTS  {1}
		--#SEVERITY   CRITICAL
		--#TIMEINDEX  0
		--#STATE      NONOPERATIONAL
		::= 2

ngwx400RestartTrap TRAP-TYPE
		ENTERPRISE    ngwx400Info
		VARIABLES     {ngwx400TrapTime, ngwx400GatewayName}
		DESCRIPTION   "GroupWise X.400 Gateway restart."
		--NMS Trap annotation
		--#TYPE       "GroupWise X.400 Gateway restart."
		--#SUMMARY    "GroupWise X.400 Gateway %s has been restarted."
		--#ARGUMENTS  {1}
		--#SEVERITY   INFORMATIONAL
		--#TIMEINDEX  0
		--#STATE      OPERATIONAL
		::= 3
 
ngwx400GroupWiseLinkTrap TRAP-TYPE
		ENTERPRISE    ngwx400Info
		VARIABLES     {ngwx400TrapTime, ngwx400GatewayName}
		DESCRIPTION   "GroupWise Link lost by GroupWise X.400 Gateway"
		--NMS Trap annotation
		--#TYPE       "GroupWise Link lost by GroupWise X.400 Gateway"
		--#SUMMARY    "GroupWise X.400 Gateway %s has lost its GroupWise Link"
		--#ARGUMENTS  {1}
		--#SEVERITY   INFORMATIONAL
		--#TIMEINDEX  0
		--#STATE      OPERATIONAL
		::= 4


END
