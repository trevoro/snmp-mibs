-- *****************************************************************
-- tiaranet-dos.mib:  Tiara Networks Denial of Service MIB
--
-- April, 2000, Gopi/Anil
--
-- Copyright (c) 1998-2005 by Tiara Networks, Inc.
-- All rights reserved.
--
-- *****************************************************************

TIARA-DOS-MIB DEFINITIONS ::= BEGIN

IMPORTS
	MODULE-IDENTITY, OBJECT-TYPE, 
        Integer32, IpAddress  FROM SNMPv2-SMI
	TruthValue            FROM SNMPv2-TC
	tiaraMgmt             FROM TIARA-NETWORKS-SMI; 

tiaraDenialOfServiceMib MODULE-IDENTITY
	LAST-UPDATED "9407272253Z" --to be corrected
	ORGANIZATION "Tiara Networks Inc."
	CONTACT-INFO
	 "       Tiara Networks
                        Customer Service

                Postal: 525 Race Street, Suite 100,
                        San Jose, CA 95126
                        USA

                   Tel: +1 408-216-4700
                   Fax: +1 408-216-4701

                E-mail: support@tiaranetworks.com"
	
	DESCRIPTION
		"The MIB module to describe Tiara's Denial of Service MIB"
	::= { tiaraMgmt 50 } 


-- DEOS

tiaraDeosGlobal           OBJECT IDENTIFIER ::= { tiaraDenialOfServiceMib 1 }


tiaraDeosWan      OBJECT-TYPE
	SYNTAX          TruthValue 
	MAX-ACCESS      read-write
	STATUS          current
	DESCRIPTION     "To enable DOS on interfaces other than ethernet interfaces, 
                        set the mib variable to the value true.
                        By default, DOS operation is disabled" 
	DEFVAL { false }
	::= { tiaraDeosGlobal 1 }


tiaraDeosPing      OBJECT-TYPE
	SYNTAX          TruthValue 
	MAX-ACCESS      read-write
	STATUS          current
	DESCRIPTION     "To enable dropping ping packets to the box, set the mib 
                        variable to the value true. 
                        By default, dropping ping is disabled"
	DEFVAL { false }
	::= { tiaraDeosGlobal 2 }



tiaraDeosIcmp      OBJECT-TYPE
	SYNTAX          TruthValue 
	MAX-ACCESS      read-write
	STATUS          current
	DESCRIPTION     "To enable dropping icmp packets to the box, set the mib
       		         By default, dropping icmp operation is disabled" 
	DEFVAL { false }
	::= { tiaraDeosGlobal 3 }

-- To configure DOS on an ethernet interface indexed by "ethNum",
-- set "statusDeosEth"  to value true.


tiaraDeosEthTable   OBJECT-TYPE
	SYNTAX          SEQUENCE OF TiaraDeosEthEntry
	MAX-ACCESS      not-accessible
	STATUS          current
	DESCRIPTION     "Table to configure DOS on ethernet interfaces.
       		        By default, DOS operation on ethernet interfaces is disabled" 
	::= { tiaraDenialOfServiceMib 2 }


tiaraDeosEthEntry         OBJECT-TYPE
        SYNTAX            TiaraDeosEthEntry
        MAX-ACCESS        not-accessible
        STATUS            current
        DESCRIPTION       "An entry in the tiaraDeosEthTable" 
	INDEX	{ ethNum }
        ::= { tiaraDeosEthTable 1 }


TiaraDeosEthEntry   ::= SEQUENCE {
    ethNum               Integer32,
    statusDeosEth        TruthValue
    }


ethNum     		    OBJECT-TYPE
    SYNTAX                  Integer32
    MAX-ACCESS              not-accessible
    STATUS                  current
    DESCRIPTION             "Index to the tiaraDeosEthTable"
        ::= {  tiaraDeosEthEntry 1 }

        
statusDeosEth   	    OBJECT-TYPE
    SYNTAX                  TruthValue
    MAX-ACCESS              read-write
    STATUS                  current
    DESCRIPTION             "To enable DOS on an ethernet interface indexed by ethNum,
                             set statusDeosEth to value true. To disable set to value false.
                             Get on statusDeosEth gives the current configuration of DOS 
                             for an ethernet interface." 
    DEFVAL   { false }
        ::= {  tiaraDeosEthEntry 2 }




tiaraIncompleteTcpTable   OBJECT-TYPE
	SYNTAX          SEQUENCE OF TiaraIncompleteTcpEntry
	MAX-ACCESS      not-accessible
	STATUS          current
	DESCRIPTION     "Table of incomplete TCP connections"
	::= { tiaraDenialOfServiceMib 3 }


tiaraIncompleteTcpEntry    OBJECT-TYPE
        SYNTAX             TiaraIncompleteTcpEntry
        MAX-ACCESS         not-accessible
        STATUS             current
        DESCRIPTION        "An entry in the tiaraIncompleteTcpTable" 
	INDEX	{ ethNum }
        ::= { tiaraIncompleteTcpTable 1 }


TiaraIncompleteTcpEntry    ::= SEQUENCE {
    tcpIncompleteIndex        Integer32,
    srcIpAddress              IpAddress,
    destIpAddress             IpAddress,
    srcPort                   Integer32,
    destPort                  Integer32
    }

tcpIncompleteIndex  	    OBJECT-TYPE
    SYNTAX                  Integer32 
    MAX-ACCESS              not-accessible 
    STATUS                  current
    DESCRIPTION             "A unique identifier for the incomplete connection"
        ::= {  tiaraIncompleteTcpEntry 1 }

        
srcIpAddress     	    OBJECT-TYPE
    SYNTAX                  IpAddress
    MAX-ACCESS              read-only
    STATUS                  current
    DESCRIPTION             "Source IP Address"
        ::= { tiaraIncompleteTcpEntry 2 }

destIpAddress     	    OBJECT-TYPE
    SYNTAX                  IpAddress
    MAX-ACCESS              read-only
    STATUS                  current
    DESCRIPTION             "Destination IP Address"
        ::= { tiaraIncompleteTcpEntry 3 }


srcPort     		    OBJECT-TYPE
    SYNTAX                  Integer32
    MAX-ACCESS              read-only
    STATUS                  current
    DESCRIPTION             "Source Port"
        ::= { tiaraIncompleteTcpEntry 4 }

destPort     		    OBJECT-TYPE
    SYNTAX                  Integer32
    MAX-ACCESS              read-only
    STATUS                  current
    DESCRIPTION             "Destination  Port"
        ::= { tiaraIncompleteTcpEntry 5 }


END
