--			Ascend mibhdsl2net MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBHDSL2NET-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibhdsl2NetworkProfile  OBJECT IDENTIFIER ::= { configuration 14}

	-- The mibhdsl2NetworkProfile table
	--
	-- This table contains parameters for the mibhdsl2NetworkProfile profile
	--

    mibhdsl2NetworkProfileTable	OBJECT-TYPE
	SYNTAX		SEQUENCE OF Mibhdsl2NetworkProfileEntry
	ACCESS		not-accessible
	STATUS		mandatory
	DESCRIPTION	"A list of mibhdsl2NetworkProfile profile entries."
	::= { mibhdsl2NetworkProfile 1 }

    mibhdsl2NetworkProfileEntry	OBJECT-TYPE
	SYNTAX		Mibhdsl2NetworkProfileEntry
	ACCESS		not-accessible
	STATUS		mandatory
	DESCRIPTION	"A mibhdsl2NetworkProfile entry containing objects that
			 maps to the parameters of mibhdsl2NetworkProfile profile."
	INDEX		{ hdsl2NetworkProfile-Shelf-o, hdsl2NetworkProfile-Slot-o, hdsl2NetworkProfile-Item-o }
	::= { mibhdsl2NetworkProfileTable 1 }

    Mibhdsl2NetworkProfileEntry ::=
	SEQUENCE {
	    hdsl2NetworkProfile-Shelf-o
		INTEGER,
	    hdsl2NetworkProfile-Slot-o
		INTEGER,
	    hdsl2NetworkProfile-Item-o
		INTEGER,
	    hdsl2NetworkProfile-Name
		DisplayString,
	    hdsl2NetworkProfile-PhysicalAddress-Shelf
		INTEGER,
	    hdsl2NetworkProfile-PhysicalAddress-Slot
		INTEGER,
	    hdsl2NetworkProfile-PhysicalAddress-ItemNumber
		INTEGER,
	    hdsl2NetworkProfile-Enabled
		INTEGER,
	    hdsl2NetworkProfile-SparingMode
		INTEGER,
	    hdsl2NetworkProfile-IgnoreLineup
		INTEGER,
	    hdsl2NetworkProfile-ProfileNumber
		INTEGER,
	    hdsl2NetworkProfile-LineConfig-TrunkGroup
		INTEGER,
	    hdsl2NetworkProfile-LineConfig-NailedGroup
		INTEGER,
	    hdsl2NetworkProfile-LineConfig-VpSwitchingVpi
		INTEGER,
	    hdsl2NetworkProfile-LineConfig-RoutePort-SlotNumber-SlotNumber
		INTEGER,
	    hdsl2NetworkProfile-LineConfig-RoutePort-SlotNumber-ShelfNumber
		INTEGER,
	    hdsl2NetworkProfile-LineConfig-RoutePort-RelativePortNumber-RelativePortNumber
		INTEGER,
	    hdsl2NetworkProfile-LineConfig-Activation
		INTEGER,
	    hdsl2NetworkProfile-LineConfig-CallRouteInfo-Shelf
		INTEGER,
	    hdsl2NetworkProfile-LineConfig-CallRouteInfo-Slot
		INTEGER,
	    hdsl2NetworkProfile-LineConfig-CallRouteInfo-ItemNumber
		INTEGER,
	    hdsl2NetworkProfile-LineConfig-UnitType
		INTEGER,
	    hdsl2NetworkProfile-LineConfig-NtrEnabled
		INTEGER,
	    hdsl2NetworkProfile-LineConfig-ClockSource
		INTEGER,
	    hdsl2NetworkProfile-LineConfig-ClockPriority
		INTEGER,
	    hdsl2NetworkProfile-LineConfig-LoopBack
		INTEGER,
	    hdsl2NetworkProfile-LineConfig-Margin
		INTEGER,
	    hdsl2NetworkProfile-LineConfig-SnextMargin
		INTEGER,
	    hdsl2NetworkProfile-LineConfig-RateMode
		INTEGER,
	    hdsl2NetworkProfile-LineConfig-MinRate
		INTEGER,
	    hdsl2NetworkProfile-LineConfig-MaxRate
		INTEGER,
	    hdsl2NetworkProfile-LineConfig-GshdslStandardNetworkType
		INTEGER,
	    hdsl2NetworkProfile-LineConfig-AnnexbAnfpEnabled
		INTEGER,
	    hdsl2NetworkProfile-LineConfig-GshdslPsdType
		INTEGER,
	    hdsl2NetworkProfile-ThreshProfiles-SpanThreshProfile
		DisplayString,
	    hdsl2NetworkProfile-ThreshProfiles-XtucThreshProfile
		DisplayString,
	    hdsl2NetworkProfile-ThreshProfiles-XturThreshProfile
		DisplayString,
	    hdsl2NetworkProfile-Action-o
		INTEGER
	}

    hdsl2NetworkProfile-Shelf-o	OBJECT-TYPE
	SYNTAX	INTEGER
	ACCESS	read-only
	STATUS	mandatory
	DESCRIPTION	""
	::= { mibhdsl2NetworkProfileEntry 1 }

    hdsl2NetworkProfile-Slot-o	OBJECT-TYPE
	SYNTAX	INTEGER
	ACCESS	read-only
	STATUS	mandatory
	DESCRIPTION	""
	::= { mibhdsl2NetworkProfileEntry 2 }

    hdsl2NetworkProfile-Item-o	OBJECT-TYPE
	SYNTAX	INTEGER
	ACCESS	read-only
	STATUS	mandatory
	DESCRIPTION	""
	::= { mibhdsl2NetworkProfileEntry 3 }

    hdsl2NetworkProfile-Name	OBJECT-TYPE
	SYNTAX	DisplayString
	ACCESS	read-write
	STATUS	mandatory
	DESCRIPTION	"For future use. The current design does not use the name field but instead references Hdsl2 lines by the physical address; we may in the future support referencing Hdsl2 lines by name as well as by address. The name consists of a null terminated ascii string supplied by the user; it defaults to the ascii form of the Hdsl2 line physical address."
	::= { mibhdsl2NetworkProfileEntry 4 }

    hdsl2NetworkProfile-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibhdsl2NetworkProfileEntry 5 }

    hdsl2NetworkProfile-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibhdsl2NetworkProfileEntry 6 }

    hdsl2NetworkProfile-PhysicalAddress-ItemNumber	OBJECT-TYPE
	SYNTAX	INTEGER
	ACCESS	read-write
	STATUS	mandatory
	DESCRIPTION	"A number that specifies an addressable entity within the context of shelf and slot."
	::= { mibhdsl2NetworkProfileEntry 7 }

    hdsl2NetworkProfile-Enabled	OBJECT-TYPE
	SYNTAX	INTEGER {
		    no (1),
		    yes (2)
		}
	ACCESS	read-write
	STATUS	mandatory
	DESCRIPTION	"TRUE if the line is enabled, otherwise FALSE."
	::= { mibhdsl2NetworkProfileEntry 8 }

    hdsl2NetworkProfile-SparingMode	OBJECT-TYPE
	SYNTAX	INTEGER {
		    inactive (1),
		    manual (2),
		    automatic (3)
		}
	ACCESS	read-write
	STATUS	mandatory
	DESCRIPTION	"Port sparing operational mode for this port."
	::= { mibhdsl2NetworkProfileEntry 24 }

    hdsl2NetworkProfile-IgnoreLineup	OBJECT-TYPE
	SYNTAX	INTEGER {
		    systemDefined (1),
		    no (2),
		    yes (3)
		}
	ACCESS	read-write
	STATUS	mandatory
	DESCRIPTION	"Ignore line up value for this port."
	::= { mibhdsl2NetworkProfileEntry 29 }

    hdsl2NetworkProfile-ProfileNumber	OBJECT-TYPE
	SYNTAX	INTEGER
	ACCESS	read-write
	STATUS	mandatory
	DESCRIPTION	"For potential backwards compatibility. The current design consists of one line profile numbered 0."
	::= { mibhdsl2NetworkProfileEntry 9 }

    hdsl2NetworkProfile-LineConfig-TrunkGroup	OBJECT-TYPE
	SYNTAX	INTEGER
	ACCESS	read-write
	STATUS	mandatory
	DESCRIPTION	"The trunk group to which this line is assigned. 0 means this line is not part of a trunk group."
	::= { mibhdsl2NetworkProfileEntry 10 }

    hdsl2NetworkProfile-LineConfig-NailedGroup	OBJECT-TYPE
	SYNTAX	INTEGER
	ACCESS	read-write
	STATUS	mandatory
	DESCRIPTION	"A number that identifies the set of lines that makes up a nailed group. 0 means this line is not part of a nailed group."
	::= { mibhdsl2NetworkProfileEntry 11 }

    hdsl2NetworkProfile-LineConfig-VpSwitchingVpi	OBJECT-TYPE
	SYNTAX	INTEGER
	ACCESS	read-write
	STATUS	mandatory
	DESCRIPTION	"The Vpi to be used for the VP switching. Rest of the valid VPIs in valid vpi-vci-range will be used for the VC switching. Changes in this range will take effect immediately. THE USER SHOULD BE VERY CAREFUL WHILE CHANGING THIS VALUE BECAUSE ALL CONNECTIONS ON THE LIM WHERE THIS PORT BELONGS WILL BE DROPPED IN ORDER TO MAKE THIS NEW VALUE EFFECTIVE IMMEDIATELY."
	::= { mibhdsl2NetworkProfileEntry 12 }

    hdsl2NetworkProfile-LineConfig-RoutePort-SlotNumber-SlotNumber	OBJECT-TYPE
	SYNTAX	INTEGER
	ACCESS	read-write
	STATUS	mandatory
	DESCRIPTION	""
	::= { mibhdsl2NetworkProfileEntry 13 }

    hdsl2NetworkProfile-LineConfig-RoutePort-SlotNumber-ShelfNumber	OBJECT-TYPE
	SYNTAX	INTEGER
	ACCESS	read-write
	STATUS	mandatory
	DESCRIPTION	"TNT is a multi shelf system. To minimise the changes required to existing code the shelf number is added to this structure as it will almost always be needed when a slot number is needed."
	::= { mibhdsl2NetworkProfileEntry 14 }

    hdsl2NetworkProfile-LineConfig-RoutePort-RelativePortNumber-RelativePortNumber	OBJECT-TYPE
	SYNTAX	INTEGER
	ACCESS	read-write
	STATUS	mandatory
	DESCRIPTION	""
	::= { mibhdsl2NetworkProfileEntry 15 }

    hdsl2NetworkProfile-LineConfig-Activation	OBJECT-TYPE
	SYNTAX	INTEGER {
		    static (1),
		    dsrActive (2),
		    dcdDsrActive (3)
		}
	ACCESS	read-write
	STATUS	mandatory
	DESCRIPTION	"Line activation mode."
	::= { mibhdsl2NetworkProfileEntry 16 }

    hdsl2NetworkProfile-LineConfig-CallRouteInfo-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibhdsl2NetworkProfileEntry 17 }

    hdsl2NetworkProfile-LineConfig-CallRouteInfo-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibhdsl2NetworkProfileEntry 18 }

    hdsl2NetworkProfile-LineConfig-CallRouteInfo-ItemNumber	OBJECT-TYPE
	SYNTAX	INTEGER
	ACCESS	read-write
	STATUS	mandatory
	DESCRIPTION	"A number that specifies an addressable entity within the context of shelf and slot."
	::= { mibhdsl2NetworkProfileEntry 19 }

    hdsl2NetworkProfile-LineConfig-UnitType	OBJECT-TYPE
	SYNTAX	INTEGER {
		    coe (1),
		    cpe (2)
		}
	ACCESS	read-write
	STATUS	mandatory
	DESCRIPTION	"The Unit Type defines if a line is acting as either a Central Office (COE) or Customer Premise Equipment (CPE). Note that the remote unit needs to be configured opposite to this configureation."
	::= { mibhdsl2NetworkProfileEntry 20 }

    hdsl2NetworkProfile-LineConfig-NtrEnabled	OBJECT-TYPE
	SYNTAX	INTEGER {
		    no (1),
		    yes (2)
		}
	ACCESS	read-write
	STATUS	mandatory
	DESCRIPTION	"TRUE if NTR functionality is enabled, otherwise FALSE. If the unit-type is COE, it will take the system clock as the input when NTR is enabled and allow the remote CPE port to recover the clock. If the unit-type is CPE, it will allow the port to possibly output the recovered clock as the system clock (if elected, see clock-source and clock-priority fields) when NTR is enabled."
	::= { mibhdsl2NetworkProfileEntry 25 }

    hdsl2NetworkProfile-LineConfig-ClockSource	OBJECT-TYPE
	SYNTAX	INTEGER {
		    eligible (1),
		    notEligible (2)
		}
	ACCESS	read-write
	STATUS	mandatory
	DESCRIPTION	"Determine whether the 8KHz clock from the HDSL2 line (unit-type has to be CPE and ntr-enabled has to be yes) is eligible to be used as the 8KHz system clock source."
	::= { mibhdsl2NetworkProfileEntry 26 }

    hdsl2NetworkProfile-LineConfig-ClockPriority	OBJECT-TYPE
	SYNTAX	INTEGER {
		    highPriority (2),
		    middlePriority (3),
		    lowPriority (4)
		}
	ACCESS	read-write
	STATUS	mandatory
	DESCRIPTION	"Clock priority assigned to the HDSL2 line. Used to select a particular HDSL2 line as the 8KHz system clock source."
	::= { mibhdsl2NetworkProfileEntry 27 }

    hdsl2NetworkProfile-LineConfig-LoopBack	OBJECT-TYPE
	SYNTAX	INTEGER {
		    none (1),
		    analog (2),
		    digital (3)
		}
	ACCESS	read-write
	STATUS	mandatory
	DESCRIPTION	"Configuration of different modem loopbacks."
	::= { mibhdsl2NetworkProfileEntry 28 }

    hdsl2NetworkProfile-LineConfig-Margin	OBJECT-TYPE
	SYNTAX	INTEGER {
		    n-0db (1),
		    n-1db (2),
		    n-2db (3),
		    n-3db (4),
		    n-4db (5),
		    n-5db (6),
		    n-6db (7),
		    n-7db (8),
		    n-8db (9),
		    n-9db (10),
		    n-10db (11),
		    disable (17)
		}
	ACCESS	read-write
	STATUS	mandatory
	DESCRIPTION	"Selects a margin range between the signal to noise floor."
	::= { mibhdsl2NetworkProfileEntry 30 }

    hdsl2NetworkProfile-LineConfig-SnextMargin	OBJECT-TYPE
	SYNTAX	INTEGER {
		    n-0db (1),
		    n-1db (2),
		    n-2db (3),
		    n-3db (4),
		    n-4db (5),
		    n-5db (6),
		    n-6db (7),
		    n-7db (8),
		    n-8db (9),
		    n-9db (10),
		    n-10db (11),
		    n-plus-10db (12),
		    n-plus-9db (13),
		    n-plus-8db (14),
		    n-plus-7db (15),
		    n-plus-6db (16),
		    n-plus-5db (17),
		    n-plus-4db (18),
		    n-plus-3db (19),
		    n-plus-2db (20),
		    n-plus-1db (21),
		    disable (22)
		}
	ACCESS	read-write
	STATUS	mandatory
	DESCRIPTION	"Selects a Snext margin range with a worst-case self next noise model given current loop insertion loss."
	::= { mibhdsl2NetworkProfileEntry 39 }

    hdsl2NetworkProfile-LineConfig-RateMode	OBJECT-TYPE
	SYNTAX	INTEGER {
		    fixed (1),
		    auto (2)
		}
	ACCESS	read-write
	STATUS	mandatory
	DESCRIPTION	"Used for G.SHDSL technology. Selects if the modem operates in Fixed or Auto rate mode."
	::= { mibhdsl2NetworkProfileEntry 31 }

    hdsl2NetworkProfile-LineConfig-MinRate	OBJECT-TYPE
	SYNTAX	INTEGER {
		    n-72000 (72001),
		    n-136000 (136001),
		    n-200000 (200001),
		    n-264000 (264001),
		    n-328000 (328001),
		    n-392000 (392001),
		    n-520000 (520001),
		    n-776000 (776001),
		    n-1032000 (1032001),
		    n-1160000 (1160001),
		    n-1288000 (1288001),
		    n-1544000 (1544001),
		    n-2056000 (2056001),
		    n-2312000 (2312001)
		}
	ACCESS	read-write
	STATUS	mandatory
	DESCRIPTION	"Used for G.SHDSL technology. When the rate-mode is set to Auto, this is the minimum rate the modem will train to."
	::= { mibhdsl2NetworkProfileEntry 32 }

    hdsl2NetworkProfile-LineConfig-MaxRate	OBJECT-TYPE
	SYNTAX	INTEGER {
		    n-72000 (72001),
		    n-136000 (136001),
		    n-200000 (200001),
		    n-264000 (264001),
		    n-328000 (328001),
		    n-392000 (392001),
		    n-520000 (520001),
		    n-776000 (776001),
		    n-1032000 (1032001),
		    n-1160000 (1160001),
		    n-1288000 (1288001),
		    n-1544000 (1544001),
		    n-2056000 (2056001),
		    n-2312000 (2312001)
		}
	ACCESS	read-write
	STATUS	mandatory
	DESCRIPTION	"Used for G.SHDSL technology. When the rate-mode is set to Auto, this is the maximum rate the modem will train to. When the rate-mode is set to Fixed, this is the only rate the mode trains to."
	::= { mibhdsl2NetworkProfileEntry 33 }

    hdsl2NetworkProfile-LineConfig-GshdslStandardNetworkType	OBJECT-TYPE
	SYNTAX	INTEGER {
		    northAmericanAnnexA (1),
		    europeanAnnexB (2),
		    autoDetect (3)
		}
	ACCESS	read-write
	STATUS	mandatory
	DESCRIPTION	"Per the G.SHDSL Standard G.991.2. This parameter allows selection for the modem to operate either the North American Annex 'A' or European Annex 'B' standard network types. The setting of auto-detect is only valid for CPE to train off of COE Standard Network settings."
	::= { mibhdsl2NetworkProfileEntry 34 }

    hdsl2NetworkProfile-LineConfig-AnnexbAnfpEnabled	OBJECT-TYPE
	SYNTAX	INTEGER {
		    no (1),
		    yes (2)
		}
	ACCESS	read-write
	STATUS	mandatory
	DESCRIPTION	"TRUE if Annex B ANFP functionality is enabled, otherwise FALSE. The gshdsl-standard-network-type must be set to European Annex B, and the port cannot be CPE. This field makes the modem perform in Annex B mode, but slightly differently. This is to comply with the UK ANFP requirements and pass the BTexact Technologies PSD measurement technique to meet BT approval. Only enable this field for that test specifically."
	::= { mibhdsl2NetworkProfileEntry 40 }

    hdsl2NetworkProfile-LineConfig-GshdslPsdType	OBJECT-TYPE
	SYNTAX	INTEGER {
		    symmetric (1),
		    asymmetric776kPsdAnnexA (4),
		    asymmetric1544kPsdAnnexA (5),
		    asymmetric2056kPsdAnnexB (6),
		    asymmetric2312kPsdAnnexB (7),
		    autoDetect (8)
		}
	ACCESS	read-write
	STATUS	mandatory
	DESCRIPTION	"Per the G.SHDSL Standard G.911.2. This parameter allows selection for the modem to output a symmetric PSD at all rates or asymmetric PSD's at fixed rates of 776kbps, 784kbps, 1544kbps, or 1552kbps for Annex A networks. Annex B networks support fixed rates of 2056kbps or 2304kbps. The setting of auto-detect is only valid for CPE to train off of COE PSD settings."
	::= { mibhdsl2NetworkProfileEntry 35 }

    hdsl2NetworkProfile-ThreshProfiles-SpanThreshProfile	OBJECT-TYPE
	SYNTAX	DisplayString
	ACCESS	read-write
	STATUS	mandatory
	DESCRIPTION	"The name consists of a null terminated ascii string supplied by the user. This profile defines the thresholds for all the HDSL2/SHDSL units for this port unless otherwise specified by the individual parameters in this subprofile."
	::= { mibhdsl2NetworkProfileEntry 36 }

    hdsl2NetworkProfile-ThreshProfiles-XtucThreshProfile	OBJECT-TYPE
	SYNTAX	DisplayString
	ACCESS	read-write
	STATUS	mandatory
	DESCRIPTION	"The name consists of a null terminated ascii string supplied by the user. This profile defines the thresholds for the DSLAM."
	::= { mibhdsl2NetworkProfileEntry 37 }

    hdsl2NetworkProfile-ThreshProfiles-XturThreshProfile	OBJECT-TYPE
	SYNTAX	DisplayString
	ACCESS	read-write
	STATUS	mandatory
	DESCRIPTION	"The name consists of a null terminated ascii string supplied by the user. This profile defines the thresholds for the remote CPE."
	::= { mibhdsl2NetworkProfileEntry 38 }

    hdsl2NetworkProfile-Action-o	OBJECT-TYPE
	SYNTAX	INTEGER {
		    noAction (1),
		    createProfile (2),
		    deleteProfile (3)
		}
	ACCESS	read-write
	STATUS	mandatory
	DESCRIPTION	""
	::= { mibhdsl2NetworkProfileEntry 23 }


	-- The mibhdsl2NetworkProfile__thresh_profiles__unit_thresh_profiles table
	--
	-- This table contains parameters for the mibhdsl2NetworkProfile__thresh_profiles__unit_thresh_profiles profile
	--

    mibhdsl2NetworkProfile-ThreshProfiles-UnitThreshProfilesTable	OBJECT-TYPE
	SYNTAX		SEQUENCE OF Mibhdsl2NetworkProfile-ThreshProfiles-UnitThreshProfilesEntry
	ACCESS		not-accessible
	STATUS		mandatory
	DESCRIPTION	"A list of mibhdsl2NetworkProfile__thresh_profiles__unit_thresh_profiles profile entries."
	::= { mibhdsl2NetworkProfile 2 }

    mibhdsl2NetworkProfile-ThreshProfiles-UnitThreshProfilesEntry	OBJECT-TYPE
	SYNTAX		Mibhdsl2NetworkProfile-ThreshProfiles-UnitThreshProfilesEntry
	ACCESS		not-accessible
	STATUS		mandatory
	DESCRIPTION	"A mibhdsl2NetworkProfile__thresh_profiles__unit_thresh_profiles entry containing objects that
			 maps to the parameters of mibhdsl2NetworkProfile__thresh_profiles__unit_thresh_profiles profile."
	INDEX		{ hdsl2NetworkProfile-ThreshProfiles-UnitThreshProfiles-Shelf-o, hdsl2NetworkProfile-ThreshProfiles-UnitThreshProfiles-Slot-o, hdsl2NetworkProfile-ThreshProfiles-UnitThreshProfiles-Item-o, hdsl2NetworkProfile-ThreshProfiles-UnitThreshProfiles-Index-o }
	::= { mibhdsl2NetworkProfile-ThreshProfiles-UnitThreshProfilesTable 1 }

    Mibhdsl2NetworkProfile-ThreshProfiles-UnitThreshProfilesEntry ::=
	SEQUENCE {
	    hdsl2NetworkProfile-ThreshProfiles-UnitThreshProfiles-Shelf-o
		INTEGER,
	    hdsl2NetworkProfile-ThreshProfiles-UnitThreshProfiles-Slot-o
		INTEGER,
	    hdsl2NetworkProfile-ThreshProfiles-UnitThreshProfiles-Item-o
		INTEGER,
	    hdsl2NetworkProfile-ThreshProfiles-UnitThreshProfiles-Index-o
		INTEGER,
	    hdsl2NetworkProfile-ThreshProfiles-UnitThreshProfiles-XruNetThreshProfile
		DisplayString,
	    hdsl2NetworkProfile-ThreshProfiles-UnitThreshProfiles-XruCustThreshProfile
		DisplayString
	}

    hdsl2NetworkProfile-ThreshProfiles-UnitThreshProfiles-Shelf-o	OBJECT-TYPE
	SYNTAX	INTEGER
	ACCESS	read-only
	STATUS	mandatory
	DESCRIPTION	""
	::= { mibhdsl2NetworkProfile-ThreshProfiles-UnitThreshProfilesEntry 1 }

    hdsl2NetworkProfile-ThreshProfiles-UnitThreshProfiles-Slot-o	OBJECT-TYPE
	SYNTAX	INTEGER
	ACCESS	read-only
	STATUS	mandatory
	DESCRIPTION	""
	::= { mibhdsl2NetworkProfile-ThreshProfiles-UnitThreshProfilesEntry 2 }

    hdsl2NetworkProfile-ThreshProfiles-UnitThreshProfiles-Item-o	OBJECT-TYPE
	SYNTAX	INTEGER
	ACCESS	read-only
	STATUS	mandatory
	DESCRIPTION	""
	::= { mibhdsl2NetworkProfile-ThreshProfiles-UnitThreshProfilesEntry 3 }

    hdsl2NetworkProfile-ThreshProfiles-UnitThreshProfiles-Index-o	OBJECT-TYPE
	SYNTAX	INTEGER
	ACCESS	read-only
	STATUS	mandatory
	DESCRIPTION	""
	::= { mibhdsl2NetworkProfile-ThreshProfiles-UnitThreshProfilesEntry 4 }

    hdsl2NetworkProfile-ThreshProfiles-UnitThreshProfiles-XruNetThreshProfile	OBJECT-TYPE
	SYNTAX	DisplayString
	ACCESS	read-write
	STATUS	mandatory
	DESCRIPTION	"The name consists of a null terminated ascii string supplied by the user. This profile defines the thresholds for the network side of regenerator unit 1."
	::= { mibhdsl2NetworkProfile-ThreshProfiles-UnitThreshProfilesEntry 5 }

    hdsl2NetworkProfile-ThreshProfiles-UnitThreshProfiles-XruCustThreshProfile	OBJECT-TYPE
	SYNTAX	DisplayString
	ACCESS	read-write
	STATUS	mandatory
	DESCRIPTION	"The name consists of a null terminated ascii string supplied by the user. This profile defines the thresholds for the customer side of regenerator unit 1."
	::= { mibhdsl2NetworkProfile-ThreshProfiles-UnitThreshProfilesEntry 6 }

END
