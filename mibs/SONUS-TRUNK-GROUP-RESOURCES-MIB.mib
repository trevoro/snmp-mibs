--
-- This SMIv2 module has been generated by smidump 0.2-cvs. Do not edit.
--

SONUS-TRUNK-GROUP-RESOURCES-MIB DEFINITIONS ::= BEGIN

IMPORTS
    Integer32, IpAddress, MODULE-IDENTITY, NOTIFICATION-TYPE, 
    OBJECT-TYPE
        FROM SNMPv2-SMI
    DisplayString, RowStatus
        FROM SNMPv2-TC
    sonusEventClass, sonusEventDescription, sonusEventLevel
        FROM SONUS-COMMON-MIB
    sonusResourcesMIBs
        FROM SONUS-SMI
    SonusBoolean, SonusName
        FROM SONUS-TC;

sonusTrunkGroupResourcesMIB MODULE-IDENTITY
    LAST-UPDATED    "200102030000Z"
    ORGANIZATION    
            "Sonus Networks, Inc."
    CONTACT-INFO    
            "   Customer Support    
             Sonus Networks, Inc,
             5 carlisle Road
             Westford, MA 01886
             USA
             
             Tel: 978-692-8999
             Fax: 978-392-9118
             E-mail: cs.snmp@sonusnet.com"
    DESCRIPTION     
            "The MIB Module for Trunk Group Resources Management."
    ::= { sonusResourcesMIBs 3 }


sonusTrunkGroupResourcesMIBObjects OBJECT IDENTIFIER
    ::= { sonusTrunkGroupResourcesMIB 1 }

sonusTrunkObjects OBJECT IDENTIFIER
    ::= { sonusTrunkGroupResourcesMIBObjects 1 }

sonusTrunkConfigObjects OBJECT IDENTIFIER
    ::= { sonusTrunkObjects 1 }

sonusTgMaxRpcLpcs OBJECT-TYPE
    SYNTAX          Integer32 (1..65535)
    MAX-ACCESS      read-write
    STATUS          current
    DESCRIPTION     
            "Maximum number of RPC-LPC pairs for this gateway."
    DEFVAL          { 500 }
    ::= { sonusTrunkConfigObjects 1 }

sonusTgMaxCics OBJECT-TYPE
    SYNTAX          Integer32 (1..65535)
    MAX-ACCESS      read-write
    STATUS          current
    DESCRIPTION     
            "Maximum number of CICs for this gateway."
    DEFVAL          { 10000 }
    ::= { sonusTrunkConfigObjects 2 }

sonusTgMaxTrunkGroups OBJECT-TYPE
    SYNTAX          Integer32 (1..250)
    MAX-ACCESS      read-write
    STATUS          current
    DESCRIPTION     
            "Maximum number of trunk groups for this gateway."
    DEFVAL          { 250 }
    ::= { sonusTrunkConfigObjects 3 }

sonusTgMaxServiceGroups OBJECT-TYPE
    SYNTAX          Integer32 (1..65535)
    MAX-ACCESS      read-write
    STATUS          current
    DESCRIPTION     
            "Maximum number of Service Groups for this gateway."
    DEFVAL          { 500 }
    ::= { sonusTrunkConfigObjects 4 }

sonusTgMaxSgInstances OBJECT-TYPE
    SYNTAX          Integer32 (1..65535)
    MAX-ACCESS      read-write
    STATUS          current
    DESCRIPTION     
            "Maximum number of Service Group Instances for this gateway."
    DEFVAL          { 500 }
    ::= { sonusTrunkConfigObjects 5 }

sonusTgObjects OBJECT IDENTIFIER
    ::= { sonusTrunkObjects 2 }

sonusTgNextIndex OBJECT-TYPE
    SYNTAX          Integer32
    MAX-ACCESS      read-only
    STATUS          current
    DESCRIPTION     
            "The next valid index to use when creating a new sonusTgEntry"
    ::= { sonusTgObjects 1 }

sonusTgTable OBJECT-TYPE
    SYNTAX          SEQUENCE OF SonusTgEntry
    MAX-ACCESS      not-accessible
    STATUS          current
    DESCRIPTION     
            "A list of trunk group entries."
    ::= { sonusTgObjects 2 }

sonusTgEntry OBJECT-TYPE
    SYNTAX          SonusTgEntry
    MAX-ACCESS      not-accessible
    STATUS          current
    DESCRIPTION     
            "Each sonusTgEntry containing configuration objects.
             Rules & Behaviors:
                  A sonusTgEntry cannot be deleted when it is enabled.
                  When disabling the trunk group entry, it must not have 
                  any associated SGs.  All SGs must be removed before
                  disabling the trunk group.
                  A sonusTgEntry cannot be modified when it is enabled."
    INDEX           { sonusTgIndex }
    ::= { sonusTgTable 1 }

SonusTgEntry ::=
    SEQUENCE {
        sonusTgIndex                    Integer32,
        sonusTgName                     SonusName,
        sonusTgProfName                 DisplayString,
        sonusTgSgSelect                 INTEGER,
        sonusTgLnpTranslate             SonusBoolean,
        sonusTg800Translate             SonusBoolean,
        sonusTgCallingNumVerify         SonusBoolean,
        sonusTgInboundReserved          Integer32,
        sonusTgIsupOnly                 SonusBoolean,
        sonusTgCarrier                  DisplayString,
        sonusTgIsupNode                 DisplayString,
        sonusTgAdminState               INTEGER,
        sonusTgMode                     INTEGER,
        sonusTgAction                   INTEGER,
        sonusTgTimeout                  Integer32,
        sonusTgRowStatus                RowStatus,
        sonusTgCirResvState             INTEGER,
        sonusTgPriorityCallReserve      Integer32,
        sonusTgIncomingCallReserve      Integer32,
        sonusTgOutgoingCallReserve      Integer32
    }

sonusTgIndex OBJECT-TYPE
    SYNTAX          Integer32
    MAX-ACCESS      read-only
    STATUS          current
    DESCRIPTION     
            "A unique value for each trunk group that is between 1
             and maximum allowed"
    ::= { sonusTgEntry 1 }

sonusTgName OBJECT-TYPE
    SYNTAX          SonusName
    MAX-ACCESS      read-write
    STATUS          current
    DESCRIPTION     
            "The name of the trunk group."
    ::= { sonusTgEntry 2 }

sonusTgProfName OBJECT-TYPE
    SYNTAX          DisplayString (SIZE(0..23))
    MAX-ACCESS      read-write
    STATUS          current
    DESCRIPTION     
            "The name of the profile applied to this trunk group entry. "
    ::= { sonusTgEntry 3 }

sonusTgSgSelect OBJECT-TYPE
    SYNTAX          INTEGER { leastcost(1), configured(2), 
                        circularforward(3), circularbackward(4) }
    MAX-ACCESS      read-write
    STATUS          current
    DESCRIPTION     
            "Selection for hunting within a PSTN trunk group that has 
             more than 1 associated service group(SG).
             It is either based on cost associated with each SG,
             how the SG is ordered during configuration (for circular also).
             		 If either circular option is chosen, then SG hunt algorithm
             		 is ignored."
    DEFVAL          { leastcost }
    ::= { sonusTgEntry 4 }

sonusTgLnpTranslate OBJECT-TYPE
    SYNTAX          SonusBoolean
    MAX-ACCESS      read-write
    STATUS          current
    DESCRIPTION     
            "This is only meaningful for PSTN trunk groups that may require
             LNP translation for the called number."
    DEFVAL          { true }
    ::= { sonusTgEntry 5 }

sonusTg800Translate OBJECT-TYPE
    SYNTAX          SonusBoolean
    MAX-ACCESS      read-write
    STATUS          current
    DESCRIPTION     
            "This is only meaningful for PSTN trunk groups that may require
             800 number translation for the called number."
    DEFVAL          { true }
    ::= { sonusTgEntry 6 }

sonusTgCallingNumVerify OBJECT-TYPE
    SYNTAX          SonusBoolean
    MAX-ACCESS      read-write
    STATUS          current
    DESCRIPTION     
            "This is only meaningful for PSTN trunk groups that requires
             verification for the calling number."
    DEFVAL          { true }
    ::= { sonusTgEntry 7 }

sonusTgInboundReserved OBJECT-TYPE
    SYNTAX          Integer32 (0..100)
    MAX-ACCESS      read-write
    STATUS          current
    DESCRIPTION     
            "This is only meaninful for PSTN Trunk Groups.  This the
             percent of channels reserved for handling inbound calls.
             Default is 0% and valid for both direction type trunks.
             The amount reserved is round off to next number. For
             example, 50% of 23 hannels is 12.5 or 13 channels.  
             Percentage selection allowed in 5% increments."
    DEFVAL          { 0 }
    ::= { sonusTgEntry 8 }

sonusTgIsupOnly OBJECT-TYPE
    SYNTAX          SonusBoolean
    MAX-ACCESS      read-write
    STATUS          current
    DESCRIPTION     
            "This is only meaningful for PSTN trunk groups that is either an
             ISUP only or mixed of ISUP and other PSTN types"
    DEFVAL          { true }
    ::= { sonusTgEntry 9 }

sonusTgCarrier OBJECT-TYPE
    SYNTAX          DisplayString (SIZE(0..23))
    MAX-ACCESS      read-write
    STATUS          current
    DESCRIPTION     
            "This is only meaningful for PSTN trunk groups and is specific
             to Isup only.  This is the name of the Isup that this trunk 
             group is bound to. "
    ::= { sonusTgEntry 10 }

sonusTgIsupNode OBJECT-TYPE
    SYNTAX          DisplayString (SIZE(0..23))
    MAX-ACCESS      read-write
    STATUS          current
    DESCRIPTION     
            "This is meaningful for PSTN trunk groups and is specific
             to Isup only.  This is the name of the Isup that this trunk 
             group is bound to. "
    ::= { sonusTgEntry 11 }

sonusTgAdminState OBJECT-TYPE
    SYNTAX          INTEGER { disabled(1), enabled(2) }
    MAX-ACCESS      read-write
    STATUS          current
    DESCRIPTION     
            "Administrative state to disable or enable a trunk group. All
             trunk groups are created with its state disabled.  If trunk group
             is disabled, the trunk group must be enabled to allow calls to 
             proceed."
    DEFVAL          { disabled }
    ::= { sonusTgEntry 12 }

sonusTgMode OBJECT-TYPE
    SYNTAX          INTEGER { inService(1), outOfService(2) }
    MAX-ACCESS      read-write
    STATUS          current
    DESCRIPTION     
            "The operation mode for this trunk."
    DEFVAL          { inService }
    ::= { sonusTgEntry 13 }

sonusTgAction OBJECT-TYPE
    SYNTAX          INTEGER { dryUp(1), force(2) }
    MAX-ACCESS      read-write
    STATUS          current
    DESCRIPTION     
            "The action for the operation mode for this trunk."
    DEFVAL          { dryUp }
    ::= { sonusTgEntry 14 }

sonusTgTimeout OBJECT-TYPE
    SYNTAX          Integer32 (1..1440)
    MAX-ACCESS      read-write
    STATUS          current
    DESCRIPTION     
            "Timeout value in minutes for the dry up action."
    DEFVAL          { 5 }
    ::= { sonusTgEntry 15 }

sonusTgRowStatus OBJECT-TYPE
    SYNTAX          RowStatus
    MAX-ACCESS      read-write
    STATUS          current
    DESCRIPTION     
            "This is for SNMP use."
    ::= { sonusTgEntry 16 }

sonusTgCirResvState OBJECT-TYPE
    SYNTAX          INTEGER { disabled(1), enabled(2) }
    MAX-ACCESS      read-write
    STATUS          current
    DESCRIPTION     
            "Administrative state to disable or enable the circuit reservation feature on a trunk group.
             All trunk groups are created with this feature disabled.  If this feature is enabled,
             the sonusTgInboundReserved feature is overriden automatically."
    DEFVAL          { disabled }
    ::= { sonusTgEntry 17 }

sonusTgPriorityCallReserve OBJECT-TYPE
    SYNTAX          Integer32 (0..100)
    MAX-ACCESS      read-write
    STATUS          current
    DESCRIPTION     
            "The minimum number of priority call allowed set for this trunk group when sonusTgCirResvState 
             is set to enabled."
    DEFVAL          { 1 }
    ::= { sonusTgEntry 18 }

sonusTgIncomingCallReserve OBJECT-TYPE
    SYNTAX          Integer32 (0..100)
    MAX-ACCESS      read-write
    STATUS          current
    DESCRIPTION     
            "The minimum number of incoming call allowed set for this trunk group when sonusTgCirResvState 
             is set to enabled."
    DEFVAL          { 1 }
    ::= { sonusTgEntry 19 }

sonusTgOutgoingCallReserve OBJECT-TYPE
    SYNTAX          Integer32 (0..100)
    MAX-ACCESS      read-write
    STATUS          current
    DESCRIPTION     
            "The minimum percent of outgoing call allowed set for this trunk group when sonusTgCirResvState 
             is set to enabled."
    DEFVAL          { 10 }
    ::= { sonusTgEntry 20 }

sonusTgStatusTable OBJECT-TYPE
    SYNTAX          SEQUENCE OF SonusTgStatusEntry
    MAX-ACCESS      not-accessible
    STATUS          current
    DESCRIPTION     
            "This table contains status information of a PSTN trunk group.
             There may not be any SG registered to a trunk group in which
             case all statistics will be zero."
    ::= { sonusTrunkObjects 3 }

sonusTgStatusEntry OBJECT-TYPE
    SYNTAX          SonusTgStatusEntry
    MAX-ACCESS      not-accessible
    STATUS          current
    DESCRIPTION     
            "Each entry describes the current status of a PSTN trunk group."
    INDEX           { sonusTgStatusIndex }
    ::= { sonusTgStatusTable 1 }

SonusTgStatusEntry ::=
    SEQUENCE {
        sonusTgStatusIndex              Integer32,
        sonusTgOperState                INTEGER,
        sonusTgPstnTotalAvailable       Integer32,
        sonusTgPstnTotalInboundRsv      Integer32,
        sonusTgPstnInboundUsage         Integer32,
        sonusTgPstnOutboundUsage        Integer32,
        sonusTgPstnTotalConfigured      Integer32,
        sonusTgAccCurrentACL            Integer32,
        sonusTgPriorityCallUsage        Integer32
    }

sonusTgStatusIndex OBJECT-TYPE
    SYNTAX          Integer32
    MAX-ACCESS      read-only
    STATUS          current
    DESCRIPTION     
            "A unique value for each trunk group between 1 and maximum 
             allowed."
    ::= { sonusTgStatusEntry 1 }

sonusTgOperState OBJECT-TYPE
    SYNTAX          INTEGER { inService(1), outOfService(2), 
                        oosPending(3) }
    MAX-ACCESS      read-only
    STATUS          current
    DESCRIPTION     
            "Current operational state of the trunk group."
    ::= { sonusTgStatusEntry 2 }

sonusTgPstnTotalAvailable OBJECT-TYPE
    SYNTAX          Integer32
    MAX-ACCESS      read-only
    STATUS          current
    DESCRIPTION     
            "The sum of all available or unblocked PSTN channels for this trunk group."
    ::= { sonusTgStatusEntry 3 }

sonusTgPstnTotalInboundRsv OBJECT-TYPE
    SYNTAX          Integer32
    MAX-ACCESS      read-only
    STATUS          current
    DESCRIPTION     
            "This is meaningful for PSTN trunk groups that are configured for
             inbound or both directions only.  This is the reserved count 
             as specified by the percentage configred for this trunk group."
    ::= { sonusTgStatusEntry 4 }

sonusTgPstnInboundUsage OBJECT-TYPE
    SYNTAX          Integer32
    MAX-ACCESS      read-only
    STATUS          current
    DESCRIPTION     
            "This is only meaningful for PSTN trunk groups that are configured
             for inbound or both directions.  This reflects the current 
             inbound or incoming usage count of this trunk group."
    ::= { sonusTgStatusEntry 5 }

sonusTgPstnOutboundUsage OBJECT-TYPE
    SYNTAX          Integer32
    MAX-ACCESS      read-only
    STATUS          current
    DESCRIPTION     
            "This is only meaningful for PSTN trunk groups that are configured
             for outbound or both directions.  This reflects the current 
             outbound, outgoing or non-priority usage count of this trunk group."
    ::= { sonusTgStatusEntry 6 }

sonusTgPstnTotalConfigured OBJECT-TYPE
    SYNTAX          Integer32
    MAX-ACCESS      read-only
    STATUS          current
    DESCRIPTION     
            "The sum of all configured and registered PSTN channels for this trunk group."
    ::= { sonusTgStatusEntry 7 }

sonusTgAccCurrentACL OBJECT-TYPE
    SYNTAX          Integer32
    MAX-ACCESS      read-only
    STATUS          current
    DESCRIPTION     
            "Current congestion level for the Trunk Group"
    ::= { sonusTgStatusEntry 8 }

sonusTgPriorityCallUsage OBJECT-TYPE
    SYNTAX          Integer32
    MAX-ACCESS      read-only
    STATUS          current
    DESCRIPTION     
            "This is only meaningful for ISUP trunk groups that are configured and
             when sonusTgCirResvState is enabled.  This reflects the current 
             priority usage count of this trunk group."
    ::= { sonusTgStatusEntry 9 }

sonusTgSgTable OBJECT-TYPE
    SYNTAX          SEQUENCE OF SonusTgSgEntry
    MAX-ACCESS      not-accessible
    STATUS          current
    DESCRIPTION     
            "This is a virtual table containing a list of service groups
             that belong to the same trunk group.   This is a doubly
             indexed table so that further details about each service
             group may be queried by name."
    ::= { sonusTrunkObjects 4 }

sonusTgSgEntry OBJECT-TYPE
    SYNTAX          SonusTgSgEntry
    MAX-ACCESS      not-accessible
    STATUS          current
    DESCRIPTION     
            "Each entry lists the name and order of each service group."
    INDEX           { sonusTgSgTgIndex, sonusTgSgIndex }
    ::= { sonusTgSgTable 1 }

SonusTgSgEntry ::=
    SEQUENCE {
        sonusTgSgTgIndex                Integer32,
        sonusTgSgIndex                  Integer32,
        sonusTgSgName                   DisplayString,
        sonusTgSgType                   INTEGER
    }

sonusTgSgTgIndex OBJECT-TYPE
    SYNTAX          Integer32
    MAX-ACCESS      read-only
    STATUS          current
    DESCRIPTION     
            "The Trunk Group index that has the following set of Service Groups."
    ::= { sonusTgSgEntry 1 }

sonusTgSgIndex OBJECT-TYPE
    SYNTAX          Integer32
    MAX-ACCESS      read-only
    STATUS          current
    DESCRIPTION     
            "A unique value for each service group in this trunk group"
    ::= { sonusTgSgEntry 2 }

sonusTgSgName OBJECT-TYPE
    SYNTAX          DisplayString (SIZE(0..23))
    MAX-ACCESS      read-only
    STATUS          current
    DESCRIPTION     
            "The name of the service group."
    ::= { sonusTgSgEntry 3 }

sonusTgSgType OBJECT-TYPE
    SYNTAX          INTEGER { ss7(1), cas(2), isdn(3), h323(4), 
                        gateway(5), dedicated(6), twostagedial(7), 
                        ras(8) }
    MAX-ACCESS      read-only
    STATUS          current
    DESCRIPTION     
            "The type of the service group."
    ::= { sonusTgSgEntry 4 }

sonusTgProfileObjects OBJECT IDENTIFIER
    ::= { sonusTrunkObjects 5 }

sonusTgProfileNextIndex OBJECT-TYPE
    SYNTAX          Integer32
    MAX-ACCESS      read-only
    STATUS          current
    DESCRIPTION     
            "The next valid index to use when creating a new sonusTgProfileEntry"
    ::= { sonusTgProfileObjects 5 }

sonusTgProfileTable OBJECT-TYPE
    SYNTAX          SEQUENCE OF SonusTgProfileEntry
    MAX-ACCESS      not-accessible
    STATUS          current
    DESCRIPTION     
            "A list of trunk group entries."
    ::= { sonusTgProfileObjects 6 }

sonusTgProfileEntry OBJECT-TYPE
    SYNTAX          SonusTgProfileEntry
    MAX-ACCESS      not-accessible
    STATUS          current
    DESCRIPTION     
            "Each sonusTgProfileEntry containing configuration objects.
             Rules & Behaviors:
                  A sonusTgProfileEntry cannot be deleted when it is enabled.
                  When disabling the trunk group entry, it must not have 
                  any associated SGs.  All SGs must be removed before
                  disabling the trunk group.
                  A sonusTgProfileEntry cannot be modified when it is enabled."
    INDEX           { sonusTgProfileIndex }
    ::= { sonusTgProfileTable 1 }

SonusTgProfileEntry ::=
    SEQUENCE {
        sonusTgProfileIndex             Integer32,
        sonusTgProfileName              SonusName,
        sonusTgProfileSgSelect          INTEGER,
        sonusTgProfileAdminState        INTEGER,
        sonusTgProfileInboundReserved   Integer32,
        sonusTgProfileLnpTranslate      SonusBoolean,
        sonusTgProfile800Translate      SonusBoolean,
        sonusTgProfileCallingNumVerify  SonusBoolean,
        sonusTgProfileIsupOnly          SonusBoolean,
        sonusTgProfileCarrier           DisplayString,
        sonusTgProfileIsupNode          DisplayString,
        sonusTgProfSgSelectState        INTEGER,
        sonusTgProfInboundReservedState INTEGER,
        sonusTgProfLnpTranslateState    INTEGER,
        sonusTgProf800TranslateState    INTEGER,
        sonusTgProfCallingNumVerifyState INTEGER,
        sonusTgProfIsupOnlyState        INTEGER,
        sonusTgProfCarrierState         INTEGER,
        sonusTgProfIsupNodeState        INTEGER,
        sonusTgProfileRowStatus         RowStatus
    }

sonusTgProfileIndex OBJECT-TYPE
    SYNTAX          Integer32
    MAX-ACCESS      read-only
    STATUS          current
    DESCRIPTION     
            "A unique value for each trunk group profile that is between 1
             and maximum allowed"
    ::= { sonusTgProfileEntry 1 }

sonusTgProfileName OBJECT-TYPE
    SYNTAX          SonusName
    MAX-ACCESS      read-write
    STATUS          current
    DESCRIPTION     
            "The name of this trunk group Profile."
    ::= { sonusTgProfileEntry 2 }

sonusTgProfileSgSelect OBJECT-TYPE
    SYNTAX          INTEGER { leastcost(1), configured(2), 
                        circularforward(3), circularbackward(4) }
    MAX-ACCESS      read-write
    STATUS          current
    DESCRIPTION     
            "Selection for hunting within a PSTN trunk group that has 
             more than 1 associated service group(SG).
             It is based on cost associated with each SG,
             how the SG is ordered during configuration (for circular also).
             		 If either circular option is chosen, then SG hunt algorithm
             		 is ignored."
    ::= { sonusTgProfileEntry 3 }

sonusTgProfileAdminState OBJECT-TYPE
    SYNTAX          INTEGER { disabled(1), enabled(2) }
    MAX-ACCESS      read-write
    STATUS          current
    DESCRIPTION     
            "Administrator state to use a trunk group Profile. All trunk
             group profiles are created with its state disabled.  When 
             disabled, the profile must be enabled to allowed to be used."
    DEFVAL          { disabled }
    ::= { sonusTgProfileEntry 4 }

sonusTgProfileInboundReserved OBJECT-TYPE
    SYNTAX          Integer32 (0..100)
    MAX-ACCESS      read-write
    STATUS          current
    DESCRIPTION     
            "This is only meaninful for PSTN Trunk Groups.  This the
             percent of channels reserved for handling inbound calls.
             Default is 0% and valid for both direction type trunks.
             The amount reserved is round off to next number. For
             example, 50% of 23 hannels is 12.5 or 13 channels.  
             Percentage selection allowed in 5% increments."
    ::= { sonusTgProfileEntry 5 }

sonusTgProfileLnpTranslate OBJECT-TYPE
    SYNTAX          SonusBoolean
    MAX-ACCESS      read-write
    STATUS          current
    DESCRIPTION     
            "This is only meaningful for PSTN trunk groups that may require
             LNP translation for the called number."
    ::= { sonusTgProfileEntry 6 }

sonusTgProfile800Translate OBJECT-TYPE
    SYNTAX          SonusBoolean
    MAX-ACCESS      read-write
    STATUS          current
    DESCRIPTION     
            "This is only meaningful for PSTN trunk groups that may require
             800 number translation for the called number."
    ::= { sonusTgProfileEntry 7 }

sonusTgProfileCallingNumVerify OBJECT-TYPE
    SYNTAX          SonusBoolean
    MAX-ACCESS      read-write
    STATUS          current
    DESCRIPTION     
            "This is only meaningful for PSTN trunk groups that requires
             verification for the calling number."
    ::= { sonusTgProfileEntry 8 }

sonusTgProfileIsupOnly OBJECT-TYPE
    SYNTAX          SonusBoolean
    MAX-ACCESS      read-write
    STATUS          current
    DESCRIPTION     
            "This is only meaningful for PSTN trunk groups that is either an
             ISUP only or mixed of ISUP and other PSTN types"
    ::= { sonusTgProfileEntry 9 }

sonusTgProfileCarrier OBJECT-TYPE
    SYNTAX          DisplayString (SIZE(0..23))
    MAX-ACCESS      read-write
    STATUS          current
    DESCRIPTION     
            "This is only meaningful for PSTN trunk groups and is specific
             to Isup only.  This is the name of the Isup that this trunk 
             group is bound to. "
    ::= { sonusTgProfileEntry 10 }

sonusTgProfileIsupNode OBJECT-TYPE
    SYNTAX          DisplayString (SIZE(0..23))
    MAX-ACCESS      read-write
    STATUS          current
    DESCRIPTION     
            "This is only meaningful for PSTN trunk groups and is specific
             to Isup only.  This is the name of the Isup that this trunk 
             group is bound to. "
    ::= { sonusTgProfileEntry 11 }

sonusTgProfSgSelectState OBJECT-TYPE
    SYNTAX          INTEGER { disabled(1), enabled(2) }
    MAX-ACCESS      read-write
    STATUS          current
    DESCRIPTION     
            "Indicates whether sonusTgProfileSgSelect object is present in this profile"
    ::= { sonusTgProfileEntry 12 }

sonusTgProfInboundReservedState OBJECT-TYPE
    SYNTAX          INTEGER { disabled(1), enabled(2) }
    MAX-ACCESS      read-write
    STATUS          current
    DESCRIPTION     
            "Indicates whether sonusTgProfileInboundReserved object is present in this profile"
    ::= { sonusTgProfileEntry 13 }

sonusTgProfLnpTranslateState OBJECT-TYPE
    SYNTAX          INTEGER { disabled(1), enabled(2) }
    MAX-ACCESS      read-write
    STATUS          current
    DESCRIPTION     
            "Indicates whether sonusTgProfileLnpTranslate object is present in this profile"
    ::= { sonusTgProfileEntry 14 }

sonusTgProf800TranslateState OBJECT-TYPE
    SYNTAX          INTEGER { disabled(1), enabled(2) }
    MAX-ACCESS      read-write
    STATUS          current
    DESCRIPTION     
            "Indicates whether sonusTgProfile800Translate object is present in this profile"
    ::= { sonusTgProfileEntry 15 }

sonusTgProfCallingNumVerifyState OBJECT-TYPE
    SYNTAX          INTEGER { disabled(1), enabled(2) }
    MAX-ACCESS      read-write
    STATUS          current
    DESCRIPTION     
            "Indicates whether sonusTgProfileCallingNumVerify object is present in this profile"
    ::= { sonusTgProfileEntry 16 }

sonusTgProfIsupOnlyState OBJECT-TYPE
    SYNTAX          INTEGER { disabled(1), enabled(2) }
    MAX-ACCESS      read-write
    STATUS          current
    DESCRIPTION     
            "Indicates whether sonusTgProfileIsupOnly object is present in this profile"
    ::= { sonusTgProfileEntry 17 }

sonusTgProfCarrierState OBJECT-TYPE
    SYNTAX          INTEGER { disabled(1), enabled(2) }
    MAX-ACCESS      read-write
    STATUS          current
    DESCRIPTION     
            "Indicates whether sonusTgProfileCarrier object is present in this profile"
    ::= { sonusTgProfileEntry 18 }

sonusTgProfIsupNodeState OBJECT-TYPE
    SYNTAX          INTEGER { disabled(1), enabled(2) }
    MAX-ACCESS      read-write
    STATUS          current
    DESCRIPTION     
            "Indicates whether sonusTgProfileIsupNode object is present in this profile"
    ::= { sonusTgProfileEntry 19 }

sonusTgProfileRowStatus OBJECT-TYPE
    SYNTAX          RowStatus
    MAX-ACCESS      read-write
    STATUS          current
    DESCRIPTION     
            "This is for SNMP use."
    ::= { sonusTgProfileEntry 20 }

sonusGatewayObjects OBJECT IDENTIFIER
    ::= { sonusTrunkGroupResourcesMIBObjects 2 }

sonusGatewayConfigObjects OBJECT IDENTIFIER
    ::= { sonusGatewayObjects 1 }

sonusTgMaxGateways OBJECT-TYPE
    SYNTAX          Integer32 (1..500)
    MAX-ACCESS      read-write
    STATUS          current
    DESCRIPTION     
            "Maximum allowable destination or remote gateways in the configuration."
    DEFVAL          { 500 }
    ::= { sonusGatewayConfigObjects 1 }

sonusDestGatewayObjects OBJECT IDENTIFIER
    ::= { sonusGatewayObjects 2 }

sonusGatewayNextIndex OBJECT-TYPE
    SYNTAX          Integer32
    MAX-ACCESS      read-only
    STATUS          current
    DESCRIPTION     
            "The next valid index to use when creating a new sonusGatewayEntry"
    ::= { sonusDestGatewayObjects 1 }

sonusGatewayTable OBJECT-TYPE
    SYNTAX          SEQUENCE OF SonusGatewayEntry
    MAX-ACCESS      not-accessible
    STATUS          current
    DESCRIPTION     
            "This is a table containing a list of IP telephony gateways 
             in the network."
    ::= { sonusDestGatewayObjects 2 }

sonusGatewayEntry OBJECT-TYPE
    SYNTAX          SonusGatewayEntry
    MAX-ACCESS      not-accessible
    STATUS          current
    DESCRIPTION     
            "Each entry lists the name and order of each gateway."
    INDEX           { sonusGatewayIndex }
    ::= { sonusGatewayTable 1 }

SonusGatewayEntry ::=
    SEQUENCE {
        sonusGatewayIndex               Integer32,
        sonusGatewayName                SonusName,
        sonusGatewayProfName            DisplayString,
        sonusGatewayType                INTEGER,
        sonusGatewayIpAddress           IpAddress,
        sonusGatewayPortNum             Integer32,
        sonusGatewayMaxConn             Integer32,
        sonusGatewayAdminState          INTEGER,
        sonusGatewayRowStatus           RowStatus
    }

sonusGatewayIndex OBJECT-TYPE
    SYNTAX          Integer32
    MAX-ACCESS      read-only
    STATUS          current
    DESCRIPTION     
            "A unique value for each gateway between 1 and maximum 
             allowed."
    ::= { sonusGatewayEntry 1 }

sonusGatewayName OBJECT-TYPE
    SYNTAX          SonusName
    MAX-ACCESS      read-write
    STATUS          current
    DESCRIPTION     
            "The name of the IP Telephony gateway."
    ::= { sonusGatewayEntry 2 }

sonusGatewayProfName OBJECT-TYPE
    SYNTAX          DisplayString (SIZE(0..23))
    MAX-ACCESS      read-write
    STATUS          current
    DESCRIPTION     
            "The name of the profile applied to this gateway entry. "
    ::= { sonusGatewayEntry 3 }

sonusGatewayType OBJECT-TYPE
    SYNTAX          INTEGER { gsx9000(1), h323(2), sip(3) }
    MAX-ACCESS      read-write
    STATUS          current
    DESCRIPTION     
            "The type of gateway."
    DEFVAL          { gsx9000 }
    ::= { sonusGatewayEntry 4 }

sonusGatewayIpAddress OBJECT-TYPE
    SYNTAX          IpAddress
    MAX-ACCESS      read-write
    STATUS          current
    DESCRIPTION     
            "This is signaling Ip address of the gateway."
    ::= { sonusGatewayEntry 5 }

sonusGatewayPortNum OBJECT-TYPE
    SYNTAX          Integer32 (1..65535)
    MAX-ACCESS      read-write
    STATUS          current
    DESCRIPTION     
            "This is the port number assigned for the signaling Ip address
             of the gateway (default is Sonus registered port 2569)."
    ::= { sonusGatewayEntry 6 }

sonusGatewayMaxConn OBJECT-TYPE
    SYNTAX          Integer32 (1..20000)
    MAX-ACCESS      read-write
    STATUS          current
    DESCRIPTION     
            "This is the maximum connections allowed for this gateway to 
             the remote gateway specified by the sonusGatewayName."
    DEFVAL          { 20000 }
    ::= { sonusGatewayEntry 7 }

sonusGatewayAdminState OBJECT-TYPE
    SYNTAX          INTEGER { disabled(1), enabled(2) }
    MAX-ACCESS      read-write
    STATUS          current
    DESCRIPTION     
            "Allow administrator to disable or enable the connection from 
             this gateway to the remote gateway. All connections to the
             remote gateways are created with its state disabled.  Once 
             disabled, the gateway must be enabled to allow calls to 
             proceed again."
    DEFVAL          { disabled }
    ::= { sonusGatewayEntry 8 }

sonusGatewayRowStatus OBJECT-TYPE
    SYNTAX          RowStatus
    MAX-ACCESS      read-write
    STATUS          current
    DESCRIPTION     
            "This is for SNMP use."
    ::= { sonusGatewayEntry 9 }

sonusDestGatewayStatusObjects OBJECT IDENTIFIER
    ::= { sonusGatewayObjects 3 }

sonusGwStatusTable OBJECT-TYPE
    SYNTAX          SEQUENCE OF SonusGwStatusEntry
    MAX-ACCESS      not-accessible
    STATUS          current
    DESCRIPTION     
            "This is a table containing a list of IP telephony gateways 
             in the network."
    ::= { sonusDestGatewayStatusObjects 3 }

sonusGwStatusEntry OBJECT-TYPE
    SYNTAX          SonusGwStatusEntry
    MAX-ACCESS      not-accessible
    STATUS          current
    DESCRIPTION     
            "Each entry lists the current connections and order of each gateway."
    INDEX           { sonusGwStatusIndex }
    ::= { sonusGwStatusTable 1 }

SonusGwStatusEntry ::=
    SEQUENCE {
        sonusGwStatusIndex              Integer32,
        sonusGwCurrConnections          Integer32
    }

sonusGwStatusIndex OBJECT-TYPE
    SYNTAX          Integer32
    MAX-ACCESS      read-only
    STATUS          current
    DESCRIPTION     
            "A unique value for each gateway between 1 and maximum 
             allowed."
    ::= { sonusGwStatusEntry 1 }

sonusGwCurrConnections OBJECT-TYPE
    SYNTAX          Integer32
    MAX-ACCESS      read-only
    STATUS          current
    DESCRIPTION     
            "The Current number of connections between this gateway and
             the remote gateway."
    ::= { sonusGwStatusEntry 2 }

sonusCarrierObjects OBJECT IDENTIFIER
    ::= { sonusTrunkGroupResourcesMIBObjects 3 }

sonusCarrierConfigObjects OBJECT IDENTIFIER
    ::= { sonusCarrierObjects 1 }

sonusTgMaxCarrierCodes OBJECT-TYPE
    SYNTAX          Integer32 (1..65535)
    MAX-ACCESS      read-write
    STATUS          current
    DESCRIPTION     
            "Maximum number of Carrier Codes for this gateway."
    DEFVAL          { 500 }
    ::= { sonusCarrierConfigObjects 1 }

sonusCarrierCodeObjects OBJECT IDENTIFIER
    ::= { sonusCarrierObjects 2 }

sonusCarrierCodeNextIndex OBJECT-TYPE
    SYNTAX          Integer32
    MAX-ACCESS      read-only
    STATUS          current
    DESCRIPTION     
            "The next valid index to use when creating a new sonusCarrierCodeEntry"
    ::= { sonusCarrierCodeObjects 1 }

sonusCarrierCodeTable OBJECT-TYPE
    SYNTAX          SEQUENCE OF SonusCarrierCodeEntry
    MAX-ACCESS      not-accessible
    STATUS          current
    DESCRIPTION     
            "This is a table containing a list of IP telephony gateways 
             in the network."
    ::= { sonusCarrierCodeObjects 2 }

sonusCarrierCodeEntry OBJECT-TYPE
    SYNTAX          SonusCarrierCodeEntry
    MAX-ACCESS      not-accessible
    STATUS          current
    DESCRIPTION     
            "Each entry lists the name and order of each gateway."
    INDEX           { sonusCarrierCodeIndex }
    ::= { sonusCarrierCodeTable 1 }

SonusCarrierCodeEntry ::=
    SEQUENCE {
        sonusCarrierCodeIndex           Integer32,
        sonusCarrierCodeName            SonusName,
        sonusCarrierCode                DisplayString,
        sonusCarrierCodeAdminState      INTEGER,
        sonusCarrierCodeRowStatus       RowStatus,
        sonusCarrierCodeNetworkIdType   INTEGER,
        sonusCarrierCodeNetworkIdPlan   INTEGER
    }

sonusCarrierCodeIndex OBJECT-TYPE
    SYNTAX          Integer32
    MAX-ACCESS      read-only
    STATUS          current
    DESCRIPTION     
            "A unique value for each carrier code between 1 and maximum 
             allowed."
    ::= { sonusCarrierCodeEntry 1 }

sonusCarrierCodeName OBJECT-TYPE
    SYNTAX          SonusName
    MAX-ACCESS      read-write
    STATUS          current
    DESCRIPTION     
            "The name assigned to this carrier code."
    ::= { sonusCarrierCodeEntry 2 }

sonusCarrierCode OBJECT-TYPE
    SYNTAX          DisplayString (SIZE(1..4))
    MAX-ACCESS      read-write
    STATUS          current
    DESCRIPTION     
            "This is the carrier code specified by the sonusCarrierCodeName.
             There are a maximum of up to 4 digits."
    ::= { sonusCarrierCodeEntry 3 }

sonusCarrierCodeAdminState OBJECT-TYPE
    SYNTAX          INTEGER { disabled(1), enabled(2) }
    MAX-ACCESS      read-write
    STATUS          current
    DESCRIPTION     
            "Allow administrator to disable or enable this carrier code.  Once 
             disabled, this carrier code must be enabled to allow calls to 
             proceed again."
    DEFVAL          { disabled }
    ::= { sonusCarrierCodeEntry 4 }

sonusCarrierCodeRowStatus OBJECT-TYPE
    SYNTAX          RowStatus
    MAX-ACCESS      read-write
    STATUS          current
    DESCRIPTION     
            "This is for SNMP use."
    ::= { sonusCarrierCodeEntry 5 }

sonusCarrierCodeNetworkIdType OBJECT-TYPE
    SYNTAX          INTEGER { ccitt(1), national(2), other(3) }
    MAX-ACCESS      read-write
    STATUS          current
    DESCRIPTION     
            "The type of network identification for this carrier code"
    DEFVAL          { national }
    ::= { sonusCarrierCodeEntry 6 }

sonusCarrierCodeNetworkIdPlan OBJECT-TYPE
    SYNTAX          INTEGER { ccittunknown(1), ccittpublicdatanetwork(2), 
                        ccittlandmobilenetwork(3), ccittreserved1(4), 
                        ccittreserved2(5), nationalunknown(6), 
                        national3digitcarriercode(7), 
                        national4digitcarriercode(8), 
                        nationalreserved1(9), nationalreserved2(10) }
    MAX-ACCESS      read-write
    STATUS          current
    DESCRIPTION     
            "The network identification plan for this carrier code"
    DEFVAL          { national4digitcarriercode }
    ::= { sonusCarrierCodeEntry 7 }

sonusTrunkGroupResourcesMIBNotifications OBJECT IDENTIFIER
    ::= { sonusTrunkGroupResourcesMIB 2 }

sonusTrunkGroupResourcesMIBNotificationsPrefix OBJECT IDENTIFIER
    ::= { sonusTrunkGroupResourcesMIBNotifications 0 }

sonusTrunkGroupResourcesMIBNotificationsObjects OBJECT IDENTIFIER
    ::= { sonusTrunkGroupResourcesMIBNotifications 1 }

sonusTrunkOutOfServiceReason OBJECT-TYPE
    SYNTAX          INTEGER { configured(1), allResourcesBlocked(2) }
    MAX-ACCESS      read-only
    STATUS          current
    DESCRIPTION     
            "The reason why the Trunk Group is out of service."
    ::= { sonusTrunkGroupResourcesMIBNotificationsObjects 1 }

sonusTrunkEnabledNotification NOTIFICATION-TYPE
    OBJECTS         { sonusTgName, sonusEventDescription, 
                      sonusEventClass, sonusEventLevel }
    STATUS          current
    DESCRIPTION     
            "This trap indicates a Trunk Group is now enabled."
    ::= { sonusTrunkGroupResourcesMIBNotificationsPrefix 1 }

sonusTrunkDisabledNotification NOTIFICATION-TYPE
    OBJECTS         { sonusTgName, sonusEventDescription, 
                      sonusEventClass, sonusEventLevel }
    STATUS          current
    DESCRIPTION     
            "This trap indicates a Trunk Group is now disabled."
    ::= { sonusTrunkGroupResourcesMIBNotificationsPrefix 2 }

sonusTrunkInServiceNotification NOTIFICATION-TYPE
    OBJECTS         { sonusTgName, sonusEventDescription, 
                      sonusEventClass, sonusEventLevel }
    STATUS          current
    DESCRIPTION     
            "This trap indicates a Trunk Group is now in service."
    ::= { sonusTrunkGroupResourcesMIBNotificationsPrefix 3 }

sonusTrunkOutOfServiceNotification NOTIFICATION-TYPE
    OBJECTS         { sonusTgName, sonusTrunkOutOfServiceReason, 
                      sonusEventDescription, sonusEventClass, 
                      sonusEventLevel }
    STATUS          current
    DESCRIPTION     
            "This trap indicates that a Trunk Group is out of service."
    ::= { sonusTrunkGroupResourcesMIBNotificationsPrefix 4 }

sonusTrunkDeletedNotification NOTIFICATION-TYPE
    OBJECTS         { sonusTgName, sonusEventDescription, 
                      sonusEventClass, sonusEventLevel }
    STATUS          current
    DESCRIPTION     
            "This trap indicates a Trunk Group is now deleted."
    ::= { sonusTrunkGroupResourcesMIBNotificationsPrefix 5 }

END -- end of module SONUS-TRUNK-GROUP-RESOURCES-MIB.
