-- 
-- Copyright 1999 by Fore Systems, Inc. 
-- Converted to SMIv2 rfc 2578,2579,2580 - STD 58
--
-- Copyright 1999 by Fore Systems Inc.
-- All Rights Reserved
--
-- This mib implements extensions to the standard DS3
-- mib to support extra configuration, statistics,
-- and diagnostic capabilities of Fore Systems
-- equipment.

Fore-DSX3-Ext-MIB DEFINITIONS ::= BEGIN

IMPORTS
         Counter32,
         Integer32,
	 OBJECT-TYPE,
	 MODULE-IDENTITY,
         NOTIFICATION-TYPE  FROM       SNMPv2-SMI
	 asx		    FROM       Fore-Common-MIB
	 trapLogIndex	    FROM       Fore-TrapLog-MIB
	 ifName		    FROM       IF-MIB
	 dsx3LineIndex	    FROM       DS3-MIB;

foreDsx3Mib MODULE-IDENTITY
          LAST-UPDATED         "9911050000Z"
          ORGANIZATION         "FORE"
          CONTACT-INFO         
              "      Postal:   FORE Systems Inc.
                               1000 FORE Drive
                               Warrendale, PA 15086-7502
                     Tel:      +1 724 742 6900
                     Email:    nm_mibs@fore.com
                     Web:      http://www.fore.com"
          DESCRIPTION
           "This mib module implements extensions to the standard DS3
	    mib to support extra configuration, statistics, and
            diagnostic capabilities of Fore Systems equipment."
    ::= { asx 15 }

-- Fore DS3 Configuration Table

foreDsx3ConfigTable OBJECT-TYPE
	SYNTAX SEQUENCE OF ForeDsx3ConfigEntry
	MAX-ACCESS not-accessible
	STATUS current
	DESCRIPTION
		"A table of configuration options, statistics, and
		 diagnostics supported by DS3 interfaces on
		 Fore Systems ATM Switches."
	::= { foreDsx3Mib 1 }

foreDsx3ConfigEntry OBJECT-TYPE
	SYNTAX	ForeDsx3ConfigEntry
	MAX-ACCESS	not-accessible
	STATUS	current
	DESCRIPTION
		"A table entry containing Fore specific extensions
		 to the standard DS3 MIB tables."
	INDEX   { dsx3LineIndex }
	::= { foreDsx3ConfigTable 1 }

ForeDsx3ConfigEntry ::= 
	SEQUENCE {
		foreDsx3ConfigReceiveCode	INTEGER,
		foreDsx3ConfigLineLength	INTEGER,
	        foreDsx3ConfigStatus            Integer32,
		foreDsx3LineTypeFraming		INTEGER,
		foreDsx3PbitPerrThrSeconds	Integer32,
		foreDsx3PbitPerrThrErrors	Integer32,
		foreDsx3PbitPerrFailEnable	INTEGER,
		foreDsx3SignalDegradeBer	Integer32,
		foreDsx3SignalFailBer		Integer32,
		foreDsx3BerErrorModel		INTEGER,
		foreDsx3BerState		INTEGER
	}

foreDsx3ConfigReceiveCode OBJECT-TYPE
	SYNTAX	INTEGER {
		ds3ReceiveNoCode (1),
		ds3ReceiveLineCode (2),
		ds3ReceivePayloadCode (3),
		ds3ReceiveResetCode (4),
		ds3ReceiveDS1LoopCode (5),
		ds3ReceiveTestPattern (6)
		}
	MAX-ACCESS	read-only
	STATUS	current
	DESCRIPTION
		"This variable indicates the type of code that was received
		across the DS3/E3 interface.

		The values mean:
		ds3ReceiveNoCode	receiving looped or normal data
		ds3ReceiveLineCode      receiving request for a line loopback
		ds3ReceivePayloadCode   receiving a request for a payload loopback
					 (i.e. all DS1/E1 in a DS3/E3 frame)
		ds3ReceiveResetCode     receiving a loopback deactivation request
		ds3ReceiveDS1LoopCode   receiving a request to loopback a particular
					DS1/E1 within a DS3/E3 frame
		ds3ReceiveTestPattern   receiving a test pattern."
	DEFVAL	{ ds3ReceiveNoCode }
	::= { foreDsx3ConfigEntry  1}

foreDsx3ConfigLineLength OBJECT-TYPE
	SYNTAX	INTEGER {
		ds3LineLt225 (1),
		ds3LineGt225 (2)
		}
	MAX-ACCESS	read-write
	STATUS	current
	DESCRIPTION
		"This variable represents the length of the physical cable
		connected to the ds3 port. The user has to set this object to
		match the physical cable in order to get the netmod to receive
		the signal on the cable. The different values are: ds3LineLt225
		(1) means the line is shorter than 225 ft, ds1LineGt225 (2)
		means the line length is greater than 220 ft. This value is not
		settable for Series A netmods and the value for these netmods
		is Gt225"
	DEFVAL	{ ds3LineGt225 }
	::= { foreDsx3ConfigEntry 2 }

foreDsx3ConfigStatus OBJECT-TYPE
	SYNTAX  Integer32 
	MAX-ACCESS	read-only
	STATUS	current
	DESCRIPTION
		"This variable represents the current status of the Dsx3
		 interface.  This variable is a bit map represented as
	         a sum.

		 The various bit positions are:

		   1 dsx3NoDefect        True if no other defects are present
		   2 dsx3RxFERF          Receiving a Far End Receive Failure
		   4 dsx3TxFERF          Sending a Far End Receive Failure
                   8 dsx3RxAIS           Receiving Alarm Indication
                  16 dsx3TxAIS           Transmitting Alarm Indication
                  32 dsx3LOF             Loss Of Frame
                  64 dsx3LOS             Loss Of Signal
                 128 dsx3Loopback        Remotly Initiatiated Loopback Operational
                 256 dsx3RxTest          Receiving Test Pattern
                 512 dsx3Other           Other, non specific falure."
        DEFVAL { 1 }
        ::= { foreDsx3ConfigEntry 3 }

foreDsx3LineTypeFraming OBJECT-TYPE
	SYNTAX	INTEGER {
		e3G751 (1),
		e3G832 (2)
		}
	MAX-ACCESS	read-only
	STATUS	current
	DESCRIPTION
		"This variable extends the 'dsx3LineType' variable from
		rfc1407. When dsx3LineType == e3Framed, this variable
		determines whether G.751 or G.832 framing is used.
		When dsx3LineType == e3Plcp, the value of this variable
		will be 1, indicating G.751 framing."
	DEFVAL	{ e3G832 }
	::= { foreDsx3ConfigEntry  4}

foreDsx3PbitPerrThrSeconds OBJECT-TYPE
	SYNTAX	Integer32
	MAX-ACCESS	read-write
	STATUS	current
	DESCRIPTION
		"This variable represents the consecutive number of
		 BAD/GOOD seconds to detect/clear an Excessive P-bit
		 Parity Error Defect. The range of values it can take
		 is between 2 and 10 inclusive."
	DEFVAL { 10 }
	::= { foreDsx3ConfigEntry 5 }

foreDsx3PbitPerrThrErrors OBJECT-TYPE
	SYNTAX	Integer32
	MAX-ACCESS	read-write
	STATUS	current
	DESCRIPTION
		"This variable is a threshold for the number of P-bit
		 Parity Errors per second and is used as a parameter to
		 the Excessive P-bit Parity Error Defect.  If the number
		 of errors exceeds the threshold, the particular second is
		 declared BAD, otherwise it is declared GOOD."
	::= { foreDsx3ConfigEntry 6 }

foreDsx3PbitPerrFailEnable OBJECT-TYPE
	SYNTAX	INTEGER {
		enabled(1),
		disabled(2)
		}
	MAX-ACCESS	read-write
	STATUS	current
	DESCRIPTION
		"This variable controls whether declaration of an
		 Excessive P-bit Parity Error Defect forces the port's
		 operState to Down."
	::= { foreDsx3ConfigEntry 7 }

foreDsx3SignalDegradeBer OBJECT-TYPE
	SYNTAX  Integer32
	MAX-ACCESS  read-write
	STATUS  current
	DESCRIPTION
		"This is the exponent of 10 for the current signal
		 degrade bit error rate (BER) threshold for this port.
		 The value -7, for example, represents a BER of 1E-7.
		 This variable is only applicable when dsx3BerErrorModel
		 is set to errorModelRandom."
	::= { foreDsx3ConfigEntry 8 }

foreDsx3SignalFailBer OBJECT-TYPE
	SYNTAX  Integer32
	MAX-ACCESS  read-write
	STATUS  current
	DESCRIPTION
		"This is the exponent of 10 for the current signal
		 fail bit error rate (BER) threshold for this port.
		 The value -4, for example, represents a BER of 1E-4.
		 This variable is only applicable when dsx3BerErrorModel
		 is set to errorModelRandom."
	::= { foreDsx3ConfigEntry 9 }


foreDsx3BerErrorModel OBJECT-TYPE
	SYNTAX  INTEGER {
		errorModelNone(0),
		errorModelRandom(1),
		errorModelBurst(2)
		}
	MAX-ACCESS read-write
	STATUS	current
	DESCRIPTION
		"This is the error distribution model to be used to
		 identify signal degrade and signal fail conditions.
		 errorModelRandom selects a random error distribution
		 and declares signal conditions based on the thresholds
		 set in dsx3SignalDegradeBer and dsx3SignalFailBer.
		 errorModelBurst selects a burst error model and declares
		 signal degrade conditions based on the thresholds set in
		 dsx3BipThrSeconds and dsx3BipThrErrors. errorModelNone
		 disables detection of signal conditions."
	DEFVAL	{ errorModelRandom }
	::= { foreDsx3ConfigEntry 10 }

foreDsx3BerState OBJECT-TYPE
	SYNTAX	INTEGER {
		berStateOk(0),
		berStateSigDegrade(1),
		berStateSigFail(2)
		}
	MAX-ACCESS read-only
	STATUS	current
	DESCRIPTION
		"This value describes the current state of the port as 
		 determined through bit error rate analysis."
	::= { foreDsx3ConfigEntry 11 }

------------------------------------------------------------------------
-- Fore DS3 Total Table

foreDsx3TotalTable OBJECT-TYPE
	SYNTAX SEQUENCE OF ForeDsx3TotalEntry
	MAX-ACCESS not-accessible
	STATUS current
	DESCRIPTION
		"A table of statistics, supported by DS3 interfaces on
		 Fore Systems Equipment."
	::= { foreDsx3Mib 2 }

foreDsx3TotalEntry OBJECT-TYPE
	SYNTAX	ForeDsx3TotalEntry
	MAX-ACCESS	not-accessible
	STATUS	current
	DESCRIPTION
		"A table entry containing Fore specific extensions
		 to the standard DS3 MIB tables."
	INDEX   { dsx3LineIndex }
	::= { foreDsx3TotalTable 1 }

ForeDsx3TotalEntry ::= 
	SEQUENCE {
		foreDsx3TotalFramingLOSs		Counter32,
		foreDsx3TotalFramingLCVs		Counter32,
		foreDsx3TotalFramingSumLCVs		Counter32,
		foreDsx3TotalFramingFERRs		Counter32,
		foreDsx3TotalFramingOOFs		Counter32,
		foreDsx3TotalFramingFERFs		Counter32,
		foreDsx3TotalFramingAISs		Counter32,
		foreDsx3TotalFramingPbitPERRs		Counter32,
		foreDsx3TotalFramingCbitPERRs		Counter32,
		foreDsx3TotalFramingFEBEs		Counter32,
		foreDsx3TotalFramingIDLEs		Counter32
	}

foreDsx3TotalFramingLOSs OBJECT-TYPE
	SYNTAX	Counter32
	MAX-ACCESS	read-only
	STATUS	current
	DESCRIPTION
		"The number of seconds in which Loss Of Signal (LOS) errors
		were detected by the DS3 Receive Framer block."
	::= { foreDsx3TotalEntry 1 }

foreDsx3TotalFramingLCVs OBJECT-TYPE
	SYNTAX	Counter32
	MAX-ACCESS	read-only
	STATUS	current
	DESCRIPTION
		"The number of Line Code Violations (LCV) that were detected by
		the DS3 Receive Framer block."
	::= { foreDsx3TotalEntry 2 }

foreDsx3TotalFramingSumLCVs OBJECT-TYPE
	SYNTAX	Counter32
	MAX-ACCESS	read-only
	STATUS	current
	DESCRIPTION
		"The number of DS3 information blocks (85 bits) which contain
		one or more Line Code Violations (LCV)."
	::= { foreDsx3TotalEntry 3 }

foreDsx3TotalFramingFERRs OBJECT-TYPE
	SYNTAX	Counter32
	MAX-ACCESS	read-only
	STATUS	current
	DESCRIPTION
		"Number of DS3 framing error (FERR) events."
	::= { foreDsx3TotalEntry 4 }

foreDsx3TotalFramingOOFs OBJECT-TYPE
	SYNTAX	Counter32
	MAX-ACCESS	read-only
	STATUS	current
	DESCRIPTION
		"Number of seconds DS3 Out Of Frame (OOF) error events were
		experienced."
	::= { foreDsx3TotalEntry  5 }

foreDsx3TotalFramingFERFs OBJECT-TYPE
	SYNTAX	Counter32
	MAX-ACCESS	read-only
	STATUS	current
	DESCRIPTION
		"The number of seconds in which Far End Receive Failure (FERF)
		state has been detected by the DS3 Receive Framer block. FERF
		signal alerts the upstream terminal that a failure has been
		detected along the downstream line."
	::= { foreDsx3TotalEntry 6}

foreDsx3TotalFramingAISs OBJECT-TYPE
	SYNTAX	Counter32
	MAX-ACCESS	read-only
	STATUS	current
	DESCRIPTION
		"The number of seconds in which Alarm Indication Signals (AIS)
		were detected by the DS3 Receive Framer block. AIS indicates
		that an upstream failure has been detected by the far end."
	::= { foreDsx3TotalEntry 7 }

foreDsx3TotalFramingPbitPERRs OBJECT-TYPE
	SYNTAX	Counter32
	MAX-ACCESS	read-only
	STATUS	current
	DESCRIPTION
		"Number of P-bit parity error (PERR) events or the 
		 number of BIP-8 errors in case of E3 G.832."
	::= { foreDsx3TotalEntry 8 }

foreDsx3TotalFramingCbitPERRs OBJECT-TYPE
	SYNTAX	Counter32
	MAX-ACCESS	read-only
	STATUS	current
	DESCRIPTION
		"Number of C-bit parity error (PERR) events."
	::= { foreDsx3TotalEntry 9 }

foreDsx3TotalFramingFEBEs OBJECT-TYPE
	SYNTAX	Counter32
	MAX-ACCESS	read-only
	STATUS	current
	DESCRIPTION
		"Number of DS3 far end block error (FEBE) events."
	::= { foreDsx3TotalEntry 10 }

foreDsx3TotalFramingIDLEs OBJECT-TYPE
	SYNTAX  Counter32
	MAX-ACCESS  read-only
	STATUS  current
	DESCRIPTION
		"The number of seconds in which IDLE signal
		was detected by the DS3 Receive Framer block."
	::= { foreDsx3TotalEntry 11 }


-- Fore DS3 Diagnostics Table

--foreDsx3DiagnosticsTable OBJECT-TYPE
--	SYNTAX SEQUENCE OF ForeDsx3DiagnosticsEntry
--	MAX-ACCESS not-accessible
--	STATUS current
--	DESCRIPTION
--		"A table of Diagnostics, supported by DS3 interfaces on
--		 Fore Systems Equipment."
--	::= { foreDsx3Mib 3 }

--foreDsx3DiagnosticsEntry OBJECT-TYPE
--	SYNTAX	foreDsx3DiagnosticsEntry
--	ACCESS	not-accessible
--	STATUS	mandatory
--	DESCRIPTION
--		"A table entry containing Fore specific extensions
--		 to the standard DS3 MIB tables."
--	INDEX   { ifIndex }
--	::= { foreDsx3DiagnosticsTable 1 }

--ForeDsx3DiagnosticsEntry ::= 
--	SEQUENCE {
--	}
	
-- Trap Section
--

foreDsx3LOFDetected NOTIFICATION-TYPE
	OBJECTS { dsx3LineIndex, ifName, trapLogIndex }
	STATUS      current
	DESCRIPTION
		"This trap indicates that Loss Of Frame(LOF) is detected on
		the incoming signal."
	::= { foreDsx3Mib 0 1 }

foreDsx3LOFCleared NOTIFICATION-TYPE
	OBJECTS { dsx3LineIndex, ifName, trapLogIndex }
	STATUS      current
	DESCRIPTION
		"This trap indicates that Loss Of Frame is cleared on
		the incoming signal."
	::= { foreDsx3Mib 0 2 }

foreDsx3AISDetected NOTIFICATION-TYPE
	OBJECTS { dsx3LineIndex, ifName, trapLogIndex }
	STATUS      current
	DESCRIPTION
		"This trap indicates that AIS Alarm is detected on
		the incoming signal."
	::= { foreDsx3Mib 0 3 }

foreDsx3AISCleared NOTIFICATION-TYPE
	OBJECTS { dsx3LineIndex, ifName, trapLogIndex }
	STATUS      current
	DESCRIPTION
		"This trap indicates that AIS Alarm is cleared on
		the incoming signal."
	::= { foreDsx3Mib 0 4 }

foreDsx3FERFDetected NOTIFICATION-TYPE
	OBJECTS { dsx3LineIndex, ifName, trapLogIndex }
	STATUS      current
	DESCRIPTION
		"This trap indicates that FERF Alarm or DS3 Yellow Alarm
		is detected on the incoming signal."
	::= { foreDsx3Mib 0 5 }

foreDsx3FERFCleared NOTIFICATION-TYPE
	OBJECTS { dsx3LineIndex, ifName, trapLogIndex }
	STATUS      current
	DESCRIPTION
		"This trap indicates that FERF Alarm or DS3 Yellow Alarm
		is cleared on the incoming signal."
	::= { foreDsx3Mib 0 6 }

foreDsx3LOSDetected NOTIFICATION-TYPE
	OBJECTS { dsx3LineIndex, ifName, trapLogIndex }
	STATUS      current
	DESCRIPTION
		"This trap indicates that the specified DS3 port has
		detected incoming LOS Alarm."
	::= { foreDsx3Mib 0 7 }

foreDsx3LOSCleared NOTIFICATION-TYPE
	OBJECTS { dsx3LineIndex, ifName, trapLogIndex }
	STATUS      current
	DESCRIPTION
		"This trap indicates that the incoming LOS Alarm has been
		cleared on the specified DS3 port."
	::= { foreDsx3Mib 0 8 }

foreDsx3IdleDetected NOTIFICATION-TYPE
	OBJECTS { dsx3LineIndex, ifName, trapLogIndex }
	STATUS      current
	DESCRIPTION
		"This trap indicates that an Idle Maintenance Signal
		(IDLE) is detected on the incoming signal."
	::= { foreDsx3Mib 0 9 }

foreDsx3IdleCleared NOTIFICATION-TYPE
	OBJECTS { dsx3LineIndex, ifName, trapLogIndex }
	STATUS      current
	DESCRIPTION
		"This trap indicates that an Idle Maintenance Signal
		(IDLE) is cleared on the incoming signal."
	::= { foreDsx3Mib 0 10 }

foreDsx3TrailChangeDetected NOTIFICATION-TYPE
	OBJECTS { dsx3LineIndex, ifName, trapLogIndex }
	STATUS      current
	DESCRIPTION
		"This trap indicates that a Trail Trace Mismatch
		was detected on the incoming signal."
	::= { foreDsx3Mib 0 11 }

foreDsx3PbitPerrDetected NOTIFICATION-TYPE
	OBJECTS { dsx3LineIndex, ifName, trapLogIndex }
	STATUS      current
	DESCRIPTION
		"This trap indicates that the specified DSX3 port is
		 experiencing P-bit Parity errors. A P-bit Parity Error
		 failure is declared when the P-bit Parity Error
		 persists for a period of 2.5 +/- 0.5 seconds."	
	::= { foreDsx3Mib 0 12 }

foreDsx3PbitPerrCleared NOTIFICATION-TYPE
	OBJECTS { dsx3LineIndex, ifName, trapLogIndex }
	STATUS      current
	DESCRIPTION
		"This trap indicates that the P-bit Parity Error failure
		 identified by trap asxDS3PbitPerrDetected has been cleared.
		 A P-bit Parity Error failure is cleared when the P-bit Parity
		 Error defect is absent for 10 +/- 0.5 seconds."
	::= { foreDsx3Mib 0 13 }


END
