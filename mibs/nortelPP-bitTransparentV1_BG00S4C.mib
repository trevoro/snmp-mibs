Nortel-Magellan-Passport-BitTransparentMIB
DEFINITIONS ::= BEGIN



IMPORTS

      OBJECT-TYPE
   FROM RFC-1212

      components,
      passportMIBs
   FROM Nortel-Magellan-Passport-UsefulDefinitionsMIB

      Counter32,
      DisplayString,
      StorageType,
      RowStatus,
      PassportCounter64,
      InterfaceIndex,
      Gauge32,
      Integer32,
      Unsigned32
   FROM Nortel-Magellan-Passport-StandardTextualConventionsMIB

      AsciiString,
      Hex,
      NonReplicated,
      EnterpriseDateAndTime,
      Link
   FROM Nortel-Magellan-Passport-TextualConventionsMIB;




-- LAST-UPDATED   "9905250000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     BitTransparent Enterprise MIB."

bitTransparentMIB OBJECT IDENTIFIER ::= { passportMIBs 46 }










-- BitTransparentDataService/n
-- The BitTransparentDataService component defines an instance of 
-- the Bit transparent data service offered by Magellan Passport. 
-- One instance of this component is required by each DS1, E1, V35 or 
-- V11 channel which is offering bit transparent traffic.
-- The instance number is arbitrary.

btds OBJECT IDENTIFIER ::= { components 81 }



btdsRowStatusTable OBJECT-TYPE
   SYNTAX     SEQUENCE OF BtdsRowStatusEntry
   ACCESS     not-accessible
   STATUS     mandatory
   DESCRIPTION
     "This entry controls the addition and deletion of 
      btds components."
::= { btds 1 }

btdsRowStatusEntry OBJECT-TYPE
   SYNTAX     BtdsRowStatusEntry
   ACCESS     not-accessible
   STATUS     mandatory
   DESCRIPTION
     "A single entry in the table represents a single 
      btds component."
   INDEX {
      btdsIndex }
::= { btdsRowStatusTable 1 }

BtdsRowStatusEntry ::= SEQUENCE {
   btdsRowStatus
      RowStatus,
   btdsComponentName
      DisplayString,
   btdsStorageType
      StorageType,
   btdsIndex
      Integer32 }

btdsRowStatus OBJECT-TYPE
   SYNTAX     RowStatus 
   ACCESS     read-write
   STATUS     mandatory
   DESCRIPTION
     "This variable is used as the basis for SNMP naming of
      btds components.
      These components can be added and deleted."
::= { btdsRowStatusEntry 1 }

btdsComponentName OBJECT-TYPE
   SYNTAX     DisplayString 
   ACCESS     read-only
   STATUS     mandatory
   DESCRIPTION
     "This variable provides the component's string name for
      use with the ASCII Console Interface"
::= { btdsRowStatusEntry 2 }

btdsStorageType OBJECT-TYPE
   SYNTAX     StorageType 
   ACCESS     read-only
   STATUS     mandatory
   DESCRIPTION
     "This variable represents the storage type value for the
      btds tables."
::= { btdsRowStatusEntry 4 }

btdsIndex OBJECT-TYPE
   SYNTAX     Integer32 (1..65535)
   ACCESS     not-accessible
   STATUS     mandatory
   DESCRIPTION
     "This variable represents the index for the btds tables."
::= { btdsRowStatusEntry 10 }

btdsCidDataTable OBJECT-TYPE
   SYNTAX     SEQUENCE OF BtdsCidDataEntry
   ACCESS     not-accessible
   STATUS     mandatory
   DESCRIPTION
     "This group contains the attribute for a component's Customer 
      Identifier (CID). Refer to the attribute description for a detailed 
      explanation of CIDs."
::= { btds 100 }

btdsCidDataEntry OBJECT-TYPE
   SYNTAX     BtdsCidDataEntry
   ACCESS     not-accessible
   STATUS     mandatory
   DESCRIPTION
     "An entry in the btdsCidDataTable."
   INDEX {
      btdsIndex }
::= { btdsCidDataTable 1 }

BtdsCidDataEntry ::= SEQUENCE {
   btdsCustomerIdentifier
      Unsigned32 }

btdsCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { btdsCidDataEntry 1 }

btdsIfEntryTable OBJECT-TYPE
   SYNTAX     SEQUENCE OF BtdsIfEntryEntry
   ACCESS     not-accessible
   STATUS     mandatory
   DESCRIPTION
     "This group contains the provisionable attributes for the ifEntry."
::= { btds 101 }

btdsIfEntryEntry OBJECT-TYPE
   SYNTAX     BtdsIfEntryEntry
   ACCESS     not-accessible
   STATUS     mandatory
   DESCRIPTION
     "An entry in the btdsIfEntryTable."
   INDEX {
      btdsIndex }
::= { btdsIfEntryTable 1 }

BtdsIfEntryEntry ::= SEQUENCE {
   btdsIfAdminStatus
      INTEGER,
   btdsIfIndex
      InterfaceIndex }

btdsIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { btdsIfEntryEntry 1 }

btdsIfIndex OBJECT-TYPE
   SYNTAX     InterfaceIndex (1..65535)
   ACCESS     read-only
   STATUS     mandatory
   DESCRIPTION
     "This is the index for the IfEntry. Its value is automatically initialized 
      during the provisioning process."
::= { btdsIfEntryEntry 2 }

btdsOperStatusTable OBJECT-TYPE
   SYNTAX     SEQUENCE OF BtdsOperStatusEntry
   ACCESS     not-accessible
   STATUS     mandatory
   DESCRIPTION
     "This group includes the Operational Status attribute. This attribute 
      defines the current operational state of this component."
::= { btds 102 }

btdsOperStatusEntry OBJECT-TYPE
   SYNTAX     BtdsOperStatusEntry
   ACCESS     not-accessible
   STATUS     mandatory
   DESCRIPTION
     "An entry in the btdsOperStatusTable."
   INDEX {
      btdsIndex }
::= { btdsOperStatusTable 1 }

BtdsOperStatusEntry ::= SEQUENCE {
   btdsSnmpOperStatus
      INTEGER }

btdsSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { btdsOperStatusEntry 1 }

btdsStateTable OBJECT-TYPE
   SYNTAX     SEQUENCE OF BtdsStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { btds 103 }

btdsStateEntry OBJECT-TYPE
   SYNTAX     BtdsStateEntry
   ACCESS     not-accessible
   STATUS     mandatory
   DESCRIPTION
     "An entry in the btdsStateTable."
   INDEX {
      btdsIndex }
::= { btdsStateTable 1 }

BtdsStateEntry ::= SEQUENCE {
   btdsAdminState
      INTEGER,
   btdsOperationalState
      INTEGER,
   btdsUsageState
      INTEGER,
   btdsAvailabilityStatus
      OCTET STRING,
   btdsProceduralStatus
      OCTET STRING,
   btdsControlStatus
      OCTET STRING,
   btdsAlarmStatus
      OCTET STRING,
   btdsStandbyStatus
      INTEGER,
   btdsUnknownStatus
      INTEGER }

btdsAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { btdsStateEntry 1 }

btdsOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { btdsStateEntry 2 }

btdsUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { btdsStateEntry 3 }

btdsAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { btdsStateEntry 4 }

btdsProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { btdsStateEntry 5 }

btdsControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { btdsStateEntry 6 }

btdsAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { btdsStateEntry 7 }

btdsStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { btdsStateEntry 8 }

btdsUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { btdsStateEntry 9 }

btdsOperationalTable OBJECT-TYPE
   SYNTAX     SEQUENCE OF BtdsOperationalEntry
   ACCESS     not-accessible
   STATUS     mandatory
   DESCRIPTION
     "This group contains operational attributes related to a Btds."
::= { btds 105 }

btdsOperationalEntry OBJECT-TYPE
   SYNTAX     BtdsOperationalEntry
   ACCESS     not-accessible
   STATUS     mandatory
   DESCRIPTION
     "An entry in the btdsOperationalTable."
   INDEX {
      btdsIndex }
::= { btdsOperationalTable 1 }

BtdsOperationalEntry ::= SEQUENCE {
   btdsServiceFailureReason
      OCTET STRING }

btdsServiceFailureReason OBJECT-TYPE
   SYNTAX     OCTET STRING (SIZE (2))
   ACCESS     read-only
   STATUS     mandatory
   DESCRIPTION
     "This attribute indicates the result of end to end negotiation with the 
      remote end across the subnet.
      
      If serviceFailureReason is undetermined, this Btds has not 
      performed end to end negotiation with the remote end, and may or 
      may not be up. serviceFailureReason is undetermined if this Btds 
      just became enabled, if there is not enough available bandwidth to 
      perform negotiation or if the remote end cannot perform negotiation 
      with this Btds.
      If serviceFailureReason is none, end to end negotiation passed.
      If serviceFailureReason is mismatchedService, end to end 
      negotiation failed because the remote end service is not a Btds.
      If serviceFailureReason is mismatchedTimeSlotAlignment, end to 
      end negotiation failed because the local Btds Framer 
      timeSlotAlignment does not match the remote Btds Framer 
      timeSlotAlignment.
      If serviceFailureReason is mismatchedCallDiscriminator, the local 
      Btds call discrimination subcomponents (Btds Mcdn and Btds 
      Dpnss1) do not match the remote Btds call discrimination 
      subcomponents.
      If serviceFailureReason is compDecodeFailed, end to end 
      negotiation failed because the information received from the remote 
      end was not recognized as valid data.

      Description of bits:
      none(0)
      undetermined(1)
      logicalConnection(2)
      mismatchedService(3)
      mismatchedTimeSlotAlignment(4)
      mismatchedCallDiscriminator(5)
      notused6(6)
      notused7(7)
      notused8(8)
      notused9(9)
      notused10(10)
      notused11(11)
      notused12(12)
      notused13(13)
      compDecodeFailed(14)"
::= { btdsOperationalEntry 1 }


-- Btds/n Framer
-- The Framer component controls link layer framing for application 
-- components sending and receiving data on a link interface. It is also 
-- through Framer, that an application component is associated with a 
-- specific hardware link interface.
-- 
-- The Framer component provides provisionable attributes related to 
-- datapath aspects of the hardware interface rather than interface 
-- specific attributes which are associated with specific hardware 
-- components (such as Lp V35/n or Lp DS1/n). The Framer 
-- component also provides a provisionable attribute which binds the 
-- application component to a specific hardware component.
-- The Framer component contains operational attributes for link 
-- interface datapath statistics (such as frame counts).

btdsFramer OBJECT IDENTIFIER ::= { btds 2 }



btdsFramerRowStatusTable OBJECT-TYPE
   SYNTAX     SEQUENCE OF BtdsFramerRowStatusEntry
   ACCESS     not-accessible
   STATUS     mandatory
   DESCRIPTION
     "This entry controls the addition and deletion of 
      btdsFramer components."
::= { btdsFramer 1 }

btdsFramerRowStatusEntry OBJECT-TYPE
   SYNTAX     BtdsFramerRowStatusEntry
   ACCESS     not-accessible
   STATUS     mandatory
   DESCRIPTION
     "A single entry in the table represents a single 
      btdsFramer component."
   INDEX {
      btdsIndex,
      btdsFramerIndex }
::= { btdsFramerRowStatusTable 1 }

BtdsFramerRowStatusEntry ::= SEQUENCE {
   btdsFramerRowStatus
      RowStatus,
   btdsFramerComponentName
      DisplayString,
   btdsFramerStorageType
      StorageType,
   btdsFramerIndex
      NonReplicated }

btdsFramerRowStatus OBJECT-TYPE
   SYNTAX     RowStatus 
   ACCESS     read-only
   STATUS     mandatory
   DESCRIPTION
     "This variable is used as the basis for SNMP naming of
      btdsFramer components.
      These components cannot be added nor deleted."
::= { btdsFramerRowStatusEntry 1 }

btdsFramerComponentName OBJECT-TYPE
   SYNTAX     DisplayString 
   ACCESS     read-only
   STATUS     mandatory
   DESCRIPTION
     "This variable provides the component's string name for
      use with the ASCII Console Interface"
::= { btdsFramerRowStatusEntry 2 }

btdsFramerStorageType OBJECT-TYPE
   SYNTAX     StorageType 
   ACCESS     read-only
   STATUS     mandatory
   DESCRIPTION
     "This variable represents the storage type value for the
      btdsFramer tables."
::= { btdsFramerRowStatusEntry 4 }

btdsFramerIndex OBJECT-TYPE
   SYNTAX     NonReplicated 
   ACCESS     not-accessible
   STATUS     mandatory
   DESCRIPTION
     "This variable represents the index for the btdsFramer tables."
::= { btdsFramerRowStatusEntry 10 }

btdsFramerProvTable OBJECT-TYPE
   SYNTAX     SEQUENCE OF BtdsFramerProvEntry
   ACCESS     not-accessible
   STATUS     mandatory
   DESCRIPTION
     "This group contains the base provisioning data for the Framer 
      component. Application or hardware interface specific provisioning 
      data is contained in other provisionable Framer groups."
::= { btdsFramer 10 }

btdsFramerProvEntry OBJECT-TYPE
   SYNTAX     BtdsFramerProvEntry
   ACCESS     not-accessible
   STATUS     mandatory
   DESCRIPTION
     "An entry in the btdsFramerProvTable."
   INDEX {
      btdsIndex,
      btdsFramerIndex }
::= { btdsFramerProvTable 1 }

BtdsFramerProvEntry ::= SEQUENCE {
   btdsFramerInterfaceName
      Link }

btdsFramerInterfaceName OBJECT-TYPE
   SYNTAX     Link 
   ACCESS     read-write
   STATUS     mandatory
   DESCRIPTION
     "This attribute contains a hardware component name.
      
      The attribute associates the application with a specific link. This 
      defines the module processor on which Framer's parent component 
      (as well as Framer itself) will run."
::= { btdsFramerProvEntry 1 }

btdsFramerChannelTable OBJECT-TYPE
   SYNTAX     SEQUENCE OF BtdsFramerChannelEntry
   ACCESS     not-accessible
   STATUS     mandatory
   DESCRIPTION
     "This group contains attributes defining the framing of data on the 
      link interface or n*64kbps channel."
::= { btdsFramer 11 }

btdsFramerChannelEntry OBJECT-TYPE
   SYNTAX     BtdsFramerChannelEntry
   ACCESS     not-accessible
   STATUS     mandatory
   DESCRIPTION
     "An entry in the btdsFramerChannelTable."
   INDEX {
      btdsIndex,
      btdsFramerIndex }
::= { btdsFramerChannelTable 1 }

BtdsFramerChannelEntry ::= SEQUENCE {
   btdsFramerProtocol
      INTEGER,
   btdsFramerNumOfIdleBytesToMonitor
      Unsigned32,
   btdsFramerIdlePattern
      Hex,
   btdsFramerTimeSlotAlignment
      INTEGER,
   btdsFramerInsertedOutputDelay
      Unsigned32,
   btdsFramerBtdsCellSize
      INTEGER }

btdsFramerProtocol OBJECT-TYPE
   SYNTAX     INTEGER  {
                 none(0),
                 hdlc(1),
                 nrziHdlc(2),
                 universal(3) }
   ACCESS     read-write
   STATUS     mandatory
   DESCRIPTION
     "This attribute specifies the ingress frames suppressed by this Btds.
      If protocol is none, this Btds does not suppress any ingress frames.
      If protocol is hdlc, this Btds suppresses ingress frames where each 
      byte is an identical non-inverted hdlc idle pattern, but only after two 
      or more consecutive frames meet this description.
      If protocol is nrziHdlc, this Btds suppresses ingress frames where 
      each byte is an identical NRZI encoded hdlc idle pattern, but only 
      after two or more consecutive frames meet this description.
      If protocol is universal, this Btds suppresses ingress frames where 
      each 16-bit word is identical, but only after a provisionable number 
      of consecutive frames meet this description. The number of 
      consecutive frames is determined by numOfIdleBytesToMonitor.
      Note that the number of idle bytes suppressed at the ingress side 
      does not necessarily equal the number of idle bytes generated at the 
      egress side."
   DEFVAL     { none }
::= { btdsFramerChannelEntry 7 }

btdsFramerNumOfIdleBytesToMonitor OBJECT-TYPE
   SYNTAX     Unsigned32 (0..32000)
   ACCESS     read-write
   STATUS     mandatory
   DESCRIPTION
     "This attribute specifies the number of consecutive repeated ingress 
      16-bit words this Btds must encounter before suppressing universal 
      ingress idle frames. This attribute is only used if protocol is 
      universal.
      numOfIdleBytesToMonitor should be larger than the largest frame 
      size that can be sent into this Btds."
   DEFVAL     { 0 }
::= { btdsFramerChannelEntry 8 }

btdsFramerIdlePattern OBJECT-TYPE
   SYNTAX     Hex (0..255)
   ACCESS     read-write
   STATUS     mandatory
   DESCRIPTION
     "This attribute specifies how to fill a local egress frame when the 
      remote Btds suppressed an ingress frame."
   DEFVAL     { 255 }
::= { btdsFramerChannelEntry 9 }

btdsFramerTimeSlotAlignment OBJECT-TYPE
   SYNTAX     INTEGER  {
                 unaligned(0),
                 frameAligned(1) }
   ACCESS     read-write
   STATUS     mandatory
   DESCRIPTION
     "This attribute specifies the time slot alignment of this Btds. With 
      time slot alignment, data sent out on a particular time slot to a link 
      is received on the same time slot. A value of unaligned specifies the 
      regular Btds application. A value of frameAligned enables frame 
      aligned Btds. When framed aligned Btds is specified, only one 
      channel may be provisioned since only one fraction of N x 64 kbit/s 
      is presently available.
      
      timeSlotAlignment can not be set to frameAligned unless this Btds 
      is running on a DS1V, E1V, 1pDS1V or 1pE1V card
      timeSlotAlignment must have the same value at both ends of a Btds. 
      If timeSlotAlignment does not have the same value at both ends of a 
      Btds, the Btds will be out of service. In this case, Btds 
      serviceFailureReason is mismatchedTimeSlotAlignment."
   DEFVAL     { unaligned }
::= { btdsFramerChannelEntry 10 }

btdsFramerInsertedOutputDelay OBJECT-TYPE
   SYNTAX     Unsigned32 (0..50)
   ACCESS     read-write
   STATUS     mandatory
   DESCRIPTION
     "This attribute defines the amount of added output delay to 
      compensate for cross network delay variations. Cross network delay 
      variations is a function of the network topology. Setting this 
      attribute will allow the Btds service to deal with cross network 
      delay variations.                                                                           This 
      attribute provides for delay in addition to the elastic buffer. Total 
      egress delay is approximately the insertedOutputDelay plus the 
      elastic buffer. The elastic buffer is the packetization timex5 cells in 
      the buffer. Packetization time per cell is calculated by taking the 
      inverse of [linespeed (kbits/sec) x (byte/8bits) x (1/cellsize (bytes))]. 
      This value is msec.The value for insertedOutputDelay should be 
      increased if the frmUnderRuns is increasing and frmLostInNetwork 
      is not increasing."
   DEFVAL     { 12 }
::= { btdsFramerChannelEntry 11 }

btdsFramerBtdsCellSize OBJECT-TYPE
   SYNTAX     INTEGER  {
                 n44(0),
                 n84(1) }
   ACCESS     read-write
   STATUS     mandatory
   DESCRIPTION
     "This attribute allows selection of larger BTDS cell sizes. Larger 
      BTDS cell sizes improve efficiency but increase the minimum 
      egress queue delay. If the associated channel is using less than 5 
      timeslots (320 kbits/sec), the default btdsCellSize will be used. 
      Setting btdsCellSize to 84 is only allowed on DS1 and E1 FPs."
   DEFVAL     { n44 }
::= { btdsFramerChannelEntry 12 }

btdsFramerStateTable OBJECT-TYPE
   SYNTAX     SEQUENCE OF BtdsFramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { btdsFramer 12 }

btdsFramerStateEntry OBJECT-TYPE
   SYNTAX     BtdsFramerStateEntry
   ACCESS     not-accessible
   STATUS     mandatory
   DESCRIPTION
     "An entry in the btdsFramerStateTable."
   INDEX {
      btdsIndex,
      btdsFramerIndex }
::= { btdsFramerStateTable 1 }

BtdsFramerStateEntry ::= SEQUENCE {
   btdsFramerAdminState
      INTEGER,
   btdsFramerOperationalState
      INTEGER,
   btdsFramerUsageState
      INTEGER }

btdsFramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { btdsFramerStateEntry 1 }

btdsFramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { btdsFramerStateEntry 2 }

btdsFramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { btdsFramerStateEntry 3 }

btdsFramerStatsTable OBJECT-TYPE
   SYNTAX     SEQUENCE OF BtdsFramerStatsEntry
   ACCESS     not-accessible
   STATUS     mandatory
   DESCRIPTION
     "This group contains the operational statistics data for a Framer 
      component."
::= { btdsFramer 13 }

btdsFramerStatsEntry OBJECT-TYPE
   SYNTAX     BtdsFramerStatsEntry
   ACCESS     not-accessible
   STATUS     mandatory
   DESCRIPTION
     "An entry in the btdsFramerStatsTable."
   INDEX {
      btdsIndex,
      btdsFramerIndex }
::= { btdsFramerStatsTable 1 }

BtdsFramerStatsEntry ::= SEQUENCE {
   btdsFramerFrmFromIf
      Counter32,
   btdsFramerSuppressedFrames
      Counter32,
   btdsFramerFrmToIf
      Counter32,
   btdsFramerLrcErrors
      Counter32,
   btdsFramerFrmLostInNetwork
      Counter32,
   btdsFramerFrmUnderRuns
      Counter32,
   btdsFramerFrmDumped
      Counter32 }

btdsFramerFrmFromIf OBJECT-TYPE
   SYNTAX     Counter32 
   ACCESS     read-only
   STATUS     mandatory
   DESCRIPTION
     "This attribute counts the number of frames received from the link 
      interface by Framer.
      This count wraps to zero after reaching its maximum value."
::= { btdsFramerStatsEntry 1 }

btdsFramerSuppressedFrames OBJECT-TYPE
   SYNTAX     Counter32 
   ACCESS     read-only
   STATUS     mandatory
   DESCRIPTION
     "This attribute counts the number of frames dropped at the interface 
      due to the idle pattern being detected.
      This count wraps to zero after reaching its maximum value."
::= { btdsFramerStatsEntry 3 }

btdsFramerFrmToIf OBJECT-TYPE
   SYNTAX     Counter32 
   ACCESS     read-only
   STATUS     mandatory
   DESCRIPTION
     "This attribute counts the number of frames transmitted to the link 
      interface by Framer.
      This count wraps to zero after reaching its maximum value."
::= { btdsFramerStatsEntry 4 }

btdsFramerLrcErrors OBJECT-TYPE
   SYNTAX     Counter32 
   ACCESS     read-only
   STATUS     mandatory
   DESCRIPTION
     "This attribute counts the number of frames received from the 
      network with LRC errors.
      This count wraps to zero after reaching its maximum value."
::= { btdsFramerStatsEntry 5 }

btdsFramerFrmLostInNetwork OBJECT-TYPE
   SYNTAX     Counter32 
   ACCESS     read-only
   STATUS     mandatory
   DESCRIPTION
     "This attribute counts the number of frames which the service knows 
      it did not receive from the network although they were sent in to the 
      network from the far end.
      This count wraps to zero after reaching its maximum value."
::= { btdsFramerStatsEntry 6 }

btdsFramerFrmUnderRuns OBJECT-TYPE
   SYNTAX     Counter32 
   ACCESS     read-only
   STATUS     mandatory
   DESCRIPTION
     "This attribute counts the number of times that a frame was needed 
      but was not available because it had been delayed too long in the 
      network.
      This error may occur repeatedly if the interface clocks at the two 
      access points to the network are operating at different rates.
      This count wraps to zero after reaching its maximum value."
::= { btdsFramerStatsEntry 7 }

btdsFramerFrmDumped OBJECT-TYPE
   SYNTAX     Counter32 
   ACCESS     read-only
   STATUS     mandatory
   DESCRIPTION
     "This attribute counts the number of frames which have been 
      dumped because the local interface output queue grew too large. 
      This can occur if the clock rate on the local interface is faster than 
      the clock rate on the remote interface and there are no silence 
      periods to absorb the difference.
      This count wraps to zero after reaching its maximum value."
::= { btdsFramerStatsEntry 8 }


-- Btds/n PLC
-- This is the description of the PLC Component for the Btds service.. 

btdsPlc OBJECT IDENTIFIER ::= { btds 3 }



btdsPlcRowStatusTable OBJECT-TYPE
   SYNTAX     SEQUENCE OF BtdsPlcRowStatusEntry
   ACCESS     not-accessible
   STATUS     mandatory
   DESCRIPTION
     "This entry controls the addition and deletion of 
      btdsPlc components."
::= { btdsPlc 1 }

btdsPlcRowStatusEntry OBJECT-TYPE
   SYNTAX     BtdsPlcRowStatusEntry
   ACCESS     not-accessible
   STATUS     mandatory
   DESCRIPTION
     "A single entry in the table represents a single 
      btdsPlc component."
   INDEX {
      btdsIndex,
      btdsPlcIndex }
::= { btdsPlcRowStatusTable 1 }

BtdsPlcRowStatusEntry ::= SEQUENCE {
   btdsPlcRowStatus
      RowStatus,
   btdsPlcComponentName
      DisplayString,
   btdsPlcStorageType
      StorageType,
   btdsPlcIndex
      NonReplicated }

btdsPlcRowStatus OBJECT-TYPE
   SYNTAX     RowStatus 
   ACCESS     read-only
   STATUS     mandatory
   DESCRIPTION
     "This variable is used as the basis for SNMP naming of
      btdsPlc components.
      These components cannot be added nor deleted."
::= { btdsPlcRowStatusEntry 1 }

btdsPlcComponentName OBJECT-TYPE
   SYNTAX     DisplayString 
   ACCESS     read-only
   STATUS     mandatory
   DESCRIPTION
     "This variable provides the component's string name for
      use with the ASCII Console Interface"
::= { btdsPlcRowStatusEntry 2 }

btdsPlcStorageType OBJECT-TYPE
   SYNTAX     StorageType 
   ACCESS     read-only
   STATUS     mandatory
   DESCRIPTION
     "This variable represents the storage type value for the
      btdsPlc tables."
::= { btdsPlcRowStatusEntry 4 }

btdsPlcIndex OBJECT-TYPE
   SYNTAX     NonReplicated 
   ACCESS     not-accessible
   STATUS     mandatory
   DESCRIPTION
     "This variable represents the index for the btdsPlc tables."
::= { btdsPlcRowStatusEntry 10 }

btdsPlcProvTable OBJECT-TYPE
   SYNTAX     SEQUENCE OF BtdsPlcProvEntry
   ACCESS     not-accessible
   STATUS     mandatory
   DESCRIPTION
     "This group contains all provisionable attributes for a permanent 
      logical connection. Note that all of the attributes are valid and 
      provisionable on both ends of a connection. However with the 
      exception of remoteName, all operational attributes are derived 
      from the originating end provisioning, which may be either end 
      unless remoteName is not provisioned on one end."
::= { btdsPlc 10 }

btdsPlcProvEntry OBJECT-TYPE
   SYNTAX     BtdsPlcProvEntry
   ACCESS     not-accessible
   STATUS     mandatory
   DESCRIPTION
     "An entry in the btdsPlcProvTable."
   INDEX {
      btdsIndex,
      btdsPlcIndex }
::= { btdsPlcProvTable 1 }

BtdsPlcProvEntry ::= SEQUENCE {
   btdsPlcRemoteName
      AsciiString,
   btdsPlcSetupPriority
      Unsigned32,
   btdsPlcHoldingPriority
      Unsigned32,
   btdsPlcRequiredTxBandwidth
      Unsigned32,
   btdsPlcRequiredRxBandwidth
      Unsigned32,
   btdsPlcRequiredTrafficType
      INTEGER,
   btdsPlcPermittedTrunkTypes
      OCTET STRING,
   btdsPlcRequiredSecurity
      Unsigned32,
   btdsPlcRequiredCustomerParm
      Unsigned32,
   btdsPlcPathAttributeToMinimize
      INTEGER,
   btdsPlcMaximumAcceptableCost
      Unsigned32,
   btdsPlcMaximumAcceptableDelay
      Unsigned32,
   btdsPlcEmissionPriority
      Unsigned32,
   btdsPlcDiscardPriority
      Unsigned32,
   btdsPlcPathType
      INTEGER,
   btdsPlcPathFailureAction
      INTEGER,
   btdsPlcBumpPreference
      INTEGER,
   btdsPlcOptimization
      INTEGER }

btdsPlcRemoteName OBJECT-TYPE
   SYNTAX     AsciiString (SIZE (0..40))
   ACCESS     read-write
   STATUS     mandatory
   DESCRIPTION
     "This attribute is the PLC's remote end point's address in the format 
      of a Passport component name The syntax of a component is:
      'em/node type/instance'. End points are identified using a node 
      name and a service name. As an example, the end point component 
      name for the third voice service on node MoonBase is:
      'EM/MoonBase VS/3'. If the remoteName is provisioned it must 
      match the remote name of the other end or the connection will not 
      be established even if the remote end is provisioned correctly. If no 
      remoteName is provisioned then this LC will accept connections 
      from any other remote LC and it will not originate calls. 
      Connections establish faster and are unique if both ends are 
      provisioned with the remoteName.
      These strings are case insensitive but the complete component name 
      must be input."
   DEFVAL     { ''H }  -- ""
::= { btdsPlcProvEntry 2 }

btdsPlcSetupPriority OBJECT-TYPE
   SYNTAX     Unsigned32 (0..4)
   ACCESS     read-write
   STATUS     mandatory
   DESCRIPTION
     "This attribute gives the priority at which a path is established. Zero 
      is the highest priority and four is the lowest. When PORS 
      establishes a path through the network, it uses the setupPriority 
      attribute to determine its potential for bumping established paths to 
      acquire their bandwidth. The holdingPriority, a complementary 
      attribute of this attribute, indicates the priority a path maintains 
      once it is established. A new path can bump an existing path if the 
      new path's setupPriority is higher (numerically less) than the 
      existing path's holdingPriority."
   DEFVAL     { 2 }
::= { btdsPlcProvEntry 3 }

btdsPlcHoldingPriority OBJECT-TYPE
   SYNTAX     Unsigned32 (0..4)
   ACCESS     read-write
   STATUS     mandatory
   DESCRIPTION
     "This attribute gives the priority that a path holds once it is 
      established. Zero(0) is the highest priority and four(4) is the lowest. 
      A path's holdingPriority determines its likelihood of being bumped 
      by a new path to acquire its bandwidth. The setupPriority, a 
      complementary attribute, indicates the priority of a path at 
      establishment time. A new path can bump an existing path if the 
      new path's setupPriority is higher (numerically less) than the 
      existing path's holdingPriority."
   DEFVAL     { 2 }
::= { btdsPlcProvEntry 4 }

btdsPlcRequiredTxBandwidth OBJECT-TYPE
   SYNTAX     Unsigned32 (0..4294967295)
   ACCESS     read-write
   STATUS     mandatory
   DESCRIPTION
     "This attribute gives the bandwidth (in bits per second) reserved by a 
      path on each of the trunks of its route. This attribute represents the 
      bandwidth for traffic outgoing to the remote end point. This value 
      should be chosen to achieve the amount of statistical bandwidth 
      sharing that is desired by the network administration. This 
      reservation is not enforced and is used to determine how many paths 
      can be supported on a trunk. Both ends should be provisioned with 
      the correct values allowing for the fact that Transmit at this end 
      represents Receive at the remote end. Note that when the values do 
      not correspond the originating end of the connection determines the 
      value."
   DEFVAL     { 64000 }
::= { btdsPlcProvEntry 5 }

btdsPlcRequiredRxBandwidth OBJECT-TYPE
   SYNTAX     Unsigned32 (0..4294967295)
   ACCESS     read-write
   STATUS     mandatory
   DESCRIPTION
     "This attribute gives the bandwidth (in bits per second) reserved by a 
      path on each of trunks of its route. This attribute represents the 
      bandwidth for traffic incoming from the remote end point. This 
      value should be chosen to achieve the amount of statistical 
      bandwidth sharing that is desired by the network administration. 
      This reservation is not enforced and is used to determine how many 
      paths can be supported on a trunk. Both ends should be provisioned 
      with the correct values allowing for the fact that transmit at this end 
      represents receive at the remote end. Note that when the values do 
      not correspond, the originating end of the connection determines the 
      value."
   DEFVAL     { 64000 }
::= { btdsPlcProvEntry 6 }

btdsPlcRequiredTrafficType OBJECT-TYPE
   SYNTAX     INTEGER  {
                 voice(0),
                 data(1),
                 video(2),
                 trafficType1(3),
                 trafficType2(4),
                 trafficType3(5),
                 trafficType4(6),
                 trafficType5(7) }
   ACCESS     read-write
   STATUS     mandatory
   DESCRIPTION
     "This attribute indicates the type of traffic transmitted over the path. 
      There are eight(8) possible traffic types, and the path can transmit 
      only one of them. The originating end of the connection determines 
      the type. These are arbitrary designations for traffic type. The voice, 
      data and video traffic types are defined, and five(5) other arbitrary 
      traffic types can be defined by the network administration. This 
      attribute is used in the route selection process to restrict the route to 
      trunks that support this traffic type. The supportedTrafficType trunk 
      attribute lists all the types of traffic allowed on the trunk. For 
      example, if requiredTrafficType is specified as trafficType1, then 
      only trunks that include trafficType1 in supportedTrafficType, will 
      be candidates for this connection."
   DEFVAL     { video }
::= { btdsPlcProvEntry 7 }

btdsPlcPermittedTrunkTypes OBJECT-TYPE
   SYNTAX     OCTET STRING (SIZE (1))
   ACCESS     read-write
   STATUS     mandatory
   DESCRIPTION
     "This attribute lists up to eight(8) types of trunk that can be used on 
      the route. The terrestrial and satellite trunk types have been 
      defined, leaving six(6) remaining arbitrary types that can be defined 
      by the network administration. The trunk's type is indicated in the 
      trunkType attribute of the Trunk component. When selecting a 
      route, PORS only chooses trunks whose trunkType are in the 
      permittedTrunkTypes for the path.

      Description of bits:
      terrestrial(0)
      satellite(1)
      trunkType1(2)
      trunkType2(3)
      trunkType3(4)
      trunkType4(5)
      trunkType5(6)
      trunkType6(7)"
   DEFVAL     { 'f8'H }
::= { btdsPlcProvEntry 8 }

btdsPlcRequiredSecurity OBJECT-TYPE
   SYNTAX     Unsigned32 (0..7)
   ACCESS     read-write
   STATUS     mandatory
   DESCRIPTION
     "This attribute indicates the required minimum level of security of 
      the trunks on the route. Zero represents the most secure and seven 
      represents the least secure. The trunk's security is indicated by the 
      trunkSecurity attribute of the Trunk component, and has values 
      identical in range and meaning to the requiredSecurity attribute. 
      PORS ensures that any route selected does not contain a trunk 
      whose trunkSecurity attribute is numerically greater than the 
      requiredSecurity."
   DEFVAL     { 4 }
::= { btdsPlcProvEntry 9 }

btdsPlcRequiredCustomerParm OBJECT-TYPE
   SYNTAX     Unsigned32 (0..7)
   ACCESS     read-write
   STATUS     mandatory
   DESCRIPTION
     "This attribute indicates the allowed customer defined parameter of 
      the trunks on the route. Its value, a number from zero to seven, is 
      chosen by network administration to have a meaning specific to 
      their network, thus allowing them to customize the use of their 
      trunks. A complementary trunk attribute, customerParameter, also 
      has a value from zero to seven. The route selection process does not 
      consider trunks whose customerParameter is greater than the 
      requiredCustomerParameter of the path."
   DEFVAL     { 4 }
::= { btdsPlcProvEntry 10 }

btdsPlcPathAttributeToMinimize OBJECT-TYPE
   SYNTAX     INTEGER  {
                 cost(0),
                 delay(1) }
   ACCESS     read-write
   STATUS     mandatory
   DESCRIPTION
     "This attribute indicates whether a route is selected on the basis of 
      minimizing the cost or the delay. Each trunk has a cost and a delay 
      metric associated with it. The cost of a selected route is the sum of 
      the trunk cost metrics for all trunks included in the route. The delay 
      of a selected route is the sum of the trunk delay metric for all trunks 
      included in the route."
   DEFVAL     { cost }
::= { btdsPlcProvEntry 11 }

btdsPlcMaximumAcceptableCost OBJECT-TYPE
   SYNTAX     Unsigned32 (0..65535)
   ACCESS     read-write
   STATUS     mandatory
   DESCRIPTION
     "This attribute indicates an upper bound on the cost metric of a route, 
      which is the sum of the cost metrics of all trunks on the route. The 
      cost metric is the trunkCost attribute of the Trunk component. If for 
      any trunk the trunkCost is larger than the maximumAcceptableCost, 
      then that trunk is not considered during the route selection. While a 
      shortest route is being selected, the route cost is being compared 
      with the maximumAcceptableCost attribute, and this is done for any 
      minimization criterion. No route is selected if the cost metric of the 
      shortest route is larger than the maximumAcceptableCost."
   DEFVAL     { 1280 }
::= { btdsPlcProvEntry 12 }

btdsPlcMaximumAcceptableDelay OBJECT-TYPE
   SYNTAX     Unsigned32 (0..100000)
   ACCESS     read-write
   STATUS     mandatory
   DESCRIPTION
     "This attribute indicates an upper bound on the delay of a route, 
      which is the sum of the delay of all trunks on the route. It should be 
      provisioned with a reasonable maximum acceptable delay for the 
      end to end one way delay of a 512-byte packet. Remember, that the 
      trunk during its staging measures a measuredRoundTripDelay. This 
      delay is divided by two and truncated to an integer number of 
      milliseconds to provide a one way delay which is used to populate 
      the delay in this trunk object in the topological database. The value 
      includes emission, propagation, and queuing delays. A 512-byte 
      packet is used to perform the measurement. 
      If for any trunk the half of the trunk's measuredRoundTripDelay is 
      larger than the maximumAcceptableDelay, then that trunk is not 
      considered during the route selection.
      While a shortest route is being selected, the route delay is being 
      compared with the maximumAcceptableDelay attribute, and this is 
      done for any minimization criterion. No route is selected if the 
      delay metric of the shortest route is larger than the 
      maximumAcceptableDelay."
   DEFVAL     { 100000 }
::= { btdsPlcProvEntry 13 }

btdsPlcEmissionPriority OBJECT-TYPE
   SYNTAX     Unsigned32 (0..2)
   ACCESS     read-write
   STATUS     mandatory
   DESCRIPTION
     "This attribute indicates the urgency with which packets on the path 
      are emitted by the trunks on the route. EmissionPriority of Zero(0) 
      indicates the highest emission priority, while two (2) indicates the 
      lowest emission priority. Packets with a higher emissionPriority (or 
      numerically less) are serviced and sent out before the packets of 
      lower emissionPriority (or numerically higher)."
   DEFVAL     { 0 }
::= { btdsPlcProvEntry 14 }

btdsPlcDiscardPriority OBJECT-TYPE
   SYNTAX     Unsigned32 (1..3)
   ACCESS     read-write
   STATUS     mandatory
   DESCRIPTION
     "This attribute indicates the importance of the packets on the path. 
      One is used for paths carrying the most important traffic, and three 
      is used for paths carrying the least important traffic. Packets with 
      lower discardPriority(numerically lower) are discarded after 
      packets with a higher discardPriority(numerically higher)."
   DEFVAL     { 1 }
::= { btdsPlcProvEntry 15 }

btdsPlcPathType OBJECT-TYPE
   SYNTAX     INTEGER  {
                 normal(0),
                 manual(1),
                 forced(2) }
   ACCESS     read-write
   STATUS     mandatory
   DESCRIPTION
     "This attribute specifies if the path for this PLC is determined 
      automatically or by static provisioning. The default (normal) is to 
      automatically choose a route with Route Selection. Normal 
      pathTypes require less provisioning and can dynamically handle 
      path failures. The other pathTypes are both manual pathTypes 
      where the operator must specify, through provisioning, a static route 
      termed the manualPath. A manual pathType connection is nearly 
      identical to a normal path type connection with the exception that 
      the route is pre-provisioned. For a manual pathType, bandwidth 
      reservations are respected along the path exactly as in a normal 
      path. The last type, the forced pathType, is also a manual path but 
      regardless of the bandwidth available the route is granted provided 
      the trunks are operational and there are sufficient Logical Channels 
      (LChs).
      The forced pathType could result in over committing the reserved 
      bandwidth allowed on a trunk. A better way to achieve the effects of 
      a forced pathType is to use a manual pathType with setupPriority = 
      0 and holdingPriority = 0. In this manner the path will reserve 
      correct bandwidth and it will bump other paths if required while not 
      being bumped itself."
   DEFVAL     { normal }
::= { btdsPlcProvEntry 16 }

btdsPlcPathFailureAction OBJECT-TYPE
   SYNTAX     INTEGER  {
                 disconnectConnection(0),
                 reRoutePath(1) }
   ACCESS     read-write
   STATUS     mandatory
   DESCRIPTION
     "This attribute is used to specify whether the application can tolerate 
      momentary interruption of a path while a new path is selected. If 
      disconnectConnection is chosen, the application is informed as 
      soon as possible about a failure by disconnection. If the attribute is 
      set to reRoutePath, the path may attempt an immediate reroute, 
      provided the failure is a recoverable failure. If rerouting fails the 
      application is informed of the failure. 
      With this option set to reRoutePath the LCo may wait up to 30 
      seconds before informing the service of complete disconnection in 
      order to allow both ends to attempt to reconnect. Note that if PLC 
      components are different at both ends only the calling end is 
      allowed to reconnect.
      All pathTypes respect this attribute. Also on a manualPath with 
      both ends provisioned with independent paths (at least with respect 
      to the failure) this option will have the desired effect that the path is 
      rerouted without complete disconnection at both ends."
   DEFVAL     { reRoutePath }
::= { btdsPlcProvEntry 17 }

btdsPlcBumpPreference OBJECT-TYPE
   SYNTAX     INTEGER  {
                 bumpWhenNecessary(0),
                 bumpToObtainBestRoute(1) }
   ACCESS     read-write
   STATUS     mandatory
   DESCRIPTION
     "This attribute controls when bumping occurs in the route selection 
      process. A connection with higher (numerically less) setupPriority 
      may bump a connection with lower (numerically higher) 
      holdingPriority in order to acquire its bandwidth and be established. 
      By default, bumping occurs only when it is necessary. That is, a 
      connection will bump another connection only if there is no other 
      way for the connection to be established. A connection may be set 
      to always bump in order to find the best route it may have."
   DEFVAL     { bumpWhenNecessary }
::= { btdsPlcProvEntry 18 }

btdsPlcOptimization OBJECT-TYPE
   SYNTAX     INTEGER  {
                 disabled(0),
                 enabled(1) }
   ACCESS     read-write
   STATUS     mandatory
   DESCRIPTION
     "This attribute is used to specify whether this connection should 
      attempt to optimize its path when requested by the routing PORS 
      component. Every path is as optimal as it can be when it is 
      established, but as network traffic patterns and configurations 
      change this path may no longer be as optimal as it could be. The 
      PORS connection manager on a module requests circuits to 
      optimize at the optimization interval."
   DEFVAL     { enabled }
::= { btdsPlcProvEntry 19 }

btdsPlcMpathTable OBJECT-TYPE
   SYNTAX     SEQUENCE OF BtdsPlcMpathEntry
   ACCESS     not-accessible
   STATUS     mandatory
   DESCRIPTION
     "This attribute is optional and specifies the sequence of trunks to be 
      used as the route for the path, thus bypassing PORS' automatic 
      route selection. If the path fails the validation, no other path can be 
      selected1. This attribute should only be used in special cases since 
      the route selection algorithm is able to find and maintain the best 
      routes. A related path attribute, the pathType, determines if this 
      route will be used as a manual or forced path type. 
      As an example, the trunk component name for the third trunk on 
      node MoonBase is 'EM/MoonBase Trk/3'. Note that only the first 
      end of the trunk that the packet would encounter is provisioned. 
      These strings are case insensitive but the complete component name 
      must be input. 
      
      Note 1: the trunk designation must be a 3-letter form, e.g., 'trk'. 
      Note 2: only the outbound trunks component names are used to 
      provision the manualPath.
      
      Note 3: It is recommended to have two independent routes specified 
      for a manual path by specifying a different manualPath 
      (non-symmetric) for each end. In this case, there is no way to select 
      which route will be used (first up wins) but if one path is torn down 
      due to a failure then the other manualPath may be used to reroute 
      the path."
::= { btdsPlc 262 }

btdsPlcMpathEntry OBJECT-TYPE
   SYNTAX     BtdsPlcMpathEntry
   ACCESS     not-accessible
   STATUS     mandatory
   DESCRIPTION
     "An entry in the btdsPlcMpathTable."
   INDEX {
      btdsIndex,
      btdsPlcIndex,
      btdsPlcMpathIndex }
::= { btdsPlcMpathTable 1 }

BtdsPlcMpathEntry ::= SEQUENCE {
   btdsPlcMpathIndex
      Integer32,
   btdsPlcMpathValue
      AsciiString }

btdsPlcMpathIndex OBJECT-TYPE
   SYNTAX     Integer32 (0..9)
   ACCESS     not-accessible
   STATUS     mandatory
   DESCRIPTION
     "This variable represents the btdsPlcMpathTable
      specific index for the btdsPlcMpathTable."
::= { btdsPlcMpathEntry 1 }

btdsPlcMpathValue OBJECT-TYPE
   SYNTAX     AsciiString (SIZE (0..40))
   ACCESS     read-write
   STATUS     mandatory
   DESCRIPTION
     "This variable represents an individual value for the
      btdsPlcMpathTable."
::= { btdsPlcMpathEntry 2 }


-- ...Lc
-- This component contains all of the operation attributes for a Path 
-- Oriented Logical Connection.

btdsLCo OBJECT IDENTIFIER ::= { btds 4 }



btdsLCoRowStatusTable OBJECT-TYPE
   SYNTAX     SEQUENCE OF BtdsLCoRowStatusEntry
   ACCESS     not-accessible
   STATUS     mandatory
   DESCRIPTION
     "This entry controls the addition and deletion of 
      btdsLCo components."
::= { btdsLCo 1 }

btdsLCoRowStatusEntry OBJECT-TYPE
   SYNTAX     BtdsLCoRowStatusEntry
   ACCESS     not-accessible
   STATUS     mandatory
   DESCRIPTION
     "A single entry in the table represents a single 
      btdsLCo component."
   INDEX {
      btdsIndex,
      btdsLCoIndex }
::= { btdsLCoRowStatusTable 1 }

BtdsLCoRowStatusEntry ::= SEQUENCE {
   btdsLCoRowStatus
      RowStatus,
   btdsLCoComponentName
      DisplayString,
   btdsLCoStorageType
      StorageType,
   btdsLCoIndex
      NonReplicated }

btdsLCoRowStatus OBJECT-TYPE
   SYNTAX     RowStatus 
   ACCESS     read-only
   STATUS     mandatory
   DESCRIPTION
     "This variable is used as the basis for SNMP naming of
      btdsLCo components.
      These components cannot be added nor deleted."
::= { btdsLCoRowStatusEntry 1 }

btdsLCoComponentName OBJECT-TYPE
   SYNTAX     DisplayString 
   ACCESS     read-only
   STATUS     mandatory
   DESCRIPTION
     "This variable provides the component's string name for
      use with the ASCII Console Interface"
::= { btdsLCoRowStatusEntry 2 }

btdsLCoStorageType OBJECT-TYPE
   SYNTAX     StorageType 
   ACCESS     read-only
   STATUS     mandatory
   DESCRIPTION
     "This variable represents the storage type value for the
      btdsLCo tables."
::= { btdsLCoRowStatusEntry 4 }

btdsLCoIndex OBJECT-TYPE
   SYNTAX     NonReplicated 
   ACCESS     not-accessible
   STATUS     mandatory
   DESCRIPTION
     "This variable represents the index for the btdsLCo tables."
::= { btdsLCoRowStatusEntry 10 }

btdsLCoPathDataTable OBJECT-TYPE
   SYNTAX     SEQUENCE OF BtdsLCoPathDataEntry
   ACCESS     not-accessible
   STATUS     mandatory
   DESCRIPTION
     "This group contains all operational attributes for the path oriented 
      LCo."
::= { btdsLCo 10 }

btdsLCoPathDataEntry OBJECT-TYPE
   SYNTAX     BtdsLCoPathDataEntry
   ACCESS     not-accessible
   STATUS     mandatory
   DESCRIPTION
     "An entry in the btdsLCoPathDataTable."
   INDEX {
      btdsIndex,
      btdsLCoIndex }
::= { btdsLCoPathDataTable 1 }

BtdsLCoPathDataEntry ::= SEQUENCE {
   btdsLCoState
      INTEGER,
   btdsLCoOverrideRemoteName
      AsciiString,
   btdsLCoEnd
      INTEGER,
   btdsLCoCostMetric
      Unsigned32,
   btdsLCoDelayMetric
      Unsigned32,
   btdsLCoRoundTripDelay
      Unsigned32,
   btdsLCoSetupPriority
      Unsigned32,
   btdsLCoHoldingPriority
      Unsigned32,
   btdsLCoRequiredTxBandwidth
      Gauge32,
   btdsLCoRequiredRxBandwidth
      Gauge32,
   btdsLCoRequiredTrafficType
      INTEGER,
   btdsLCoPermittedTrunkTypes
      OCTET STRING,
   btdsLCoRequiredSecurity
      Unsigned32,
   btdsLCoRequiredCustomerParameter
      Unsigned32,
   btdsLCoEmissionPriority
      Unsigned32,
   btdsLCoDiscardPriority
      Unsigned32,
   btdsLCoPathType
      INTEGER,
   btdsLCoRetryCount
      Unsigned32,
   btdsLCoPathFailureCount
      Unsigned32,
   btdsLCoReasonForNoRoute
      INTEGER,
   btdsLCoLastTearDownReason
      INTEGER,
   btdsLCoPathFailureAction
      INTEGER,
   btdsLCoBumpPreference
      INTEGER,
   btdsLCoOptimization
      INTEGER,
   btdsLCoPathUpDateTime
      EnterpriseDateAndTime }

btdsLCoState OBJECT-TYPE
   SYNTAX     INTEGER  {
                 pathDown(0),
                 selectingRoute(1),
                 connecting(2),
                 pathUp(3),
                 pathDownRetrying(4) }
   ACCESS     read-only
   STATUS     mandatory
   DESCRIPTION
     "This attribute reflects the current state of the connection. The 
      pathDown state indicates a connection that has no remote end 
      provisioned or the application has not yet signalled for a path. The 
      selectingRoute state occurs when a request has been sent to route 
      selector and it has not yet responded. The connectingState occurs 
      while a path is being established. The pathUp state is the normal 
      operational state of a path. The pathDownRetrying state indicates a 
      path that attempted route selection but received no route and is now 
      waiting to retry route selection again."
::= { btdsLCoPathDataEntry 1 }

btdsLCoOverrideRemoteName OBJECT-TYPE
   SYNTAX     AsciiString (SIZE (0..40))
   ACCESS     read-write
   STATUS     mandatory
   DESCRIPTION
     "If set and the current PLC remoteName is blank this remoteName 
      will override the blank PLC remoteName. Usually you would set 
      this attribute and then lock/unlock the service component which 
      will result in this new overrideRemoteName being used as if it had 
      been provisioned into the PLC remoteName. The advantage of this 
      attribute is that the connection's remoteName can be changed 
      immediately without having to 'activate prov' but the disadvantage 
      is that the overrideRemoteName is not permanent and if the card or 
      switch is reset the override will be lost."
::= { btdsLCoPathDataEntry 2 }

btdsLCoEnd OBJECT-TYPE
   SYNTAX     INTEGER  {
                 calling(0),
                 called(1) }
   ACCESS     read-only
   STATUS     mandatory
   DESCRIPTION
     "This attribute identifies whether this is the calling or called end of 
      the path."
::= { btdsLCoPathDataEntry 3 }

btdsLCoCostMetric OBJECT-TYPE
   SYNTAX     Unsigned32 (0..65535)
   ACCESS     read-only
   STATUS     mandatory
   DESCRIPTION
     "This attribute gives the route's total cost metric. It is calculated as 
      the sum of the cost metric of all trunks in the path at the time the 
      connection was established. The cost metric of a trunk is defined by 
      the trunkCost attribute of the Trunk component. The costMetric for 
      an LCo that is originated and terminated on the same module is 0."
::= { btdsLCoPathDataEntry 4 }

btdsLCoDelayMetric OBJECT-TYPE
   SYNTAX     Unsigned32 (0..100000)
   ACCESS     read-only
   STATUS     mandatory
   DESCRIPTION
     "This attribute gives the total delay of the route as the one way delay 
      for a 512 byte packet. It is calculated as the sum of the delays of all 
      trunks in the path stored in topology at the time the connection was 
      established. The delay for an LCo that is originated and terminated 
      on the same module is 0."
::= { btdsLCoPathDataEntry 5 }

btdsLCoRoundTripDelay OBJECT-TYPE
   SYNTAX     Unsigned32 (0..200000)
   ACCESS     read-only
   STATUS     mandatory
   DESCRIPTION
     "This attribute contains the time taken for a packet (cell) of 44 bytes 
      to be transmitted to the remote LCo and return to this LCo. The 
      number reported is given in milliseconds to the nearest millisecond. 
      A value of one millisecond is reported if the time is less than 1 
      millisecond even though the delay may be less than 1 Millisecond 
      when the LCo is originated and terminated on the same module."
::= { btdsLCoPathDataEntry 6 }

btdsLCoSetupPriority OBJECT-TYPE
   SYNTAX     Unsigned32 (0..4)
   ACCESS     read-only
   STATUS     mandatory
   DESCRIPTION
     "This attribute gives the priority at which the current path is 
      established. Zero is the highest priority and four is the lowest. The 
      holdingPriority, a complementary attribute of this component, 
      indicates the priority a path maintains once it is established."
::= { btdsLCoPathDataEntry 7 }

btdsLCoHoldingPriority OBJECT-TYPE
   SYNTAX     Unsigned32 (0..4)
   ACCESS     read-only
   STATUS     mandatory
   DESCRIPTION
     "This attribute gives the priority at which a path holds its current 
      path once the path is established. Zero is the highest priority and 
      four is the lowest. The setupPriority, a complementary attribute, 
      indicates the priority of a path at establishment time."
::= { btdsLCoPathDataEntry 8 }

btdsLCoRequiredTxBandwidth OBJECT-TYPE
   SYNTAX     Gauge32 (0..4294967295)
   ACCESS     read-only
   STATUS     mandatory
   DESCRIPTION
     "This attribute gives the actual bandwidth (in bits per second) 
      reserved by this path on each of the trunks of its route. This attribute 
      represents the bandwidth for traffic outgoing to the remote end 
      point. The originating end of the connection determines this value."
::= { btdsLCoPathDataEntry 9 }

btdsLCoRequiredRxBandwidth OBJECT-TYPE
   SYNTAX     Gauge32 (0..4294967295)
   ACCESS     read-only
   STATUS     mandatory
   DESCRIPTION
     "This attribute gives the actual bandwidth (in bits per second) 
      reserved by this path on each of trunks of its route. This attribute 
      represents the bandwidth for traffic incoming from the remote end 
      point. The originating end of the connection determines this value"
::= { btdsLCoPathDataEntry 10 }

btdsLCoRequiredTrafficType OBJECT-TYPE
   SYNTAX     INTEGER  {
                 voice(0),
                 data(1),
                 video(2),
                 trafficType1(3),
                 trafficType2(4),
                 trafficType3(5),
                 trafficType4(6),
                 trafficType5(7) }
   ACCESS     read-only
   STATUS     mandatory
   DESCRIPTION
     "This operational attribute indicates the type of traffic transmitted 
      over the path. There are eight possible traffic types, and the path can 
      transmit only one of them. The originating end of the connection 
      determines the type. These are arbitrary designations for traffic 
      type. The voice, data and video traffic types are defined, and five 
      other arbitrary traffic types can be defined by the network 
      administration. This attribute is used in the route selection process 
      to restrict the route to trunks that support this traffic type. The 
      supportedTrafficType trunk attribute lists all the types of traffic 
      allowed on the trunk. For example, if requiredTrafficType is 
      specified as trafficType1 then only trunks that include trafficType1 
      in supportedTrafficType, will be candidates for this connection."
::= { btdsLCoPathDataEntry 11 }

btdsLCoPermittedTrunkTypes OBJECT-TYPE
   SYNTAX     OCTET STRING (SIZE (1))
   ACCESS     read-only
   STATUS     mandatory
   DESCRIPTION
     "This operational attribute lists up to eight types of trunk that can be 
      used on the route. The originating end of the connection determines 
      the types. The terrestrial and satellite trunk types have been 
      defined, leaving six remaining arbitrary types that can be defined by 
      the network administration. The trunk's type is indicated in the 
      trunkType attribute of the Trunk component. When selecting a 
      route, PORS only chooses trunks whose trunkType are in the 
      permittedTrunkTypes for the path.

      Description of bits:
      terrestrial(0)
      satellite(1)
      trunkType1(2)
      trunkType2(3)
      trunkType3(4)
      trunkType4(5)
      trunkType5(6)
      trunkType6(7)"
::= { btdsLCoPathDataEntry 12 }

btdsLCoRequiredSecurity OBJECT-TYPE
   SYNTAX     Unsigned32 (0..7)
   ACCESS     read-only
   STATUS     mandatory
   DESCRIPTION
     "This attribute indicates the required minimum level of security of 
      the trunks on the route. Zero represents the most secure and seven 
      represents the least secure. The trunk's security is indicated by the 
      trunkSecurity attribute of the Trunk component, and has values 
      identical in range and meaning to the requiredSecurity attribute. 
      PORS ensures that any route selected does not contain a trunk 
      whose trunkSecurity attribute is numerically greater than the 
      requiredSecurity."
::= { btdsLCoPathDataEntry 13 }

btdsLCoRequiredCustomerParameter OBJECT-TYPE
   SYNTAX     Unsigned32 (0..7)
   ACCESS     read-only
   STATUS     mandatory
   DESCRIPTION
     "This attribute indicates the allowed customer defined parameter of 
      the trunks on the route.The originating end of the connection 
      determines the customer defined parameter. Its value, a number 
      from zero to seven, is chosen by a network administration to have a 
      meaning specific to their network, thus allowing them to customize 
      the use of their trunks. A complementary trunk attribute, 
      customerParameter, also has a value from zero to seven. The route 
      selection process does not consider trunks whose 
      customerParameter is greater than the requiredCustomerParameter 
      of the path."
::= { btdsLCoPathDataEntry 14 }

btdsLCoEmissionPriority OBJECT-TYPE
   SYNTAX     Unsigned32 (0..2)
   ACCESS     read-only
   STATUS     mandatory
   DESCRIPTION
     "This attribute indicates the urgency with which packets on the path 
      are emitted by the trunks on the route. The originating end of the 
      connection selects the emissionPriority. EmissionPriority of zero 
      indicates the highest emission priority, while two indicates the 
      lowest emission priority. Packets with a higher emissionPriority (or 
      numerically less) are serviced and sent out before the packets of 
      lower emissionPriority (or numerically higher)."
::= { btdsLCoPathDataEntry 15 }

btdsLCoDiscardPriority OBJECT-TYPE
   SYNTAX     Unsigned32 (1..3)
   ACCESS     read-only
   STATUS     mandatory
   DESCRIPTION
     "This attribute indicates the importance of the packets on the 
      path.The originating end of the connection sets discardPriority. One 
      is used for paths carrying the most important traffic, and three is 
      used for paths carrying the least important traffic. Packets with 
      lower discardPriority(numerically lower) are discarded after 
      packets with a higher discardPriority(numerically higher)."
::= { btdsLCoPathDataEntry 16 }

btdsLCoPathType OBJECT-TYPE
   SYNTAX     INTEGER  {
                 normal(0),
                 manual(1),
                 forced(2) }
   ACCESS     read-only
   STATUS     mandatory
   DESCRIPTION
     "This attribute indicates whether the path for this PLC was 
      determined automatically or by static provisioning. Normal 
      pathTypes are selected automatically by Route Selector.The other 
      pathTypes are both manual pathTypes where the operator must 
      specify, through provisioning, a static route termed the manualPath. 
      A manual pathType connection is nearly identical to a normal path 
      type connection with the exception that the route is pre-provisioned. 
      For a manual pathType, bandwidth reservations are respected along 
      the path exactly as in a normal path. The last type, the forced 
      pathType, is also a manual path but regardless of the bandwidth 
      available the route is granted provided the trunks are operational 
      and there are sufficient Logical Channels (LChs).
      
      The forced pathType could result in over committing the reserved 
      bandwidth allowed on a trunk. A better way to achieve the effects of 
      a forced pathType is to use a manual pathType with setupPriority = 
      0 and holdingPriority = 0. In this manner the path will reserve 
      correct bandwidth and it will bump other paths if required while not 
      being bumped itself."
::= { btdsLCoPathDataEntry 17 }

btdsLCoRetryCount OBJECT-TYPE
   SYNTAX     Unsigned32 (0..255)
   ACCESS     read-only
   STATUS     mandatory
   DESCRIPTION
     "This attribute is the count of the number of times the path chosen 
      during route selection could not be instantiated. This count should 
      be three or below if the network is performing adequately. A high 
      value indicates that the route selection is often performed using an 
      out-of-date view of available network bandwidth and/or topology.
      This attribute will only increase at the calling end of the connection.
      This attribute is reset each time a path reconnects and stops 
      counting when it reaches its maximum value."
::= { btdsLCoPathDataEntry 18 }

btdsLCoPathFailureCount OBJECT-TYPE
   SYNTAX     Unsigned32 (0..65535)
   ACCESS     read-only
   STATUS     mandatory
   DESCRIPTION
     "This attribute is the count of the number of times the path has 
      successfully connected. It is set to zero the first time the path is up. 
      If a path fails anytime after connecting this count will be 
      incremented when the path is up again. Failed route requests do not 
      count in this statistic. See retryCount above. This attribute stops 
      counting at its maximum value."
::= { btdsLCoPathDataEntry 19 }

btdsLCoReasonForNoRoute OBJECT-TYPE
   SYNTAX     INTEGER  {
                 none(0),
                 destinationNameTooLong(1),
                 destinationNotSpecified(2),
                 unknownDestinationName(3),
                 incorrectDestination(4),
                 incorrectDestinationEndPoint(5),
                 unknownSource(6),
                 unknownDestination(7),
                 sameNode(8),
                 routeCostTooMuch(9),
                 routesDelayTooLong(10),
                 attributesNotMet(11),
                 anError(12),
                 attributeProfileProblem(13),
                 manualPathIndexProblem(14) }
   ACCESS     read-only
   STATUS     mandatory
   DESCRIPTION
     "This attribute is the route selection's reasonForNoRoute and 
      provides a brief reason for which a route was not selected. The 
      reasons are essentially self-explanatory. Perhaps two reasons for no 
      route require some explanation. The reason 
      unknownRemoteNodeName is issued when the remote node name 
      is not in the topological database. The reason plcAttributesNotMet 
      is issued when there is no network connectivity at a level specified 
      by the PLC attributes. This reason is also issued when there is no 
      physical connectivity between two end nodes."
   DEFVAL     { none }
::= { btdsLCoPathDataEntry 20 }

btdsLCoLastTearDownReason OBJECT-TYPE
   SYNTAX     INTEGER  {
                 none(0),
                 normalShutDown(1),
                 insufficientTxLcOrBandwidth(2),
                 insufficientRxLcOrBandwidth(3),
                 trunkFailure(4),
                 trunkCardFailure(5),
                 operatorForced(6),
                 lostLcnClash(7),
                 networkCongestion(8),
                 trunkNotFound(9),
                 farEndNotFound(10),
                 wrongModuleReached(11),
                 farEndBusy(12),
                 callLoopedBack(13),
                 unknownReason(14),
                 farEndNotReady(15),
                 remoteNameMismatch(16),
                 serviceTypeMismatch(17),
                 reconnectFromFarEnd(18),
                 bumped(19),
                 accessCardFailure(20),
                 optimized(21),
                 overrideRemoteName(22),
                 trunkOrFarEndDidNotSupportMode(23) }
   ACCESS     read-only
   STATUS     mandatory
   DESCRIPTION
     "This attribute reflects the last tear down reason for a connection 
      (LCo). In many cases this displays the reason for a momentary 
      service interruption. This attribute applies to the last path failure 
      only. If a path is no longer up, this may give an indication to the 
      reason that the path has failed. In many cases an alarm will also be 
      generated with more specific information. The following is a brief 
      description of the reasons:
      none - This path has no information for the teardown this is typical 
      of a path provisioned with no remoteName that has not been up.
      normalShutDown - This path has gone down due to normal call 
      termination.
      insufficientTxLcOrBandwidth - At present there is either no 
      available bandwidth or logical channel numbers available on one or 
      more of the trunks for this path in the transmit direction.
      insufficientRxLcOrBandwidth - At present there is either no 
      available bandwidth or logical channel numbers available on one or 
      more of the trunks for this path in the receive direction.
      trunkFailure- A trunk on the path has failed or has gone down due 
      to a provisioning change of a critical attribute.
      trunkCardFailure- A trunk FP card has failed along the path.
      accessCardFailure- The FP on which the peer access service was 
      running has failed.
      operatorForced- The path has terminated due to the operator 
      locking a trunk along the path.
      lostLcnClash- The path has terminated because the PA's at both 
      ends of an intermediate trunk have allocated the same LC to 
      different calls. When this happens both calls must go down and then 
      try to come up again a fraction of a second later (effectively 
      ensuring that they will now be assigned different LC's). It is normal 
      to get the odd clash especially when the PA's usedLC is 
      approaching the PA's maxLC.
      networkCongestion - The path has failed due to control information 
      being lost and not recoverable.
      trunkNotFound - Occurs on a manual path usually. Check for 
      trunks not up or names provisioned incorrectly.
      farEndNotFound - The far end is not provisioned or is not up. 
      Check remote Name.
      wrongModuleReached - This may occur on a manual path. Check 
      provisioning for correct trunk and service names. For a normal 
      path, the network Topology may be changing check remoteName.
      farEndBusy - The far end has been reached but it is busy. Check 
      remoteName and remote end provisioning.
      callLoopedBack - This LCo is provisioned to call itself. Re-
      provision since this is invalid.
      unknownReason - The failure was not resolved.
      farEndNotReady - The remote end was reached but the connection 
      was refused due to the remote end not being enabled.
      remoteNameMismatch - The remote end has alarmed and rejected 
      this setup due to remoteName provisioning.
      serviceTypeMismatch - The remote Service Type does not match 
      this service type. Check provisioning.
      reconnectFromFarEnd - The remote end re-established this 
      connection. Check the remote end lastTearDownReason to 
      determine the real reason.
      bumped - Another call bumped this path from a trunk to get 
      bandwidth (or an LC) which it required to come up. This other path 
      had a higher setupPriority than this path's holdingPriority hence it 
      was allowed to steal the bandwidth (or LC) from this path.
      optimized - This call has been rerouted due to the optimization 
      feature. The call is still active this just indicates why the path 
      changed.
      trunkOrFarEndDidNotSupportMode - This call was unable to 
      complete because a mode required by the service was not supported 
      by one of the trunks the route went through or by the far end service 
      it connected to. Currently the only mode that this applies to is the 
      map/mux mode on TRUNK PA ATM component. Map mode was 
      required by the application (CES/FrAtm etc.) but was not available 
      on the TRUNK PA ATM component through which the call was 
      routed or the far end CES/FrAtm component did not specify the 
      same mode."
   DEFVAL     { none }
::= { btdsLCoPathDataEntry 21 }

btdsLCoPathFailureAction OBJECT-TYPE
   SYNTAX     INTEGER  {
                 disconnectConnection(0),
                 reRoutePath(1) }
   ACCESS     read-only
   STATUS     mandatory
   DESCRIPTION
     "This attribute displays whether the application is set to tolerate 
      momentary interruption of a path while a new path is selected. If 
      disconnectConnection is displayed, the application is informed as 
      soon as possible about a failure by disconnection. If the attribute 
      displays reRoutePath, the path may attempt an immediate reroute, 
      provided the failure is a recoverable failure. If rerouting fails the 
      application is informed of the failure. 
      With this option set to reRoutePath the LCo may wait up to 30 
      seconds before informing the service of complete disconnection in 
      order to allow both ends to attempt to reconnect. Note that if PLC 
      components are different at both ends only the calling end is 
      allowed to reconnect.
      
      All pathTypes respect this attribute. Also on a manualPath with 
      both ends provisioned with independent paths (at least with respect 
      to the failure) this option will have the desired effect that the path is 
      rerouted without complete disconnection at both ends"
::= { btdsLCoPathDataEntry 22 }

btdsLCoBumpPreference OBJECT-TYPE
   SYNTAX     INTEGER  {
                 bumpWhenNecessary(0),
                 bumpToObtainBestRoute(1) }
   ACCESS     read-only
   STATUS     mandatory
   DESCRIPTION
     "This attribute specifies when bumping will occur during route 
      selection process. Bumping may occur when necessary or always. It 
      will be necessary for a connection to bump if there is not enough 
      resources for the connection to be established and these resources 
      are occupied by a connection whose setupPriority is lower 
      (numerically higher) than the connection's setupPriority. A 
      connection may also always bump in order to obtain the best route."
::= { btdsLCoPathDataEntry 23 }

btdsLCoOptimization OBJECT-TYPE
   SYNTAX     INTEGER  {
                 disabled(0),
                 enabled(1) }
   ACCESS     read-only
   STATUS     mandatory
   DESCRIPTION
     "This attribute is used to specify whether this connection should 
      attempt to optimize its path when requested by the routing PORS 
      component. Every path is as optimal as it can be when it is 
      established, but as network traffic patterns and configurations 
      change this path may no longer be as optimal as it could be. The 
      PORS connection manager on a module requests circuits to 
      optimize at the optimization interval."
::= { btdsLCoPathDataEntry 24 }

btdsLCoPathUpDateTime OBJECT-TYPE
   SYNTAX     EnterpriseDateAndTime (SIZE (0 | 19))
   ACCESS     read-only
   STATUS     mandatory
   DESCRIPTION
     "This is the time stamp when the current path was established or 
      reestablished."
::= { btdsLCoPathDataEntry 25 }

btdsLCoStatsTable OBJECT-TYPE
   SYNTAX     SEQUENCE OF BtdsLCoStatsEntry
   ACCESS     not-accessible
   STATUS     mandatory
   DESCRIPTION
     "This group contains the operational statistics attributes for the path 
      oriented LCo."
::= { btdsLCo 11 }

btdsLCoStatsEntry OBJECT-TYPE
   SYNTAX     BtdsLCoStatsEntry
   ACCESS     not-accessible
   STATUS     mandatory
   DESCRIPTION
     "An entry in the btdsLCoStatsTable."
   INDEX {
      btdsIndex,
      btdsLCoIndex }
::= { btdsLCoStatsTable 1 }

BtdsLCoStatsEntry ::= SEQUENCE {
   btdsLCoPktsToNetwork
      PassportCounter64,
   btdsLCoBytesToNetwork
      PassportCounter64,
   btdsLCoPktsFromNetwork
      PassportCounter64,
   btdsLCoBytesFromNetwork
      PassportCounter64 }

btdsLCoPktsToNetwork OBJECT-TYPE
   SYNTAX     PassportCounter64 
   ACCESS     read-only
   STATUS     mandatory
   DESCRIPTION
     "This attribute counts the number of packets transmitted to the 
      network over this Logical Connection."
::= { btdsLCoStatsEntry 1 }

btdsLCoBytesToNetwork OBJECT-TYPE
   SYNTAX     PassportCounter64 
   ACCESS     read-only
   STATUS     mandatory
   DESCRIPTION
     "This attribute counts the number of bytes sent to the network over 
      this Logical Connection."
::= { btdsLCoStatsEntry 2 }

btdsLCoPktsFromNetwork OBJECT-TYPE
   SYNTAX     PassportCounter64 
   ACCESS     read-only
   STATUS     mandatory
   DESCRIPTION
     "This attribute counts the number of packets received from the 
      remote LCo via the network."
::= { btdsLCoStatsEntry 3 }

btdsLCoBytesFromNetwork OBJECT-TYPE
   SYNTAX     PassportCounter64 
   ACCESS     read-only
   STATUS     mandatory
   DESCRIPTION
     "This attribute counts the number of bytes received from the remote 
      LCo via the network."
::= { btdsLCoStatsEntry 4 }

btdsLCoPathTable OBJECT-TYPE
   SYNTAX     SEQUENCE OF BtdsLCoPathEntry
   ACCESS     not-accessible
   STATUS     mandatory
   DESCRIPTION
     "This attribute contains the trunk component names over which the 
      path has been instantiated and the remote end point name 
      terminating the path."
::= { btdsLCo 264 }

btdsLCoPathEntry OBJECT-TYPE
   SYNTAX     BtdsLCoPathEntry
   ACCESS     not-accessible
   STATUS     mandatory
   DESCRIPTION
     "An entry in the btdsLCoPathTable."
   INDEX {
      btdsIndex,
      btdsLCoIndex,
      btdsLCoPathValue }
::= { btdsLCoPathTable 1 }

BtdsLCoPathEntry ::= SEQUENCE {
   btdsLCoPathValue
      AsciiString }

btdsLCoPathValue OBJECT-TYPE
   SYNTAX     AsciiString (SIZE (0..40))
   ACCESS     read-only
   STATUS     mandatory
   DESCRIPTION
     "This variable represents both the value and the index for the
      btdsLCoPathTable."
::= { btdsLCoPathEntry 1 }


-- Btds/n Dpnss1
-- The Dpnss1 component handles Digital Private Network Signalling 
-- System No1 (DPNSS 1) messages for the purpose of voice/data call 
-- discrimination. Discrimination between a voice call and a data call 
-- causes adjustment of the VoiceService operational mode. 
-- A single instance of Dpnss1 component can be provisioned under a 
-- Btds/n component.
-- 
-- The operational mode of any VoiceService provisioned within one 
-- Primary Rate Interface (PRI) is controlled by the same Dpnss1 
-- component. 
-- 
-- To perform call discrimination, both ends of a Btds connection 
-- require the same call discrimination subcomponent (Mcdn or 
-- Dpnss1). Btds serviceFailureReason is 
-- mismatchedCallDiscriminator if the ends of a Btds connection 
-- have different call discrimination subcomponents.

btdsDpnss1 OBJECT IDENTIFIER ::= { btds 5 }



btdsDpnss1RowStatusTable OBJECT-TYPE
   SYNTAX     SEQUENCE OF BtdsDpnss1RowStatusEntry
   ACCESS     not-accessible
   STATUS     mandatory
   DESCRIPTION
     "This entry controls the addition and deletion of 
      btdsDpnss1 components."
::= { btdsDpnss1 1 }

btdsDpnss1RowStatusEntry OBJECT-TYPE
   SYNTAX     BtdsDpnss1RowStatusEntry
   ACCESS     not-accessible
   STATUS     mandatory
   DESCRIPTION
     "A single entry in the table represents a single 
      btdsDpnss1 component."
   INDEX {
      btdsIndex,
      btdsDpnss1Index }
::= { btdsDpnss1RowStatusTable 1 }

BtdsDpnss1RowStatusEntry ::= SEQUENCE {
   btdsDpnss1RowStatus
      RowStatus,
   btdsDpnss1ComponentName
      DisplayString,
   btdsDpnss1StorageType
      StorageType,
   btdsDpnss1Index
      NonReplicated }

btdsDpnss1RowStatus OBJECT-TYPE
   SYNTAX     RowStatus 
   ACCESS     read-write
   STATUS     mandatory
   DESCRIPTION
     "This variable is used as the basis for SNMP naming of
      btdsDpnss1 components.
      These components can be added and deleted."
::= { btdsDpnss1RowStatusEntry 1 }

btdsDpnss1ComponentName OBJECT-TYPE
   SYNTAX     DisplayString 
   ACCESS     read-only
   STATUS     mandatory
   DESCRIPTION
     "This variable provides the component's string name for
      use with the ASCII Console Interface"
::= { btdsDpnss1RowStatusEntry 2 }

btdsDpnss1StorageType OBJECT-TYPE
   SYNTAX     StorageType 
   ACCESS     read-only
   STATUS     mandatory
   DESCRIPTION
     "This variable represents the storage type value for the
      btdsDpnss1 tables."
::= { btdsDpnss1RowStatusEntry 4 }

btdsDpnss1Index OBJECT-TYPE
   SYNTAX     NonReplicated 
   ACCESS     not-accessible
   STATUS     mandatory
   DESCRIPTION
     "This variable represents the index for the btdsDpnss1 tables."
::= { btdsDpnss1RowStatusEntry 10 }

btdsDpnss1ProvTable OBJECT-TYPE
   SYNTAX     SEQUENCE OF BtdsDpnss1ProvEntry
   ACCESS     not-accessible
   STATUS     mandatory
   DESCRIPTION
     "This group contains the provisionable attribute for the Dpnss1 
      component to handle DPNSS 1 messages."
::= { btdsDpnss1 10 }

btdsDpnss1ProvEntry OBJECT-TYPE
   SYNTAX     BtdsDpnss1ProvEntry
   ACCESS     not-accessible
   STATUS     mandatory
   DESCRIPTION
     "An entry in the btdsDpnss1ProvTable."
   INDEX {
      btdsIndex,
      btdsDpnss1Index }
::= { btdsDpnss1ProvTable 1 }

BtdsDpnss1ProvEntry ::= SEQUENCE {
   btdsDpnss1TimeslotsX
      OCTET STRING }

btdsDpnss1TimeslotsX OBJECT-TYPE
   SYNTAX     OCTET STRING (SIZE (4))
   ACCESS     read-write
   STATUS     mandatory
   DESCRIPTION
     "This attribute contains the list of timeslots that are provisioned X 
      for call collision resolution. A timeslot not provisioned as X is 
      assumed to be Y.

      Description of bits:
      notused0(0)
      n1(1)
      n2(2)
      n3(3)
      n4(4)
      n5(5)
      n6(6)
      n7(7)
      n8(8)
      n9(9)
      n10(10)
      n11(11)
      n12(12)
      n13(13)
      n14(14)
      n15(15)
      n16(16)
      n17(17)
      n18(18)
      n19(19)
      n20(20)
      n21(21)
      n22(22)
      n23(23)
      n24(24)
      n25(25)
      n26(26)
      n27(27)
      n28(28)
      n29(29)
      n30(30)
      n31(31)"
::= { btdsDpnss1ProvEntry 1 }

btdsDpnss1VdcdTable OBJECT-TYPE
   SYNTAX     SEQUENCE OF BtdsDpnss1VdcdEntry
   ACCESS     not-accessible
   STATUS     mandatory
   DESCRIPTION
     "This group contains attributes which count the protocol messages 
      indicating changes to operational modes of VoiceServices."
::= { btdsDpnss1 12 }

btdsDpnss1VdcdEntry OBJECT-TYPE
   SYNTAX     BtdsDpnss1VdcdEntry
   ACCESS     not-accessible
   STATUS     mandatory
   DESCRIPTION
     "An entry in the btdsDpnss1VdcdTable."
   INDEX {
      btdsIndex,
      btdsDpnss1Index }
::= { btdsDpnss1VdcdTable 1 }

BtdsDpnss1VdcdEntry ::= SEQUENCE {
   btdsDpnss1NewVoiceCalls
      Counter32,
   btdsDpnss1NewDataCalls
      Counter32,
   btdsDpnss1VoiceToData
      Counter32,
   btdsDpnss1DataToVoice
      Counter32,
   btdsDpnss1CallClears
      Counter32 }

btdsDpnss1NewVoiceCalls OBJECT-TYPE
   SYNTAX     Counter32 
   ACCESS     read-only
   STATUS     mandatory
   DESCRIPTION
     "This attribute counts the number of messages indicating beginning 
      of establishment of a voice call. 
      This count wraps to zero after reaching its maximum value."
::= { btdsDpnss1VdcdEntry 1 }

btdsDpnss1NewDataCalls OBJECT-TYPE
   SYNTAX     Counter32 
   ACCESS     read-only
   STATUS     mandatory
   DESCRIPTION
     "This attribute counts the number of messages indicating beginning 
      of establishment of a data call. 
      This count wraps to zero after reaching its maximum value."
::= { btdsDpnss1VdcdEntry 2 }

btdsDpnss1VoiceToData OBJECT-TYPE
   SYNTAX     Counter32 
   ACCESS     read-only
   STATUS     mandatory
   DESCRIPTION
     "This attribute counts the number of messages indicating a change of 
      a call operational mode from voice transmission to data 
      transmission. 
      This count wraps to zero after reaching its maximum value."
::= { btdsDpnss1VdcdEntry 3 }

btdsDpnss1DataToVoice OBJECT-TYPE
   SYNTAX     Counter32 
   ACCESS     read-only
   STATUS     mandatory
   DESCRIPTION
     "This attribute counts the number of messages indicating a change of 
      a call operational mode from data transmission to voice 
      transmission. 
      This count wraps to zero after reaching its maximum value."
::= { btdsDpnss1VdcdEntry 4 }

btdsDpnss1CallClears OBJECT-TYPE
   SYNTAX     Counter32 
   ACCESS     read-only
   STATUS     mandatory
   DESCRIPTION
     "This attribute counts the number of CCS messages indicating the 
      end of a call. 
      This count wraps to zero after reaching its maximum value."
::= { btdsDpnss1VdcdEntry 5 }

btdsDpnss1FramesTable OBJECT-TYPE
   SYNTAX     SEQUENCE OF BtdsDpnss1FramesEntry
   ACCESS     not-accessible
   STATUS     mandatory
   DESCRIPTION
     "This group contains attributes which count layer 2 frames 
      potentially significant for voice/data call discrimination. See also 
      the description of HdlcStatistics group."
::= { btdsDpnss1 13 }

btdsDpnss1FramesEntry OBJECT-TYPE
   SYNTAX     BtdsDpnss1FramesEntry
   ACCESS     not-accessible
   STATUS     mandatory
   DESCRIPTION
     "An entry in the btdsDpnss1FramesTable."
   INDEX {
      btdsIndex,
      btdsDpnss1Index }
::= { btdsDpnss1FramesTable 1 }

BtdsDpnss1FramesEntry ::= SEQUENCE {
   btdsDpnss1FrmProcessed
      Counter32,
   btdsDpnss1FrmInvalid
      Counter32 }

btdsDpnss1FrmProcessed OBJECT-TYPE
   SYNTAX     Counter32 
   ACCESS     read-only
   STATUS     mandatory
   DESCRIPTION
     "This attribute counts the number of valid layer 2 frames containing 
      an Information Field with a protocol message. Changes to 
      operational mode of a VoiceService are triggered only by a subset of 
      processed frames. Many frames refer to the call progress and are 
      ignored from the standpoint of voice/data call discrimination. 
      This count wraps to zero after reaching its maximum value."
::= { btdsDpnss1FramesEntry 1 }

btdsDpnss1FrmInvalid OBJECT-TYPE
   SYNTAX     Counter32 
   ACCESS     read-only
   STATUS     mandatory
   DESCRIPTION
     "This attribute counts the number of invalid layer 2 frames 
      For DPNSS 1, a frames is counted as invalid if 
      - it is shorter than 3 octets or longer than 48 octets (excluding two 
      octets of Cyclic Redundancy Check), or 
      - it has an invalid bit combination in the Address Field, or 
      - the Control Field is inconsistent with the Address Field, or 
      - the type of data is invalid, or 
      - it relates to time slot 0. 
      For MCDN, a frame is counted as invalid if 
      - it is shorter than 4 or longer than 264 octets (excluding two octets 
      of Cyclic Redundancy Check), or 
      - it has an invalid bit combination in the Address Field, or 
      - it has missing or incorrect mandatory information elements. 
      This count wraps to zero after reaching its maximum value."
::= { btdsDpnss1FramesEntry 2 }

btdsDpnss1HdlcTable OBJECT-TYPE
   SYNTAX     SEQUENCE OF BtdsDpnss1HdlcEntry
   ACCESS     not-accessible
   STATUS     mandatory
   DESCRIPTION
     "This group contains attributes which count the signalling frame 
      events."
::= { btdsDpnss1 14 }

btdsDpnss1HdlcEntry OBJECT-TYPE
   SYNTAX     BtdsDpnss1HdlcEntry
   ACCESS     not-accessible
   STATUS     mandatory
   DESCRIPTION
     "An entry in the btdsDpnss1HdlcTable."
   INDEX {
      btdsIndex,
      btdsDpnss1Index }
::= { btdsDpnss1HdlcTable 1 }

BtdsDpnss1HdlcEntry ::= SEQUENCE {
   btdsDpnss1FrmFromIf
      Counter32,
   btdsDpnss1Aborts
      Counter32,
   btdsDpnss1CrcErrors
      Counter32,
   btdsDpnss1NonOctetErrors
      Counter32,
   btdsDpnss1Overruns
      Counter32,
   btdsDpnss1LargeFrmErrors
      Counter32 }

btdsDpnss1FrmFromIf OBJECT-TYPE
   SYNTAX     Counter32 
   ACCESS     read-only
   STATUS     mandatory
   DESCRIPTION
     "This attribute counts the number of all hdlc frames, correct or not, 
      received from the PRI. 
      This count wraps to zero after reaching its maximum value."
::= { btdsDpnss1HdlcEntry 2 }

btdsDpnss1Aborts OBJECT-TYPE
   SYNTAX     Counter32 
   ACCESS     read-only
   STATUS     mandatory
   DESCRIPTION
     "This attribute counts the number of frame receptions aborted before 
      completion, due to incoming frame format errors. 
      This count wraps to zero after reaching its maximum value."
::= { btdsDpnss1HdlcEntry 3 }

btdsDpnss1CrcErrors OBJECT-TYPE
   SYNTAX     Counter32 
   ACCESS     read-only
   STATUS     mandatory
   DESCRIPTION
     "This attribute counts the number of frames received with CRC 
      errors. 
      This count wraps to zero after reaching its maximum value."
::= { btdsDpnss1HdlcEntry 4 }

btdsDpnss1NonOctetErrors OBJECT-TYPE
   SYNTAX     Counter32 
   ACCESS     read-only
   STATUS     mandatory
   DESCRIPTION
     "This attribute counts the number of frames received that were non 
      octet aligned. 
      This count wraps to zero after reaching its maximum value."
::= { btdsDpnss1HdlcEntry 5 }

btdsDpnss1Overruns OBJECT-TYPE
   SYNTAX     Counter32 
   ACCESS     read-only
   STATUS     mandatory
   DESCRIPTION
     "This attribute counts the number of frames received for which 
      overruns occurred. 
      This count wraps to zero after reaching its maximum value."
::= { btdsDpnss1HdlcEntry 6 }

btdsDpnss1LargeFrmErrors OBJECT-TYPE
   SYNTAX     Counter32 
   ACCESS     read-only
   STATUS     mandatory
   DESCRIPTION
     "This attribute counts the number of received frames which were 
      longer than 1024 octets. 
      This count wraps to zero after reaching its maximum value."
::= { btdsDpnss1HdlcEntry 8 }

btdsDpnss1TSlotTable OBJECT-TYPE
   SYNTAX     SEQUENCE OF BtdsDpnss1TSlotEntry
   ACCESS     not-accessible
   STATUS     mandatory
   DESCRIPTION
     "This attribute displays the operational mode of every time slot 
      which is serviced by a voice service. 
      The value idle means that the time slot is not used to service a call, 
      hence the concerned voice service's bandwidth in the Passport 
      subnet is available for other uses. 
      The value voice means that a phone call is in progress. All 
      provisioned voice service's value added features have been activated 
      (features such as voice compression, silence suppression, echo 
      cancellation). 
      The value data means that a data call is in progress. All provisioned 
      voice service's value added features have been de-activated, so that 
      a clear 64 kbit/sec data connection is provided accross the Passport 
      subnet."
::= { btdsDpnss1 286 }

btdsDpnss1TSlotEntry OBJECT-TYPE
   SYNTAX     BtdsDpnss1TSlotEntry
   ACCESS     not-accessible
   STATUS     mandatory
   DESCRIPTION
     "An entry in the btdsDpnss1TSlotTable."
   INDEX {
      btdsIndex,
      btdsDpnss1Index,
      btdsDpnss1TSlotIndex }
::= { btdsDpnss1TSlotTable 1 }

BtdsDpnss1TSlotEntry ::= SEQUENCE {
   btdsDpnss1TSlotIndex
      Integer32,
   btdsDpnss1TSlotValue
      INTEGER }

btdsDpnss1TSlotIndex OBJECT-TYPE
   SYNTAX     Integer32 (1..31)
   ACCESS     not-accessible
   STATUS     mandatory
   DESCRIPTION
     "This variable represents the index for the btdsDpnss1TSlotTable."
::= { btdsDpnss1TSlotEntry 1 }

btdsDpnss1TSlotValue OBJECT-TYPE
   SYNTAX     INTEGER  {
                 idle(0),
                 voice(1),
                 data(2) }
   ACCESS     read-only
   STATUS     mandatory
   DESCRIPTION
     "This variable represents an individual value for the
      btdsDpnss1TSlotTable."
::= { btdsDpnss1TSlotEntry 2 }


-- Btds/n Mcdn
-- The Mcdn component handles MCDN protocol, or Meridian 1 
-- ISDN Primary Rate Interface, messages for the purpose of 
-- voice/data call discrimination. Discrimination between a voice call 
-- and a data call causes adjustment of the VoiceService operational 
-- mode. 
-- A single instance of Mcdn component can be provisioned under a 
-- Btds/n component. 
-- The operational mode of any VoiceService provisioned within one 
-- Primary Rate Interface (PRI) is controlled by the same Mcdn 
-- component.
-- 
-- To perform call discrimination, both ends of a Btds connection 
-- require the same call discrimination subcomponent (Mcdn or 
-- Dpnss1). Btds serviceFailureReason is 
-- mismatchedCallDiscriminator if the ends of a Btds connection 
-- have different call discrimination subcomponents.

btdsMcdn OBJECT IDENTIFIER ::= { btds 6 }



btdsMcdnRowStatusTable OBJECT-TYPE
   SYNTAX     SEQUENCE OF BtdsMcdnRowStatusEntry
   ACCESS     not-accessible
   STATUS     mandatory
   DESCRIPTION
     "This entry controls the addition and deletion of 
      btdsMcdn components."
::= { btdsMcdn 1 }

btdsMcdnRowStatusEntry OBJECT-TYPE
   SYNTAX     BtdsMcdnRowStatusEntry
   ACCESS     not-accessible
   STATUS     mandatory
   DESCRIPTION
     "A single entry in the table represents a single 
      btdsMcdn component."
   INDEX {
      btdsIndex,
      btdsMcdnIndex }
::= { btdsMcdnRowStatusTable 1 }

BtdsMcdnRowStatusEntry ::= SEQUENCE {
   btdsMcdnRowStatus
      RowStatus,
   btdsMcdnComponentName
      DisplayString,
   btdsMcdnStorageType
      StorageType,
   btdsMcdnIndex
      NonReplicated }

btdsMcdnRowStatus OBJECT-TYPE
   SYNTAX     RowStatus 
   ACCESS     read-write
   STATUS     mandatory
   DESCRIPTION
     "This variable is used as the basis for SNMP naming of
      btdsMcdn components.
      These components can be added and deleted."
::= { btdsMcdnRowStatusEntry 1 }

btdsMcdnComponentName OBJECT-TYPE
   SYNTAX     DisplayString 
   ACCESS     read-only
   STATUS     mandatory
   DESCRIPTION
     "This variable provides the component's string name for
      use with the ASCII Console Interface"
::= { btdsMcdnRowStatusEntry 2 }

btdsMcdnStorageType OBJECT-TYPE
   SYNTAX     StorageType 
   ACCESS     read-only
   STATUS     mandatory
   DESCRIPTION
     "This variable represents the storage type value for the
      btdsMcdn tables."
::= { btdsMcdnRowStatusEntry 4 }

btdsMcdnIndex OBJECT-TYPE
   SYNTAX     NonReplicated 
   ACCESS     not-accessible
   STATUS     mandatory
   DESCRIPTION
     "This variable represents the index for the btdsMcdn tables."
::= { btdsMcdnRowStatusEntry 10 }

btdsMcdnProvTable OBJECT-TYPE
   SYNTAX     SEQUENCE OF BtdsMcdnProvEntry
   ACCESS     not-accessible
   STATUS     mandatory
   DESCRIPTION
     "This group contains the provisionable attribute for the Mcdn 
      component."
::= { btdsMcdn 10 }

btdsMcdnProvEntry OBJECT-TYPE
   SYNTAX     BtdsMcdnProvEntry
   ACCESS     not-accessible
   STATUS     mandatory
   DESCRIPTION
     "An entry in the btdsMcdnProvTable."
   INDEX {
      btdsIndex,
      btdsMcdnIndex }
::= { btdsMcdnProvTable 1 }

BtdsMcdnProvEntry ::= SEQUENCE {
   btdsMcdnAdjPbxSide
      INTEGER }

btdsMcdnAdjPbxSide OBJECT-TYPE
   SYNTAX     INTEGER  {
                 slave(0),
                 master(1) }
   ACCESS     read-write
   STATUS     mandatory
   DESCRIPTION
     "This attribute holds the provisioning related to call collision 
      resolution. Its value must be that same as in the adjacent PBX, at 
      the other end of the PRI. To provision the call collision resolution in 
      Nortel's SL1 and Meridian 1 PBXs, the network operator responds 
      to the prompt SIDE by entering either MAS or SLAV. So if the 
      SLAV was entered, then the adjPbxSide has to be provisioned slave."
   DEFVAL     { slave }
::= { btdsMcdnProvEntry 1 }

btdsMcdnVdcdTable OBJECT-TYPE
   SYNTAX     SEQUENCE OF BtdsMcdnVdcdEntry
   ACCESS     not-accessible
   STATUS     mandatory
   DESCRIPTION
     "This group contains attributes which count the protocol messages 
      indicating changes to operational modes of VoiceServices."
::= { btdsMcdn 12 }

btdsMcdnVdcdEntry OBJECT-TYPE
   SYNTAX     BtdsMcdnVdcdEntry
   ACCESS     not-accessible
   STATUS     mandatory
   DESCRIPTION
     "An entry in the btdsMcdnVdcdTable."
   INDEX {
      btdsIndex,
      btdsMcdnIndex }
::= { btdsMcdnVdcdTable 1 }

BtdsMcdnVdcdEntry ::= SEQUENCE {
   btdsMcdnNewVoiceCalls
      Counter32,
   btdsMcdnNewDataCalls
      Counter32,
   btdsMcdnVoiceToData
      Counter32,
   btdsMcdnDataToVoice
      Counter32,
   btdsMcdnCallClears
      Counter32 }

btdsMcdnNewVoiceCalls OBJECT-TYPE
   SYNTAX     Counter32 
   ACCESS     read-only
   STATUS     mandatory
   DESCRIPTION
     "This attribute counts the number of messages indicating beginning 
      of establishment of a voice call. 
      This count wraps to zero after reaching its maximum value."
::= { btdsMcdnVdcdEntry 1 }

btdsMcdnNewDataCalls OBJECT-TYPE
   SYNTAX     Counter32 
   ACCESS     read-only
   STATUS     mandatory
   DESCRIPTION
     "This attribute counts the number of messages indicating beginning 
      of establishment of a data call. 
      This count wraps to zero after reaching its maximum value."
::= { btdsMcdnVdcdEntry 2 }

btdsMcdnVoiceToData OBJECT-TYPE
   SYNTAX     Counter32 
   ACCESS     read-only
   STATUS     mandatory
   DESCRIPTION
     "This attribute counts the number of messages indicating a change of 
      a call operational mode from voice transmission to data 
      transmission. 
      This count wraps to zero after reaching its maximum value."
::= { btdsMcdnVdcdEntry 3 }

btdsMcdnDataToVoice OBJECT-TYPE
   SYNTAX     Counter32 
   ACCESS     read-only
   STATUS     mandatory
   DESCRIPTION
     "This attribute counts the number of messages indicating a change of 
      a call operational mode from data transmission to voice 
      transmission. 
      This count wraps to zero after reaching its maximum value."
::= { btdsMcdnVdcdEntry 4 }

btdsMcdnCallClears OBJECT-TYPE
   SYNTAX     Counter32 
   ACCESS     read-only
   STATUS     mandatory
   DESCRIPTION
     "This attribute counts the number of CCS messages indicating the 
      end of a call. 
      This count wraps to zero after reaching its maximum value."
::= { btdsMcdnVdcdEntry 5 }

btdsMcdnFramesTable OBJECT-TYPE
   SYNTAX     SEQUENCE OF BtdsMcdnFramesEntry
   ACCESS     not-accessible
   STATUS     mandatory
   DESCRIPTION
     "This group contains attributes which count layer 2 frames 
      potentially significant for voice/data call discrimination. See also 
      the description of HdlcStatistics group."
::= { btdsMcdn 13 }

btdsMcdnFramesEntry OBJECT-TYPE
   SYNTAX     BtdsMcdnFramesEntry
   ACCESS     not-accessible
   STATUS     mandatory
   DESCRIPTION
     "An entry in the btdsMcdnFramesTable."
   INDEX {
      btdsIndex,
      btdsMcdnIndex }
::= { btdsMcdnFramesTable 1 }

BtdsMcdnFramesEntry ::= SEQUENCE {
   btdsMcdnFrmProcessed
      Counter32,
   btdsMcdnFrmInvalid
      Counter32 }

btdsMcdnFrmProcessed OBJECT-TYPE
   SYNTAX     Counter32 
   ACCESS     read-only
   STATUS     mandatory
   DESCRIPTION
     "This attribute counts the number of valid layer 2 frames containing 
      an Information Field with a protocol message. Changes to 
      operational mode of a VoiceService are triggered only by a subset of 
      processed frames. Many frames refer to the call progress and are 
      ignored from the standpoint of voice/data call discrimination. 
      This count wraps to zero after reaching its maximum value."
::= { btdsMcdnFramesEntry 1 }

btdsMcdnFrmInvalid OBJECT-TYPE
   SYNTAX     Counter32 
   ACCESS     read-only
   STATUS     mandatory
   DESCRIPTION
     "This attribute counts the number of invalid layer 2 frames 
      For DPNSS 1, a frames is counted as invalid if 
      - it is shorter than 3 octets or longer than 48 octets (excluding two 
      octets of Cyclic Redundancy Check), or 
      - it has an invalid bit combination in the Address Field, or 
      - the Control Field is inconsistent with the Address Field, or 
      - the type of data is invalid, or 
      - it relates to time slot 0. 
      For MCDN, a frame is counted as invalid if 
      - it is shorter than 4 or longer than 264 octets (excluding two octets 
      of Cyclic Redundancy Check), or 
      - it has an invalid bit combination in the Address Field, or 
      - it has missing or incorrect mandatory information elements. 
      This count wraps to zero after reaching its maximum value."
::= { btdsMcdnFramesEntry 2 }

btdsMcdnHdlcTable OBJECT-TYPE
   SYNTAX     SEQUENCE OF BtdsMcdnHdlcEntry
   ACCESS     not-accessible
   STATUS     mandatory
   DESCRIPTION
     "This group contains attributes which count the signalling frame 
      events."
::= { btdsMcdn 14 }

btdsMcdnHdlcEntry OBJECT-TYPE
   SYNTAX     BtdsMcdnHdlcEntry
   ACCESS     not-accessible
   STATUS     mandatory
   DESCRIPTION
     "An entry in the btdsMcdnHdlcTable."
   INDEX {
      btdsIndex,
      btdsMcdnIndex }
::= { btdsMcdnHdlcTable 1 }

BtdsMcdnHdlcEntry ::= SEQUENCE {
   btdsMcdnFrmFromIf
      Counter32,
   btdsMcdnAborts
      Counter32,
   btdsMcdnCrcErrors
      Counter32,
   btdsMcdnNonOctetErrors
      Counter32,
   btdsMcdnOverruns
      Counter32,
   btdsMcdnLargeFrmErrors
      Counter32 }

btdsMcdnFrmFromIf OBJECT-TYPE
   SYNTAX     Counter32 
   ACCESS     read-only
   STATUS     mandatory
   DESCRIPTION
     "This attribute counts the number of all hdlc frames, correct or not, 
      received from the PRI. 
      This count wraps to zero after reaching its maximum value."
::= { btdsMcdnHdlcEntry 2 }

btdsMcdnAborts OBJECT-TYPE
   SYNTAX     Counter32 
   ACCESS     read-only
   STATUS     mandatory
   DESCRIPTION
     "This attribute counts the number of frame receptions aborted before 
      completion, due to incoming frame format errors. 
      This count wraps to zero after reaching its maximum value."
::= { btdsMcdnHdlcEntry 3 }

btdsMcdnCrcErrors OBJECT-TYPE
   SYNTAX     Counter32 
   ACCESS     read-only
   STATUS     mandatory
   DESCRIPTION
     "This attribute counts the number of frames received with CRC 
      errors. 
      This count wraps to zero after reaching its maximum value."
::= { btdsMcdnHdlcEntry 4 }

btdsMcdnNonOctetErrors OBJECT-TYPE
   SYNTAX     Counter32 
   ACCESS     read-only
   STATUS     mandatory
   DESCRIPTION
     "This attribute counts the number of frames received that were non 
      octet aligned. 
      This count wraps to zero after reaching its maximum value."
::= { btdsMcdnHdlcEntry 5 }

btdsMcdnOverruns OBJECT-TYPE
   SYNTAX     Counter32 
   ACCESS     read-only
   STATUS     mandatory
   DESCRIPTION
     "This attribute counts the number of frames received for which 
      overruns occurred. 
      This count wraps to zero after reaching its maximum value."
::= { btdsMcdnHdlcEntry 6 }

btdsMcdnLargeFrmErrors OBJECT-TYPE
   SYNTAX     Counter32 
   ACCESS     read-only
   STATUS     mandatory
   DESCRIPTION
     "This attribute counts the number of received frames which were 
      longer than 1024 octets. 
      This count wraps to zero after reaching its maximum value."
::= { btdsMcdnHdlcEntry 8 }

btdsMcdnTSlotTable OBJECT-TYPE
   SYNTAX     SEQUENCE OF BtdsMcdnTSlotEntry
   ACCESS     not-accessible
   STATUS     mandatory
   DESCRIPTION
     "This attribute displays the operational mode of every time slot 
      which is serviced by a voice service. 
      The value idle means that the time slot is not used to service a call, 
      hence the concerned voice service's bandwidth in the Passport 
      subnet is available for other uses. 
      The value voice means that a phone call is in progress. All 
      provisioned voice service's value added features have been activated 
      (features such as voice compression, silence suppression, echo 
      cancellation). 
      The value data means that a data call is in progress. All provisioned 
      voice service's value added features have been de-activated, so that 
      a clear 64 kbit/sec data connection is provided accross the Passport 
      subnet."
::= { btdsMcdn 286 }

btdsMcdnTSlotEntry OBJECT-TYPE
   SYNTAX     BtdsMcdnTSlotEntry
   ACCESS     not-accessible
   STATUS     mandatory
   DESCRIPTION
     "An entry in the btdsMcdnTSlotTable."
   INDEX {
      btdsIndex,
      btdsMcdnIndex,
      btdsMcdnTSlotIndex }
::= { btdsMcdnTSlotTable 1 }

BtdsMcdnTSlotEntry ::= SEQUENCE {
   btdsMcdnTSlotIndex
      Integer32,
   btdsMcdnTSlotValue
      INTEGER }

btdsMcdnTSlotIndex OBJECT-TYPE
   SYNTAX     Integer32 (1..31)
   ACCESS     not-accessible
   STATUS     mandatory
   DESCRIPTION
     "This variable represents the index for the btdsMcdnTSlotTable."
::= { btdsMcdnTSlotEntry 1 }

btdsMcdnTSlotValue OBJECT-TYPE
   SYNTAX     INTEGER  {
                 idle(0),
                 voice(1),
                 data(2) }
   ACCESS     read-only
   STATUS     mandatory
   DESCRIPTION
     "This variable represents an individual value for the
      btdsMcdnTSlotTable."
::= { btdsMcdnTSlotEntry 2 }




-- 
-- Version and Compliance statements
-- 



-- Object-Group Statement:
-- A list of all current accessible leaf objects.

-- OBJECTS { btdsPlcRequiredSecurity,
--           btdsDpnss1NonOctetErrors,
--           btdsPlcPathAttributeToMinimize,
--           btdsLCoLastTearDownReason,
--           btdsUnknownStatus,
--           btdsFramerStorageType,
--           btdsPlcPathFailureAction,
--           btdsLCoRequiredSecurity,
--           btdsLCoPathFailureCount,
--           btdsPlcRequiredTxBandwidth,
--           btdsPlcHoldingPriority,
--           btdsPlcMaximumAcceptableDelay,
--           btdsPlcMaximumAcceptableCost,
--           btdsSnmpOperStatus,
--           btdsRowStatus,
--           btdsIfIndex,
--           btdsLCoPathFailureAction,
--           btdsPlcPermittedTrunkTypes,
--           btdsLCoRequiredTxBandwidth,
--           btdsLCoHoldingPriority,
--           btdsFramerProtocol,
--           btdsLCoRoundTripDelay,
--           btdsFramerIdlePattern,
--           btdsLCoBytesFromNetwork,
--           btdsStorageType,
--           btdsDpnss1FrmInvalid,
--           btdsPlcRequiredTrafficType,
--           btdsLCoEnd,
--           btdsLCoBumpPreference,
--           btdsPlcRequiredRxBandwidth,
--           btdsDpnss1Aborts,
--           btdsMcdnCallClears,
--           btdsFramerAdminState,
--           btdsLCoRetryCount,
--           btdsMcdnLargeFrmErrors,
--           btdsFramerFrmDumped,
--           btdsControlStatus,
--           btdsAdminState,
--           btdsMcdnCrcErrors,
--           btdsFramerRowStatus,
--           btdsLCoPktsFromNetwork,
--           btdsMcdnComponentName,
--           btdsIfAdminStatus,
--           btdsMcdnOverruns,
--           btdsCustomerIdentifier,
--           btdsLCoRequiredTrafficType,
--           btdsFramerLrcErrors,
--           btdsMcdnAborts,
--           btdsFramerUsageState,
--           btdsPlcRemoteName,
--           btdsLCoDelayMetric,
--           btdsUsageState,
--           btdsLCoCostMetric,
--           btdsFramerFrmLostInNetwork,
--           btdsDpnss1CallClears,
--           btdsLCoRequiredRxBandwidth,
--           btdsFramerTimeSlotAlignment,
--           btdsLCoComponentName,
--           btdsFramerOperationalState,
--           btdsDpnss1DataToVoice,
--           btdsLCoOverrideRemoteName,
--           btdsOperationalState,
--           btdsFramerSuppressedFrames,
--           btdsDpnss1Overruns,
--           btdsMcdnStorageType,
--           btdsDpnss1VoiceToData,
--           btdsFramerInsertedOutputDelay,
--           btdsFramerBtdsCellSize,
--           btdsMcdnAdjPbxSide,
--           btdsStandbyStatus,
--           btdsLCoPathValue,
--           btdsDpnss1ComponentName,
--           btdsLCoRequiredCustomerParameter,
--           btdsMcdnDataToVoice,
--           btdsMcdnNewDataCalls,
--           btdsAvailabilityStatus,
--           btdsMcdnFrmInvalid,
--           btdsAlarmStatus,
--           btdsPlcStorageType,
--           btdsPlcBumpPreference,
--           btdsDpnss1TimeslotsX,
--           btdsMcdnFrmFromIf,
--           btdsMcdnFrmProcessed,
--           btdsFramerNumOfIdleBytesToMonitor,
--           btdsMcdnNewVoiceCalls,
--           btdsDpnss1CrcErrors,
--           btdsMcdnRowStatus,
--           btdsPlcSetupPriority,
--           btdsPlcPathType,
--           btdsPlcOptimization,
--           btdsLCoStorageType,
--           btdsMcdnVoiceToData,
--           btdsDpnss1NewDataCalls,
--           btdsLCoSetupPriority,
--           btdsPlcMpathValue,
--           btdsPlcRowStatus,
--           btdsLCoOptimization,
--           btdsFramerFrmToIf,
--           btdsPlcComponentName,
--           btdsPlcEmissionPriority,
--           btdsDpnss1FrmFromIf,
--           btdsDpnss1FrmProcessed,
--           btdsDpnss1StorageType,
--           btdsProceduralStatus,
--           btdsLCoRowStatus,
--           btdsMcdnNonOctetErrors,
--           btdsLCoState,
--           btdsLCoPathUpDateTime,
--           btdsPlcRequiredCustomerParm,
--           btdsLCoEmissionPriority,
--           btdsDpnss1TSlotValue,
--           btdsFramerComponentName,
--           btdsPlcDiscardPriority,
--           btdsFramerInterfaceName,
--           btdsFramerFrmUnderRuns,
--           btdsComponentName,
--           btdsLCoReasonForNoRoute,
--           btdsMcdnTSlotValue,
--           btdsDpnss1NewVoiceCalls,
--           btdsLCoPathType,
--           btdsLCoBytesToNetwork,
--           btdsServiceFailureReason,
--           btdsDpnss1LargeFrmErrors,
--           btdsLCoPktsToNetwork,
--           btdsLCoPermittedTrunkTypes,
--           btdsDpnss1RowStatus,
--           btdsLCoDiscardPriority,
--           btdsFramerFrmFromIf }
-- STATUS  mandatory
-- DESCRIPTION
--   "A list of all current accessible leaf objects."

bitTransparentGroup OBJECT IDENTIFIER ::= { bitTransparentMIB 1 }
bitTransparentGroupBE OBJECT IDENTIFIER ::= { bitTransparentGroup 5 }
bitTransparentGroupBE01 OBJECT IDENTIFIER ::= { bitTransparentGroupBE 2 }
bitTransparentGroupBE01A OBJECT IDENTIFIER ::= { bitTransparentGroupBE01 2 }



-- Agent-Capabilities Statement:

-- PRODUCT-RELEASE "Passport Release 7.0 BitTransparent."
-- STATUS          mandatory
-- DESCRIPTION     "BitTransparent MIB: MIB Version BE01A,
--                  Software Version BG00S4C."
-- SUPPORTS        Nortel-Magellan-Passport-BitTransparentMIB
--    INCLUDES     { bitTransparentGroupBE01A }

bitTransparentCapabilities OBJECT IDENTIFIER ::= { bitTransparentMIB 3 }
bitTransparentCapabilitiesBE OBJECT IDENTIFIER ::= { bitTransparentCapabilities 5 }
bitTransparentCapabilitiesBE01 OBJECT IDENTIFIER ::= { bitTransparentCapabilitiesBE 2 }
bitTransparentCapabilitiesBE01A OBJECT IDENTIFIER ::= { bitTransparentCapabilitiesBE01 2 }





END
