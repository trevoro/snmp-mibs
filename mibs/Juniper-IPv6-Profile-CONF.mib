-- *****************************************************************************
-- Juniper-IPv6-Profile-CONF
--
-- SNMP Agent Capabilities definitions for the IPv6 Profile MIB.
--
-- Copyright (c) 2003 Juniper Networks, Inc.  All rights reserved.
-- *****************************************************************************

Juniper-IPv6-Profile-CONF  DEFINITIONS ::= BEGIN

IMPORTS
    MODULE-IDENTITY
        FROM SNMPv2-SMI
    AGENT-CAPABILITIES
        FROM SNMPv2-CONF
    juniProfileAgents
        FROM Juniper-Agents;

juniIpv6ProfileAgent  MODULE-IDENTITY
    LAST-UPDATED "200303111923Z"  -- 11-Mar-03 02:23 PM EST
    ORGANIZATION "Juniper Networks, Inc."
    CONTACT-INFO
        "       Juniper Networks, Inc.
        Postal: 10 Technology Park Drive
                Westford, MA  01886-3146
                USA
        Tel:    +1 978 589 5800
        E-mail: mib@Juniper.net"
    DESCRIPTION
        "The agent capabilities definitions for the IPv6 Profile component of
        the SNMP agent in the Juniper E-series family of products."
    -- Revision History
    REVISION    "200303111923Z"  -- 11-Mar-03 02:23 PM EST  - JUNOSe 5.1
    DESCRIPTION
        "The initial release of this management information module."
    ::= { juniProfileAgents 5 }


-- *****************************************************************************
-- IPv6 Profile SNMP Agent Capabilities definitions
-- *****************************************************************************
juniIpv6ProfileAgentV1  AGENT-CAPABILITIES
    PRODUCT-RELEASE
        "Version 1 of the IPv6 Profile component of the JUNOSe SNMP agent.  This
        version of the IPv6 Profile component is supported in JUNOSe 5.1 and
        subsequent system releases."
    STATUS      current
    DESCRIPTION
        "The MIB supported by the SNMP agent for the IPv6 Profile application
        in JUNOSe."
    SUPPORTS    Juniper-IPV6-PROFILE-MIB
        INCLUDES  {
            juniIpv6ProfileGroup }
    ::= { juniIpv6ProfileAgent 1 }

END
