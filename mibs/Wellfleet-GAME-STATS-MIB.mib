Wellfleet-GAME-STATS-MIB DEFINITIONS ::= BEGIN

-- Created by mdl2asn version 3.1
-- Creation date: Wed Aug 30 16:41:52 EDT 1995


    IMPORTS

      OBJECT-TYPE
        FROM RFC-1212
      DisplayString
        FROM RFC1213-MIB
      wfGameGroup
        FROM Wellfleet-COMMON-MIB;


    wfKernelTable OBJECT-TYPE
        SYNTAX	SEQUENCE OF WfKernelEntry
        ACCESS	not-accessible
        STATUS	mandatory
        DESCRIPTION
                "Table of kernel statistics, indexed by slot number"
        ::= { wfGameGroup 1 }

    wfKernelEntry OBJECT-TYPE
        SYNTAX	WfKernelEntry
        ACCESS	not-accessible
        STATUS	mandatory
        DESCRIPTION
                "A particular interface"
        INDEX	{ wfKernelSlot }
        ::= { wfKernelTable 1 }

    WfKernelEntry ::= SEQUENCE {
    	    wfKernelSlot
    		INTEGER,
    	    wfKernelMemorySize
    		INTEGER,
    	    wfKernelMemoryFree
    		INTEGER,
    	    wfKernelMemorySegsTotal
    		INTEGER,
    	    wfKernelMemorySegsFree
    		INTEGER,
    	    wfKernelMemoryMaxSegFree
    		INTEGER,
    	    wfKernelBuffersTotal
    		INTEGER,
    	    wfKernelBuffersFree
    		INTEGER,
    	    wfKernelTasksTotal
    		INTEGER,
    	    wfKernelTasksInQueue
    		INTEGER,
    	    wfKernelTimersTotal
    		INTEGER,
    	    wfKernelTimersActive
    		INTEGER,
    	    wfKernelBufOwnerTask1
    		DisplayString,
    	    wfKernelBufOwnerTask1Bufs
    		INTEGER,
    	    wfKernelBufOwnerTask2
    		DisplayString,
    	    wfKernelBufOwnerTask2Bufs
    		INTEGER,
    	    wfKernelBufOwnerTask3
    		DisplayString,
    	    wfKernelBufOwnerTask3Bufs
    		INTEGER,
    	    wfKernelBufOwnerTask4
    		DisplayString,
    	    wfKernelBufOwnerTask4Bufs
    		INTEGER,
    	    wfKernelBufOwnerTask5
    		DisplayString,
    	    wfKernelBufOwnerTask5Bufs
    		INTEGER,
    	    wfKernelBufOwnerTask6
    		DisplayString,
    	    wfKernelBufOwnerTask6Bufs
    		INTEGER,
    	    wfKernelBufOwnerTask7
    		DisplayString,
    	    wfKernelBufOwnerTask7Bufs
    		INTEGER,
    	    wfKernelBufOwnerTask8
    		DisplayString,
    	    wfKernelBufOwnerTask8Bufs
    		INTEGER,
    	    wfKernelBufOwnerTask9
    		DisplayString,
    	    wfKernelBufOwnerTask9Bufs
    		INTEGER,
    	    wfKernelBufOwnerTask10
    		DisplayString,
    	    wfKernelBufOwnerTask10Bufs
    		INTEGER,
    	    wfKernelMemOwnerTask1
    		DisplayString,
    	    wfKernelMemOwnerTask1Size
    		INTEGER,
    	    wfKernelMemOwnerTask2
    		DisplayString,
    	    wfKernelMemOwnerTask2Size
    		INTEGER,
    	    wfKernelMemOwnerTask3
    		DisplayString,
    	    wfKernelMemOwnerTask3Size
    		INTEGER,
    	    wfKernelMemOwnerTask4
    		DisplayString,
    	    wfKernelMemOwnerTask4Size
    		INTEGER,
    	    wfKernelMemOwnerTask5
    		DisplayString,
    	    wfKernelMemOwnerTask5Size
    		INTEGER,
    	    wfKernelMemOwnerTask6
    		DisplayString,
    	    wfKernelMemOwnerTask6Size
    		INTEGER,
    	    wfKernelMemOwnerTask7
    		DisplayString,
    	    wfKernelMemOwnerTask7Size
    		INTEGER,
    	    wfKernelMemOwnerTask8
    		DisplayString,
    	    wfKernelMemOwnerTask8Size
    		INTEGER,
    	    wfKernelMemOwnerTask9
    		DisplayString,
    	    wfKernelMemOwnerTask9Size
    		INTEGER,
    	    wfKernelMemOwnerTask10
    		DisplayString,
    	    wfKernelMemOwnerTask10Size
    		INTEGER,
    	    wfKernelAliasBuffsDropped
    		INTEGER,
    	    wfKernelBallocFail
    		INTEGER,
    	    wfKernelReplenEmpty
    		INTEGER,
    	    wfKernelMemoryFreeLow
    		INTEGER,
	    wfKernelAliasNoMembers
		INTEGER
        }

    wfKernelSlot OBJECT-TYPE
        SYNTAX	INTEGER
        ACCESS	read-only
        STATUS	mandatory
        DESCRIPTION
                "The slot number indexes the kernel statistics table"
        ::= { wfKernelEntry 1 }

    wfKernelMemorySize OBJECT-TYPE
        SYNTAX	INTEGER
        ACCESS	read-only
        STATUS	mandatory
        DESCRIPTION
                "The total size of allocatable memory, in bytes"
        ::= { wfKernelEntry 2 }

    wfKernelMemoryFree OBJECT-TYPE
        SYNTAX	INTEGER
        ACCESS	read-only
        STATUS	mandatory
        DESCRIPTION
                "The amount of memory which hasn't been allocated yet, in bytes"
        ::= { wfKernelEntry 3 }

    wfKernelMemorySegsTotal OBJECT-TYPE
        SYNTAX	INTEGER
        ACCESS	read-only
        STATUS	mandatory
        DESCRIPTION
                "Total number of memory segments in the kernel"
        ::= { wfKernelEntry 4 }

    wfKernelMemorySegsFree OBJECT-TYPE
        SYNTAX	INTEGER
        ACCESS	read-only
        STATUS	mandatory
        DESCRIPTION
                "Total number of unallocated memory segments in the kernel"
        ::= { wfKernelEntry 5 }

    wfKernelMemoryMaxSegFree OBJECT-TYPE
        SYNTAX	INTEGER
        ACCESS	read-only
        STATUS	mandatory
        DESCRIPTION
                "Size of the largest unallocated memory segment"
        ::= { wfKernelEntry 6 }

    wfKernelBuffersTotal OBJECT-TYPE
        SYNTAX	INTEGER
        ACCESS	read-only
        STATUS	mandatory
        DESCRIPTION
                "Total number of packet buffers"
        ::= { wfKernelEntry 7 }

    wfKernelBuffersFree OBJECT-TYPE
        SYNTAX	INTEGER
        ACCESS	read-only
        STATUS	mandatory
        DESCRIPTION
                "Number of packet buffers in the free pool"
        ::= { wfKernelEntry 8 }

    wfKernelTasksTotal OBJECT-TYPE
        SYNTAX	INTEGER
        ACCESS	read-only
        STATUS	mandatory
        DESCRIPTION
                "Number of tasks running"
        ::= { wfKernelEntry 9 }

    wfKernelTasksInQueue OBJECT-TYPE
        SYNTAX	INTEGER
        ACCESS	read-only
        STATUS	mandatory
        DESCRIPTION
                "Number of tasks awaiting scheduling"
        ::= { wfKernelEntry 10 }

    wfKernelTimersTotal OBJECT-TYPE
        SYNTAX	INTEGER
        ACCESS	read-only
        STATUS	mandatory
        DESCRIPTION
                "Total number of timers available"
        ::= { wfKernelEntry 11 }

    wfKernelTimersActive OBJECT-TYPE
        SYNTAX	INTEGER
        ACCESS	read-only
        STATUS	mandatory
        DESCRIPTION
                "Total number of timers in use by tasks"
        ::= { wfKernelEntry 12 }

    wfKernelBufOwnerTask1 OBJECT-TYPE
        SYNTAX	DisplayString
        ACCESS	read-only
        STATUS	mandatory
        DESCRIPTION
                "Activation address of task which owns many buffers"
        ::= { wfKernelEntry 13 }

    wfKernelBufOwnerTask1Bufs OBJECT-TYPE
        SYNTAX	INTEGER
        ACCESS	read-only
        STATUS	mandatory
        DESCRIPTION
                "Number of buffers owned by the task"
        ::= { wfKernelEntry 14 }

    wfKernelBufOwnerTask2 OBJECT-TYPE
        SYNTAX	DisplayString
        ACCESS	read-only
        STATUS	mandatory
        DESCRIPTION
                "Activation address of task which owns many buffers"
        ::= { wfKernelEntry 15 }

    wfKernelBufOwnerTask2Bufs OBJECT-TYPE
        SYNTAX	INTEGER
        ACCESS	read-only
        STATUS	mandatory
        DESCRIPTION
                "Number of buffers owned by the task"
        ::= { wfKernelEntry 16 }

    wfKernelBufOwnerTask3 OBJECT-TYPE
        SYNTAX	DisplayString
        ACCESS	read-only
        STATUS	mandatory
        DESCRIPTION
                "Activation address of task which owns many buffers"
        ::= { wfKernelEntry 17 }

    wfKernelBufOwnerTask3Bufs OBJECT-TYPE
        SYNTAX	INTEGER
        ACCESS	read-only
        STATUS	mandatory
        DESCRIPTION
                "Number of buffers owned by the task"
        ::= { wfKernelEntry 18 }

    wfKernelBufOwnerTask4 OBJECT-TYPE
        SYNTAX	DisplayString
        ACCESS	read-only
        STATUS	mandatory
        DESCRIPTION
                "Activation address of task which owns many buffers"
        ::= { wfKernelEntry 19 }

    wfKernelBufOwnerTask4Bufs OBJECT-TYPE
        SYNTAX	INTEGER
        ACCESS	read-only
        STATUS	mandatory
        DESCRIPTION
                "Number of buffers owned by the task"
        ::= { wfKernelEntry 20 }

    wfKernelBufOwnerTask5 OBJECT-TYPE
        SYNTAX	DisplayString
        ACCESS	read-only
        STATUS	mandatory
        DESCRIPTION
                "Activation address of task which owns many buffers"
        ::= { wfKernelEntry 21 }

    wfKernelBufOwnerTask5Bufs OBJECT-TYPE
        SYNTAX	INTEGER
        ACCESS	read-only
        STATUS	mandatory
        DESCRIPTION
                "Number of buffers owned by the task"
        ::= { wfKernelEntry 22 }

    wfKernelBufOwnerTask6 OBJECT-TYPE
        SYNTAX	DisplayString
        ACCESS	read-only
        STATUS	mandatory
        DESCRIPTION
                "Activation address of task which owns many buffers"
        ::= { wfKernelEntry 23 }

    wfKernelBufOwnerTask6Bufs OBJECT-TYPE
        SYNTAX	INTEGER
        ACCESS	read-only
        STATUS	mandatory
        DESCRIPTION
                "Number of buffers owned by the task"
        ::= { wfKernelEntry 24 }

    wfKernelBufOwnerTask7 OBJECT-TYPE
        SYNTAX	DisplayString
        ACCESS	read-only
        STATUS	mandatory
        DESCRIPTION
                "Activation address of task which owns many buffers"
        ::= { wfKernelEntry 25 }

    wfKernelBufOwnerTask7Bufs OBJECT-TYPE
        SYNTAX	INTEGER
        ACCESS	read-only
        STATUS	mandatory
        DESCRIPTION
                "Number of buffers owned by the task"
        ::= { wfKernelEntry 26 }

    wfKernelBufOwnerTask8 OBJECT-TYPE
        SYNTAX	DisplayString
        ACCESS	read-only
        STATUS	mandatory
        DESCRIPTION
                "Activation address of task which owns many buffers"
        ::= { wfKernelEntry 27 }

    wfKernelBufOwnerTask8Bufs OBJECT-TYPE
        SYNTAX	INTEGER
        ACCESS	read-only
        STATUS	mandatory
        DESCRIPTION
                "Number of buffers owned by the task"
        ::= { wfKernelEntry 28 }

    wfKernelBufOwnerTask9 OBJECT-TYPE
        SYNTAX	DisplayString
        ACCESS	read-only
        STATUS	mandatory
        DESCRIPTION
                "Activation address of task which owns many buffers"
        ::= { wfKernelEntry 29 }

    wfKernelBufOwnerTask9Bufs OBJECT-TYPE
        SYNTAX	INTEGER
        ACCESS	read-only
        STATUS	mandatory
        DESCRIPTION
                "Number of buffers owned by the task"
        ::= { wfKernelEntry 30 }

    wfKernelBufOwnerTask10 OBJECT-TYPE
        SYNTAX	DisplayString
        ACCESS	read-only
        STATUS	mandatory
        DESCRIPTION
                "Activation address of task which owns many buffers"
        ::= { wfKernelEntry 31 }

    wfKernelBufOwnerTask10Bufs OBJECT-TYPE
        SYNTAX	INTEGER
        ACCESS	read-only
        STATUS	mandatory
        DESCRIPTION
                "Number of buffers owned by the task"
        ::= { wfKernelEntry 32 }

    wfKernelMemOwnerTask1 OBJECT-TYPE
        SYNTAX	DisplayString
        ACCESS	read-only
        STATUS	mandatory
        DESCRIPTION
                "Activation address of task which owns a sizable amount of memory"
        ::= { wfKernelEntry 33 }

    wfKernelMemOwnerTask1Size OBJECT-TYPE
        SYNTAX	INTEGER
        ACCESS	read-only
        STATUS	mandatory
        DESCRIPTION
                "Amount of memory owned by the task"
        ::= { wfKernelEntry 34 }

    wfKernelMemOwnerTask2 OBJECT-TYPE
        SYNTAX	DisplayString
        ACCESS	read-only
        STATUS	mandatory
        DESCRIPTION
                "Activation address of task which owns a sizable amount of memory"
        ::= { wfKernelEntry 35 }

    wfKernelMemOwnerTask2Size OBJECT-TYPE
        SYNTAX	INTEGER
        ACCESS	read-only
        STATUS	mandatory
        DESCRIPTION
                "Amount of memory owned by the task"
        ::= { wfKernelEntry 36 }

    wfKernelMemOwnerTask3 OBJECT-TYPE
        SYNTAX	DisplayString
        ACCESS	read-only
        STATUS	mandatory
        DESCRIPTION
                "Activation address of task which owns a sizable amount of memory"
        ::= { wfKernelEntry 37 }

    wfKernelMemOwnerTask3Size OBJECT-TYPE
        SYNTAX	INTEGER
        ACCESS	read-only
        STATUS	mandatory
        DESCRIPTION
                "Amount of memory owned by the task"
        ::= { wfKernelEntry 38 }

    wfKernelMemOwnerTask4 OBJECT-TYPE
        SYNTAX	DisplayString
        ACCESS	read-only
        STATUS	mandatory
        DESCRIPTION
                "Activation address of task which owns a sizable amount of memory"
        ::= { wfKernelEntry 39 }

    wfKernelMemOwnerTask4Size OBJECT-TYPE
        SYNTAX	INTEGER
        ACCESS	read-only
        STATUS	mandatory
        DESCRIPTION
                "Amount of memory owned by the task"
        ::= { wfKernelEntry 40 }

    wfKernelMemOwnerTask5 OBJECT-TYPE
        SYNTAX	DisplayString
        ACCESS	read-only
        STATUS	mandatory
        DESCRIPTION
                "Activation address of task which owns a sizable amount of memory"
        ::= { wfKernelEntry 41 }

    wfKernelMemOwnerTask5Size OBJECT-TYPE
        SYNTAX	INTEGER
        ACCESS	read-only
        STATUS	mandatory
        DESCRIPTION
                "Amount of memory owned by the task"
        ::= { wfKernelEntry 42 }

    wfKernelMemOwnerTask6 OBJECT-TYPE
        SYNTAX	DisplayString
        ACCESS	read-only
        STATUS	mandatory
        DESCRIPTION
                "Activation address of task which owns a sizable amount of memory"
        ::= { wfKernelEntry 43 }

    wfKernelMemOwnerTask6Size OBJECT-TYPE
        SYNTAX	INTEGER
        ACCESS	read-only
        STATUS	mandatory
        DESCRIPTION
                "Amount of memory owned by the task"
        ::= { wfKernelEntry 44 }

    wfKernelMemOwnerTask7 OBJECT-TYPE
        SYNTAX	DisplayString
        ACCESS	read-only
        STATUS	mandatory
        DESCRIPTION
                "Activation address of task which owns a sizable amount of memory"
        ::= { wfKernelEntry 45 }

    wfKernelMemOwnerTask7Size OBJECT-TYPE
        SYNTAX	INTEGER
        ACCESS	read-only
        STATUS	mandatory
        DESCRIPTION
                "Amount of memory owned by the task"
        ::= { wfKernelEntry 46 }

    wfKernelMemOwnerTask8 OBJECT-TYPE
        SYNTAX	DisplayString
        ACCESS	read-only
        STATUS	mandatory
        DESCRIPTION
                "Activation address of task which owns a sizable amount of memory"
        ::= { wfKernelEntry 47 }

    wfKernelMemOwnerTask8Size OBJECT-TYPE
        SYNTAX	INTEGER
        ACCESS	read-only
        STATUS	mandatory
        DESCRIPTION
                "Amount of memory owned by the task"
        ::= { wfKernelEntry 48 }

    wfKernelMemOwnerTask9 OBJECT-TYPE
        SYNTAX	DisplayString
        ACCESS	read-only
        STATUS	mandatory
        DESCRIPTION
                "Activation address of task which owns a sizable amount of memory"
        ::= { wfKernelEntry 49 }

    wfKernelMemOwnerTask9Size OBJECT-TYPE
        SYNTAX	INTEGER
        ACCESS	read-only
        STATUS	mandatory
        DESCRIPTION
                "Amount of memory owned by the task"
        ::= { wfKernelEntry 50 }

    wfKernelMemOwnerTask10 OBJECT-TYPE
        SYNTAX	DisplayString
        ACCESS	read-only
        STATUS	mandatory
        DESCRIPTION
                "Activation address of task which owns a sizable amount of memory"
        ::= { wfKernelEntry 51 }

    wfKernelMemOwnerTask10Size OBJECT-TYPE
        SYNTAX	INTEGER
        ACCESS	read-only
        STATUS	mandatory
        DESCRIPTION
                "Amount of memory owned by the task"
        ::= { wfKernelEntry 52 }

    wfKernelAliasBuffsDropped OBJECT-TYPE
        SYNTAX	INTEGER
        ACCESS	read-only
        STATUS	mandatory
        DESCRIPTION
                "Number of alias buffers dropped due to lack of copy buffers"
        ::= { wfKernelEntry 53 }

    wfKernelBallocFail OBJECT-TYPE
        SYNTAX	INTEGER
        ACCESS	read-only
        STATUS	mandatory
        DESCRIPTION
                "The number of times a buffer couldn't be allocated via g_balloc because the free buffer pool was empty"
        ::= { wfKernelEntry 54 }

    wfKernelReplenEmpty OBJECT-TYPE
        SYNTAX	INTEGER
        ACCESS	read-only
        STATUS	mandatory
        DESCRIPTION
                "The number of times the free buffer pool was emptied via g_breplen"
        ::= { wfKernelEntry 55 }

    wfKernelMemoryFreeLow OBJECT-TYPE
        SYNTAX	INTEGER
        ACCESS	read-only
        STATUS	mandatory
        DESCRIPTION
                "The low point of the free memory pool, in bytes"
        ::= { wfKernelEntry 56 }

     wfKernelAliasNoMembers OBJECT-TYPE
         SYNTAX  INTEGER
         ACCESS  read-only
         STATUS  mandatory
         DESCRIPTION
                 "Number of alias buffers dropped due to either no members, or GID_GAME is the only member" 
         ::= { wfKernelEntry 57 }



    wfKernParamTable OBJECT-TYPE
        SYNTAX	SEQUENCE OF WfKernParamEntry
        ACCESS	not-accessible
        STATUS	mandatory
        DESCRIPTION
                "Table of kernel parameter records, indexed by slot number"
        ::= { wfGameGroup 2 }

    wfKernParamEntry OBJECT-TYPE
        SYNTAX	WfKernParamEntry
        ACCESS	not-accessible
        STATUS	mandatory
        DESCRIPTION
                "A particular interface"
        INDEX	{ wfKernParamSlot }
        ::= { wfKernParamTable 1 }

    WfKernParamEntry ::= SEQUENCE {
    	    wfKernParamSlot
    		INTEGER,
    	    wfKernParamTotMem
    		INTEGER,
    	    wfKernParamLocMem
    		INTEGER,
    	    wfKernParamGlobMem
    		INTEGER
        }

    wfKernParamSlot OBJECT-TYPE
        SYNTAX	INTEGER
        ACCESS	read-only
        STATUS	mandatory
        DESCRIPTION
                "The slot number indexes the kernel parameter table"
        ::= { wfKernParamEntry 1 }

    wfKernParamTotMem OBJECT-TYPE
        SYNTAX	INTEGER
        ACCESS	read-only
        STATUS	mandatory
        DESCRIPTION
                "The size of total Physical memory in Kbytes"
        ::= { wfKernParamEntry 2 }

    wfKernParamLocMem OBJECT-TYPE
        SYNTAX	INTEGER
        ACCESS	read-only
        STATUS	mandatory
        DESCRIPTION
                "The size of Local memory in Kbytes"
        ::= { wfKernParamEntry 3 }

    wfKernParamGlobMem OBJECT-TYPE
        SYNTAX	INTEGER
        ACCESS	read-only
        STATUS	mandatory
        DESCRIPTION
                "The size of Global memory in Kbytes"
        ::= { wfKernParamEntry 4 }

    wfKernCfgParamTable OBJECT-TYPE
        SYNTAX	SEQUENCE OF WfKernCfgParamEntry
        ACCESS	not-accessible
        STATUS	mandatory
        DESCRIPTION
                "Table of kernel configurable parameter records, indexed by slot number"
        ::= { wfGameGroup 3 }

    wfKernCfgParamEntry OBJECT-TYPE
        SYNTAX	WfKernCfgParamEntry
        ACCESS	not-accessible
        STATUS	mandatory
        DESCRIPTION
                "A particular interface"
        INDEX	{ wfKernCfgParamSlot }
        ::= { wfKernCfgParamTable 1 }

    WfKernCfgParamEntry ::= SEQUENCE {
    	    wfKernCfgParamDelete
    		INTEGER,
    	    wfKernCfgParamSlot
    		INTEGER,
    	    wfKernCfgParamStatus
    		INTEGER,
    	    wfKernCfgParamLocMem
    		INTEGER,
    	    wfKernCfgParamGlobMem
    		INTEGER,
    	    wfKernCfgParamGlobMemReset
    		INTEGER,
    	    wfKernCfgParamBufSize
    		INTEGER,
    	    wfKernCfgParamBufSizeReset
    		INTEGER
        }

    wfKernCfgParamDelete OBJECT-TYPE
        SYNTAX	INTEGER {
    		    created(1),
    		    deleted(2)
    		}
        ACCESS	read-write
        STATUS	mandatory
        DESCRIPTION
                "Create/Delete a kernel configurable parameter record."
        DEFVAL	{ created }
        ::= { wfKernCfgParamEntry 1 }

    wfKernCfgParamSlot OBJECT-TYPE
        SYNTAX	INTEGER
        ACCESS	read-only
        STATUS	mandatory
        DESCRIPTION
                "The slot number indexes the kernel configurable parameters record"
        ::= { wfKernCfgParamEntry 2 }

    wfKernCfgParamStatus OBJECT-TYPE
        SYNTAX	INTEGER
        ACCESS	read-only
        STATUS	mandatory
        DESCRIPTION
                "Status of last kernel configurable parameter change request."
        ::= { wfKernCfgParamEntry 3 }

    wfKernCfgParamLocMem OBJECT-TYPE
        SYNTAX	INTEGER
        ACCESS	read-only
        STATUS	mandatory
        DESCRIPTION
                "The amount of configured local memory in Kbytes"
        ::= { wfKernCfgParamEntry 4 }

    wfKernCfgParamGlobMem OBJECT-TYPE
        SYNTAX	INTEGER
        ACCESS	read-write
        STATUS	mandatory
        DESCRIPTION
                "The amount of configured global memory in kbytes"
        ::= { wfKernCfgParamEntry 5 }

    wfKernCfgParamGlobMemReset OBJECT-TYPE
        SYNTAX	INTEGER {
    		    on(1),
    		    off(2)
    		}
        ACCESS	read-write
        STATUS	mandatory
        DESCRIPTION
                "Reset the slot back to the software default global memory size.
                The software default value for global memory allocation will
                now be used on this slot for all memory configurations."
        DEFVAL	{ off }
        ::= { wfKernCfgParamEntry 6 }

    wfKernCfgParamBufSize OBJECT-TYPE
        SYNTAX	INTEGER
        ACCESS	read-write
        STATUS	mandatory
        DESCRIPTION
                "The configured buffer size in kbytes "
        ::= { wfKernCfgParamEntry 7 }

    wfKernCfgParamBufSizeReset OBJECT-TYPE
        SYNTAX	INTEGER {
    		    on(1),
    		    off(2)
    		}
        ACCESS	read-write
        STATUS	mandatory
        DESCRIPTION
                "Reset the slot back to the software default buffer size.
                The software default value for buffer size allocation will
                now be used on this slot for all buffer carvings."
        DEFVAL	{ off }
        ::= { wfKernCfgParamEntry 8 }

    wfKernelSysCfgTable OBJECT-TYPE
        SYNTAX	SEQUENCE OF WfKernelSysCfgEntry
        ACCESS	not-accessible
        STATUS	mandatory
        DESCRIPTION
                "Table of kernel's system configuration records, indexed by slot number"
        ::= { wfGameGroup 5 }

    wfKernelSysCfgEntry OBJECT-TYPE
        SYNTAX	WfKernelSysCfgEntry
        ACCESS	not-accessible
        STATUS	mandatory
        DESCRIPTION
                "A particular interface"
        INDEX	{ wfKernelSysCfgSlot }
        ::= { wfKernelSysCfgTable 1 }

    WfKernelSysCfgEntry ::= SEQUENCE {
    	    wfKernelSysCfgDelete
    		INTEGER,
    	    wfKernelSysCfgSlot
    		INTEGER,
    	    wfKernelSysCfgLogging
    		INTEGER
        }

    wfKernelSysCfgDelete OBJECT-TYPE
        SYNTAX	INTEGER {
    		    created(1),
    		    deleted(2)
    		}
        ACCESS	read-write
        STATUS	mandatory
        DESCRIPTION
                "Create/Delete a kernel configurable parameter record."
        DEFVAL	{ created }
        ::= { wfKernelSysCfgEntry 1 }

    wfKernelSysCfgSlot OBJECT-TYPE
        SYNTAX	INTEGER
        ACCESS	read-only
        STATUS	mandatory
        DESCRIPTION
                "The slot number indexes the kernel's system configuration record"
        ::= { wfKernelSysCfgEntry 2 }

    wfKernelSysCfgLogging OBJECT-TYPE
        SYNTAX	INTEGER {
    		    on(1),
    		    off(2)
    		}
        ACCESS	read-write
        STATUS	mandatory
        DESCRIPTION
                "Status of last kernel configurable parameter change request."
        DEFVAL	{ on }
        ::= { wfKernelSysCfgEntry 3 }

    END  -- Wellfleet-GAME-STATS-MIB
