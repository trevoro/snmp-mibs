RFC1158-MIB DEFINITIONS ::= BEGIN

IMPORTS 	IpAddress, enterprises, Gauge, TimeTicks, Counter, OBJECT-TYPE
				FROM RFC1155-SMI
			PhysAddress
				FROM SNMPv2-TC;

          ncd                           OBJECT IDENTIFIER ::= { enterprises 82 }
          ncd-mibs                      OBJECT IDENTIFIER ::= { ncd 2 }
          ncd-mibs-mib1                 OBJECT IDENTIFIER ::= { ncd-mibs 1 }
          ncd-mibs-mib2                 OBJECT IDENTIFIER ::= { ncd-mibs 2 }
          ncd-mibs-mib3                 OBJECT IDENTIFIER ::= { ncd-mibs 3 }
          ncdSystem                     OBJECT IDENTIFIER ::= { ncd-mibs-mib1 1 }
          ncdMbuf                       OBJECT IDENTIFIER ::= { ncd-mibs-mib1 2 }
          ncdEther                      OBJECT IDENTIFIER ::= { ncd-mibs-mib1 3 }
          ncdSerial                     OBJECT IDENTIFIER ::= { ncd-mibs-mib1 4 }
          ncdTcp                        OBJECT IDENTIFIER ::= { ncd-mibs-mib1 5 }
          ncdTftp                       OBJECT IDENTIFIER ::= { ncd-mibs-mib1 7 }
          ncdNfs                        OBJECT IDENTIFIER ::= { ncd-mibs-mib1 8 }
          ncdXdmcp                      OBJECT IDENTIFIER ::= { ncd-mibs-mib2 11 }
          ncdDecnet                     OBJECT IDENTIFIER ::= { ncd-mibs-mib2 12 }
          ncdLat                        OBJECT IDENTIFIER ::= { ncd-mibs-mib2 13 }
          ncdNameResolver               OBJECT IDENTIFIER ::= { ncd-mibs-mib2 14 }
          ncdFontService                OBJECT IDENTIFIER ::= { ncd-mibs-mib2 15 }
          ncdArp                        OBJECT IDENTIFIER ::= { ncd-mibs-mib2 19 }
          ncdIp                         OBJECT IDENTIFIER ::= { ncd-mibs-mib3 1 }
          ncdUdp                        OBJECT IDENTIFIER ::= { ncd-mibs-mib3 2 }
          ncdSerialDaemon               OBJECT IDENTIFIER ::= { ncd-mibs-mib3 3 }
          ncdDnetNameResolver           OBJECT IDENTIFIER ::= { ncd-mibs-mib3 4 }
          ncdBoot                       OBJECT IDENTIFIER ::= { ncd-mibs-mib3 5 }
          ncdConfig                     OBJECT IDENTIFIER ::= { ncd-mibs-mib3 6 }
          ncdXserver                    OBJECT IDENTIFIER ::= { ncd-mibs-mib3 7 }
          ncdDiag                       OBJECT IDENTIFIER ::= { ncd-mibs-mib3 8 }
          ncdDps                        OBJECT IDENTIFIER ::= { ncd-mibs-mib3 9 }
          ncdExec                       OBJECT IDENTIFIER ::= { ncd-mibs-mib3 10 }
          ncdLogin                      OBJECT IDENTIFIER ::= { ncd-mibs-mib3 11 }
          ncdPex                        OBJECT IDENTIFIER ::= { ncd-mibs-mib3 12 }
          ncdTerm                       OBJECT IDENTIFIER ::= { ncd-mibs-mib3 13 }
          ncdFile                       OBJECT IDENTIFIER ::= { ncd-mibs-mib3 14 }
          ncdPref                       OBJECT IDENTIFIER ::= { ncd-mibs-mib3 15 }
          ncdAccess                     OBJECT IDENTIFIER ::= { ncd-mibs-mib3 16 }
          ncdTokenRing                  OBJECT IDENTIFIER ::= { ncd-mibs-mib3 17 }
          ncdXremote                    OBJECT IDENTIFIER ::= { ncd-mibs-mib3 18 }
          ncdPpp                        OBJECT IDENTIFIER ::= { ncd-mibs-mib3 19 }
          ncdPrefPex                    OBJECT IDENTIFIER ::= { ncd-mibs-mib3 20 }
          ncd3270                       OBJECT IDENTIFIER ::= { ncd-mibs-mib3 21 }
          ncdParallel                   OBJECT IDENTIFIER ::= { ncd-mibs-mib3 22 }
          ncdTBD                        OBJECT IDENTIFIER ::= { ncd-mibs-mib3 99 }

          -- the ncdSystem Group

          ncdSysMemTotal OBJECT-TYPE
              SYNTAX  INTEGER
              ACCESS  read-only
              STATUS  optional
              ::= { ncdSystem 1 }

          ncdSysMemAvail OBJECT-TYPE
              SYNTAX  Gauge
              ACCESS  read-only
              STATUS  optional
              ::= { ncdSystem 2 }

          ncdSysMemFrags OBJECT-TYPE
              SYNTAX  Gauge
              ACCESS  read-only
              STATUS  optional
              ::= { ncdSystem 3 }

          ncdSysIdleTime OBJECT-TYPE
              SYNTAX  TimeTicks
              ACCESS  read-only
              STATUS  optional
              ::= { ncdSystem 4 }

          ncdSysBootPromVersion OBJECT-TYPE
              SYNTAX  OCTET STRING
              ACCESS  read-only
              STATUS  optional
              ::= { ncdSystem 5 }

          ncdSysKeyboardControllerVersion OBJECT-TYPE
              SYNTAX  OCTET STRING
              ACCESS  read-only
              STATUS  optional
              ::= { ncdSystem 6 }

          ncdSysAdminStatus OBJECT-TYPE
              SYNTAX  INTEGER
              ACCESS  read-write
              STATUS  optional
              ::= { ncdSystem 7 }

          ncdSysMemCode OBJECT-TYPE
              SYNTAX  INTEGER
              ACCESS  read-only
              STATUS  optional
              ::= { ncdSystem 8 }

          ncdSysQueryNameAtBoot OBJECT-TYPE
              SYNTAX  INTEGER
              ACCESS  read-write
              STATUS  optional
              ::= { ncdSystem 9 }

          ncdSysLowMemWarningThreshold OBJECT-TYPE
              SYNTAX  INTEGER
              ACCESS  read-write
              STATUS  optional
              ::= { ncdSystem 10 }

          ncdSysLicenseKey OBJECT-TYPE
              SYNTAX  OCTET STRING
              ACCESS  read-write
              STATUS  optional
              ::= { ncdSystem 11 }

          ncdSysLicensedFeatures OBJECT-TYPE
              SYNTAX  OCTET STRING
              ACCESS  read-only
              STATUS  optional
              ::= { ncdSystem 12 }

          ncdSysOptionalFeatures OBJECT-TYPE
              SYNTAX  OCTET STRING
              ACCESS  read-only
              STATUS  optional
              ::= { ncdSystem 13 }


          -- the ncdMbuf Group

          ncdMbufTotal OBJECT-TYPE
              SYNTAX  INTEGER
              ACCESS  read-only
              STATUS  optional
              ::= { ncdMbuf 1 }

          ncdMbufAvail OBJECT-TYPE
              SYNTAX  Gauge
              ACCESS  read-only
              STATUS  optional
              ::= { ncdMbuf 2 }

          ncdMbufClusterTotal OBJECT-TYPE
              SYNTAX  INTEGER
              ACCESS  read-only
              STATUS  optional
              ::= { ncdMbuf 3 }

          ncdMbufClusterAvail OBJECT-TYPE
              SYNTAX  Gauge
              ACCESS  read-only
              STATUS  optional
              ::= { ncdMbuf 4 }

          ncdMbufReserved OBJECT-TYPE
              SYNTAX  Gauge
              ACCESS  read-only
              STATUS  optional
              ::= { ncdMbuf 5 }

          ncdMbufDrops OBJECT-TYPE
              SYNTAX  Counter
              ACCESS  read-only
              STATUS  optional
              ::= { ncdMbuf 6 }

          ncdMbufWaits OBJECT-TYPE
              SYNTAX  Counter
              ACCESS  read-only
              STATUS  optional
              ::= { ncdMbuf 7 }

          ncdMbufPacketDatas OBJECT-TYPE
              SYNTAX  Gauge
              ACCESS  read-only
              STATUS  optional
              ::= { ncdMbuf 8 }

          ncdMbufPacketHeaders OBJECT-TYPE
              SYNTAX  Gauge
              ACCESS  read-only
              STATUS  optional
              ::= { ncdMbuf 9 }

          ncdMbufConnCtrlStructs OBJECT-TYPE
              SYNTAX  Gauge
              ACCESS  read-only
              STATUS  optional
              ::= { ncdMbuf 10 }

          ncdMbufATTable OBJECT-TYPE
              SYNTAX  Gauge
              ACCESS  read-only
              STATUS  optional
              ::= { ncdMbuf 11 }

          ncdMbufConnNames OBJECT-TYPE
              SYNTAX  Gauge
              ACCESS  read-only
              STATUS  optional
              ::= { ncdMbuf 12 }

          ncdMbufConnOptions OBJECT-TYPE
              SYNTAX  Gauge
              ACCESS  read-only
              STATUS  optional
              ::= { ncdMbuf 13 }

          ncdMbufFrags OBJECT-TYPE
              SYNTAX  Gauge
              ACCESS  read-only
              STATUS  optional
              ::= { ncdMbuf 14 }

          ncdMbufInterfaceAddr OBJECT-TYPE
              SYNTAX  Gauge
              ACCESS  read-only
              STATUS  optional
              ::= { ncdMbuf 15 }

          ncdMbufProtoCtrlStructs OBJECT-TYPE
              SYNTAX  Gauge
              ACCESS  read-only
              STATUS  optional
              ::= { ncdMbuf 16 }


          -- the ncdEther Group

          ncdEtherTable OBJECT-TYPE
              SYNTAX  SEQUENCE OF NcdEtherEntry
              ACCESS  not-accessible
              STATUS  optional
              ::= { ncdEther 1 }

          ncdEtherEntry OBJECT-TYPE
              SYNTAX  NcdEtherEntry
              ACCESS  not-accessible
              STATUS  optional
              ::= { ncdEtherTable 1 }

          NcdEtherEntry ::=
              SEQUENCE {
                  ncdEtherTableIndex
                      INTEGER,
                  ncdEtherInCrcErrors
                      Counter,
                  ncdEtherInMisseds
                      Counter,
                  ncdEtherInFrameErrors
                      Counter,
                  ncdEtherSingleCollisions
                      Counter,
                  ncdEtherMultipleCollisions
                      Counter,
                  ncdEtherLateCollisions
                      Counter,
                  ncdEtherOutDeferreds
                      Counter,
                  ncdEtherOutRetryErrors
                      Counter,
                  ncdEtherLostCarriers
                      Counter,
                  ncdEtherRestarts
                      Counter
              }

          ncdEtherTableIndex OBJECT-TYPE
              SYNTAX  INTEGER
              ACCESS  read-only
              STATUS  optional
              ::= { ncdEtherEntry 11 }

          ncdEtherInCrcErrors OBJECT-TYPE
              SYNTAX  Counter
              ACCESS  read-only
              STATUS  optional
              ::= { ncdEtherEntry 1 }

          ncdEtherInMisseds OBJECT-TYPE
              SYNTAX  Counter
              ACCESS  read-only
              STATUS  optional
              ::= { ncdEtherEntry 2 }

          ncdEtherInFrameErrors OBJECT-TYPE
              SYNTAX  Counter
              ACCESS  read-only
              STATUS  optional
              ::= { ncdEtherEntry 3 }

          ncdEtherSingleCollisions OBJECT-TYPE
              SYNTAX  Counter
              ACCESS  read-only
              STATUS  optional
              ::= { ncdEtherEntry 4 }

          ncdEtherMultipleCollisions OBJECT-TYPE
              SYNTAX  Counter
              ACCESS  read-only
              STATUS  optional
              ::= { ncdEtherEntry 5 }

          ncdEtherLateCollisions OBJECT-TYPE
              SYNTAX  Counter
              ACCESS  read-only
              STATUS  optional
              ::= { ncdEtherEntry 6 }

          ncdEtherOutDeferreds OBJECT-TYPE
              SYNTAX  Counter
              ACCESS  read-only
              STATUS  optional
              ::= { ncdEtherEntry 7 }

          ncdEtherOutRetryErrors OBJECT-TYPE
              SYNTAX  Counter
              ACCESS  read-only
              STATUS  optional
              ::= { ncdEtherEntry 8 }

          ncdEtherLostCarriers OBJECT-TYPE
              SYNTAX  Counter
              ACCESS  read-only
              STATUS  optional
              ::= { ncdEtherEntry 9 }

          ncdEtherRestarts OBJECT-TYPE
              SYNTAX  Counter
              ACCESS  read-only
              STATUS  optional
              ::= { ncdEtherEntry 10 }

          ncdEtherUseSNAPEncap OBJECT-TYPE
              SYNTAX  INTEGER
              ACCESS  read-write
              STATUS  optional
              ::= { ncdEther 11 }


          -- the ncdSerial Group

          ncdSerialTable OBJECT-TYPE
              SYNTAX  SEQUENCE OF NcdSerialEntry
              ACCESS  not-accessible
              STATUS  optional
              ::= { ncdSerial 1 }

          ncdSerialEntry OBJECT-TYPE
              SYNTAX  NcdSerialEntry
              ACCESS  not-accessible
              STATUS  optional
              ::= { ncdSerialTable 1 }

          NcdSerialEntry ::=
              SEQUENCE {
                  ncdSerialInPortNumber
                      INTEGER,
                  ncdSerialInOverruns
                      INTEGER,
                  ncdSerialInFrameErrors
                      INTEGER,
                  ncdSerialInParityErrors
                      INTEGER,
                  ncdSerialInBreakErrors
                      INTEGER,
                  ncdSerialInTotCharXmit
                      INTEGER,
                  ncdSerialInTotXmitInt
                      INTEGER,
                  ncdSerialInTotCharRcv
                      INTEGER,
                  ncdSerialInTotRcvInt
                      INTEGER,
                  ncdSerialInTotRcvErr
                      INTEGER
              }

          ncdSerialInPortNumber OBJECT-TYPE
              SYNTAX  INTEGER
              ACCESS  read-only
              STATUS  optional
              ::= { ncdSerialEntry 5 }

          ncdSerialInOverruns OBJECT-TYPE
              SYNTAX  INTEGER
              ACCESS  read-only
              STATUS  optional
              ::= { ncdSerialEntry 1 }

          ncdSerialInFrameErrors OBJECT-TYPE
              SYNTAX  INTEGER
              ACCESS  read-only
              STATUS  optional
              ::= { ncdSerialEntry 2 }

          ncdSerialInParityErrors OBJECT-TYPE
              SYNTAX  INTEGER
              ACCESS  read-only
              STATUS  optional
              ::= { ncdSerialEntry 3 }

          ncdSerialInBreakErrors OBJECT-TYPE
              SYNTAX  INTEGER
              ACCESS  read-only
              STATUS  optional
              ::= { ncdSerialEntry 4 }

          ncdSerialInTotCharXmit OBJECT-TYPE
              SYNTAX  INTEGER
              ACCESS  read-only
              STATUS  optional
              ::= { ncdSerialEntry 6 }

          ncdSerialInTotXmitInt OBJECT-TYPE
              SYNTAX  INTEGER
              ACCESS  read-only
              STATUS  optional
              ::= { ncdSerialEntry 7 }

          ncdSerialInTotCharRcv OBJECT-TYPE
              SYNTAX  INTEGER
              ACCESS  read-only
              STATUS  optional
              ::= { ncdSerialEntry 8 }

          ncdSerialInTotRcvInt OBJECT-TYPE
              SYNTAX  INTEGER
              ACCESS  read-only
              STATUS  optional
              ::= { ncdSerialEntry 9 }

          ncdSerialInTotRcvErr OBJECT-TYPE
              SYNTAX  INTEGER
              ACCESS  read-only
              STATUS  optional
              ::= { ncdSerialEntry 10 }

          ncdSerialIfTable OBJECT-TYPE
              SYNTAX  SEQUENCE OF NcdSerialIfEntry
              ACCESS  not-accessible
              STATUS  optional
              ::= { ncdSerial 2 }

          ncdSerialIfEntry OBJECT-TYPE
              SYNTAX  NcdSerialIfEntry
              ACCESS  not-accessible
              STATUS  optional
              ::= { ncdSerialIfTable 1 }

          NcdSerialIfEntry ::=
              SEQUENCE {
                  ncdSerialIfTableIndex
                      INTEGER,
                  ncdSerialIfTablePortNumber
                      INTEGER,
                  ncdSerialIfTableMode
                      INTEGER,
                  ncdSerialIfTableCurMode
                      INTEGER,
                  ncdSerialIfTableBaudRate
                      INTEGER,
                  ncdSerialIfTableDataBits
                      INTEGER,
                  ncdSerialIfTableStopBits
                      INTEGER,
                  ncdSerialIfTableParity
                      INTEGER,
                  ncdSerialIfTableHandshake
                      INTEGER,
                  ncdSerialIfTableActionOnDiscon
                      INTEGER
              }

          ncdSerialIfTableIndex OBJECT-TYPE
              SYNTAX  INTEGER
              ACCESS  read-only
              STATUS  optional
              ::= { ncdSerialIfEntry 1 }

          ncdSerialIfTablePortNumber OBJECT-TYPE
              SYNTAX  INTEGER
              ACCESS  read-only
              STATUS  optional
              ::= { ncdSerialIfEntry 2 }

          ncdSerialIfTableMode OBJECT-TYPE
              SYNTAX  INTEGER
              ACCESS  read-write
              STATUS  optional
              ::= { ncdSerialIfEntry 3 }

          ncdSerialIfTableCurMode OBJECT-TYPE
              SYNTAX  INTEGER
              ACCESS  read-write
              STATUS  optional
              ::= { ncdSerialIfEntry 9 }

          ncdSerialIfTableBaudRate OBJECT-TYPE
              SYNTAX  INTEGER
              ACCESS  read-write
              STATUS  optional
              ::= { ncdSerialIfEntry 4 }

          ncdSerialIfTableDataBits OBJECT-TYPE
              SYNTAX  INTEGER
              ACCESS  read-write
              STATUS  optional
              ::= { ncdSerialIfEntry 5 }

          ncdSerialIfTableStopBits OBJECT-TYPE
              SYNTAX  INTEGER
              ACCESS  read-write
              STATUS  optional
              ::= { ncdSerialIfEntry 6 }

          ncdSerialIfTableParity OBJECT-TYPE
              SYNTAX  INTEGER
              ACCESS  read-write
              STATUS  optional
              ::= { ncdSerialIfEntry 7 }

          ncdSerialIfTableHandshake OBJECT-TYPE
              SYNTAX  INTEGER
              ACCESS  read-write
              STATUS  optional
              ::= { ncdSerialIfEntry 8 }

          ncdSerialIfTableActionOnDiscon OBJECT-TYPE
              SYNTAX  INTEGER
              ACCESS  read-write
              STATUS  optional
              ::= { ncdSerialIfEntry 10 }

          ncdSerialSDTable OBJECT-TYPE
              SYNTAX  SEQUENCE OF NcdSerialSDEntry
              ACCESS  not-accessible
              STATUS  optional
              ::= { ncdSerial 3 }

          ncdSerialSDEntry OBJECT-TYPE
              SYNTAX  NcdSerialSDEntry
              ACCESS  not-accessible
              STATUS  optional
              ::= { ncdSerialSDTable 1 }

          NcdSerialSDEntry ::=
              SEQUENCE {
                  ncdSerialSDTableIndex
                      INTEGER,
                  ncdSerialSDTablePortNumber
                      INTEGER,
                  ncdSerialSDTableUseSerialProt
                      INTEGER,
                  ncdSerialSDTableTCPPort
                      INTEGER,
                  ncdSerialSDTableUseNCDnetObjName
                      OCTET STRING,
                  ncdSerialSDTableEnableLAT
                      INTEGER,
                  ncdSerialSDTableLATServName
                      OCTET STRING,
                  ncdSerialSDTableLATServRating
                      INTEGER
              }

          ncdSerialSDTableIndex OBJECT-TYPE
              SYNTAX  INTEGER
              ACCESS  read-only
              STATUS  optional
              ::= { ncdSerialSDEntry 1 }

          ncdSerialSDTablePortNumber OBJECT-TYPE
              SYNTAX  INTEGER
              ACCESS  read-only
              STATUS  optional
              ::= { ncdSerialSDEntry 2 }

          ncdSerialSDTableUseSerialProt OBJECT-TYPE
              SYNTAX  INTEGER
              ACCESS  read-write
              STATUS  optional
              ::= { ncdSerialSDEntry 3 }

          ncdSerialSDTableTCPPort OBJECT-TYPE
              SYNTAX  INTEGER
              ACCESS  read-write
              STATUS  optional
              ::= { ncdSerialSDEntry 4 }

          ncdSerialSDTableUseNCDnetObjName OBJECT-TYPE
              SYNTAX  OCTET STRING
              ACCESS  read-write
              STATUS  optional
              ::= { ncdSerialSDEntry 5 }

          ncdSerialSDTableEnableLAT OBJECT-TYPE
              SYNTAX  INTEGER
              ACCESS  read-write
              STATUS  optional
              ::= { ncdSerialSDEntry 6 }

          ncdSerialSDTableLATServName OBJECT-TYPE
              SYNTAX  OCTET STRING
              ACCESS  read-write
              STATUS  optional
              ::= { ncdSerialSDEntry 7 }

          ncdSerialSDTableLATServRating OBJECT-TYPE
              SYNTAX  INTEGER
              ACCESS  read-write
              STATUS  optional
              ::= { ncdSerialSDEntry 8 }


          -- the ncdTcp Group

          ncdTcpRetransDrops OBJECT-TYPE
              SYNTAX  Counter
              ACCESS  read-only
              STATUS  optional
              ::= { ncdTcp 1 }

          ncdTcpOutKeepAlives OBJECT-TYPE
              SYNTAX  Counter
              ACCESS  read-only
              STATUS  optional
              ::= { ncdTcp 2 }

          ncdTcpKeepAliveDrops OBJECT-TYPE
              SYNTAX  Counter
              ACCESS  read-only
              STATUS  optional
              ::= { ncdTcp 3 }

          ncdTcpInAcks OBJECT-TYPE
              SYNTAX  Counter
              ACCESS  read-only
              STATUS  optional
              ::= { ncdTcp 4 }

          ncdTcpOutBareAcks OBJECT-TYPE
              SYNTAX  Counter
              ACCESS  read-only
              STATUS  optional
              ::= { ncdTcp 5 }

          ncdTcpConnectTimeout OBJECT-TYPE
              SYNTAX  TimeTicks
              ACCESS  read-write
              STATUS  optional
              ::= { ncdTcp 6 }

          ncdTcpMaxRxt OBJECT-TYPE
              SYNTAX  INTEGER
              ACCESS  read-write
              STATUS  optional
              ::= { ncdTcp 7 }

          ncdTcpKeepIdle OBJECT-TYPE
              SYNTAX  TimeTicks
              ACCESS  read-write
              STATUS  optional
              ::= { ncdTcp 8 }

          ncdTcpKeepAliveIntvl OBJECT-TYPE
              SYNTAX  TimeTicks
              ACCESS  read-write
              STATUS  optional
              ::= { ncdTcp 9 }

          ncdTcpMaxKeepAliveIdeTime OBJECT-TYPE
              SYNTAX  TimeTicks
              ACCESS  read-write
              STATUS  optional
              ::= { ncdTcp 10 }

          ncdTcpDfltLingerTime OBJECT-TYPE
              SYNTAX  TimeTicks
              ACCESS  read-write
              STATUS  optional
              ::= { ncdTcp 11 }

          ncdTcpRecvBufferSize OBJECT-TYPE
              SYNTAX  INTEGER
              ACCESS  read-write
              STATUS  optional
              ::= { ncdTcp 12 }

          ncdTcpSendBufferSize OBJECT-TYPE
              SYNTAX  INTEGER
              ACCESS  read-write
              STATUS  optional
              ::= { ncdTcp 13 }


          -- the ncdTftp Group

          ncdTftpClientReadReqs OBJECT-TYPE
              SYNTAX  Counter
              ACCESS  read-only
              STATUS  optional
              ::= { ncdTftp 1 }

          ncdTftpClientWriteReqs OBJECT-TYPE
              SYNTAX  Counter
              ACCESS  read-only
              STATUS  optional
              ::= { ncdTftp 2 }

          ncdTftpClientInDataPkts OBJECT-TYPE
              SYNTAX  Counter
              ACCESS  read-only
              STATUS  optional
              ::= { ncdTftp 3 }

          ncdTftpClientInAcks OBJECT-TYPE
              SYNTAX  Counter
              ACCESS  read-only
              STATUS  optional
              ::= { ncdTftp 4 }

          ncdTftpClientInNoFileErrors OBJECT-TYPE
              SYNTAX  Counter
              ACCESS  read-only
              STATUS  optional
              ::= { ncdTftp 5 }

          ncdTftpClientInAccessErrors OBJECT-TYPE
              SYNTAX  Counter
              ACCESS  read-only
              STATUS  optional
              ::= { ncdTftp 6 }

          ncdTftpClientInDiskFullErrors OBJECT-TYPE
              SYNTAX  Counter
              ACCESS  read-only
              STATUS  optional
              ::= { ncdTftp 7 }

          ncdTftpClientNoBufs OBJECT-TYPE
              SYNTAX  Counter
              ACCESS  read-only
              STATUS  optional
              ::= { ncdTftp 8 }

          ncdTftpClientOutDataPkts OBJECT-TYPE
              SYNTAX  Counter
              ACCESS  read-only
              STATUS  optional
              ::= { ncdTftp 9 }

          ncdTftpClientOutAcks OBJECT-TYPE
              SYNTAX  Counter
              ACCESS  read-only
              STATUS  optional
              ::= { ncdTftp 10 }

          ncdTftpClientRetrans OBJECT-TYPE
              SYNTAX  Counter
              ACCESS  read-only
              STATUS  optional
              ::= { ncdTftp 11 }


          -- the ncdNfs Group

          ncdNfsClientNulls OBJECT-TYPE
              SYNTAX  Counter
              ACCESS  read-only
              STATUS  optional
              ::= { ncdNfs 1 }

          ncdNfsClientGetAttributes OBJECT-TYPE
              SYNTAX  Counter
              ACCESS  read-only
              STATUS  optional
              ::= { ncdNfs 2 }

          ncdNfsClientSetAttributes OBJECT-TYPE
              SYNTAX  Counter
              ACCESS  read-only
              STATUS  optional
              ::= { ncdNfs 3 }

          ncdNfsClientGetRoots OBJECT-TYPE
              SYNTAX  Counter
              ACCESS  read-only
              STATUS  optional
              ::= { ncdNfs 4 }

          ncdNfsClientLookups OBJECT-TYPE
              SYNTAX  Counter
              ACCESS  read-only
              STATUS  optional
              ::= { ncdNfs 5 }

          ncdNfsClientReadLinks OBJECT-TYPE
              SYNTAX  Counter
              ACCESS  read-only
              STATUS  optional
              ::= { ncdNfs 6 }

          ncdNfsClientReads OBJECT-TYPE
              SYNTAX  Counter
              ACCESS  read-only
              STATUS  optional
              ::= { ncdNfs 7 }

          ncdNfsClientWriteCaches OBJECT-TYPE
              SYNTAX  Counter
              ACCESS  read-only
              STATUS  optional
              ::= { ncdNfs 8 }

          ncdNfsClientWrites OBJECT-TYPE
              SYNTAX  Counter
              ACCESS  read-only
              STATUS  optional
              ::= { ncdNfs 9 }

          ncdNfsClientCreates OBJECT-TYPE
              SYNTAX  Counter
              ACCESS  read-only
              STATUS  optional
              ::= { ncdNfs 10 }

          ncdNfsClientRemoves OBJECT-TYPE
              SYNTAX  Counter
              ACCESS  read-only
              STATUS  optional
              ::= { ncdNfs 11 }

          ncdNfsClientRenames OBJECT-TYPE
              SYNTAX  Counter
              ACCESS  read-only
              STATUS  optional
              ::= { ncdNfs 12 }

          ncdNfsClientCreateLinks OBJECT-TYPE
              SYNTAX  Counter
              ACCESS  read-only
              STATUS  optional
              ::= { ncdNfs 13 }

          ncdNfsClientCreateSymlinks OBJECT-TYPE
              SYNTAX  Counter
              ACCESS  read-only
              STATUS  optional
              ::= { ncdNfs 14 }

          ncdNfsClientMakeDirs OBJECT-TYPE
              SYNTAX  Counter
              ACCESS  read-only
              STATUS  optional
              ::= { ncdNfs 15 }

          ncdNfsClientRemoveDirs OBJECT-TYPE
              SYNTAX  Counter
              ACCESS  read-only
              STATUS  optional
              ::= { ncdNfs 16 }

          ncdNfsClientReadDirs OBJECT-TYPE
              SYNTAX  Counter
              ACCESS  read-only
              STATUS  optional
              ::= { ncdNfs 17 }

          ncdNfsClientFileSysStats OBJECT-TYPE
              SYNTAX  Counter
              ACCESS  read-only
              STATUS  optional
              ::= { ncdNfs 18 }


          -- the ncdXdmcp Group

          ncdXdmcpSendKeepAlivesTime OBJECT-TYPE
              SYNTAX  TimeTicks
              ACCESS  read-write
              STATUS  optional
              ::= { ncdXdmcp 1 }

          ncdXdmcpKeepAlivesDeadTime OBJECT-TYPE
              SYNTAX  TimeTicks
              ACCESS  read-write
              STATUS  optional
              ::= { ncdXdmcp 2 }

          ncdXdmcpcpDisplayClass OBJECT-TYPE
              SYNTAX  OCTET STRING
              ACCESS  read-write
              STATUS  optional
              ::= { ncdXdmcp 3 }

          ncdXdmcpMfgDisplayId OBJECT-TYPE
              SYNTAX  OCTET STRING
              ACCESS  read-only
              STATUS  optional
              ::= { ncdXdmcp 4 }

          ncdXdmcpBroadcastWaitTime OBJECT-TYPE
              SYNTAX  INTEGER
              ACCESS  read-write
              STATUS  optional
              ::= { ncdXdmcp 5 }

          ncdXdmcpBroadcasts OBJECT-TYPE
              SYNTAX  INTEGER
              ACCESS  read-write
              STATUS  optional
              ::= { ncdXdmcp 6 }

          ncdXdmcpIndirects OBJECT-TYPE
              SYNTAX  INTEGER
              ACCESS  read-write
              STATUS  optional
              ::= { ncdXdmcp 7 }

          ncdXdmcpWhenFirstClientExits OBJECT-TYPE
              SYNTAX  INTEGER
              ACCESS  read-write
              STATUS  optional
              ::= { ncdXdmcp 8 }


          -- the ncdDecnet Group

          ncdDecnetConnectTimeout OBJECT-TYPE
              SYNTAX  TimeTicks
              ACCESS  read-write
              STATUS  optional
              ::= { ncdDecnet 1 }

          ncdDecnetRetransLimit OBJECT-TYPE
              SYNTAX  INTEGER
              ACCESS  read-write
              STATUS  optional
              ::= { ncdDecnet 2 }

          ncdDecnetKeepaliveTimeout OBJECT-TYPE
              SYNTAX  TimeTicks
              ACCESS  read-write
              STATUS  optional
              ::= { ncdDecnet 3 }

          ncdDecnetHelloTimeout OBJECT-TYPE
              SYNTAX  TimeTicks
              ACCESS  read-write
              STATUS  optional
              ::= { ncdDecnet 4 }

          ncdDecnetRouterTimeout OBJECT-TYPE
              SYNTAX  TimeTicks
              ACCESS  read-write
              STATUS  optional
              ::= { ncdDecnet 5 }

          ncdDecnetMopIdTimeout OBJECT-TYPE
              SYNTAX  TimeTicks
              ACCESS  read-write
              STATUS  optional
              ::= { ncdDecnet 6 }

          ncdDecnetAddress OBJECT-TYPE
              SYNTAX  PhysAddress
              ACCESS  read-only
              STATUS  optional
              ::= { ncdDecnet 8 }

          ncdDecnetNewAddress OBJECT-TYPE
              SYNTAX  PhysAddress
              ACCESS  read-write
              STATUS  optional
              ::= { ncdDecnet 9 }

          ncdDecnetDesignatedRouter OBJECT-TYPE
              SYNTAX  PhysAddress
              ACCESS  read-write
              STATUS  optional
              ::= { ncdDecnet 10 }

          ncdDecnetDnetUserName OBJECT-TYPE
              SYNTAX  OCTET STRING
              ACCESS  read-write
              STATUS  optional
              ::= { ncdDecnet 11 }

          ncdDecnetMopResetEnabled OBJECT-TYPE
              SYNTAX  INTEGER
              ACCESS  read-write
              STATUS  optional
              ::= { ncdDecnet 12 }

          ncdDecnetDataBlocksXmt OBJECT-TYPE
              SYNTAX  INTEGER
              ACCESS  read-only
              STATUS  optional
              ::= { ncdDecnet 13 }

          ncdDecnetDataBlocksRcv OBJECT-TYPE
              SYNTAX  INTEGER
              ACCESS  read-only
              STATUS  optional
              ::= { ncdDecnet 14 }

          ncdDecnetDataBytesXmt OBJECT-TYPE
              SYNTAX  INTEGER
              ACCESS  read-only
              STATUS  optional
              ::= { ncdDecnet 15 }

          ncdDecnetDataBytesRcv OBJECT-TYPE
              SYNTAX  INTEGER
              ACCESS  read-only
              STATUS  optional
              ::= { ncdDecnet 16 }

          ncdDecnetHelloPacketsXmt OBJECT-TYPE
              SYNTAX  INTEGER
              ACCESS  read-only
              STATUS  optional
              ::= { ncdDecnet 17 }

          ncdDecnetHelloPacketsRcv OBJECT-TYPE
              SYNTAX  INTEGER
              ACCESS  read-only
              STATUS  optional
              ::= { ncdDecnet 18 }

          ncdDecnetCntCircDown OBJECT-TYPE
              SYNTAX  INTEGER
              ACCESS  read-only
              STATUS  optional
              ::= { ncdDecnet 19 }

          ncdDecnetInErrs OBJECT-TYPE
              SYNTAX  INTEGER
              ACCESS  read-only
              STATUS  optional
              ::= { ncdDecnet 20 }

          ncdDecnetOutErrs OBJECT-TYPE
              SYNTAX  INTEGER
              ACCESS  read-only
              STATUS  optional
              ::= { ncdDecnet 21 }

          ncdDecnetLastZeroTime OBJECT-TYPE
              SYNTAX  INTEGER
              ACCESS  read-only
              STATUS  optional
              ::= { ncdDecnet 22 }

          ncdDecnetCurrentAddress OBJECT-TYPE
              SYNTAX  PhysAddress
              ACCESS  read-only
              STATUS  optional
              ::= { ncdDecnet 23 }


          -- the ncdLat Group

          ncdLatConnectTimeout OBJECT-TYPE
              SYNTAX  TimeTicks
              ACCESS  read-write
              STATUS  optional
              ::= { ncdLat 1 }

          ncdLatCircuitFlushTimeout OBJECT-TYPE
              SYNTAX  TimeTicks
              ACCESS  read-write
              STATUS  optional
              ::= { ncdLat 2 }

          ncdLatRetransTimeout OBJECT-TYPE
              SYNTAX  TimeTicks
              ACCESS  read-write
              STATUS  optional
              ::= { ncdLat 3 }

          ncdLatRetransLimit OBJECT-TYPE
              SYNTAX  INTEGER
              ACCESS  read-write
              STATUS  optional
              ::= { ncdLat 4 }

          ncdLatKeepaliveTimeout OBJECT-TYPE
              SYNTAX  TimeTicks
              ACCESS  read-write
              STATUS  optional
              ::= { ncdLat 5 }

          ncdLatGroupCodes OBJECT-TYPE
              SYNTAX  OCTET STRING
              ACCESS  read-write
              STATUS  optional
              ::= { ncdLat 6 }

          ncdLatMaxDirEntries OBJECT-TYPE
              SYNTAX  INTEGER
              ACCESS  read-write
              STATUS  optional
              ::= { ncdLat 7 }


          -- the ncdNameResolver Group

          ncdNameResolverTransactTimeout OBJECT-TYPE
              SYNTAX  TimeTicks
              ACCESS  read-write
              STATUS  optional
              ::= { ncdNameResolver 1 }

          ncdNameResolverNumericalAddrs OBJECT-TYPE
              SYNTAX  INTEGER
              ACCESS  read-only
              STATUS  optional
              ::= { ncdNameResolver 2 }

          ncdNameResolverCacheHits OBJECT-TYPE
              SYNTAX  INTEGER
              ACCESS  read-only
              STATUS  optional
              ::= { ncdNameResolver 3 }

          ncdNameResolverServerHits OBJECT-TYPE
              SYNTAX  INTEGER
              ACCESS  read-only
              STATUS  optional
              ::= { ncdNameResolver 4 }

          ncdNameResolverCacheOverflows OBJECT-TYPE
              SYNTAX  INTEGER
              ACCESS  read-only
              STATUS  optional
              ::= { ncdNameResolver 5 }

          ncdNameResolverNoNameErrs OBJECT-TYPE
              SYNTAX  INTEGER
              ACCESS  read-only
              STATUS  optional
              ::= { ncdNameResolver 6 }

          ncdNameResolverBadNameErrs OBJECT-TYPE
              SYNTAX  INTEGER
              ACCESS  read-only
              STATUS  optional
              ::= { ncdNameResolver 7 }

          ncdNameResolverRspErrs OBJECT-TYPE
              SYNTAX  INTEGER
              ACCESS  read-only
              STATUS  optional
              ::= { ncdNameResolver 8 }

          ncdNameResolverNoRspErrs OBJECT-TYPE
              SYNTAX  INTEGER
              ACCESS  read-only
              STATUS  optional
              ::= { ncdNameResolver 9 }

          ncdNameResolverSysErrs OBJECT-TYPE
              SYNTAX  INTEGER
              ACCESS  read-only
              STATUS  optional
              ::= { ncdNameResolver 10 }

          ncdNameResolverNoMemErrs OBJECT-TYPE
              SYNTAX  INTEGER
              ACCESS  read-only
              STATUS  optional
              ::= { ncdNameResolver 11 }

          ncdNameResolverNameCacheMaxSize OBJECT-TYPE
              SYNTAX  INTEGER
              ACCESS  read-write
              STATUS  optional
              ::= { ncdNameResolver 12 }

          ncdNameResolverNameCacheMaxTimeout OBJECT-TYPE
              SYNTAX  INTEGER
              ACCESS  read-write
              STATUS  optional
              ::= { ncdNameResolver 13 }

          ncdNameResolverNameCacheTable OBJECT-TYPE
              SYNTAX  SEQUENCE OF NcdNameResolverNameCacheEntry
              ACCESS  not-accessible
              STATUS  optional
              ::= { ncdNameResolver 14 }

          ncdNameResolverNameCacheEntry OBJECT-TYPE
              SYNTAX  NcdNameResolverNameCacheEntry
              ACCESS  not-accessible
              STATUS  optional
              ::= { ncdNameResolverNameCacheTable 1 }

          NcdNameResolverNameCacheEntry ::=
              SEQUENCE {
                  ncdNameResolverTableIndex
                      INTEGER,
                  ncdNameResolverTableName
                      OCTET STRING,
                  ncdNameResolverTableAddress
                      OCTET STRING,
                  ncdNameResolverTableExpTime
                      INTEGER
              }

          ncdNameResolverTableIndex OBJECT-TYPE
              SYNTAX  INTEGER
              ACCESS  read-only
              STATUS  optional
              ::= { ncdNameResolverNameCacheEntry 1 }

          ncdNameResolverTableName OBJECT-TYPE
              SYNTAX  OCTET STRING
              ACCESS  read-write
              STATUS  optional
              ::= { ncdNameResolverNameCacheEntry 2 }

          ncdNameResolverTableAddress OBJECT-TYPE
              SYNTAX  OCTET STRING
              ACCESS  read-write
              STATUS  optional
              ::= { ncdNameResolverNameCacheEntry 3 }

          ncdNameResolverTableExpTime OBJECT-TYPE
              SYNTAX  INTEGER
              ACCESS  read-write
              STATUS  optional
              ::= { ncdNameResolverNameCacheEntry 4 }

          ncdNameResolverProtocol OBJECT-TYPE
              SYNTAX  INTEGER
              ACCESS  read-write
              STATUS  optional
              ::= { ncdNameResolver 15 }

          ncdNameResolverRtxTimeout OBJECT-TYPE
              SYNTAX  INTEGER
              ACCESS  read-write
              STATUS  optional
              ::= { ncdNameResolver 16 }

          ncdNameResolverRequests OBJECT-TYPE
              SYNTAX  INTEGER
              ACCESS  read-only
              STATUS  optional
              ::= { ncdNameResolver 17 }

          ncdNameResolverNameServersTable OBJECT-TYPE
              SYNTAX  SEQUENCE OF NcdNameResolverNameServersEntry
              ACCESS  not-accessible
              STATUS  optional
              ::= { ncdNameResolver 18 }

          ncdNameResolverNameServersEntry OBJECT-TYPE
              SYNTAX  NcdNameResolverNameServersEntry
              ACCESS  not-accessible
              STATUS  optional
              ::= { ncdNameResolverNameServersTable 1 }

          NcdNameResolverNameServersEntry ::=
              SEQUENCE {
                  ncdInetNameServersTableIndex
                      INTEGER,
                  ncdInetNameServersTableAddress
                      IpAddress
              }

          ncdInetNameServersTableIndex OBJECT-TYPE
              SYNTAX  INTEGER
              ACCESS  read-only
              STATUS  optional
              ::= { ncdNameResolverNameServersEntry 1 }

          ncdInetNameServersTableAddress OBJECT-TYPE
              SYNTAX  IpAddress
              ACCESS  read-write
              STATUS  optional
              ::= { ncdNameResolverNameServersEntry 2 }

          ncdNameResolverDnsDefaultDomain OBJECT-TYPE
              SYNTAX  OCTET STRING
              ACCESS  read-write
              STATUS  optional
              ::= { ncdNameResolver 19 }

          ncdNameResolverDnsDoNameSearch OBJECT-TYPE
              SYNTAX  INTEGER
              ACCESS  read-write
              STATUS  optional
              ::= { ncdNameResolver 20 }


          -- the ncdFontService Group

          ncdFontServiceCacheSize OBJECT-TYPE
              SYNTAX  INTEGER
              ACCESS  read-only
              STATUS  optional
              ::= { ncdFontService 2 }

          ncdFontServiceCacheUsed OBJECT-TYPE
              SYNTAX  Gauge
              ACCESS  read-only
              STATUS  optional
              ::= { ncdFontService 3 }

          ncdFontServiceNumCachedFonts OBJECT-TYPE
              SYNTAX  Gauge
              ACCESS  read-only
              STATUS  optional
              ::= { ncdFontService 4 }

          ncdFontServiceNetLoads OBJECT-TYPE
              SYNTAX  Counter
              ACCESS  read-only
              STATUS  optional
              ::= { ncdFontService 5 }

          ncdFontServiceReferenceIncs OBJECT-TYPE
              SYNTAX  Counter
              ACCESS  read-only
              STATUS  optional
              ::= { ncdFontService 6 }

          ncdFontServiceCacheHits OBJECT-TYPE
              SYNTAX  Counter
              ACCESS  read-only
              STATUS  optional
              ::= { ncdFontService 7 }

          ncdFontServiceFontsInUse OBJECT-TYPE
              SYNTAX  INTEGER
              ACCESS  read-only
              STATUS  optional
              ::= { ncdFontService 9 }


          -- the ncdArp Group

          ncdArpIncompleteEntryTimeout OBJECT-TYPE
              SYNTAX  TimeTicks
              ACCESS  read-write
              STATUS  optional
              ::= { ncdArp 1 }

          ncdArpCompleteEntryTimeout OBJECT-TYPE
              SYNTAX  TimeTicks
              ACCESS  read-write
              STATUS  optional
              ::= { ncdArp 2 }


          -- the ncdIp Group

          ncdIpNewAddress OBJECT-TYPE
              SYNTAX  IpAddress
              ACCESS  read-write
              STATUS  optional
              ::= { ncdIp 1 }

          ncdIpInitDfltGatewy1 OBJECT-TYPE
              SYNTAX  IpAddress
              ACCESS  read-write
              STATUS  optional
              ::= { ncdIp 2 }

          ncdIpInitDfltGatewy2 OBJECT-TYPE
              SYNTAX  IpAddress
              ACCESS  read-write
              STATUS  optional
              ::= { ncdIp 3 }

          ncdIpDynamicAddressDiscovery OBJECT-TYPE
              SYNTAX  INTEGER
              ACCESS  read-write
              STATUS  optional
              ::= { ncdIp 4 }

          ncdIpUseProxyArp OBJECT-TYPE
              SYNTAX  INTEGER
              ACCESS  read-write
              STATUS  optional
              ::= { ncdIp 5 }

          ncdIpUseRouterDiscovery OBJECT-TYPE
              SYNTAX  INTEGER
              ACCESS  read-write
              STATUS  optional
              ::= { ncdIp 6 }

          ncdIpUseRouterDiscoverySolicit OBJECT-TYPE
              SYNTAX  INTEGER
              ACCESS  read-write
              STATUS  optional
              ::= { ncdIp 7 }

          ncdIpRouteExtendedDiagnostics OBJECT-TYPE
              SYNTAX  INTEGER
              ACCESS  read-write
              STATUS  optional
              ::= { ncdIp 8 }

          ncdIpRspToBcastIcmp OBJECT-TYPE
              SYNTAX  INTEGER
              ACCESS  read-write
              STATUS  optional
              ::= { ncdIp 9 }

          ncdIpEquivAddressesTable OBJECT-TYPE
              SYNTAX  SEQUENCE OF NcdIpEquivAddressesEntry
              ACCESS  not-accessible
              STATUS  optional
              ::= { ncdIp 11 }

          ncdIpEquivAddressesEntry OBJECT-TYPE
              SYNTAX  NcdIpEquivAddressesEntry
              ACCESS  not-accessible
              STATUS  optional
              ::= { ncdIpEquivAddressesTable 1 }

          NcdIpEquivAddressesEntry ::=
              SEQUENCE {
                  ncdIpEATIndex
                      INTEGER,
                  ncdIpEATAddresses
                      IpAddress
              }

          ncdIpEATIndex OBJECT-TYPE
              SYNTAX  INTEGER
              ACCESS  read-only
              STATUS  optional
              ::= { ncdIpEquivAddressesEntry 1 }

          ncdIpEATAddresses OBJECT-TYPE
              SYNTAX  IpAddress
              ACCESS  read-write
              STATUS  optional
              ::= { ncdIpEquivAddressesEntry 2 }


          -- the ncdSerialDaemon Group

          ncdSerialDaemonStatsTable OBJECT-TYPE
              SYNTAX  SEQUENCE OF NcdSerialDaemonStatsEntry
              ACCESS  not-accessible
              STATUS  optional
              ::= { ncdSerialDaemon 1 }

          ncdSerialDaemonStatsEntry OBJECT-TYPE
              SYNTAX  NcdSerialDaemonStatsEntry
              ACCESS  not-accessible
              STATUS  optional
              ::= { ncdSerialDaemonStatsTable 1 }

          NcdSerialDaemonStatsEntry ::=
              SEQUENCE {
                  ncdSerialDaemonPortNumber
                      INTEGER,
                  ncdSerialDaemonConnAccepts
                      INTEGER,
                  ncdSerialDaemonConnBadAccesses
                      INTEGER,
                  ncdSerialDaemonConnIOErrors
                      INTEGER,
                  ncdSerialDaemonConnEofCloses
                      INTEGER
              }

          ncdSerialDaemonPortNumber OBJECT-TYPE
              SYNTAX  INTEGER
              ACCESS  read-only
              STATUS  optional
              ::= { ncdSerialDaemonStatsEntry 1 }

          ncdSerialDaemonConnAccepts OBJECT-TYPE
              SYNTAX  INTEGER
              ACCESS  read-only
              STATUS  optional
              ::= { ncdSerialDaemonStatsEntry 2 }

          ncdSerialDaemonConnBadAccesses OBJECT-TYPE
              SYNTAX  INTEGER
              ACCESS  read-only
              STATUS  optional
              ::= { ncdSerialDaemonStatsEntry 3 }

          ncdSerialDaemonConnIOErrors OBJECT-TYPE
              SYNTAX  INTEGER
              ACCESS  read-only
              STATUS  optional
              ::= { ncdSerialDaemonStatsEntry 4 }

          ncdSerialDaemonConnEofCloses OBJECT-TYPE
              SYNTAX  INTEGER
              ACCESS  read-only
              STATUS  optional
              ::= { ncdSerialDaemonStatsEntry 5 }


          -- the ncdDnetNameResolver Group

          ncdDnetNameResolverRequests OBJECT-TYPE
              SYNTAX  INTEGER
              ACCESS  read-only
              STATUS  optional
              ::= { ncdDnetNameResolver 1 }

          ncdDnetNameResolverNumericalAddrs OBJECT-TYPE
              SYNTAX  INTEGER
              ACCESS  read-only
              STATUS  optional
              ::= { ncdDnetNameResolver 2 }

          ncdDnetNameResolverCacheHits OBJECT-TYPE
              SYNTAX  INTEGER
              ACCESS  read-only
              STATUS  optional
              ::= { ncdDnetNameResolver 3 }

          ncdDnetNameResolverServerHits OBJECT-TYPE
              SYNTAX  INTEGER
              ACCESS  read-only
              STATUS  optional
              ::= { ncdDnetNameResolver 4 }

          ncdDnetNameResolverCacheOverflows OBJECT-TYPE
              SYNTAX  INTEGER
              ACCESS  read-only
              STATUS  optional
              ::= { ncdDnetNameResolver 5 }

          ncdDnetNameResolverNoNameErrs OBJECT-TYPE
              SYNTAX  INTEGER
              ACCESS  read-only
              STATUS  optional
              ::= { ncdDnetNameResolver 6 }

          ncdDnetNameResolverBadNameErrs OBJECT-TYPE
              SYNTAX  INTEGER
              ACCESS  read-only
              STATUS  optional
              ::= { ncdDnetNameResolver 7 }

          ncdDnetNameResolverRspErrs OBJECT-TYPE
              SYNTAX  INTEGER
              ACCESS  read-only
              STATUS  optional
              ::= { ncdDnetNameResolver 8 }

          ncdDnetNameResolverNoRspErrs OBJECT-TYPE
              SYNTAX  INTEGER
              ACCESS  read-only
              STATUS  optional
              ::= { ncdDnetNameResolver 9 }

          ncdDnetNameResolverSysErrs OBJECT-TYPE
              SYNTAX  INTEGER
              ACCESS  read-only
              STATUS  optional
              ::= { ncdDnetNameResolver 10 }

          ncdDnetNameResolverNoMemErrs OBJECT-TYPE
              SYNTAX  INTEGER
              ACCESS  read-only
              STATUS  optional
              ::= { ncdDnetNameResolver 11 }

          ncdDnetNameResolverNameCacheMaxSize OBJECT-TYPE
              SYNTAX  INTEGER
              ACCESS  read-write
              STATUS  optional
              ::= { ncdDnetNameResolver 12 }

          ncdDnetNameResolverNameCacheMaxTimeout OBJECT-TYPE
              SYNTAX  INTEGER
              ACCESS  read-write
              STATUS  optional
              ::= { ncdDnetNameResolver 13 }

          ncdDnetNameResolverNameCacheTable OBJECT-TYPE
              SYNTAX  SEQUENCE OF NcdDnetNameResolverNameCacheEntry
              ACCESS  not-accessible
              STATUS  optional
              ::= { ncdDnetNameResolver 14 }

          ncdDnetNameResolverNameCacheEntry OBJECT-TYPE
              SYNTAX  NcdDnetNameResolverNameCacheEntry
              ACCESS  not-accessible
              STATUS  optional
              ::= { ncdDnetNameResolverNameCacheTable 1 }

          NcdDnetNameResolverNameCacheEntry ::=
              SEQUENCE {
                  ncdDnetNameResolverIndex
                      INTEGER,
                  ncdDnetNameResolverName
                      OCTET STRING,
                  ncdDnetNameResolverAddress
                      OCTET STRING,
                  ncdDnetNameResolverExpTime
                      INTEGER
              }

          ncdDnetNameResolverIndex OBJECT-TYPE
              SYNTAX  INTEGER
              ACCESS  read-only
              STATUS  optional
              ::= { ncdDnetNameResolverNameCacheEntry 1 }

          ncdDnetNameResolverName OBJECT-TYPE
              SYNTAX  OCTET STRING
              ACCESS  read-write
              STATUS  optional
              ::= { ncdDnetNameResolverNameCacheEntry 2 }

          ncdDnetNameResolverAddress OBJECT-TYPE
              SYNTAX  OCTET STRING
              ACCESS  read-write
              STATUS  optional
              ::= { ncdDnetNameResolverNameCacheEntry 3 }

          ncdDnetNameResolverExpTime OBJECT-TYPE
              SYNTAX  INTEGER
              ACCESS  read-write
              STATUS  optional
              ::= { ncdDnetNameResolverNameCacheEntry 4 }

          ncdDnetNameResolverTransactTimeout OBJECT-TYPE
              SYNTAX  INTEGER
              ACCESS  read-write
              STATUS  optional
              ::= { ncdDnetNameResolver 15 }

          ncdDnetNameResolverServersTable OBJECT-TYPE
              SYNTAX  SEQUENCE OF NcdDnetNameResolverServersEntry
              ACCESS  not-accessible
              STATUS  optional
              ::= { ncdDnetNameResolver 16 }

          ncdDnetNameResolverServersEntry OBJECT-TYPE
              SYNTAX  NcdDnetNameResolverServersEntry
              ACCESS  not-accessible
              STATUS  optional
              ::= { ncdDnetNameResolverServersTable 1 }

          NcdDnetNameResolverServersEntry ::=
              SEQUENCE {
                  ncdDnetNameResolverServerIndex
                      INTEGER,
                  ncdDnetNameResolverServer
                      PhysAddress
              }

          ncdDnetNameResolverServerIndex OBJECT-TYPE
              SYNTAX  INTEGER
              ACCESS  read-only
              STATUS  optional
              ::= { ncdDnetNameResolverServersEntry 1 }

          ncdDnetNameResolverServer OBJECT-TYPE
              SYNTAX  PhysAddress
              ACCESS  read-write
              STATUS  optional
              ::= { ncdDnetNameResolverServersEntry 2 }


          -- the ncdBoot Group

          ncdBootServerAutomatically OBJECT-TYPE
              SYNTAX  INTEGER
              ACCESS  read-write
              STATUS  optional
              ::= { ncdBoot 1 }

          ncdBootRamTest OBJECT-TYPE
              SYNTAX  INTEGER
              ACCESS  read-write
              STATUS  optional
              ::= { ncdBoot 2 }

          ncdBootActualSource OBJECT-TYPE
              SYNTAX  INTEGER
              ACCESS  read-only
              STATUS  optional
              ::= { ncdBoot 3 }

          ncdBootActualServer OBJECT-TYPE
              SYNTAX  IpAddress
              ACCESS  read-only
              STATUS  optional
              ::= { ncdBoot 4 }

          ncdBootDesiredSource OBJECT-TYPE
              SYNTAX  INTEGER
              ACCESS  read-write
              STATUS  optional
              ::= { ncdBoot 5 }

          ncdBootPersist OBJECT-TYPE
              SYNTAX  INTEGER
              ACCESS  read-write
              STATUS  optional
              ::= { ncdBoot 6 }

          ncdBootDefaultServer OBJECT-TYPE
              SYNTAX  IpAddress
              ACCESS  read-write
              STATUS  optional
              ::= { ncdBoot 7 }

          ncdBootMonitorReverseVideo OBJECT-TYPE
              SYNTAX  INTEGER
              ACCESS  read-write
              STATUS  optional
              ::= { ncdBoot 8 }

          ncdBootDesiredInetServer OBJECT-TYPE
              SYNTAX  IpAddress
              ACCESS  read-write
              STATUS  optional
              ::= { ncdBoot 9 }

          ncdBootUseRelativeHexFile OBJECT-TYPE
              SYNTAX  INTEGER
              ACCESS  read-write
              STATUS  optional
              ::= { ncdBoot 10 }

          ncdBootUseAbsoluteHexFile OBJECT-TYPE
              SYNTAX  INTEGER
              ACCESS  read-write
              STATUS  optional
              ::= { ncdBoot 11 }

          ncdBootUseRelativeMemSizeFile OBJECT-TYPE
              SYNTAX  INTEGER
              ACCESS  read-write
              STATUS  optional
              ::= { ncdBoot 12 }

          ncdBootUseAbsoluteMemSizeFile OBJECT-TYPE
              SYNTAX  INTEGER
              ACCESS  read-write
              STATUS  optional
              ::= { ncdBoot 13 }

          ncdBootUseRelativeProductFile OBJECT-TYPE
              SYNTAX  INTEGER
              ACCESS  read-write
              STATUS  optional
              ::= { ncdBoot 14 }

          ncdBootUseAbsoluteProductFile OBJECT-TYPE
              SYNTAX  INTEGER
              ACCESS  read-write
              STATUS  optional
              ::= { ncdBoot 15 }

          ncdBootEnableICMPSubnetMaskRequest OBJECT-TYPE
              SYNTAX  INTEGER
              ACCESS  read-write
              STATUS  optional
              ::= { ncdBoot 16 }

          ncdBootBroadcastInetRequest OBJECT-TYPE
              SYNTAX  INTEGER
              ACCESS  read-write
              STATUS  optional
              ::= { ncdBoot 17 }

          ncdBootMop OBJECT-TYPE
              SYNTAX  INTEGER
              ACCESS  read-write
              STATUS  optional
              ::= { ncdBoot 18 }

          ncdBootMopWithFileName OBJECT-TYPE
              SYNTAX  INTEGER
              ACCESS  read-write
              STATUS  optional
              ::= { ncdBoot 19 }

          ncdBootCustomFile OBJECT-TYPE
              SYNTAX  OCTET STRING
              ACCESS  read-write
              STATUS  optional
              ::= { ncdBoot 20 }

          ncdBootTftpDirectory OBJECT-TYPE
              SYNTAX  OCTET STRING
              ACCESS  read-write
              STATUS  optional
              ::= { ncdBoot 21 }

          ncdBootNfsDirectory OBJECT-TYPE
              SYNTAX  OCTET STRING
              ACCESS  read-write
              STATUS  optional
              ::= { ncdBoot 22 }


          -- the ncdConfig Group

          ncdConfigInitFileLoad OBJECT-TYPE
              SYNTAX  INTEGER
              ACCESS  read-write
              STATUS  optional
              ::= { ncdConfig 1 }

          ncdConfigInitPersistentFileLoad OBJECT-TYPE
              SYNTAX  INTEGER
              ACCESS  read-write
              STATUS  optional
              ::= { ncdConfig 2 }

          ncdConfigDfltUnixDirectory OBJECT-TYPE
              SYNTAX  OCTET STRING
              ACCESS  read-write
              STATUS  optional
              ::= { ncdConfig 3 }

          ncdConfigDfltVmsDirectory OBJECT-TYPE
              SYNTAX  OCTET STRING
              ACCESS  read-write
              STATUS  optional
              ::= { ncdConfig 4 }

          ncdConfigInitFile OBJECT-TYPE
              SYNTAX  OCTET STRING
              ACCESS  read-write
              STATUS  optional
              ::= { ncdConfig 5 }

          ncdConfigInitUseUnitNameFile OBJECT-TYPE
              SYNTAX  INTEGER
              ACCESS  read-write
              STATUS  optional
              ::= { ncdConfig 6 }

          ncdConfigInitUseFQUnitName OBJECT-TYPE
              SYNTAX  INTEGER
              ACCESS  read-write
              STATUS  optional
              ::= { ncdConfig 7 }

          ncdConfigInitUseEnetUnitAddrFile OBJECT-TYPE
              SYNTAX  INTEGER
              ACCESS  read-write
              STATUS  optional
              ::= { ncdConfig 8 }

          ncdConfigInitUseInetUnitAddrFile OBJECT-TYPE
              SYNTAX  INTEGER
              ACCESS  read-write
              STATUS  optional
              ::= { ncdConfig 9 }

          ncdConfigInitUseDecimalInetUnitAddr OBJECT-TYPE
              SYNTAX  INTEGER
              ACCESS  read-write
              STATUS  optional
              ::= { ncdConfig 10 }

          ncdConfigInitUseGenericFile OBJECT-TYPE
              SYNTAX  INTEGER
              ACCESS  read-write
              STATUS  optional
              ::= { ncdConfig 11 }

          ncdConfigTelnetPort OBJECT-TYPE
              SYNTAX  INTEGER
              ACCESS  read-write
              STATUS  optional
              ::= { ncdConfig 12 }

          ncdConfigTcpPort OBJECT-TYPE
              SYNTAX  INTEGER
              ACCESS  read-write
              STATUS  optional
              ::= { ncdConfig 13 }

          ncdConfigDfltFile OBJECT-TYPE
              SYNTAX  OCTET STRING
              ACCESS  read-write
              STATUS  optional
              ::= { ncdConfig 14 }

          ncdConfigAutoSaveNvram OBJECT-TYPE
              SYNTAX  INTEGER
              ACCESS  read-write
              STATUS  optional
              ::= { ncdConfig 15 }

          ncdConfigAutoSaveFile OBJECT-TYPE
              SYNTAX  INTEGER
              ACCESS  read-write
              STATUS  optional
              ::= { ncdConfig 16 }

          ncdConfigAutoSaveFileName OBJECT-TYPE
              SYNTAX  OCTET STRING
              ACCESS  read-write
              STATUS  optional
              ::= { ncdConfig 17 }

          ncdConfigAutoSaveChanges OBJECT-TYPE
              SYNTAX  INTEGER
              ACCESS  read-write
              STATUS  optional
              ::= { ncdConfig 18 }

          ncdConfigPrefdTelnetPort OBJECT-TYPE
              SYNTAX  INTEGER
              ACCESS  read-write
              STATUS  optional
              ::= { ncdConfig 19 }

          ncdConfigPrefdTcpPort OBJECT-TYPE
              SYNTAX  INTEGER
              ACCESS  read-write
              STATUS  optional
              ::= { ncdConfig 20 }

          ncdConfigPrefdDnetObject OBJECT-TYPE
              SYNTAX  OCTET STRING
              ACCESS  read-write
              STATUS  optional
              ::= { ncdConfig 21 }

          ncdConfigInitUseDnetUnitAddrFile OBJECT-TYPE
              SYNTAX  INTEGER
              ACCESS  read-write
              STATUS  optional
              ::= { ncdConfig 22 }

          ncdConfigDnetObject OBJECT-TYPE
              SYNTAX  OCTET STRING
              ACCESS  read-write
              STATUS  optional
              ::= { ncdConfig 23 }


          -- the ncdXserver Group

          ncdXserverCurrentKeyboard OBJECT-TYPE
              SYNTAX  INTEGER
              ACCESS  read-write
              STATUS  optional
              ::= { ncdXserver 1 }

          ncdXserverKeyboardTypeChoices OBJECT-TYPE
              SYNTAX  SEQUENCE OF NcdXserverKeyboardTypeEntry
              ACCESS  not-accessible
              STATUS  optional
              ::= { ncdXserver 2 }

          ncdXserverKeyboardTypeEntry OBJECT-TYPE
              SYNTAX  NcdXserverKeyboardTypeEntry
              ACCESS  not-accessible
              STATUS  optional
              ::= { ncdXserverKeyboardTypeChoices 1 }

          NcdXserverKeyboardTypeEntry ::=
              SEQUENCE {
                  ncdXserverKeyboardChoiceIndex
                      INTEGER,
                  ncdXserverCurrentKeyboardChoice
                      OCTET STRING
              }

          ncdXserverKeyboardChoiceIndex OBJECT-TYPE
              SYNTAX  INTEGER
              ACCESS  read-only
              STATUS  optional
              ::= { ncdXserverKeyboardTypeEntry 1 }

          ncdXserverCurrentKeyboardChoice OBJECT-TYPE
              SYNTAX  OCTET STRING
              ACCESS  read-only
              STATUS  optional
              ::= { ncdXserverKeyboardTypeEntry 2 }

          ncdXserverNarrowKeyTable OBJECT-TYPE
              SYNTAX  INTEGER
              ACCESS  read-write
              STATUS  optional
              ::= { ncdXserver 3 }

          ncdXserverDeadKeySupport OBJECT-TYPE
              SYNTAX  INTEGER
              ACCESS  read-write
              STATUS  optional
              ::= { ncdXserver 4 }

          ncdXserverMouseButtons OBJECT-TYPE
              SYNTAX  INTEGER
              ACCESS  read-write
              STATUS  optional
              ::= { ncdXserver 5 }

          ncdXserverDefaultFontPathTable OBJECT-TYPE
              SYNTAX  SEQUENCE OF NcdXserverDefaultFontPathEntry
              ACCESS  not-accessible
              STATUS  optional
              ::= { ncdXserver 6 }

          ncdXserverDefaultFontPathEntry OBJECT-TYPE
              SYNTAX  NcdXserverDefaultFontPathEntry
              ACCESS  not-accessible
              STATUS  optional
              ::= { ncdXserverDefaultFontPathTable 1 }

          NcdXserverDefaultFontPathEntry ::=
              SEQUENCE {
                  ncdXserverFontPathTableIndex
                      INTEGER,
                  ncdXserverFontPathTableEntry
                      OCTET STRING
              }

          ncdXserverFontPathTableIndex OBJECT-TYPE
              SYNTAX  INTEGER
              ACCESS  read-only
              STATUS  optional
              ::= { ncdXserverDefaultFontPathEntry 1 }

          ncdXserverFontPathTableEntry OBJECT-TYPE
              SYNTAX  OCTET STRING
              ACCESS  read-write
              STATUS  optional
              ::= { ncdXserverDefaultFontPathEntry 2 }

          ncdXserverDefaultFont OBJECT-TYPE
              SYNTAX  OCTET STRING
              ACCESS  read-write
              STATUS  optional
              ::= { ncdXserver 7 }

          ncdXserverFontCacheSize OBJECT-TYPE
              SYNTAX  INTEGER
              ACCESS  read-write
              STATUS  optional
              ::= { ncdXserver 8 }

          ncdXserverRetainFonts OBJECT-TYPE
              SYNTAX  INTEGER
              ACCESS  read-write
              STATUS  optional
              ::= { ncdXserver 9 }

          ncdXserverFontDirFileName OBJECT-TYPE
              SYNTAX  OCTET STRING
              ACCESS  read-write
              STATUS  optional
              ::= { ncdXserver 10 }

          ncdXserverFontAliasFileName OBJECT-TYPE
              SYNTAX  OCTET STRING
              ACCESS  read-write
              STATUS  optional
              ::= { ncdXserver 11 }

          ncdXserverFontPathAliasTable OBJECT-TYPE
              SYNTAX  SEQUENCE OF NcdXserverFontPathAliasEntry
              ACCESS  not-accessible
              STATUS  optional
              ::= { ncdXserver 12 }

          ncdXserverFontPathAliasEntry OBJECT-TYPE
              SYNTAX  NcdXserverFontPathAliasEntry
              ACCESS  not-accessible
              STATUS  optional
              ::= { ncdXserverFontPathAliasTable 1 }

          NcdXserverFontPathAliasEntry ::=
              SEQUENCE {
                  ncdXserverAliasTableIndex
                      INTEGER,
                  ncdXserverAliasTableAlias
                      OCTET STRING,
                  ncdXserverAliasTableValue
                      OCTET STRING
              }

          ncdXserverAliasTableIndex OBJECT-TYPE
              SYNTAX  INTEGER
              ACCESS  read-only
              STATUS  optional
              ::= { ncdXserverFontPathAliasEntry 1 }

          ncdXserverAliasTableAlias OBJECT-TYPE
              SYNTAX  OCTET STRING
              ACCESS  read-write
              STATUS  optional
              ::= { ncdXserverFontPathAliasEntry 2 }

          ncdXserverAliasTableValue OBJECT-TYPE
              SYNTAX  OCTET STRING
              ACCESS  read-write
              STATUS  optional
              ::= { ncdXserverFontPathAliasEntry 3 }

          ncdXserverFontserverRetryAttempts OBJECT-TYPE
              SYNTAX  INTEGER
              ACCESS  read-write
              STATUS  optional
              ::= { ncdXserver 13 }

          ncdXserverFontserverReadTimeout OBJECT-TYPE
              SYNTAX  INTEGER
              ACCESS  read-write
              STATUS  optional
              ::= { ncdXserver 14 }

          ncdXserverFontserverOpenTimeout OBJECT-TYPE
              SYNTAX  INTEGER
              ACCESS  read-write
              STATUS  optional
              ::= { ncdXserver 15 }

          ncdXserverFontserverReopenTimeout OBJECT-TYPE
              SYNTAX  INTEGER
              ACCESS  read-write
              STATUS  optional
              ::= { ncdXserver 16 }

          ncdXserverXDisabledExt OBJECT-TYPE
              SYNTAX  SEQUENCE OF NcdXserverXDisabledEntry
              ACCESS  not-accessible
              STATUS  optional
              ::= { ncdXserver 17 }

          ncdXserverXDisabledEntry OBJECT-TYPE
              SYNTAX  NcdXserverXDisabledEntry
              ACCESS  not-accessible
              STATUS  optional
              ::= { ncdXserverXDisabledExt 1 }

          NcdXserverXDisabledEntry ::=
              SEQUENCE {
                  ncdXserverDisExtTableIndex
                      INTEGER,
                  ncdXserverDisExtTableName
                      OCTET STRING
              }

          ncdXserverDisExtTableIndex OBJECT-TYPE
              SYNTAX  INTEGER
              ACCESS  read-only
              STATUS  optional
              ::= { ncdXserverXDisabledEntry 1 }

          ncdXserverDisExtTableName OBJECT-TYPE
              SYNTAX  OCTET STRING
              ACCESS  read-write
              STATUS  optional
              ::= { ncdXserverXDisabledEntry 2 }

          ncdXserverXServerRetainSettings OBJECT-TYPE
              SYNTAX  INTEGER
              ACCESS  read-write
              STATUS  optional
              ::= { ncdXserver 18 }

          ncdXserverInitialXResources OBJECT-TYPE
              SYNTAX  OCTET STRING
              ACCESS  read-write
              STATUS  optional
              ::= { ncdXserver 19 }

          ncdXserverArcCacheSize OBJECT-TYPE
              SYNTAX  INTEGER
              ACCESS  read-write
              STATUS  optional
              ::= { ncdXserver 20 }

          ncdXserverRgbPath OBJECT-TYPE
              SYNTAX  OCTET STRING
              ACCESS  read-write
              STATUS  optional
              ::= { ncdXserver 21 }

          ncdXserverXDefaultVisual OBJECT-TYPE
              SYNTAX  INTEGER
              ACCESS  read-write
              STATUS  optional
              ::= { ncdXserver 22 }

          ncdXserverColormapTable OBJECT-TYPE
              SYNTAX  SEQUENCE OF NcdXserverColormapEntry
              ACCESS  not-accessible
              STATUS  optional
              ::= { ncdXserver 23 }

          ncdXserverColormapEntry OBJECT-TYPE
              SYNTAX  NcdXserverColormapEntry
              ACCESS  not-accessible
              STATUS  optional
              ::= { ncdXserverColormapTable 1 }

          NcdXserverColormapEntry ::=
              SEQUENCE {
                  ncdXserverCTIndex
                      INTEGER,
                  ncdXserverCTPixel
                      INTEGER,
                  ncdXserverCTRgb
                      OCTET STRING,
                  ncdXserverCTReadOnly
                      INTEGER
              }

          ncdXserverCTIndex OBJECT-TYPE
              SYNTAX  INTEGER
              ACCESS  read-only
              STATUS  optional
              ::= { ncdXserverColormapEntry 1 }

          ncdXserverCTPixel OBJECT-TYPE
              SYNTAX  INTEGER
              ACCESS  read-write
              STATUS  optional
              ::= { ncdXserverColormapEntry 2 }

          ncdXserverCTRgb OBJECT-TYPE
              SYNTAX  OCTET STRING
              ACCESS  read-write
              STATUS  optional
              ::= { ncdXserverColormapEntry 3 }

          ncdXserverCTReadOnly OBJECT-TYPE
              SYNTAX  INTEGER
              ACCESS  read-write
              STATUS  optional
              ::= { ncdXserverColormapEntry 4 }

          ncdXserverXBlackPixel OBJECT-TYPE
              SYNTAX  INTEGER
              ACCESS  read-write
              STATUS  optional
              ::= { ncdXserver 24 }

          ncdXserverXWhitePixel OBJECT-TYPE
              SYNTAX  INTEGER
              ACCESS  read-write
              STATUS  optional
              ::= { ncdXserver 25 }

          ncdXserverInputExtensionDevice OBJECT-TYPE
              SYNTAX  INTEGER
              ACCESS  read-write
              STATUS  optional
              ::= { ncdXserver 26 }

          ncdXserverKeysymDBPath OBJECT-TYPE
              SYNTAX  OCTET STRING
              ACCESS  read-write
              STATUS  optional
              ::= { ncdXserver 27 }

          ncdXServerTouchscreenCalibrationLimitsTable OBJECT-TYPE
              SYNTAX  SEQUENCE OF NcdXServerTouchscreenCalibrationLimitsEntry
              ACCESS  not-accessible
              STATUS  optional
              ::= { ncdXserver 28 }

          ncdXServerTouchscreenCalibrationLimitsEntry OBJECT-TYPE
              SYNTAX  NcdXServerTouchscreenCalibrationLimitsEntry
              ACCESS  not-accessible
              STATUS  optional
              ::= { ncdXServerTouchscreenCalibrationLimitsTable 1 }

          NcdXServerTouchscreenCalibrationLimitsEntry ::=
              SEQUENCE {
                  ncdXserverTouchscreenCalibrationLimitsIndex
                      INTEGER,
                  ncdXserverTouchscreenCalibrationLimitsXMin
                      INTEGER,
                  ncdXserverTouchscreenCalibrationLimitsYMin
                      INTEGER,
                  ncdXserverTouchscreenCalibrationLimitsXMax
                      INTEGER,
                  ncdXserverTouchscreenCalibrationLimitsYMax
                      INTEGER
              }

          ncdXserverTouchscreenCalibrationLimitsIndex OBJECT-TYPE
              SYNTAX  INTEGER
              ACCESS  read-only
              STATUS  optional
              ::= { ncdXServerTouchscreenCalibrationLimitsEntry 1 }

          ncdXserverTouchscreenCalibrationLimitsXMin OBJECT-TYPE
              SYNTAX  INTEGER
              ACCESS  read-write
              STATUS  optional
              ::= { ncdXServerTouchscreenCalibrationLimitsEntry 2 }

          ncdXserverTouchscreenCalibrationLimitsYMin OBJECT-TYPE
              SYNTAX  INTEGER
              ACCESS  read-write
              STATUS  optional
              ::= { ncdXServerTouchscreenCalibrationLimitsEntry 3 }

          ncdXserverTouchscreenCalibrationLimitsXMax OBJECT-TYPE
              SYNTAX  INTEGER
              ACCESS  read-write
              STATUS  optional
              ::= { ncdXServerTouchscreenCalibrationLimitsEntry 4 }

          ncdXserverTouchscreenCalibrationLimitsYMax OBJECT-TYPE
              SYNTAX  INTEGER
              ACCESS  read-write
              STATUS  optional
              ::= { ncdXServerTouchscreenCalibrationLimitsEntry 5 }


          -- the ncdDiag Group

          ncdDiagTimestampEnabled OBJECT-TYPE
              SYNTAX  INTEGER
              ACCESS  read-write
              STATUS  optional
              ::= { ncdDiag 1 }

          ncdDiagTimestampGranularity OBJECT-TYPE
              SYNTAX  INTEGER
              ACCESS  read-write
              STATUS  optional
              ::= { ncdDiag 2 }

          ncdDiagConfiguredBufferSize OBJECT-TYPE
              SYNTAX  INTEGER
              ACCESS  read-write
              STATUS  optional
              ::= { ncdDiag 3 }

          ncdDiagLogFile OBJECT-TYPE
              SYNTAX  OCTET STRING
              ACCESS  read-write
              STATUS  optional
              ::= { ncdDiag 4 }

          ncdDiagTelnetPort OBJECT-TYPE
              SYNTAX  INTEGER
              ACCESS  read-write
              STATUS  optional
              ::= { ncdDiag 5 }

          ncdDiagTcpPort OBJECT-TYPE
              SYNTAX  INTEGER
              ACCESS  read-write
              STATUS  optional
              ::= { ncdDiag 6 }

          ncdDiagDnetObject OBJECT-TYPE
              SYNTAX  OCTET STRING
              ACCESS  read-write
              STATUS  optional
              ::= { ncdDiag 7 }

          ncdSevereSystemErrors OBJECT-TYPE
              SYNTAX  INTEGER
              ACCESS  read-write
              STATUS  optional
              ::= { ncdDiag 8 }


          -- the ncdDps Group

          ncdDpsResourcePath OBJECT-TYPE
              SYNTAX  OCTET STRING
              ACCESS  read-write
              STATUS  optional
              ::= { ncdDps 1 }


          -- the ncdExec Group

          ncdExecStartupCommandsTable OBJECT-TYPE
              SYNTAX  SEQUENCE OF NcdExecStartupCommandsEntry
              ACCESS  not-accessible
              STATUS  optional
              ::= { ncdExec 1 }

          ncdExecStartupCommandsEntry OBJECT-TYPE
              SYNTAX  NcdExecStartupCommandsEntry
              ACCESS  not-accessible
              STATUS  optional
              ::= { ncdExecStartupCommandsTable 1 }

          NcdExecStartupCommandsEntry ::=
              SEQUENCE {
                  ncdExecSTCIndex
                      INTEGER,
                  ncdExecSTCCommands
                      OCTET STRING
              }

          ncdExecSTCIndex OBJECT-TYPE
              SYNTAX  INTEGER
              ACCESS  read-only
              STATUS  optional
              ::= { ncdExecStartupCommandsEntry 1 }

          ncdExecSTCCommands OBJECT-TYPE
              SYNTAX  OCTET STRING
              ACCESS  read-write
              STATUS  optional
              ::= { ncdExecStartupCommandsEntry 2 }

          ncdExecDisabledCommandsTable OBJECT-TYPE
              SYNTAX  SEQUENCE OF NcdExecDisabledCommandsEntry
              ACCESS  not-accessible
              STATUS  optional
              ::= { ncdExec 2 }

          ncdExecDisabledCommandsEntry OBJECT-TYPE
              SYNTAX  NcdExecDisabledCommandsEntry
              ACCESS  not-accessible
              STATUS  optional
              ::= { ncdExecDisabledCommandsTable 1 }

          NcdExecDisabledCommandsEntry ::=
              SEQUENCE {
                  ncdExecDCIndex
                      INTEGER,
                  ncdExecDCCommands
                      OCTET STRING
              }

          ncdExecDCIndex OBJECT-TYPE
              SYNTAX  INTEGER
              ACCESS  read-only
              STATUS  optional
              ::= { ncdExecDisabledCommandsEntry 1 }

          ncdExecDCCommands OBJECT-TYPE
              SYNTAX  OCTET STRING
              ACCESS  read-write
              STATUS  optional
              ::= { ncdExecDisabledCommandsEntry 2 }


          -- the ncdLogin Group

          ncdLoginDfltHostsTable OBJECT-TYPE
              SYNTAX  SEQUENCE OF NcdLoginDfltHostsEntry
              ACCESS  not-accessible
              STATUS  optional
              ::= { ncdLogin 1 }

          ncdLoginDfltHostsEntry OBJECT-TYPE
              SYNTAX  NcdLoginDfltHostsEntry
              ACCESS  not-accessible
              STATUS  optional
              ::= { ncdLoginDfltHostsTable 1 }

          NcdLoginDfltHostsEntry ::=
              SEQUENCE {
                  ncdLoginDHTIndex
                      INTEGER,
                  ncdLoginDHTNetwork
                      INTEGER,
                  ncdLoginDHTHost
                      OCTET STRING,
                  ncdLoginDHTDescription
                      OCTET STRING
              }

          ncdLoginDHTIndex OBJECT-TYPE
              SYNTAX  INTEGER
              ACCESS  read-only
              STATUS  optional
              ::= { ncdLoginDfltHostsEntry 1 }

          ncdLoginDHTNetwork OBJECT-TYPE
              SYNTAX  INTEGER
              ACCESS  read-write
              STATUS  optional
              ::= { ncdLoginDfltHostsEntry 2 }

          ncdLoginDHTHost OBJECT-TYPE
              SYNTAX  OCTET STRING
              ACCESS  read-write
              STATUS  optional
              ::= { ncdLoginDfltHostsEntry 3 }

          ncdLoginDHTDescription OBJECT-TYPE
              SYNTAX  OCTET STRING
              ACCESS  read-write
              STATUS  optional
              ::= { ncdLoginDfltHostsEntry 4 }

          ncdLoginRestrictConnectionChoices OBJECT-TYPE
              SYNTAX  INTEGER
              ACCESS  read-write
              STATUS  optional
              ::= { ncdLogin 2 }

          ncdLoginDisabledNetTable OBJECT-TYPE
              SYNTAX  SEQUENCE OF NcdLoginDisabledNetEntry
              ACCESS  not-accessible
              STATUS  optional
              ::= { ncdLogin 3 }

          ncdLoginDisabledNetEntry OBJECT-TYPE
              SYNTAX  NcdLoginDisabledNetEntry
              ACCESS  not-accessible
              STATUS  optional
              ::= { ncdLoginDisabledNetTable 1 }

          NcdLoginDisabledNetEntry ::=
              SEQUENCE {
                  ncdLoginDNTIndex
                      INTEGER,
                  ncdLoginDNTName
                      OCTET STRING
              }

          ncdLoginDNTIndex OBJECT-TYPE
              SYNTAX  INTEGER
              ACCESS  read-only
              STATUS  optional
              ::= { ncdLoginDisabledNetEntry 1 }

          ncdLoginDNTName OBJECT-TYPE
              SYNTAX  OCTET STRING
              ACCESS  read-write
              STATUS  optional
              ::= { ncdLoginDisabledNetEntry 2 }

          ncdLoginAutoMapDelay OBJECT-TYPE
              SYNTAX  INTEGER
              ACCESS  read-write
              STATUS  optional
              ::= { ncdLogin 4 }

          ncdLoginDwLoginAccount OBJECT-TYPE
              SYNTAX  OCTET STRING
              ACCESS  read-write
              STATUS  optional
              ::= { ncdLogin 13 }

          ncdLoginDwPassword OBJECT-TYPE
              SYNTAX  OCTET STRING
              ACCESS  read-write
              STATUS  optional
              ::= { ncdLogin 14 }


          -- the ncdPex Group

          ncdPexSetupMaxModelClipPlanes OBJECT-TYPE
              SYNTAX  INTEGER
              ACCESS  read-write
              STATUS  optional
              ::= { ncdPex 1 }

          ncdPexSetupMaxNonAmbientLights OBJECT-TYPE
              SYNTAX  INTEGER
              ACCESS  read-write
              STATUS  optional
              ::= { ncdPex 2 }

          ncdPexSetupMaxNamesetNames OBJECT-TYPE
              SYNTAX  INTEGER
              ACCESS  read-write
              STATUS  optional
              ::= { ncdPex 3 }

          ncdPexSetupMonRefRedu OBJECT-TYPE
              SYNTAX  OCTET STRING
              ACCESS  read-write
              STATUS  optional
              ::= { ncdPex 4 }

          ncdPexSetupMonRefRedv OBJECT-TYPE
              SYNTAX  OCTET STRING
              ACCESS  read-write
              STATUS  optional
              ::= { ncdPex 5 }

          ncdPexSetupMonRefRedY OBJECT-TYPE
              SYNTAX  OCTET STRING
              ACCESS  read-write
              STATUS  optional
              ::= { ncdPex 6 }

          ncdPexSetupMonRefGreenu OBJECT-TYPE
              SYNTAX  OCTET STRING
              ACCESS  read-write
              STATUS  optional
              ::= { ncdPex 7 }

          ncdPexSetupMonRefGreenv OBJECT-TYPE
              SYNTAX  OCTET STRING
              ACCESS  read-write
              STATUS  optional
              ::= { ncdPex 8 }

          ncdPexSetupMonRefGreenY OBJECT-TYPE
              SYNTAX  OCTET STRING
              ACCESS  read-write
              STATUS  optional
              ::= { ncdPex 9 }

          ncdPexSetupMonRefBlueu OBJECT-TYPE
              SYNTAX  OCTET STRING
              ACCESS  read-write
              STATUS  optional
              ::= { ncdPex 10 }

          ncdPexSetupMonRefBluev OBJECT-TYPE
              SYNTAX  OCTET STRING
              ACCESS  read-write
              STATUS  optional
              ::= { ncdPex 11 }

          ncdPexSetupMonRefBlueY OBJECT-TYPE
              SYNTAX  OCTET STRING
              ACCESS  read-write
              STATUS  optional
              ::= { ncdPex 12 }

          ncdPexSetupMonRefWhiteu OBJECT-TYPE
              SYNTAX  OCTET STRING
              ACCESS  read-write
              STATUS  optional
              ::= { ncdPex 13 }

          ncdPexSetupMonRefWhitev OBJECT-TYPE
              SYNTAX  OCTET STRING
              ACCESS  read-write
              STATUS  optional
              ::= { ncdPex 14 }

          ncdPexSetupMonRefWhiteY OBJECT-TYPE
              SYNTAX  OCTET STRING
              ACCESS  read-write
              STATUS  optional
              ::= { ncdPex 15 }


          -- the ncdTerm Group

          ncdTermDfltConnectionTable OBJECT-TYPE
              SYNTAX  SEQUENCE OF NcdTermDfltConnectionEntry
              ACCESS  not-accessible
              STATUS  optional
              ::= { ncdTerm 1 }

          ncdTermDfltConnectionEntry OBJECT-TYPE
              SYNTAX  NcdTermDfltConnectionEntry
              ACCESS  not-accessible
              STATUS  optional
              ::= { ncdTermDfltConnectionTable 1 }

          NcdTermDfltConnectionEntry ::=
              SEQUENCE {
                  ncdTermDCTIndex
                      INTEGER,
                  ncdTermDCTProtocol
                      INTEGER,
                  ncdTermDCTHost
                      OCTET STRING,
                  ncdTermDCTDescription
                      OCTET STRING
              }

          ncdTermDCTIndex OBJECT-TYPE
              SYNTAX  INTEGER
              ACCESS  read-only
              STATUS  optional
              ::= { ncdTermDfltConnectionEntry 1 }

          ncdTermDCTProtocol OBJECT-TYPE
              SYNTAX  INTEGER
              ACCESS  read-write
              STATUS  optional
              ::= { ncdTermDfltConnectionEntry 2 }

          ncdTermDCTHost OBJECT-TYPE
              SYNTAX  OCTET STRING
              ACCESS  read-write
              STATUS  optional
              ::= { ncdTermDfltConnectionEntry 3 }

          ncdTermDCTDescription OBJECT-TYPE
              SYNTAX  OCTET STRING
              ACCESS  read-write
              STATUS  optional
              ::= { ncdTermDfltConnectionEntry 4 }

          ncdTermRestrictConnectionChoices OBJECT-TYPE
              SYNTAX  INTEGER
              ACCESS  read-write
              STATUS  optional
              ::= { ncdTerm 2 }

          ncdTermAutoMapDelay OBJECT-TYPE
              SYNTAX  INTEGER
              ACCESS  read-write
              STATUS  optional
              ::= { ncdTerm 3 }

          ncdTermDfltConnectTimeout OBJECT-TYPE
              SYNTAX  INTEGER
              ACCESS  read-write
              STATUS  optional
              ::= { ncdTerm 4 }

          ncdTermDelayLATDisplay OBJECT-TYPE
              SYNTAX  INTEGER
              ACCESS  read-write
              STATUS  optional
              ::= { ncdTerm 5 }


          -- the ncdFile Group

          ncdFileInitialFileServer1 OBJECT-TYPE
              SYNTAX  IpAddress
              ACCESS  read-write
              STATUS  optional
              ::= { ncdFile 1 }

          ncdFileInitialFileServer1Protocol OBJECT-TYPE
              SYNTAX  INTEGER
              ACCESS  read-write
              STATUS  optional
              ::= { ncdFile 2 }

          ncdFileInitialFileServer2 OBJECT-TYPE
              SYNTAX  IpAddress
              ACCESS  read-write
              STATUS  optional
              ::= { ncdFile 3 }

          ncdFileInitialFileServer2Protocol OBJECT-TYPE
              SYNTAX  INTEGER
              ACCESS  read-write
              STATUS  optional
              ::= { ncdFile 4 }

          ncdFileInitialFileServersUseVmsTftp OBJECT-TYPE
              SYNTAX  INTEGER
              ACCESS  read-write
              STATUS  optional
              ::= { ncdFile 5 }

          ncdFileServiceTable OBJECT-TYPE
              SYNTAX  SEQUENCE OF NcdFileServiceEntry
              ACCESS  not-accessible
              STATUS  optional
              ::= { ncdFile 6 }

          ncdFileServiceEntry OBJECT-TYPE
              SYNTAX  NcdFileServiceEntry
              ACCESS  not-accessible
              STATUS  optional
              ::= { ncdFileServiceTable 1 }

          NcdFileServiceEntry ::=
              SEQUENCE {
                  ncdFileSTIndex
                      INTEGER,
                  ncdFileSTLocalUnixMountPoint
                      OCTET STRING,
                  ncdFileSTLocalVmsMountPoint
                      OCTET STRING,
                  ncdFileSTServerAddress
                      IpAddress,
                  ncdFileSTProtocol
                      INTEGER,
                  ncdFileSTServerMountPoint
                      OCTET STRING,
                  ncdFileSTFileNameType
                      INTEGER,
                  ncdFileSTRetransTimeout
                      INTEGER,
                  ncdFileSTTransTimeout
                      INTEGER,
                  ncdFileSTReadSize
                      INTEGER,
                  ncdFileSTWriteSize
                      INTEGER
              }

          ncdFileSTIndex OBJECT-TYPE
              SYNTAX  INTEGER
              ACCESS  read-only
              STATUS  optional
              ::= { ncdFileServiceEntry 1 }

          ncdFileSTLocalUnixMountPoint OBJECT-TYPE
              SYNTAX  OCTET STRING
              ACCESS  read-write
              STATUS  optional
              ::= { ncdFileServiceEntry 2 }

          ncdFileSTLocalVmsMountPoint OBJECT-TYPE
              SYNTAX  OCTET STRING
              ACCESS  read-write
              STATUS  optional
              ::= { ncdFileServiceEntry 3 }

          ncdFileSTServerAddress OBJECT-TYPE
              SYNTAX  IpAddress
              ACCESS  read-write
              STATUS  optional
              ::= { ncdFileServiceEntry 4 }

          ncdFileSTProtocol OBJECT-TYPE
              SYNTAX  INTEGER
              ACCESS  read-write
              STATUS  optional
              ::= { ncdFileServiceEntry 5 }

          ncdFileSTServerMountPoint OBJECT-TYPE
              SYNTAX  OCTET STRING
              ACCESS  read-write
              STATUS  optional
              ::= { ncdFileServiceEntry 6 }

          ncdFileSTFileNameType OBJECT-TYPE
              SYNTAX  INTEGER
              ACCESS  read-write
              STATUS  optional
              ::= { ncdFileServiceEntry 7 }

          ncdFileSTRetransTimeout OBJECT-TYPE
              SYNTAX  INTEGER
              ACCESS  read-write
              STATUS  optional
              ::= { ncdFileServiceEntry 8 }

          ncdFileSTTransTimeout OBJECT-TYPE
              SYNTAX  INTEGER
              ACCESS  read-write
              STATUS  optional
              ::= { ncdFileServiceEntry 9 }

          ncdFileSTReadSize OBJECT-TYPE
              SYNTAX  INTEGER
              ACCESS  read-write
              STATUS  optional
              ::= { ncdFileServiceEntry 10 }

          ncdFileSTWriteSize OBJECT-TYPE
              SYNTAX  INTEGER
              ACCESS  read-write
              STATUS  optional
              ::= { ncdFileServiceEntry 11 }

          ncdFileExtendedDiagnostics OBJECT-TYPE
              SYNTAX  INTEGER
              ACCESS  read-write
              STATUS  optional
              ::= { ncdFile 7 }

          ncdFileRegressiveSearch OBJECT-TYPE
              SYNTAX  INTEGER
              ACCESS  read-write
              STATUS  optional
              ::= { ncdFile 8 }

          ncdFileServerHolddownTime OBJECT-TYPE
              SYNTAX  INTEGER
              ACCESS  read-write
              STATUS  optional
              ::= { ncdFile 9 }

          ncdFileUnmountTime OBJECT-TYPE
              SYNTAX  INTEGER
              ACCESS  read-write
              STATUS  optional
              ::= { ncdFile 10 }

          ncdFileDfltVmsExtension OBJECT-TYPE
              SYNTAX  OCTET STRING
              ACCESS  read-write
              STATUS  optional
              ::= { ncdFile 11 }

          ncdFileManagerTelnetPort OBJECT-TYPE
              SYNTAX  INTEGER
              ACCESS  read-write
              STATUS  optional
              ::= { ncdFile 12 }

          ncdFileManagerTcpPort OBJECT-TYPE
              SYNTAX  INTEGER
              ACCESS  read-write
              STATUS  optional
              ::= { ncdFile 13 }

          ncdFileManagerDnetObject OBJECT-TYPE
              SYNTAX  OCTET STRING
              ACCESS  read-write
              STATUS  optional
              ::= { ncdFile 14 }


          -- the ncdPref Group

          ncdPrefKbdFuncKeyMap OBJECT-TYPE
              SYNTAX  INTEGER
              ACCESS  read-write
              STATUS  optional
              ::= { ncdPref 1 }

          ncdPrefKbdAutoRepeat OBJECT-TYPE
              SYNTAX  INTEGER
              ACCESS  read-write
              STATUS  optional
              ::= { ncdPref 2 }

          ncdPrefKdbAutoRepeatAfter OBJECT-TYPE
              SYNTAX  TimeTicks
              ACCESS  read-write
              STATUS  optional
              ::= { ncdPref 3 }

          ncdPrefKbdAutoRepeatRate OBJECT-TYPE
              SYNTAX  INTEGER
              ACCESS  read-write
              STATUS  optional
              ::= { ncdPref 4 }

          ncdPrefKeyClickVolume OBJECT-TYPE
              SYNTAX  INTEGER
              ACCESS  read-write
              STATUS  optional
              ::= { ncdPref 5 }

          ncdPrefKbdLedsTable OBJECT-TYPE
              SYNTAX  SEQUENCE OF NcdPrefKbdLedsEntry
              ACCESS  not-accessible
              STATUS  optional
              ::= { ncdPref 6 }

          ncdPrefKbdLedsEntry OBJECT-TYPE
              SYNTAX  NcdPrefKbdLedsEntry
              ACCESS  not-accessible
              STATUS  optional
              ::= { ncdPrefKbdLedsTable 1 }

          NcdPrefKbdLedsEntry ::=
              SEQUENCE {
                  ncdPrefLedsTableIndex
                      INTEGER,
                  ncdPrefLedsTableEntry
                      INTEGER
              }

          ncdPrefLedsTableIndex OBJECT-TYPE
              SYNTAX  INTEGER
              ACCESS  read-only
              STATUS  optional
              ::= { ncdPrefKbdLedsEntry 1 }

          ncdPrefLedsTableEntry OBJECT-TYPE
              SYNTAX  INTEGER
              ACCESS  read-write
              STATUS  optional
              ::= { ncdPrefKbdLedsEntry 2 }

          ncdPrefBellEnabled OBJECT-TYPE
              SYNTAX  INTEGER
              ACCESS  read-write
              STATUS  optional
              ::= { ncdPref 7 }

          ncdPrefBellVolume OBJECT-TYPE
              SYNTAX  INTEGER
              ACCESS  read-write
              STATUS  optional
              ::= { ncdPref 8 }

          ncdPrefBellPitch OBJECT-TYPE
              SYNTAX  INTEGER
              ACCESS  read-write
              STATUS  optional
              ::= { ncdPref 9 }

          ncdPrefBellDuration OBJECT-TYPE
              SYNTAX  TimeTicks
              ACCESS  read-write
              STATUS  optional
              ::= { ncdPref 10 }

          ncdPrefMouseThresholdDistance OBJECT-TYPE
              SYNTAX  INTEGER
              ACCESS  read-write
              STATUS  optional
              ::= { ncdPref 11 }

          ncdPrefMouseAcceration OBJECT-TYPE
              SYNTAX  INTEGER
              ACCESS  read-write
              STATUS  optional
              ::= { ncdPref 12 }

          ncdPrefMouseButtonArragement OBJECT-TYPE
              SYNTAX  INTEGER
              ACCESS  read-write
              STATUS  optional
              ::= { ncdPref 13 }

          ncdPrefScreenBackground OBJECT-TYPE
              SYNTAX  INTEGER
              ACCESS  read-write
              STATUS  optional
              ::= { ncdPref 14 }

          ncdPrefScreenSolidColor OBJECT-TYPE
              SYNTAX  OCTET STRING
              ACCESS  read-write
              STATUS  optional
              ::= { ncdPref 15 }

          ncdPrefScreenBitmapFile OBJECT-TYPE
              SYNTAX  OCTET STRING
              ACCESS  read-write
              STATUS  optional
              ::= { ncdPref 16 }

          ncdPrefScreenBackBitmapForeground OBJECT-TYPE
              SYNTAX  OCTET STRING
              ACCESS  read-write
              STATUS  optional
              ::= { ncdPref 17 }

          ncdPrefScreenBackBitmapBackground OBJECT-TYPE
              SYNTAX  OCTET STRING
              ACCESS  read-write
              STATUS  optional
              ::= { ncdPref 18 }

          ncdPrefScreenSaverEnabled OBJECT-TYPE
              SYNTAX  INTEGER
              ACCESS  read-write
              STATUS  optional
              ::= { ncdPref 20 }

          ncdPrefScreenSaverAllowExposures OBJECT-TYPE
              SYNTAX  INTEGER
              ACCESS  read-write
              STATUS  optional
              ::= { ncdPref 21 }

          ncdPrefScreenSaverAfter OBJECT-TYPE
              SYNTAX  INTEGER
              ACCESS  read-write
              STATUS  optional
              ::= { ncdPref 22 }

          ncdPrefScreenSaverChangeAfter OBJECT-TYPE
              SYNTAX  INTEGER
              ACCESS  read-write
              STATUS  optional
              ::= { ncdPref 23 }

          ncdPrefScreenSaverStyle OBJECT-TYPE
              SYNTAX  INTEGER
              ACCESS  read-write
              STATUS  optional
              ::= { ncdPref 24 }

          ncdPrefScreenSaverBitmapFile OBJECT-TYPE
              SYNTAX  OCTET STRING
              ACCESS  read-write
              STATUS  optional
              ::= { ncdPref 25 }

          ncdPrefFontExtendedDiagnostics OBJECT-TYPE
              SYNTAX  INTEGER
              ACCESS  read-write
              STATUS  optional
              ::= { ncdPref 26 }

          ncdPrefFontPathTable OBJECT-TYPE
              SYNTAX  SEQUENCE OF NcdPrefFontPathEntry
              ACCESS  not-accessible
              STATUS  optional
              ::= { ncdPref 27 }

          ncdPrefFontPathEntry OBJECT-TYPE
              SYNTAX  NcdPrefFontPathEntry
              ACCESS  not-accessible
              STATUS  optional
              ::= { ncdPrefFontPathTable 1 }

          NcdPrefFontPathEntry ::=
              SEQUENCE {
                  ncdPrefFontPathTableIndex
                      INTEGER,
                  ncdPrefFontPathTableEntry
                      OCTET STRING
              }

          ncdPrefFontPathTableIndex OBJECT-TYPE
              SYNTAX  INTEGER
              ACCESS  read-only
              STATUS  optional
              ::= { ncdPrefFontPathEntry 1 }

          ncdPrefFontPathTableEntry OBJECT-TYPE
              SYNTAX  OCTET STRING
              ACCESS  read-write
              STATUS  optional
              ::= { ncdPrefFontPathEntry 2 }

          ncdPrefScreenRes OBJECT-TYPE
              SYNTAX  INTEGER
              ACCESS  read-write
              STATUS  optional
              ::= { ncdPref 29 }

          ncdPrefUseBackingStore OBJECT-TYPE
              SYNTAX  INTEGER
              ACCESS  read-write
              STATUS  optional
              ::= { ncdPref 30 }

          ncdPrefPermitOldBugs OBJECT-TYPE
              SYNTAX  INTEGER
              ACCESS  read-write
              STATUS  optional
              ::= { ncdPref 31 }

          ncdPrefOldDwCompatibility OBJECT-TYPE
              SYNTAX  INTEGER
              ACCESS  read-write
              STATUS  optional
              ::= { ncdPref 32 }

          ncdPrefOldDwKbdCompatibility OBJECT-TYPE
              SYNTAX  INTEGER
              ACCESS  read-write
              STATUS  optional
              ::= { ncdPref 33 }

          ncdPrefOldDwImageCompatibility OBJECT-TYPE
              SYNTAX  INTEGER
              ACCESS  read-write
              STATUS  optional
              ::= { ncdPref 34 }

          ncdPrefConsoleAutoLogoutIdleTime OBJECT-TYPE
              SYNTAX  INTEGER
              ACCESS  read-write
              STATUS  optional
              ::= { ncdPref 35 }

          ncdPrefConsoleAutoLogoutCancelDelay OBJECT-TYPE
              SYNTAX  INTEGER
              ACCESS  read-write
              STATUS  optional
              ::= { ncdPref 36 }

          ncdPrefConsoleAutoLockTime OBJECT-TYPE
              SYNTAX  INTEGER
              ACCESS  read-write
              STATUS  optional
              ::= { ncdPref 37 }

          ncdPrefConsoleLockScreenPasswdDflt OBJECT-TYPE
              SYNTAX  OCTET STRING
              ACCESS  read-write
              STATUS  optional
              ::= { ncdPref 38 }

          ncdPrefConsoleBlankScreenDelay OBJECT-TYPE
              SYNTAX  INTEGER
              ACCESS  read-write
              STATUS  optional
              ::= { ncdPref 39 }

          ncdPrefConsoleShowTimestamps OBJECT-TYPE
              SYNTAX  INTEGER
              ACCESS  read-write
              STATUS  optional
              ::= { ncdPref 40 }

          ncdPrefMaximumGain OBJECT-TYPE
              SYNTAX  INTEGER
              ACCESS  read-write
              STATUS  optional
              ::= { ncdPref 41 }

          ncdPrefSIESamplingMethod OBJECT-TYPE
              SYNTAX  INTEGER
              ACCESS  read-write
              STATUS  optional
              ::= { ncdPref 42 }

          ncdPrefSIEContrast OBJECT-TYPE
              SYNTAX  INTEGER
              ACCESS  read-write
              STATUS  optional
              ::= { ncdPref 43 }

          ncdPrefConsoleKeyString OBJECT-TYPE
              SYNTAX  OCTET STRING
              ACCESS  read-write
              STATUS  optional
              ::= { ncdPref 44 }

          ncdPrefTouchscreenButtonReleaseThreshold OBJECT-TYPE
              SYNTAX  INTEGER
              ACCESS  read-write
              STATUS  optional
              ::= { ncdPref 45 }

          ncdPrefCurrentPointingDevice OBJECT-TYPE
              SYNTAX  INTEGER
              ACCESS  read-write
              STATUS  optional
              ::= { ncdPref 46 }

          ncdPrefTouchscreenButtonPressThreshold OBJECT-TYPE
              SYNTAX  INTEGER
              ACCESS  read-write
              STATUS  optional
              ::= { ncdPref 47 }

          ncdPrefPowerManageStandbyTime OBJECT-TYPE
              SYNTAX  INTEGER
              ACCESS  read-write
              STATUS  optional
              ::= { ncdPref 50 }

          ncdPrefPowerManageSuspendTime OBJECT-TYPE
              SYNTAX  INTEGER
              ACCESS  read-write
              STATUS  optional
              ::= { ncdPref 51 }

          ncdPrefPowerManagePowerdownTime OBJECT-TYPE
              SYNTAX  INTEGER
              ACCESS  read-write
              STATUS  optional
              ::= { ncdPref 52 }

          ncdPrefPowerManageEnable OBJECT-TYPE
              SYNTAX  INTEGER
              ACCESS  read-write
              STATUS  optional
              ::= { ncdPref 53 }


          -- the ncdAccess Group

          ncdAccessXdmAuthCookie OBJECT-TYPE
              SYNTAX  OCTET STRING
              ACCESS  read-write
              STATUS  optional
              ::= { ncdAccess 1 }

          ncdAccessDfltAccessEnabled OBJECT-TYPE
              SYNTAX  INTEGER
              ACCESS  read-write
              STATUS  optional
              ::= { ncdAccess 2 }

          ncdAccessAccessEnabled OBJECT-TYPE
              SYNTAX  INTEGER
              ACCESS  read-write
              STATUS  optional
              ::= { ncdAccess 3 }

          ncdAccessAccessControlTable OBJECT-TYPE
              SYNTAX  SEQUENCE OF NcdAccessAccessControlEntry
              ACCESS  not-accessible
              STATUS  optional
              ::= { ncdAccess 4 }

          ncdAccessAccessControlEntry OBJECT-TYPE
              SYNTAX  NcdAccessAccessControlEntry
              ACCESS  not-accessible
              STATUS  optional
              ::= { ncdAccessAccessControlTable 1 }

          NcdAccessAccessControlEntry ::=
              SEQUENCE {
                  ncdAccessACTIndex
                      INTEGER,
                  ncdAccessACTAddress
                      OCTET STRING,
                  ncdAccessACTFamily
                      INTEGER
              }

          ncdAccessACTIndex OBJECT-TYPE
              SYNTAX  INTEGER
              ACCESS  read-only
              STATUS  optional
              ::= { ncdAccessAccessControlEntry 1 }

          ncdAccessACTAddress OBJECT-TYPE
              SYNTAX  OCTET STRING
              ACCESS  read-write
              STATUS  optional
              ::= { ncdAccessAccessControlEntry 2 }

          ncdAccessACTFamily OBJECT-TYPE
              SYNTAX  INTEGER
              ACCESS  read-write
              STATUS  optional
              ::= { ncdAccessAccessControlEntry 3 }

          ncdAccessConfigdReadOnlyPasswd OBJECT-TYPE
              SYNTAX  OCTET STRING
              ACCESS  read-write
              STATUS  optional
              ::= { ncdAccess 5 }

          ncdAccessConfigdReadWritePasswd OBJECT-TYPE
              SYNTAX  OCTET STRING
              ACCESS  read-write
              STATUS  optional
              ::= { ncdAccess 6 }

          ncdAccessConfigdEnforePasswdsLocally OBJECT-TYPE
              SYNTAX  INTEGER
              ACCESS  read-write
              STATUS  optional
              ::= { ncdAccess 7 }

          ncdAccessConfigdAccessControlEnabled OBJECT-TYPE
              SYNTAX  INTEGER
              ACCESS  read-write
              STATUS  optional
              ::= { ncdAccess 8 }

          ncdAccessConfigdHostTable OBJECT-TYPE
              SYNTAX  SEQUENCE OF NcdAccessConfigdHostEntry
              ACCESS  not-accessible
              STATUS  optional
              ::= { ncdAccess 9 }

          ncdAccessConfigdHostEntry OBJECT-TYPE
              SYNTAX  NcdAccessConfigdHostEntry
              ACCESS  not-accessible
              STATUS  optional
              ::= { ncdAccessConfigdHostTable 1 }

          NcdAccessConfigdHostEntry ::=
              SEQUENCE {
                  ncdAccessCHTIndex
                      INTEGER,
                  ncdAccessCHTAddress
                      OCTET STRING,
                  ncdAccessCHTFamily
                      INTEGER
              }

          ncdAccessCHTIndex OBJECT-TYPE
              SYNTAX  INTEGER
              ACCESS  read-only
              STATUS  optional
              ::= { ncdAccessConfigdHostEntry 1 }

          ncdAccessCHTAddress OBJECT-TYPE
              SYNTAX  OCTET STRING
              ACCESS  read-write
              STATUS  optional
              ::= { ncdAccessConfigdHostEntry 2 }

          ncdAccessCHTFamily OBJECT-TYPE
              SYNTAX  INTEGER
              ACCESS  read-write
              STATUS  optional
              ::= { ncdAccessConfigdHostEntry 3 }

          ncdAccessPrefdReadOnlyPasswd OBJECT-TYPE
              SYNTAX  OCTET STRING
              ACCESS  read-write
              STATUS  optional
              ::= { ncdAccess 10 }

          ncdAccessPrefdReadWritePasswd OBJECT-TYPE
              SYNTAX  OCTET STRING
              ACCESS  read-write
              STATUS  optional
              ::= { ncdAccess 11 }

          ncdAccessPrefdEnforcePasswdsLocally OBJECT-TYPE
              SYNTAX  INTEGER
              ACCESS  read-write
              STATUS  optional
              ::= { ncdAccess 12 }

          ncdAccessSnmpReadOnlyCommunity1 OBJECT-TYPE
              SYNTAX  OCTET STRING
              ACCESS  read-write
              STATUS  optional
              ::= { ncdAccess 13 }

          ncdAccessSnmpReadOnlyCommunity2 OBJECT-TYPE
              SYNTAX  OCTET STRING
              ACCESS  read-write
              STATUS  optional
              ::= { ncdAccess 14 }

          ncdAccessSnmpReadOnlyAccessControl OBJECT-TYPE
              SYNTAX  INTEGER
              ACCESS  read-write
              STATUS  optional
              ::= { ncdAccess 15 }

          ncdAccessSnmpReadOnlyAccessControlTable OBJECT-TYPE
              SYNTAX  SEQUENCE OF NcdAccessSnmpReadOnlyAccessControlEntry
              ACCESS  not-accessible
              STATUS  optional
              ::= { ncdAccess 16 }

          ncdAccessSnmpReadOnlyAccessControlEntry OBJECT-TYPE
              SYNTAX  NcdAccessSnmpReadOnlyAccessControlEntry
              ACCESS  not-accessible
              STATUS  optional
              ::= { ncdAccessSnmpReadOnlyAccessControlTable 1 }

          NcdAccessSnmpReadOnlyAccessControlEntry ::=
              SEQUENCE {
                  ncdAccessSnmpROAccessControlTableIndex
                      INTEGER,
                  ncdAccessSnmpROAccessControlTableHost
                      OCTET STRING
              }

          ncdAccessSnmpROAccessControlTableIndex OBJECT-TYPE
              SYNTAX  INTEGER
              ACCESS  read-only
              STATUS  optional
              ::= { ncdAccessSnmpReadOnlyAccessControlEntry 1 }

          ncdAccessSnmpROAccessControlTableHost OBJECT-TYPE
              SYNTAX  OCTET STRING
              ACCESS  read-write
              STATUS  optional
              ::= { ncdAccessSnmpReadOnlyAccessControlEntry 2 }

          ncdAccessSnmpReadWriteCommunity1 OBJECT-TYPE
              SYNTAX  OCTET STRING
              ACCESS  read-write
              STATUS  optional
              ::= { ncdAccess 17 }

          ncdAccessSnmpReadWriteCommunity2 OBJECT-TYPE
              SYNTAX  OCTET STRING
              ACCESS  read-write
              STATUS  optional
              ::= { ncdAccess 18 }

          ncdAccessSnmpReadWriteAccessControl OBJECT-TYPE
              SYNTAX  INTEGER
              ACCESS  read-write
              STATUS  optional
              ::= { ncdAccess 19 }

          ncdAccessSnmpReadWriteAccessControlTable OBJECT-TYPE
              SYNTAX  SEQUENCE OF NcdAccessSnmpReadWriteAccessControlEntry
              ACCESS  not-accessible
              STATUS  optional
              ::= { ncdAccess 20 }

          ncdAccessSnmpReadWriteAccessControlEntry OBJECT-TYPE
              SYNTAX  NcdAccessSnmpReadWriteAccessControlEntry
              ACCESS  not-accessible
              STATUS  optional
              ::= { ncdAccessSnmpReadWriteAccessControlTable 1 }

          NcdAccessSnmpReadWriteAccessControlEntry ::=
              SEQUENCE {
                  ncdAccessSnmpRWAccessControlTableIndex
                      INTEGER,
                  ncdAccessSnmpRWAccessControlTableAddress
                      OCTET STRING
              }

          ncdAccessSnmpRWAccessControlTableIndex OBJECT-TYPE
              SYNTAX  INTEGER
              ACCESS  read-only
              STATUS  optional
              ::= { ncdAccessSnmpReadWriteAccessControlEntry 1 }

          ncdAccessSnmpRWAccessControlTableAddress OBJECT-TYPE
              SYNTAX  OCTET STRING
              ACCESS  read-write
              STATUS  optional
              ::= { ncdAccessSnmpReadWriteAccessControlEntry 2 }

          ncdAccessSnmpResetEnabled OBJECT-TYPE
              SYNTAX  INTEGER
              ACCESS  read-write
              STATUS  optional
              ::= { ncdAccess 21 }

          ncdAccessSnmpTrapMonitorsTable OBJECT-TYPE
              SYNTAX  SEQUENCE OF NcdAccessSnmpTrapMonitorsEntry
              ACCESS  not-accessible
              STATUS  optional
              ::= { ncdAccess 22 }

          ncdAccessSnmpTrapMonitorsEntry OBJECT-TYPE
              SYNTAX  NcdAccessSnmpTrapMonitorsEntry
              ACCESS  not-accessible
              STATUS  optional
              ::= { ncdAccessSnmpTrapMonitorsTable 1 }

          NcdAccessSnmpTrapMonitorsEntry ::=
              SEQUENCE {
                  ncdAccessSnmpTMTIndex
                      INTEGER,
                  ncdAccessSnmpTMTHost
                      IpAddress,
                  ncdAccessSnmpTMTCommunity
                      OCTET STRING
              }

          ncdAccessSnmpTMTIndex OBJECT-TYPE
              SYNTAX  INTEGER
              ACCESS  read-only
              STATUS  optional
              ::= { ncdAccessSnmpTrapMonitorsEntry 1 }

          ncdAccessSnmpTMTHost OBJECT-TYPE
              SYNTAX  IpAddress
              ACCESS  read-write
              STATUS  optional
              ::= { ncdAccessSnmpTrapMonitorsEntry 2 }

          ncdAccessSnmpTMTCommunity OBJECT-TYPE
              SYNTAX  OCTET STRING
              ACCESS  read-write
              STATUS  optional
              ::= { ncdAccessSnmpTrapMonitorsEntry 3 }

          ncdAccessMopResetPasswd OBJECT-TYPE
              SYNTAX  OCTET STRING
              ACCESS  read-write
              STATUS  optional
              ::= { ncdAccess 23 }

          ncdAccessDiagdAccessControlEnabled OBJECT-TYPE
              SYNTAX  INTEGER
              ACCESS  read-write
              STATUS  optional
              ::= { ncdAccess 24 }

          ncdAccessDiagdAccessControlTable OBJECT-TYPE
              SYNTAX  SEQUENCE OF NcdAccessDiagdAccessControlEntry
              ACCESS  not-accessible
              STATUS  optional
              ::= { ncdAccess 25 }

          ncdAccessDiagdAccessControlEntry OBJECT-TYPE
              SYNTAX  NcdAccessDiagdAccessControlEntry
              ACCESS  not-accessible
              STATUS  optional
              ::= { ncdAccessDiagdAccessControlTable 1 }

          NcdAccessDiagdAccessControlEntry ::=
              SEQUENCE {
                  ncdAccessDiagdACTIndex
                      INTEGER,
                  ncdAccessDiagdACTAddress
                      OCTET STRING,
                  ncdAccessDiagdACTFamily
                      INTEGER
              }

          ncdAccessDiagdACTIndex OBJECT-TYPE
              SYNTAX  INTEGER
              ACCESS  read-only
              STATUS  optional
              ::= { ncdAccessDiagdAccessControlEntry 1 }

          ncdAccessDiagdACTAddress OBJECT-TYPE
              SYNTAX  OCTET STRING
              ACCESS  read-write
              STATUS  optional
              ::= { ncdAccessDiagdAccessControlEntry 2 }

          ncdAccessDiagdACTFamily OBJECT-TYPE
              SYNTAX  INTEGER
              ACCESS  read-write
              STATUS  optional
              ::= { ncdAccessDiagdAccessControlEntry 3 }

          ncdAccessNfsUserId OBJECT-TYPE
              SYNTAX  INTEGER
              ACCESS  read-write
              STATUS  optional
              ::= { ncdAccess 26 }

          ncdAccessNfsGroupId OBJECT-TYPE
              SYNTAX  INTEGER
              ACCESS  read-write
              STATUS  optional
              ::= { ncdAccess 27 }

          ncdAccessExecdAccessControlEnabled OBJECT-TYPE
              SYNTAX  INTEGER
              ACCESS  read-write
              STATUS  optional
              ::= { ncdAccess 28 }

          ncdAccessExecdAccessControlTable OBJECT-TYPE
              SYNTAX  SEQUENCE OF NcdAccessExecdAccessControlEntry
              ACCESS  not-accessible
              STATUS  optional
              ::= { ncdAccess 29 }

          ncdAccessExecdAccessControlEntry OBJECT-TYPE
              SYNTAX  NcdAccessExecdAccessControlEntry
              ACCESS  not-accessible
              STATUS  optional
              ::= { ncdAccessExecdAccessControlTable 1 }

          NcdAccessExecdAccessControlEntry ::=
              SEQUENCE {
                  ncdAccessExecdACTIndex
                      INTEGER,
                  ncdAccessExecdACTAddress
                      OCTET STRING,
                  ncdAccessExecdACTFamily
                      INTEGER
              }

          ncdAccessExecdACTIndex OBJECT-TYPE
              SYNTAX  INTEGER
              ACCESS  read-only
              STATUS  optional
              ::= { ncdAccessExecdAccessControlEntry 1 }

          ncdAccessExecdACTAddress OBJECT-TYPE
              SYNTAX  OCTET STRING
              ACCESS  read-write
              STATUS  optional
              ::= { ncdAccessExecdAccessControlEntry 2 }

          ncdAccessExecdACTFamily OBJECT-TYPE
              SYNTAX  INTEGER
              ACCESS  read-write
              STATUS  optional
              ::= { ncdAccessExecdAccessControlEntry 3 }

          ncdAccessSerialdLatPasswdTable OBJECT-TYPE
              SYNTAX  SEQUENCE OF NcdAccessSerialdLatPasswdEntry
              ACCESS  not-accessible
              STATUS  optional
              ::= { ncdAccess 30 }

          ncdAccessSerialdLatPasswdEntry OBJECT-TYPE
              SYNTAX  NcdAccessSerialdLatPasswdEntry
              ACCESS  not-accessible
              STATUS  optional
              ::= { ncdAccessSerialdLatPasswdTable 1 }

          NcdAccessSerialdLatPasswdEntry ::=
              SEQUENCE {
                  ncdAccessSerialdLPTIndex
                      INTEGER,
                  ncdAccessSerialdLPTPortNumber
                      INTEGER,
                  ncdAccessSerialdLPTPassword
                      OCTET STRING
              }

          ncdAccessSerialdLPTIndex OBJECT-TYPE
              SYNTAX  INTEGER
              ACCESS  read-only
              STATUS  optional
              ::= { ncdAccessSerialdLatPasswdEntry 1 }

          ncdAccessSerialdLPTPortNumber OBJECT-TYPE
              SYNTAX  INTEGER
              ACCESS  read-only
              STATUS  optional
              ::= { ncdAccessSerialdLatPasswdEntry 2 }

          ncdAccessSerialdLPTPassword OBJECT-TYPE
              SYNTAX  OCTET STRING
              ACCESS  read-write
              STATUS  optional
              ::= { ncdAccessSerialdLatPasswdEntry 3 }

          ncdAccessSerialdAccessControlEnabled OBJECT-TYPE
              SYNTAX  INTEGER
              ACCESS  read-write
              STATUS  optional
              ::= { ncdAccess 31 }

          ncdAccessSerialdAccessControlTable OBJECT-TYPE
              SYNTAX  SEQUENCE OF NcdAccessSerialdAccessControlEntry
              ACCESS  not-accessible
              STATUS  optional
              ::= { ncdAccess 32 }

          ncdAccessSerialdAccessControlEntry OBJECT-TYPE
              SYNTAX  NcdAccessSerialdAccessControlEntry
              ACCESS  not-accessible
              STATUS  optional
              ::= { ncdAccessSerialdAccessControlTable 1 }

          NcdAccessSerialdAccessControlEntry ::=
              SEQUENCE {
                  ncdAccessSerialdACTIndex
                      INTEGER,
                  ncdAccessSerialdACTAddress
                      OCTET STRING,
                  ncdAccessSerialdACTFamily
                      INTEGER
              }

          ncdAccessSerialdACTIndex OBJECT-TYPE
              SYNTAX  INTEGER
              ACCESS  read-only
              STATUS  optional
              ::= { ncdAccessSerialdAccessControlEntry 1 }

          ncdAccessSerialdACTAddress OBJECT-TYPE
              SYNTAX  OCTET STRING
              ACCESS  read-write
              STATUS  optional
              ::= { ncdAccessSerialdAccessControlEntry 2 }

          ncdAccessSerialdACTFamily OBJECT-TYPE
              SYNTAX  INTEGER
              ACCESS  read-write
              STATUS  optional
              ::= { ncdAccessSerialdAccessControlEntry 3 }

          ncdAccessFileManagerPasswd OBJECT-TYPE
              SYNTAX  OCTET STRING
              ACCESS  read-write
              STATUS  optional
              ::= { ncdAccess 33 }

          ncdAccessFiledAccessControlEnabled OBJECT-TYPE
              SYNTAX  INTEGER
              ACCESS  read-write
              STATUS  optional
              ::= { ncdAccess 34 }

          ncdAccessFiledAccessControlTable OBJECT-TYPE
              SYNTAX  SEQUENCE OF NcdAccessFiledAccessControlEntry
              ACCESS  not-accessible
              STATUS  optional
              ::= { ncdAccess 35 }

          ncdAccessFiledAccessControlEntry OBJECT-TYPE
              SYNTAX  NcdAccessFiledAccessControlEntry
              ACCESS  not-accessible
              STATUS  optional
              ::= { ncdAccessFiledAccessControlTable 1 }

          NcdAccessFiledAccessControlEntry ::=
              SEQUENCE {
                  ncdAccessFiledACTIndex
                      INTEGER,
                  ncdAccessFiledACTAddress
                      OCTET STRING,
                  ncdAccessFiledACTFamily
                      INTEGER
              }

          ncdAccessFiledACTIndex OBJECT-TYPE
              SYNTAX  INTEGER
              ACCESS  read-only
              STATUS  optional
              ::= { ncdAccessFiledAccessControlEntry 1 }

          ncdAccessFiledACTAddress OBJECT-TYPE
              SYNTAX  OCTET STRING
              ACCESS  read-write
              STATUS  optional
              ::= { ncdAccessFiledAccessControlEntry 2 }

          ncdAccessFiledACTFamily OBJECT-TYPE
              SYNTAX  INTEGER
              ACCESS  read-write
              STATUS  optional
              ::= { ncdAccessFiledAccessControlEntry 3 }

          ncdAccessParalleldLatPasswdTable OBJECT-TYPE
              SYNTAX  SEQUENCE OF NcdAccessParalleldLatPasswdEntry
              ACCESS  not-accessible
              STATUS  optional
              ::= { ncdAccess 36 }

          ncdAccessParalleldLatPasswdEntry OBJECT-TYPE
              SYNTAX  NcdAccessParalleldLatPasswdEntry
              ACCESS  not-accessible
              STATUS  optional
              ::= { ncdAccessParalleldLatPasswdTable 1 }

          NcdAccessParalleldLatPasswdEntry ::=
              SEQUENCE {
                  ncdAccessParalleldLPTIndex
                      INTEGER,
                  ncdAccessParalleldLPTPortNumber
                      INTEGER,
                  ncdAccessParalleldLPTPassword
                      OCTET STRING
              }

          ncdAccessParalleldLPTIndex OBJECT-TYPE
              SYNTAX  INTEGER
              ACCESS  read-only
              STATUS  optional
              ::= { ncdAccessParalleldLatPasswdEntry 1 }

          ncdAccessParalleldLPTPortNumber OBJECT-TYPE
              SYNTAX  INTEGER
              ACCESS  read-only
              STATUS  optional
              ::= { ncdAccessParalleldLatPasswdEntry 2 }

          ncdAccessParalleldLPTPassword OBJECT-TYPE
              SYNTAX  OCTET STRING
              ACCESS  read-write
              STATUS  optional
              ::= { ncdAccessParalleldLatPasswdEntry 3 }

          ncdAccessGlobalPasswd OBJECT-TYPE
              SYNTAX  OCTET STRING
              ACCESS  read-write
              STATUS  optional
              ::= { ncdAccess 38 }

          ncdAccessConsoleDisplayPassword OBJECT-TYPE
              SYNTAX  OCTET STRING
              ACCESS  read-write
              STATUS  optional
              ::= { ncdAccess 42 }

          ncdAccessConsoleEnforcePasswordLocally OBJECT-TYPE
              SYNTAX  INTEGER
              ACCESS  read-write
              STATUS  optional
              ::= { ncdAccess 43 }


          -- the ncdTokenRing Group

          ncdTokenRingSpeed OBJECT-TYPE
              SYNTAX  INTEGER
              ACCESS  read-write
              STATUS  optional
              ::= { ncdTokenRing 1 }


          -- the ncdXremote Group

          ncdXremoteVersion OBJECT-TYPE
              SYNTAX  INTEGER
              ACCESS  read-only
              STATUS  optional
              ::= { ncdXremote 1 }

          ncdXremoteState OBJECT-TYPE
              SYNTAX  OCTET STRING
              ACCESS  read-only
              STATUS  optional
              ::= { ncdXremote 2 }

          ncdXremotePktsTransmitted OBJECT-TYPE
              SYNTAX  INTEGER
              ACCESS  read-only
              STATUS  optional
              ::= { ncdXremote 3 }

          ncdXremotePktTransErrors OBJECT-TYPE
              SYNTAX  INTEGER
              ACCESS  read-only
              STATUS  optional
              ::= { ncdXremote 4 }

          ncdXremotePktsRetrans OBJECT-TYPE
              SYNTAX  INTEGER
              ACCESS  read-only
              STATUS  optional
              ::= { ncdXremote 5 }

          ncdXremotePktsReceived OBJECT-TYPE
              SYNTAX  INTEGER
              ACCESS  read-only
              STATUS  optional
              ::= { ncdXremote 6 }

          ncdXremotePktsWithErrorsReceived OBJECT-TYPE
              SYNTAX  INTEGER
              ACCESS  read-only
              STATUS  optional
              ::= { ncdXremote 7 }

          ncdXremotePktsOutOfSequence OBJECT-TYPE
              SYNTAX  INTEGER
              ACCESS  read-only
              STATUS  optional
              ::= { ncdXremote 8 }

          ncdXremoteRoundTripTime OBJECT-TYPE
              SYNTAX  TimeTicks
              ACCESS  read-only
              STATUS  optional
              ::= { ncdXremote 9 }

          ncdXremoteTimeOut OBJECT-TYPE
              SYNTAX  TimeTicks
              ACCESS  read-only
              STATUS  optional
              ::= { ncdXremote 10 }

          ncdXremoteTransWinSize OBJECT-TYPE
              SYNTAX  INTEGER
              ACCESS  read-only
              STATUS  optional
              ::= { ncdXremote 11 }

          ncdXremoteTransSequenceNumber OBJECT-TYPE
              SYNTAX  INTEGER
              ACCESS  read-only
              STATUS  optional
              ::= { ncdXremote 12 }

          ncdXremoteUnackPkt OBJECT-TYPE
              SYNTAX  INTEGER
              ACCESS  read-only
              STATUS  optional
              ::= { ncdXremote 13 }

          ncdXremoteReceiveWinSize OBJECT-TYPE
              SYNTAX  INTEGER
              ACCESS  read-only
              STATUS  optional
              ::= { ncdXremote 14 }

          ncdXremoteNxtReceiveSequenceNumber OBJECT-TYPE
              SYNTAX  INTEGER
              ACCESS  read-only
              STATUS  optional
              ::= { ncdXremote 15 }

          ncdXremoteCompressType OBJECT-TYPE
              SYNTAX  INTEGER
              ACCESS  read-write
              STATUS  optional
              ::= { ncdXremote 16 }

          ncdXremoteAuthEnabled OBJECT-TYPE
              SYNTAX  INTEGER
              ACCESS  read-write
              STATUS  optional
              ::= { ncdXremote 17 }

          ncdXremoteEscTable OBJECT-TYPE
              SYNTAX  SEQUENCE OF NcdXremoteEscEntry
              ACCESS  not-accessible
              STATUS  optional
              ::= { ncdXremote 18 }

          ncdXremoteEscEntry OBJECT-TYPE
              SYNTAX  NcdXremoteEscEntry
              ACCESS  not-accessible
              STATUS  optional
              ::= { ncdXremoteEscTable 1 }

          NcdXremoteEscEntry ::=
              SEQUENCE {
                  ncdXremoteEscIndex
                      INTEGER,
                  ncdXremoteEscChar
                      INTEGER
              }

          ncdXremoteEscIndex OBJECT-TYPE
              SYNTAX  INTEGER
              ACCESS  read-only
              STATUS  optional
              ::= { ncdXremoteEscEntry 1 }

          ncdXremoteEscChar OBJECT-TYPE
              SYNTAX  INTEGER
              ACCESS  read-write
              STATUS  optional
              ::= { ncdXremoteEscEntry 2 }

          ncdXremoteNetEnabled OBJECT-TYPE
              SYNTAX  INTEGER
              ACCESS  read-write
              STATUS  optional
              ::= { ncdXremote 19 }

          ncdXremoteListenPort OBJECT-TYPE
              SYNTAX  INTEGER
              ACCESS  read-write
              STATUS  optional
              ::= { ncdXremote 20 }


          -- the ncdPpp Group

          ncdPppSlipIfTable OBJECT-TYPE
              SYNTAX  SEQUENCE OF NcdPppSlipIfEntry
              ACCESS  not-accessible
              STATUS  optional
              ::= { ncdPpp 1 }

          ncdPppSlipIfEntry OBJECT-TYPE
              SYNTAX  NcdPppSlipIfEntry
              ACCESS  not-accessible
              STATUS  optional
              ::= { ncdPppSlipIfTable 1 }

          NcdPppSlipIfEntry ::=
              SEQUENCE {
                  ncdPppSlipIfTablePortNumber
                      INTEGER,
                  ncdPppSlipIfTableIpAddress
                      IpAddress,
                  ncdPppSlipIfTablePeerIpAddress
                      IpAddress,
                  ncdPppSlipIfTableDfltGateway
                      INTEGER,
                  ncdPppSlipIfTableVJCompression
                      INTEGER
              }

          ncdPppSlipIfTablePortNumber OBJECT-TYPE
              SYNTAX  INTEGER
              ACCESS  read-only
              STATUS  optional
              ::= { ncdPppSlipIfEntry 1 }

          ncdPppSlipIfTableIpAddress OBJECT-TYPE
              SYNTAX  IpAddress
              ACCESS  read-write
              STATUS  optional
              ::= { ncdPppSlipIfEntry 2 }

          ncdPppSlipIfTablePeerIpAddress OBJECT-TYPE
              SYNTAX  IpAddress
              ACCESS  read-write
              STATUS  optional
              ::= { ncdPppSlipIfEntry 3 }

          ncdPppSlipIfTableDfltGateway OBJECT-TYPE
              SYNTAX  INTEGER
              ACCESS  read-write
              STATUS  optional
              ::= { ncdPppSlipIfEntry 4 }

          ncdPppSlipIfTableVJCompression OBJECT-TYPE
              SYNTAX  INTEGER
              ACCESS  read-write
              STATUS  optional
              ::= { ncdPppSlipIfEntry 5 }

          ncdPppIfTable OBJECT-TYPE
              SYNTAX  SEQUENCE OF NcdPppIfEntry
              ACCESS  not-accessible
              STATUS  optional
              ::= { ncdPpp 2 }

          ncdPppIfEntry OBJECT-TYPE
              SYNTAX  NcdPppIfEntry
              ACCESS  not-accessible
              STATUS  optional
              ::= { ncdPppIfTable 1 }

          NcdPppIfEntry ::=
              SEQUENCE {
                  ncdPppIfTablePortNumber
                      INTEGER,
                  ncdPppIfTableCtlCharMap
                      INTEGER,
                  ncdPppIfTableMTU
                      INTEGER,
                  ncdPppIfTableProtocolComp
                      INTEGER,
                  ncdPppIfTableACComp
                      INTEGER,
                  ncdPppIfTablePassive
                      INTEGER,
                  ncdPppIfTableOldOptions
                      INTEGER
              }

          ncdPppIfTablePortNumber OBJECT-TYPE
              SYNTAX  INTEGER
              ACCESS  read-only
              STATUS  optional
              ::= { ncdPppIfEntry 1 }

          ncdPppIfTableCtlCharMap OBJECT-TYPE
              SYNTAX  INTEGER
              ACCESS  read-write
              STATUS  optional
              ::= { ncdPppIfEntry 2 }

          ncdPppIfTableMTU OBJECT-TYPE
              SYNTAX  INTEGER
              ACCESS  read-write
              STATUS  optional
              ::= { ncdPppIfEntry 3 }

          ncdPppIfTableProtocolComp OBJECT-TYPE
              SYNTAX  INTEGER
              ACCESS  read-write
              STATUS  optional
              ::= { ncdPppIfEntry 4 }

          ncdPppIfTableACComp OBJECT-TYPE
              SYNTAX  INTEGER
              ACCESS  read-write
              STATUS  optional
              ::= { ncdPppIfEntry 5 }

          ncdPppIfTablePassive OBJECT-TYPE
              SYNTAX  INTEGER
              ACCESS  read-write
              STATUS  optional
              ::= { ncdPppIfEntry 6 }

          ncdPppIfTableOldOptions OBJECT-TYPE
              SYNTAX  INTEGER
              ACCESS  read-write
              STATUS  optional
              ::= { ncdPppIfEntry 7 }


          -- the ncdPrefPex Group

          ncdPrefPexNomLinWidth OBJECT-TYPE
              SYNTAX  INTEGER
              ACCESS  read-write
              STATUS  optional
              ::= { ncdPrefPex 1 }

          ncdPrefPexNomEdgeWidth OBJECT-TYPE
              SYNTAX  INTEGER
              ACCESS  read-write
              STATUS  optional
              ::= { ncdPrefPex 2 }

          ncdPrefPexNomMarkSiz OBJECT-TYPE
              SYNTAX  INTEGER
              ACCESS  read-write
              STATUS  optional
              ::= { ncdPrefPex 3 }

          ncdPrefPexDitFlatShadedSurface OBJECT-TYPE
              SYNTAX  INTEGER
              ACCESS  read-write
              STATUS  optional
              ::= { ncdPrefPex 4 }

          ncdPrefPexDitInterpSurface OBJECT-TYPE
              SYNTAX  INTEGER
              ACCESS  read-write
              STATUS  optional
              ::= { ncdPrefPex 5 }

          ncdPrefPexSurfaceInterStyle OBJECT-TYPE
              SYNTAX  INTEGER
              ACCESS  read-write
              STATUS  optional
              ::= { ncdPrefPex 6 }

          ncdPrefPexSurfaceInterpMethod OBJECT-TYPE
              SYNTAX  INTEGER
              ACCESS  read-write
              STATUS  optional
              ::= { ncdPrefPex 7 }

          ncdPrefPexSurfaceReflectModel OBJECT-TYPE
              SYNTAX  INTEGER
              ACCESS  read-write
              STATUS  optional
              ::= { ncdPrefPex 8 }

          ncdPrefPexColorClipMethod OBJECT-TYPE
              SYNTAX  INTEGER
              ACCESS  read-write
              STATUS  optional
              ::= { ncdPrefPex 9 }


          -- the ncd3270 Group

          ncd3270DfltConnectionTable OBJECT-TYPE
              SYNTAX  SEQUENCE OF Ncd3270DfltConnectionEntry
              ACCESS  not-accessible
              STATUS  optional
              ::= { ncd3270 1 }

          ncd3270DfltConnectionEntry OBJECT-TYPE
              SYNTAX  Ncd3270DfltConnectionEntry
              ACCESS  not-accessible
              STATUS  optional
              ::= { ncd3270DfltConnectionTable 1 }

          Ncd3270DfltConnectionEntry ::=
              SEQUENCE {
                  ncd3270DCTIndex
                      INTEGER,
                  ncd3270DCTProtocol
                      INTEGER,
                  ncdTermDCTHost
                      OCTET STRING,
                  ncdTermDCTPort
                      OCTET STRING,
                  ncd3270DCTModel
                      INTEGER,
                  ncdTermDCTDescription
                      OCTET STRING
              }

          ncd3270DCTIndex OBJECT-TYPE
              SYNTAX  INTEGER
              ACCESS  read-only
              STATUS  optional
              ::= { ncd3270DfltConnectionEntry 1 }

          ncd3270DCTProtocol OBJECT-TYPE
              SYNTAX  INTEGER
              ACCESS  read-write
              STATUS  optional
              ::= { ncd3270DfltConnectionEntry 2 }

          ncdTermDCTHost OBJECT-TYPE
              SYNTAX  OCTET STRING
              ACCESS  read-write
              STATUS  optional
              ::= { ncd3270DfltConnectionEntry 3 }

          ncdTermDCTPort OBJECT-TYPE
              SYNTAX  OCTET STRING
              ACCESS  read-write
              STATUS  optional
              ::= { ncd3270DfltConnectionEntry 4 }

          ncd3270DCTModel OBJECT-TYPE
              SYNTAX  INTEGER
              ACCESS  read-write
              STATUS  optional
              ::= { ncd3270DfltConnectionEntry 5 }

          ncdTermDCTDescription OBJECT-TYPE
              SYNTAX  OCTET STRING
              ACCESS  read-write
              STATUS  optional
              ::= { ncd3270DfltConnectionEntry 6 }

          ncd3270Enable3270Emulation OBJECT-TYPE
              SYNTAX  INTEGER
              ACCESS  read-write
              STATUS  optional
              ::= { ncd3270 2 }


          -- the ncdParallel Group

          ncdParallelDTable OBJECT-TYPE
              SYNTAX  SEQUENCE OF NcdParallelDEntry
              ACCESS  not-accessible
              STATUS  optional
              ::= { ncdParallel 1 }

          ncdParallelDEntry OBJECT-TYPE
              SYNTAX  NcdParallelDEntry
              ACCESS  not-accessible
              STATUS  optional
              ::= { ncdParallelDTable 1 }

          NcdParallelDEntry ::=
              SEQUENCE {
                  ncdParallelDTableIndex
                      INTEGER,
                  ncdParallelDTablePortNumber
                      INTEGER,
                  ncdParallelDTableUseParaProt
                      INTEGER,
                  ncdParallelDTableTCPPort
                      INTEGER,
                  ncdParallelDTableNCDnetObjName
                      OCTET STRING,
                  ncdParallelDTableEnableLAT
                      INTEGER,
                  ncdParallelDTableLATServName
                      OCTET STRING,
                  ncdParallelDTableLATServRating
                      INTEGER
              }

          ncdParallelDTableIndex OBJECT-TYPE
              SYNTAX  INTEGER
              ACCESS  read-only
              STATUS  optional
              ::= { ncdParallelDEntry 1 }

          ncdParallelDTablePortNumber OBJECT-TYPE
              SYNTAX  INTEGER
              ACCESS  read-only
              STATUS  optional
              ::= { ncdParallelDEntry 2 }

          ncdParallelDTableUseParaProt OBJECT-TYPE
              SYNTAX  INTEGER
              ACCESS  read-write
              STATUS  optional
              ::= { ncdParallelDEntry 3 }

          ncdParallelDTableTCPPort OBJECT-TYPE
              SYNTAX  INTEGER
              ACCESS  read-write
              STATUS  optional
              ::= { ncdParallelDEntry 4 }

          ncdParallelDTableNCDnetObjName OBJECT-TYPE
              SYNTAX  OCTET STRING
              ACCESS  read-write
              STATUS  optional
              ::= { ncdParallelDEntry 5 }

          ncdParallelDTableEnableLAT OBJECT-TYPE
              SYNTAX  INTEGER
              ACCESS  read-write
              STATUS  optional
              ::= { ncdParallelDEntry 6 }

          ncdParallelDTableLATServName OBJECT-TYPE
              SYNTAX  OCTET STRING
              ACCESS  read-write
              STATUS  optional
              ::= { ncdParallelDEntry 7 }

          ncdParallelDTableLATServRating OBJECT-TYPE
              SYNTAX  INTEGER
              ACCESS  read-write
              STATUS  optional
              ::= { ncdParallelDEntry 8 }

          ncdParallelDStatsTbl OBJECT-TYPE
              SYNTAX  SEQUENCE OF NcdParallelDStatsEntryrvRating
              ACCESS  not-accessible
              STATUS  optional
              ::= { ncdParallel 2 }

          ncdParallelDStatsEntryrvRating OBJECT-TYPE
              SYNTAX  NcdParallelDStatsEntryrvRating
              ACCESS  not-accessible
              STATUS  optional
              ::= { ncdParallelDStatsTbl 1 }

          NcdParallelDStatsEntryrvRating ::=
              SEQUENCE {
                  ncdParallelDStatsTblPortNumber
                      INTEGER,
                  ncdParallelDStatsTblConnAccepts
                      INTEGER,
                  ncdParallelDStatsTblConnBadAccesses
                      INTEGER,
                  ncdParallelDStatsTblConnIOErrors
                      INTEGER,
                  ncdParallelDStatsTblConnEofCloses
                      INTEGER
              }

          ncdParallelDStatsTblPortNumber OBJECT-TYPE
              SYNTAX  INTEGER
              ACCESS  read-only
              STATUS  optional
              ::= { ncdParallelDStatsEntryrvRating 1 }

          ncdParallelDStatsTblConnAccepts OBJECT-TYPE
              SYNTAX  INTEGER
              ACCESS  read-only
              STATUS  optional
              ::= { ncdParallelDStatsEntryrvRating 2 }

          ncdParallelDStatsTblConnBadAccesses OBJECT-TYPE
              SYNTAX  INTEGER
              ACCESS  read-only
              STATUS  optional
              ::= { ncdParallelDStatsEntryrvRating 3 }

          ncdParallelDStatsTblConnIOErrors OBJECT-TYPE
              SYNTAX  INTEGER
              ACCESS  read-only
              STATUS  optional
              ::= { ncdParallelDStatsEntryrvRating 4 }

          ncdParallelDStatsTblConnEofCloses OBJECT-TYPE
              SYNTAX  INTEGER
              ACCESS  read-only
              STATUS  optional
              ::= { ncdParallelDStatsEntryrvRating 5 }

          END
