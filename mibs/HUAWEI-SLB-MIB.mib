-- ===========================================================
-- Copyright (C) 2009 by HUAWEI TECHNOLOGIES. All rights reserved.
-- 
-- Description: HUAWEI-SLB-MIB
-- Reference:     
-- Version: 1.0
-- History: 
-- ===========================================================

    HUAWEI-SLB-MIB DEFINITIONS ::= BEGIN
    IMPORTS
    hwDatacomm
    FROM HUAWEI-MIB
    OBJECT-GROUP, MODULE-COMPLIANCE, NOTIFICATION-GROUP
    FROM SNMPv2-CONF
    IpAddress, Integer32, OBJECT-TYPE, MODULE-IDENTITY, NOTIFICATION-TYPE
    FROM SNMPv2-SMI;


    hwSLBMIB MODULE-IDENTITY 
    LAST-UPDATED "200911301200Z" -- November 30, 2009 at 12:00 GMT
    ORGANIZATION 
    "Huawei Technologies Co., Ltd."
    CONTACT-INFO 
    "
    NanJing Institute,Huawei Technologies Co.,Ltd.
    HuiHong Mansion,No.91 BaiXia Rd.
    NanJing, P.R. of China
    Zipcode:210001

    Http://www.huawei.com                                                           
    E-mail:support@huawei.com "
    DESCRIPTION 
    "The MIB describes Server Load Balance"
    REVISION "200911301200Z" -- November 30, 2009 at 12:00 GMT
    DESCRIPTION 
    "Initial revision."
    ::= { hwDatacomm 225 }



    --
    -- Node definitions
    --

    hwSlbMibObjects OBJECT IDENTIFIER ::= { hwSLBMIB 1 }

    hwSlbTrapObjects OBJECT IDENTIFIER ::= { hwSlbMibObjects 1 }


    hwIpAddress OBJECT-TYPE
    SYNTAX IpAddress
    MAX-ACCESS accessible-for-notify
    STATUS current
    DESCRIPTION
    "The object indicates the IP address of a load balance member."
    ::= { hwSlbTrapObjects 1 }


    hwMemberName OBJECT-TYPE
    SYNTAX OCTET STRING(SIZE (32))
    MAX-ACCESS accessible-for-notify
    STATUS current
    DESCRIPTION
    "The object indicates the member in a load balance group, each member in the load balance group will provide 
    same services to clients, system will select one member to serve the clients' requests."
    ::= { hwSlbTrapObjects 2 }

    hwGroupName OBJECT-TYPE
    SYNTAX OCTET STRING(SIZE (32))
    MAX-ACCESS accessible-for-notify
    STATUS current
    DESCRIPTION
    "The object indicates the group name of members, each group members may contain same services and typically reside 
    in the same physical location in a data center. "
    ::= { hwSlbTrapObjects 3 }

    hwPort OBJECT-TYPE
    SYNTAX Integer32(1..65535)
    MAX-ACCESS accessible-for-notify
    STATUS current
    DESCRIPTION
    "The TCP or UDP port number, the range can from 1 to 65535."
    ::= { hwSlbTrapObjects 4 }

    hwProbeName OBJECT-TYPE
    SYNTAX OCTET STRING(SIZE (32))
    MAX-ACCESS accessible-for-notify
    STATUS current
    DESCRIPTION
    "The object indicates a probe that is used to detect failures for members in a group. 
    When you initially configure a health probe, you should define its type and name."
    ::= { hwSlbTrapObjects 5 }

    hwProbeType OBJECT-TYPE
    SYNTAX   INTEGER
    {
    icmp(1),
    tcp(2),
    udp(3),
    http(4)
    }
    MAX-ACCESS accessible-for-notify
    STATUS current
    DESCRIPTION
    "The object indicates probe type. S9300 support ICMP, TCP, UDP, HTTP probe types."
    ::= { hwSlbTrapObjects 6 }

    hwConnectionNum OBJECT-TYPE
    SYNTAX Integer32(1..4000000)
    MAX-ACCESS accessible-for-notify
    STATUS current
    DESCRIPTION
    "The object indicates the connection number of a group member, usually five-tuple is used to 
    describe a connection(source IP, detination IP, source port, destination port, protocal)."
    ::= { hwSlbTrapObjects 7 } 

    hwMasterGroup OBJECT-TYPE
    SYNTAX OCTET STRING(SIZE (32))
    MAX-ACCESS accessible-for-notify
    STATUS current
    DESCRIPTION
    "The object indicates the master group.
    In order to improve reliability, S9300 can bind master group and backup group together to provide load 
    balance service, operators can config two load balance group: one as master, the other as backup"
    ::= { hwSlbTrapObjects 8 } 
    
    hwMasterGroupActiveNum OBJECT-TYPE
    SYNTAX Integer32(0..100)
    MAX-ACCESS accessible-for-notify
    STATUS current
    DESCRIPTION
    "The object indicates the active member number in the master server group."
    ::= { hwSlbTrapObjects 9 }

    hwMasterGroupTotalNum OBJECT-TYPE
    SYNTAX Integer32(1..100)
    MAX-ACCESS accessible-for-notify
    STATUS current
    DESCRIPTION
    "The object indicates the total number of in-service members in the master group."

    ::= { hwSlbTrapObjects 10 }

    hwBackupGroup OBJECT-TYPE
    SYNTAX OCTET STRING(SIZE (32))
    MAX-ACCESS accessible-for-notify
    STATUS current
    DESCRIPTION
    "The object indicates the backup group.
    In order to improve reliability, S9300 can bind master group and backup group together to provide load 
    balance service, operators can config two load balance group one as master, the other as backup"
    ::= { hwSlbTrapObjects 11 } 

    hwBackupGroupActiveNum OBJECT-TYPE
    SYNTAX Integer32(0..100)
    MAX-ACCESS accessible-for-notify
    STATUS current
    DESCRIPTION
    "The object indicates the active member number in the backup server group."
    ::= { hwSlbTrapObjects 12 }
    
    hwBackupGroupTotalNum OBJECT-TYPE
    SYNTAX Integer32(1..100)
    MAX-ACCESS accessible-for-notify
    STATUS current
    DESCRIPTION
    "The object indicates the total number of in-service members in the backup group."
    ::= { hwSlbTrapObjects 13 }

    hwActionName OBJECT-TYPE
    SYNTAX OCTET STRING(SIZE (32))
    MAX-ACCESS accessible-for-notify
    STATUS current
    DESCRIPTION
    "The object indicates the policy action. Operators can define different actions 
    for clients request: forward packets, drop packets, load balance, sticky load balance."
    ::= { hwSlbTrapObjects 14 }

    hwCurWorkGroupName OBJECT-TYPE
    SYNTAX OCTET STRING(SIZE (32))
    MAX-ACCESS accessible-for-notify
    STATUS current
    DESCRIPTION
    "The object indicates the current working group, the working group may be master group or backup group."
    ::= { hwSlbTrapObjects 15 }
    
    hwSlbNotifications OBJECT IDENTIFIER ::= { hwSlbMibObjects 2 }


    hwMemberInstanceStateUp NOTIFICATION-TYPE
    OBJECTS { hwGroupName, hwMemberName, hwIpAddress, hwPort }
    STATUS current
    DESCRIPTION 
    "Member state changes to up. S9300 will select the member to accept clients' new requests."
    ::= { hwSlbNotifications 1 }


    hwMemberInstanceStateDown NOTIFICATION-TYPE
    OBJECTS { hwGroupName, hwMemberName, hwIpAddress, hwPort }
    STATUS current
    DESCRIPTION 
    "Member state changes to down. S9300 will not select the member when clients' new requests come."
    ::= { hwSlbNotifications 2 }


    hwGroupStateSwitchover NOTIFICATION-TYPE
    OBJECTS { hwActionName, hwMasterGroup, hwMasterGroupActiveNum,hwMasterGroupTotalNum,hwBackupGroup,hwBackupGroupActiveNum,
      hwBackupGroupTotalNum, hwCurWorkGroupName}
    STATUS current
    DESCRIPTION 
    "When there are members' state change, current work group may change from master group to backup group 
    or from backup group to master group."
    ::= { hwSlbNotifications 3 }

    hwMemberConnectionFull NOTIFICATION-TYPE
    OBJECTS { hwMemberName, hwConnectionNum }
    STATUS current
    DESCRIPTION 
    "The connections for the physical member attains threshold."
    ::= { hwSlbNotifications 4 }


    hwMemberConnectionFullRestore NOTIFICATION-TYPE
    OBJECTS { hwMemberName, hwConnectionNum }
    STATUS current
    DESCRIPTION 
    "The connections for the physical member restores to normal."
    ::= { hwSlbNotifications 5 }


    hwMemberInstanceConnectionFull NOTIFICATION-TYPE
    OBJECTS { hwGroupName, hwMemberName, hwConnectionNum }
    STATUS current
    DESCRIPTION 
    "The connections for the group member attains threshold."
    ::= { hwSlbNotifications 6 }


    hwMemberInstanceConnectionFullRestore NOTIFICATION-TYPE
    OBJECTS { hwGroupName, hwMemberName, hwConnectionNum }
    STATUS current
    DESCRIPTION 
    "The connections for the group member restores nomal."
    ::= { hwSlbNotifications 7 }


    hwProbeInstanceStateUp NOTIFICATION-TYPE
    OBJECTS { hwGroupName, hwMemberName, hwProbeName, hwProbeType, hwIpAddress, 
    hwPort }
    STATUS current
    DESCRIPTION 
    "Probe is used to check load balance member health, when there are expected response from load balance 
    member, probe state will change to up."
    ::= { hwSlbNotifications 8 }


    hwProbeInstanceStateDown NOTIFICATION-TYPE
    OBJECTS { hwGroupName, hwMemberName, hwProbeName, hwProbeType, hwIpAddress, 
    hwPort }
    STATUS current
    DESCRIPTION 
    "Probe is used to check load balance member health, when there are no expected response from load balance 
    member, probe state will change to down."
    ::= { hwSlbNotifications 9 }


    --    ============================================================================   
    hwSlbConformance OBJECT IDENTIFIER ::= { hwSlbMibObjects 3 }


    hwSlbGroups OBJECT IDENTIFIER ::= { hwSlbConformance 1 }


    hwSlbTrapObjectsGroup OBJECT-GROUP
    OBJECTS { hwIpAddress, hwMemberName, hwGroupName, hwPort, hwProbeName, 
    hwProbeType, hwConnectionNum,hwActionName, hwMasterGroup, hwMasterGroupActiveNum,hwMasterGroupTotalNum,hwBackupGroup,hwBackupGroupActiveNum,
    hwBackupGroupTotalNum, hwCurWorkGroupName }
    STATUS current
    DESCRIPTION 
    "The group of objects that comprise SlbTrapObjects."
    ::= { hwSlbGroups 1 }


    hwSlbNotificationsGroup NOTIFICATION-GROUP
    NOTIFICATIONS { hwMemberInstanceStateUp, hwMemberInstanceStateDown, hwGroupStateSwitchover, hwMemberInstanceConnectionFull, 
    hwMemberInstanceConnectionFullRestore, hwProbeInstanceStateUp, hwProbeInstanceStateDown, hwMemberConnectionFull, hwMemberConnectionFullRestore
    }
    STATUS current
    DESCRIPTION 
    "The group of objects that comprise SlbNotifications."
    ::= { hwSlbGroups 2 }


    hwSlbCompliances OBJECT IDENTIFIER ::= { hwSlbConformance 2 }


    --    ----------------------------------------------------------------------------
    -- compliance statements
    -- ----------------------------------------------------------------------------            
    -- this module 
    hwSlbCompliance MODULE-COMPLIANCE
    STATUS current
    DESCRIPTION 
    "The compliance statement for entities implementing
    Huawei server load balance MIB."
    MODULE -- this module
    MANDATORY-GROUPS { hwSlbTrapObjectsGroup, hwSlbNotificationsGroup }
    ::= { hwSlbCompliances 1 }



    END

--
-- HUAWEI-SLB-MIB.MIB
--
