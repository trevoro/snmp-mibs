-- GWPOA MIB
-- Novell GroupWise Post Office Agent (POA) Management Information Base (MIB)
-- Copyright (C) 1994, 1995, 1996, 1997, 2000 Novell Inc.,  All Rights Reserved
-- Naming Tree: 1.3.6.1.4.1.23
--      iso(1) org(3) dod(6) internet(1) private(4) enterprises(1) novell(23)
-- Date: January 15, 1997
-- added platform and version variables


GWPOA-MIB DEFINITIONS ::= BEGIN

IMPORTS
        Counter, TimeTicks, Gauge, enterprises  FROM RFC1155-SMI
        DisplayString                           FROM RFC1213-MIB
        TRAP-TYPE                               FROM RFC-1215
        OBJECT-TYPE                             FROM RFC-1212;

novell         OBJECT IDENTIFIER   ::= { enterprises 23 }
mibDoc         OBJECT IDENTIFIER   ::= { novell       2 }
gwpoa          OBJECT IDENTIFIER   ::= { mibDoc      38 }
poa            OBJECT IDENTIFIER   ::= { gwpoa        1 }
poaTrapInfo    OBJECT IDENTIFIER   ::= { gwpoa        2 }
poaTraps       OBJECT IDENTIFIER   ::= { gwpoa        3 }

-- ====================================== POA Get/Set Variables =========
poaTable OBJECT-TYPE
	SYNTAX SEQUENCE OF POAEntry
	ACCESS not-accessible
	STATUS mandatory
	DESCRIPTION "A table of POA objects"
	::= { poa 1 }

poaEntry OBJECT-TYPE
	SYNTAX POAEntry
	ACCESS not-accessible
	STATUS mandatory
	DESCRIPTION "An entry in the POA Table"
	INDEX  { poaIndex }
	::= { poaTable 1 }

POAEntry ::=
	SEQUENCE {
			poaIndex INTEGER,
			poaPostOfficeName DisplayString,
			poaTotalMsgs Counter,
			poaProblemMsgs Counter,
			poaStatuses Counter,
			poaDeliveredUsers Counter,
			poaExecutedRules Counter,
			poaUndeliverableMsgs Counter,
			poaPriorityQueues Gauge,
			poaNormalQueues Gauge,
			poaUptime TimeTicks,
			poaCurrentLogFile DisplayString,
			poaLogLevel INTEGER,
			poaFileLogging INTEGER,
			poaMaxLogFileAge INTEGER,
			poaMaxLogDiskSpace INTEGER,
			poaCSRequests Counter,
			poaCSRequestsPending Counter,
			poaCSUserTimeouts Counter,
			poaCSFileQueues Counter,
			poaCSUsersConnected Counter,
			poaGUID DisplayString,
			poaOS DisplayString,
			poaVersion DisplayString,
			poaAdmThreadStatus DisplayString,
			poaAdmCompletedMsgs Counter,
			poaAdmErrorMsgs Counter,
			poaAdmInQueueMsgs Gauge,
			poaAdmDBStatus DisplayString,
			poaAdmDBSortLang DisplayString,
			poaAdmDBRecoverCnt Counter,
			poaDN 					DisplayString,
			poaAvailDiskSpace		Counter,
			poaHTTPPort				INTEGER,
			poaAdmDBStatusNumber	INTEGER,
			poaMTPStatus			INTEGER,
			poaUptimeInSeconds	INTEGER
			}

poaIndex OBJECT-TYPE
       SYNTAX  INTEGER
       ACCESS  read-write
       STATUS  mandatory
       DESCRIPTION
       "Index into the POA table"
   ::= { poaEntry 1 }

poaPostOfficeName OBJECT-TYPE
       SYNTAX  DisplayString (SIZE (0..255))
       ACCESS  read-only
       STATUS  mandatory
       DESCRIPTION
       "The name of the Post Office this Agent is serving."
   ::= { poaEntry 2 }

poaTotalMsgs OBJECT-TYPE
       SYNTAX  Counter
       ACCESS  read-only
       STATUS  mandatory
       DESCRIPTION
      "The number of total messages processed."
   ::= { poaEntry 3 }

poaProblemMsgs OBJECT-TYPE
       SYNTAX  Counter
       ACCESS  read-only
       STATUS  mandatory
       DESCRIPTION
      "The number of problem messages."
   ::= { poaEntry 4 }

poaStatuses OBJECT-TYPE
       SYNTAX  Counter
       ACCESS  read-only
       STATUS  mandatory
       DESCRIPTION
      "The number of completed status messages."
   ::= { poaEntry 5 }

poaDeliveredUsers OBJECT-TYPE
       SYNTAX  Counter
       ACCESS  read-only
       STATUS  mandatory
       DESCRIPTION
      "The number of users receiving messages."
   ::= { poaEntry 6 }

poaExecutedRules OBJECT-TYPE
       SYNTAX  Counter
       ACCESS  read-only
       STATUS  mandatory
       DESCRIPTION
      "The number of rules executed."
   ::= { poaEntry 7 }

poaUndeliverableMsgs OBJECT-TYPE
       SYNTAX  Counter
       ACCESS  read-only
       STATUS  mandatory
       DESCRIPTION
      "The number of users not delivered to."
   ::= { poaEntry 8 }

poaPriorityQueues OBJECT-TYPE
       SYNTAX  Gauge
       ACCESS  read-only
       STATUS  mandatory
       DESCRIPTION
      "The number of priority messages waiting to be processed."
   ::= { poaEntry 9 }

poaNormalQueues OBJECT-TYPE
       SYNTAX  Gauge
       ACCESS  read-only
       STATUS  mandatory
       DESCRIPTION
      "The number of normal messages waiting to be processed."
   ::= { poaEntry 10 }

poaUptime OBJECT-TYPE
       SYNTAX  TimeTicks
       ACCESS  read-only
       STATUS  mandatory
       DESCRIPTION
      "Uptime of the Post Office Agent."
   ::= { poaEntry 11 }

poaCurrentLogFile OBJECT-TYPE
       SYNTAX  DisplayString (SIZE (0..255))
       ACCESS  read-only
       STATUS  mandatory
       DESCRIPTION
      "Current log file."
   ::= { poaEntry 12 }

poaLogLevel OBJECT-TYPE
       SYNTAX  INTEGER { normal(0), verbose(1) }
       ACCESS  read-write
       STATUS  mandatory
       DESCRIPTION
      "Post Office Agent Log Level: Normal, Verbose"
   ::= { poaEntry 13 }

poaFileLogging OBJECT-TYPE
       SYNTAX  INTEGER { no(0), yes(1) }
       ACCESS  read-write
       STATUS  mandatory
       DESCRIPTION
      "Post Office Agent disk logging: YES or NO"
   ::= { poaEntry 14 }

poaMaxLogFileAge OBJECT-TYPE
       SYNTAX  INTEGER
       ACCESS  read-write
       STATUS  mandatory
       DESCRIPTION
      "Maximum age for Post Office Agent log files."
   ::= { poaEntry 15 }

poaMaxLogDiskSpace OBJECT-TYPE
       SYNTAX  INTEGER
       ACCESS  read-write
       STATUS  mandatory
       DESCRIPTION
      "Maximum disk space for Post Office Agent log files."
   ::= { poaEntry 16 }

poaCSRequests OBJECT-TYPE
       SYNTAX  INTEGER
       ACCESS  read-only
       STATUS  mandatory
       DESCRIPTION
	   "The number of Client/Server requests"
   ::= { poaEntry 17 }

poaCSRequestsPending OBJECT-TYPE
       SYNTAX  INTEGER
       ACCESS  read-only
       STATUS  mandatory
       DESCRIPTION
	   "The number of Client/Server requests pending"
   ::= { poaEntry 18 }

poaCSUserTimeouts OBJECT-TYPE
       SYNTAX  INTEGER
       ACCESS  read-only
       STATUS  mandatory
       DESCRIPTION
	   "The number of users that timed out"
   ::= { poaEntry 19 }

poaCSFileQueues OBJECT-TYPE
       SYNTAX  INTEGER
       ACCESS  read-only
       STATUS  mandatory
       DESCRIPTION
	   "The number of messages in the queues"
   ::= { poaEntry 20 }

poaCSUsersConnected OBJECT-TYPE
       SYNTAX  INTEGER
       ACCESS  read-only
       STATUS  mandatory
       DESCRIPTION
	   "The number of connected User Session"
   ::= { poaEntry 21 }

poaGUID OBJECT-TYPE
       SYNTAX  DisplayString (SIZE (0..36))
       ACCESS  read-only
       STATUS  mandatory
       DESCRIPTION
      "Post Office Agent globally unique identifier."
   ::= { poaEntry 22 }

poaOS OBJECT-TYPE
       SYNTAX  DisplayString (SIZE (0..64))
       ACCESS  read-only
       STATUS  mandatory
       DESCRIPTION
       "Operating System name and version"
   ::= { poaEntry 23 }

poaVersion OBJECT-TYPE
       SYNTAX  DisplayString (SIZE (0..64))
       ACCESS  read-only
       STATUS  mandatory
       DESCRIPTION
       "Version and date this agent."
   ::= { poaEntry 24 }

poaAdmThreadStatus OBJECT-TYPE
       SYNTAX  DisplayString (SIZE (0..64))
       ACCESS  read-only
       STATUS  mandatory
       DESCRIPTION
       "Admin thread status: Running, Suspended, Unknown."
   ::= { poaEntry 25 }

poaAdmCompletedMsgs OBJECT-TYPE
       SYNTAX  Counter
       ACCESS  read-only
       STATUS  mandatory
       DESCRIPTION
      "Number of Admin messages processed since startup by this POA."
   ::= { poaEntry 26 }

poaAdmErrorMsgs OBJECT-TYPE
       SYNTAX  Counter
       ACCESS  read-only
       STATUS  mandatory
       DESCRIPTION
      "Number of Admin message errors since startup by this POA."
   ::= { poaEntry 27 }

poaAdmInQueueMsgs OBJECT-TYPE
       SYNTAX  Gauge
       ACCESS  read-only
       STATUS  mandatory
       DESCRIPTION
      "Number of Admin messages waiting to be processed."
   ::= { poaEntry 28 }

poaAdmDBStatus OBJECT-TYPE
       SYNTAX  DisplayString (SIZE (0..64))
       ACCESS  read-only
       STATUS  mandatory
       DESCRIPTION
       "Post Office database status: Normal, DB Error, Unknown."
   ::= { poaEntry 29 }

poaAdmDBSortLang OBJECT-TYPE
       SYNTAX  DisplayString (SIZE (0..64))
       ACCESS  read-only
       STATUS  mandatory
       DESCRIPTION
       "Post Office database sort language."
   ::= { poaEntry 30 }

poaAdmDBRecoverCnt OBJECT-TYPE
       SYNTAX  Counter
       ACCESS  read-only
       STATUS  mandatory
       DESCRIPTION
      "Number of DB recoveries performed since startup by this POA."
   ::= { poaEntry 31 }

poaDN OBJECT-TYPE
       SYNTAX  DisplayString (SIZE (0..255))
       ACCESS  read-only
       STATUS  mandatory
       DESCRIPTION
       "Distinguished Name of POA agent."
   ::= { poaEntry 32 }

poaAvailDiskSpace OBJECT-TYPE
       SYNTAX  Counter
       ACCESS  read-only
       STATUS  mandatory
       DESCRIPTION
      "Number of MB of disk space available."
      ::= { poaEntry 33 }

poaHTTPPort OBJECT-TYPE
       SYNTAX  INTEGER 
       ACCESS  read-write
       STATUS  mandatory
       DESCRIPTION
      "HTTP used: 0 or port number"
   ::= { poaEntry 34 }

poaAdmDBStatusNumber OBJECT-TYPE
       SYNTAX  INTEGER { normal(0), error(1), recovering(2), unknown(3) }
       ACCESS  read-write
       STATUS  mandatory
       DESCRIPTION
      "Numeric Post Office database status"
   ::= { poaEntry 35}
   
poaMTPStatus OBJECT-TYPE
       SYNTAX  INTEGER { unknown(0), closed(1), open(2), sendopen(3), receiveopen(4)  }
       ACCESS  read-write
       STATUS  mandatory
       DESCRIPTION
      "Status of the message transfer protocol"
   ::= { poaEntry 36}

poaUptimeInSeconds OBJECT-TYPE
       SYNTAX  INTEGER 
       ACCESS  read-only
       STATUS  mandatory
       DESCRIPTION
      "Uptime of the Post Office Agent in seconds"
   ::= { poaEntry 37}
 
-- poaADAQCount OBJECT-TYPE
--       SYNTAX  Counter
--       ACCESS  read-only
--       STATUS  mandatory
--       DESCRIPTION
--      "Number of messages in admin queues."
--   ::= { mtaEntry 35 }

-- poaADAQSize OBJECT-TYPE
--       SYNTAX  Counter
--       ACCESS  read-only
--       STATUS  mandatory
--       DESCRIPTION
--      "Size of all messages in admin queues."
--   ::= { mtaEntry 36 }

-- poaOldestQMsg OBJECT-TYPE
--       SYNTAX  TimeTicks
--       ACCESS  read-only
--       STATUS  mandatory
--       DESCRIPTION
--      "Date stamp of oldest message in any of the queues."
--   ::= { mtaEntry 37 }

-- poaOldestQDestname OBJECT-TYPE
--       SYNTAX  DisplayString (SIZE (0..13))
--       ACCESS  read-only
--       STATUS  mandatory
--       DESCRIPTION
--       "Facility/domain name of oldest message."
--   ::= { mtaEntry 38 }

-- poaOldestADAQMsg OBJECT-TYPE
--       SYNTAX  TimeTicks
--       ACCESS  read-only
--       STATUS  mandatory
--       DESCRIPTION
--      "Date stamp of oldest message in ADA queues."
--   ::= { mtaEntry 39}


-- ================================================== poaTrapInfo =========
-- The poaTrapInfo group
-- These objects are used only in traps produced by POA

poaTrapTime OBJECT-TYPE
		SYNTAX  INTEGER
		ACCESS  not-accessible
		STATUS  mandatory
		DESCRIPTION "The time the trap occurred. Seconds since Jan 1, 1970 (GMT)"
	::= { poaTrapInfo 1 }

-- ================================================== POA Traps =========

poaStartTrap TRAP-TYPE
		ENTERPRISE    poaTraps
		VARIABLES     {poaTrapTime, poaPostOfficeName, poaGUID}
		DESCRIPTION   "GroupWise Post Office Agent (POA) has started."
		--NMS Trap annotation
		--#TYPE       "POA has started."
		--#SUMMARY    "GroupWise Post Office Agent (POA) at Post Office %s has started."
		--#ARGUMENTS  {1}
		--#SEVERITY   INFORMATIONAL
		--#TIMEINDEX  0
		--#HELP       "GWALARM.HLP"
		--#HELPTAG    101
		--#STATE      OPERATIONAL
		::= 1

poaShutdownTrap TRAP-TYPE
		ENTERPRISE    poaTraps
		VARIABLES     {poaTrapTime, poaPostOfficeName, poaGUID}
		DESCRIPTION   "GroupWise Post Office Agent (POA) has shut down."
		--NMS Trap annotation
		--#TYPE       "POA has shut down."
		--#SUMMARY    "GroupWise Post Office Agent (POA) at Post Office %s has shut down."
		--#ARGUMENTS  {1}
		--#SEVERITY   CRITICAL
		--#TIMEINDEX  0
		--#HELP       "GWALARM.HLP"
		--#HELPTAG    102
		--#STATE      NONOPERATIONAL
		::= 2

END
