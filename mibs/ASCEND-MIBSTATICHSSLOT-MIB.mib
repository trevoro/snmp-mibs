--			Ascend mibstatichsslot MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBSTATICHSSLOT-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibmibProfHighSpeedSlotStatic  OBJECT IDENTIFIER ::= { configuration 32}

	-- The mibmibProfHighSpeedSlotStatic table
	--
	-- This table contains parameters for the mibmibProfHighSpeedSlotStatic profile
	--

    mibmibProfHighSpeedSlotStaticTable	OBJECT-TYPE
	SYNTAX		SEQUENCE OF MibmibProfHighSpeedSlotStaticEntry
	ACCESS		not-accessible
	STATUS		mandatory
	DESCRIPTION	"A list of mibmibProfHighSpeedSlotStatic profile entries."
	::= { mibmibProfHighSpeedSlotStatic 1 }

    mibmibProfHighSpeedSlotStaticEntry	OBJECT-TYPE
	SYNTAX		MibmibProfHighSpeedSlotStaticEntry
	ACCESS		not-accessible
	STATUS		mandatory
	DESCRIPTION	"A mibmibProfHighSpeedSlotStatic entry containing objects that
			 maps to the parameters of mibmibProfHighSpeedSlotStatic profile."
	INDEX		{ mibProfHighSpeedSlotStatic-Shelf-o, mibProfHighSpeedSlotStatic-Slot-o, mibProfHighSpeedSlotStatic-Item-o }
	::= { mibmibProfHighSpeedSlotStaticTable 1 }

    MibmibProfHighSpeedSlotStaticEntry ::=
	SEQUENCE {
	    mibProfHighSpeedSlotStatic-Shelf-o
		INTEGER,
	    mibProfHighSpeedSlotStatic-Slot-o
		INTEGER,
	    mibProfHighSpeedSlotStatic-Item-o
		INTEGER,
	    mibProfHighSpeedSlotStatic-Name
		DisplayString,
	    mibProfHighSpeedSlotStatic-PhysicalAddress-Shelf
		INTEGER,
	    mibProfHighSpeedSlotStatic-PhysicalAddress-Slot
		INTEGER,
	    mibProfHighSpeedSlotStatic-PhysicalAddress-ItemNumber
		INTEGER,
	    mibProfHighSpeedSlotStatic-AtmParameters-IncomingPriority
		INTEGER,
	    mibProfHighSpeedSlotStatic-TrunkCacConfig-Enable
		INTEGER,
	    mibProfHighSpeedSlotStatic-TrunkCacConfig-PortNum
		DisplayString,
	    mibProfHighSpeedSlotStatic-TrunkCacConfig-LineRate
		INTEGER,
	    mibProfHighSpeedSlotStatic-TrunkCacConfig-OverSubscription
		INTEGER,
	    mibProfHighSpeedSlotStatic-Action-o
		INTEGER
	}

    mibProfHighSpeedSlotStatic-Shelf-o	OBJECT-TYPE
	SYNTAX	INTEGER
	ACCESS	read-only
	STATUS	mandatory
	DESCRIPTION	""
	::= { mibmibProfHighSpeedSlotStaticEntry 1 }

    mibProfHighSpeedSlotStatic-Slot-o	OBJECT-TYPE
	SYNTAX	INTEGER
	ACCESS	read-only
	STATUS	mandatory
	DESCRIPTION	""
	::= { mibmibProfHighSpeedSlotStaticEntry 2 }

    mibProfHighSpeedSlotStatic-Item-o	OBJECT-TYPE
	SYNTAX	INTEGER
	ACCESS	read-only
	STATUS	mandatory
	DESCRIPTION	""
	::= { mibmibProfHighSpeedSlotStaticEntry 3 }

    mibProfHighSpeedSlotStatic-Name	OBJECT-TYPE
	SYNTAX	DisplayString
	ACCESS	read-write
	STATUS	mandatory
	DESCRIPTION	"For future use. The current design does not use this name attribute but instead references a LIM or CM slot by its profile index; we may in the future support referencing a LIM or CM slot by its name as well as by its physical address. This name attribute consists of a null-terminated ASCII string; is read-only; and defaults to the ASCII form of this LIM or CM slot physical address."
	::= { mibmibProfHighSpeedSlotStaticEntry 4 }

    mibProfHighSpeedSlotStatic-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibmibProfHighSpeedSlotStaticEntry 5 }

    mibProfHighSpeedSlotStatic-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibmibProfHighSpeedSlotStaticEntry 6 }

    mibProfHighSpeedSlotStatic-PhysicalAddress-ItemNumber	OBJECT-TYPE
	SYNTAX	INTEGER
	ACCESS	read-write
	STATUS	mandatory
	DESCRIPTION	"A number that specifies an addressable entity within the context of shelf and slot."
	::= { mibmibProfHighSpeedSlotStaticEntry 7 }

    mibProfHighSpeedSlotStatic-AtmParameters-IncomingPriority	OBJECT-TYPE
	SYNTAX	INTEGER {
		    lowPriority (1),
		    highPriority (2)
		}
	ACCESS	read-write
	STATUS	mandatory
	DESCRIPTION	"Specifies the relative priority of ATM cells incoming from this LIM or CM slot. A slot's incoming-priority is used to select the appropriate outgoing queue that is associated with the outgoing port from the internal ATM cell processing engine. All ports on this slot and all ATM service categories share the same incoming-priority. An outgoing port (from the internal ATM cell processing engine) can have multiple queues associated with a given QoS. The incoming-priority is used to select which queue to use among all the queues associated with the given QoS."
	::= { mibmibProfHighSpeedSlotStaticEntry 8 }

    mibProfHighSpeedSlotStatic-TrunkCacConfig-Enable	OBJECT-TYPE
	SYNTAX	INTEGER {
		    no (1),
		    yes (2)
		}
	ACCESS	read-write
	STATUS	mandatory
	DESCRIPTION	"Enable or Disable CAC on this port. yes: CAC is enable on this port. no: CAC is disable on this port"
	::= { mibmibProfHighSpeedSlotStaticEntry 10 }

    mibProfHighSpeedSlotStatic-TrunkCacConfig-PortNum	OBJECT-TYPE
	SYNTAX	DisplayString
	ACCESS	read-only
	STATUS	mandatory
	DESCRIPTION	"Identifies this trunk port within the system. It is a read only field."
	::= { mibmibProfHighSpeedSlotStaticEntry 11 }

    mibProfHighSpeedSlotStatic-TrunkCacConfig-LineRate	OBJECT-TYPE
	SYNTAX	INTEGER
	ACCESS	read-only
	STATUS	mandatory
	DESCRIPTION	"Line rate of the trunk port in Kbits/sec. The trunk port can have real-time (guaranteed) traffic bandwidth up to this limit. In case of over subscription, there is no guarantee."
	::= { mibmibProfHighSpeedSlotStaticEntry 12 }

    mibProfHighSpeedSlotStatic-TrunkCacConfig-OverSubscription	OBJECT-TYPE
	SYNTAX	INTEGER
	ACCESS	read-write
	STATUS	mandatory
	DESCRIPTION	"Allowed to specify over subscription to the line rate to a factor of over-subscription/10. e.g Allowed BW = (over-subscription * line-rate) /10"
	::= { mibmibProfHighSpeedSlotStaticEntry 13 }

    mibProfHighSpeedSlotStatic-Action-o	OBJECT-TYPE
	SYNTAX	INTEGER {
		    noAction (1),
		    createProfile (2),
		    deleteProfile (3)
		}
	ACCESS	read-write
	STATUS	mandatory
	DESCRIPTION	""
	::= { mibmibProfHighSpeedSlotStaticEntry 9 }

END
