-- *****************************************************************
-- CISCO-ENVMON-CAPABILITY.my:
-- CISCO-ENVMON-MIB AGENT-CAPABILITIES
--
-- January 1995, Sandra Durham
--
-- Copyright (c) 1995, 1997, 2003, 2004, 2006 by Cisco Systems, Inc.
-- All rights reserved.
-- *****************************************************************

CISCO-ENVMON-CAPABILITY DEFINITIONS ::= BEGIN

IMPORTS
        MODULE-IDENTITY
                FROM SNMPv2-SMI
        AGENT-CAPABILITIES
                FROM SNMPv2-CONF
        ciscoAgentCapability
                FROM CISCO-SMI;

ciscoEnvMonCapability MODULE-IDENTITY
        LAST-UPDATED    "200604190000Z"
        ORGANIZATION    "Cisco Systems, Inc."
        CONTACT-INFO
                "       Cisco Systems
                        Customer Service

                Postal: 170 West Tasman Drive
                        San Jose, CA  95134
                        USA

                   Tel: +1 800 553-NETS

                E-mail: cs-snmp@cisco.com"
        DESCRIPTION
                "Agent capabilities for CISCO-ENVMON-MIB."

        REVISION        "200604190000Z"
        DESCRIPTION
                "Added VARIATION for ciscoEnvMonTemperatureLastShutdown to
                agent capability statement ciscoEnvMonCapV12R0119ECat6K."

        REVISION        "200412160100Z"
        DESCRIPTION
                "Added agent capabilities for 38xx, 37xx, 
                 26xx, 28xx, VG224 and IAD243x platforms."

        REVISION        "200403260000Z"
        DESCRIPTION
                "Added agent capability statements 
                 ciscoEnvMonCapCatOSV08R0101Cat6k,
                 ciscoEnvMonCapCatOSV08R0101Cat4k,
                 ciscoEnvMonCapV12R0119ECat6K."

        REVISION        "9611120000Z"
        DESCRIPTION
                "Added agent capabilities for platform c3600."

        REVISION        "9501230000Z"
        DESCRIPTION
                "Initial version of this MIB module."
    ::= { ciscoAgentCapability 33 }


ciscoEnvMonCapabilityV10R03 AGENT-CAPABILITIES
    PRODUCT-RELEASE      "Cisco IOS 10.3"
    STATUS               obsolete 
                            -- superseded by ciscoEnvMonCapabilityV11R02
    DESCRIPTION          "Cisco Environmental Monitor MIB capabilities"

    SUPPORTS             CISCO-ENVMON-MIB
        INCLUDES         { ciscoEnvMonMIBGroup }
 
    ::= { ciscoEnvMonCapability 1 }

ciscoEnvMonCapabilityV11R02 AGENT-CAPABILITIES
    PRODUCT-RELEASE      "Cisco IOS 11.2 on mid-range platforms C3600."
    STATUS               current
    DESCRIPTION          "Cisco Environmental Monitor MIB capabilities."
 
    SUPPORTS             CISCO-ENVMON-MIB         
        INCLUDES         { ciscoEnvMonMIBGroup }
  
        VARIATION        ciscoEnvMonTemperatureStatusValue
            DESCRIPTION  "Object not supported on the platform."

        VARIATION        ciscoEnvMonTemperatureThreshold
            DESCRIPTION  "Object not supported on the platform."

        VARIATION        ciscoEnvMonTemperatureLastShutdown
            DESCRIPTION  "Object not supported on the platform."

        VARIATION        ciscoEnvMonTemperatureState
            SYNTAX       INTEGER { normal(1),  warning(2)  }
            DESCRIPTION "Only limited set of enumerated values
                         are supported."

        VARIATION        ciscoEnvMonSupplyState
            SYNTAX       INTEGER { normal(1), warning(2), critical(3) }
            DESCRIPTION "Only limited set of enumerated values
                         are supported."

    ::= { ciscoEnvMonCapability 2 }

ciscoEnvMonCapCatOSV08R0101Cat6k AGENT-CAPABILITIES
    PRODUCT-RELEASE      "Cisco CatOS 8.1(1) on Catalyst 6000/6500
                          and Cisco 7600 series devices."
    STATUS               current
    DESCRIPTION          "CISCO-ENVMON-MIB capabilities."

    SUPPORTS             CISCO-ENVMON-MIB
        INCLUDES         { ciscoEnvMonMIBGroupRev, 
                           ciscoEnvMonMIBNotifGroup,
                           ciscoEnvMonMIBMiscNotifGroup,
                           ciscoEnvMonEnableStatChangeGroup,
                           ciscoEnvMonStatChangeNotifGroup }

        VARIATION        ciscoEnvMonVoltageStatusDescr
            ACCESS       not-implemented
            DESCRIPTION  "Object not supported on the platform."

        VARIATION        ciscoEnvMonVoltageStatusValue
            ACCESS       not-implemented
            DESCRIPTION  "Object not supported on the platform."

        VARIATION        ciscoEnvMonVoltageThresholdLow
            ACCESS       not-implemented
            DESCRIPTION  "Object not supported on the platform."

        VARIATION        ciscoEnvMonVoltageThresholdHigh
            ACCESS       not-implemented
            DESCRIPTION  "Object not supported on the platform."

        VARIATION        ciscoEnvMonVoltageLastShutdown
            ACCESS       not-implemented
            DESCRIPTION  "Object not supported on the platform."

        VARIATION        ciscoEnvMonVoltageState
            ACCESS       not-implemented
            DESCRIPTION  "Object not supported on the platform."

        VARIATION        ciscoEnvMonEnableVoltageNotification
            ACCESS       not-implemented
            DESCRIPTION  "Object not supported on the platform."

        VARIATION        ciscoEnvMonVoltageNotification
            ACCESS       not-implemented
            DESCRIPTION  "Object not supported on the platform."

        VARIATION        ciscoEnvMonVoltStatusChangeNotif
            ACCESS       not-implemented
            DESCRIPTION  "Object not supported on the platform."

    ::= { ciscoEnvMonCapability 3 }

ciscoEnvMonCapCatOSV08R0101Cat4k AGENT-CAPABILITIES
    PRODUCT-RELEASE      "Cisco CatOS 8.1(1) on Catalyst 4000/4500 
                          series devices."
    STATUS               current
    DESCRIPTION          "CISCO-ENVMON-MIB capabilities." 

    SUPPORTS             CISCO-ENVMON-MIB
        INCLUDES         { ciscoEnvMonMIBGroupRev,
                           ciscoEnvMonMIBNotifGroup,
                           ciscoEnvMonMIBMiscNotifGroup,
                           ciscoEnvMonEnableStatChangeGroup,
                           ciscoEnvMonStatChangeNotifGroup }

        VARIATION        ciscoEnvMonVoltageStatusDescr
            ACCESS       not-implemented
            DESCRIPTION  "Object not supported on the platform."

        VARIATION        ciscoEnvMonVoltageStatusValue
            ACCESS       not-implemented
            DESCRIPTION  "Object not supported on the platform."

        VARIATION        ciscoEnvMonVoltageThresholdLow
            ACCESS       not-implemented
            DESCRIPTION  "Object not supported on the platform."

        VARIATION        ciscoEnvMonVoltageThresholdHigh
            ACCESS       not-implemented
            DESCRIPTION  "Object not supported on the platform."

        VARIATION        ciscoEnvMonVoltageLastShutdown
            ACCESS       not-implemented
            DESCRIPTION  "Object not supported on the platform."

        VARIATION        ciscoEnvMonVoltageState
            ACCESS       not-implemented
            DESCRIPTION  "Object not supported on the platform."

        VARIATION        ciscoEnvMonTemperatureStatusDescr
            ACCESS       not-implemented
            DESCRIPTION  "Object not supported on the platform."

        VARIATION        ciscoEnvMonTemperatureStatusDescr
            ACCESS       not-implemented
            DESCRIPTION  "Object not supported on the platform."

        VARIATION        ciscoEnvMonTemperatureStatusValue
            ACCESS       not-implemented
            DESCRIPTION  "Object not supported on the platform."

        VARIATION        ciscoEnvMonTemperatureThreshold
            ACCESS       not-implemented
            DESCRIPTION  "Object not supported on the platform."

        VARIATION        ciscoEnvMonTemperatureLastShutdown
            ACCESS       not-implemented
            DESCRIPTION  "Object not supported on the platform."

        VARIATION        ciscoEnvMonTemperatureState
            ACCESS       not-implemented
            DESCRIPTION  "Object not supported on the platform."

        VARIATION        ciscoEnvMonEnableShutdownNotification
            ACCESS       not-implemented
            DESCRIPTION  "Object not supported on the platform."

        VARIATION        ciscoEnvMonEnableVoltageNotification
            ACCESS       not-implemented
            DESCRIPTION  "Object not supported on the platform."

        VARIATION        ciscoEnvMonEnableTemperatureNotification
            ACCESS       not-implemented
            DESCRIPTION  "Object not supported on the platform."

        VARIATION        ciscoEnvMonShutdownNotification
            ACCESS       not-implemented
            DESCRIPTION  "Object not supported on the platform."

        VARIATION        ciscoEnvMonVoltageNotification
           ACCESS       not-implemented
           DESCRIPTION  "Object not supported on the platform."

        VARIATION        ciscoEnvMonTemperatureNotification
            ACCESS       not-implemented
            DESCRIPTION  "Object not supported on the platform."

        VARIATION        ciscoEnvMonVoltStatusChangeNotif
            ACCESS       not-implemented
            DESCRIPTION  "Object not supported on the platform."

        VARIATION        ciscoEnvMonTempStatusChangeNotif
            ACCESS       not-implemented
            DESCRIPTION  "Object not supported on the platform."

    ::= { ciscoEnvMonCapability 4 }

ciscoEnvMonCapV12R0119ECat6K AGENT-CAPABILITIES
    PRODUCT-RELEASE   "Cisco IOS 12.1(19E) on Catalyst 6000/6500
                       and Cisco 7600 series devices."
    STATUS            current
    DESCRIPTION       "CISCO-ENVMON-MIB capabilities."

    SUPPORTS          CISCO-ENVMON-MIB
        INCLUDES      { ciscoEnvMonMIBGroupRev,
                        ciscoEnvMonMIBNotifGroup,
                        ciscoEnvMonMIBMiscNotifGroup,
                        ciscoEnvMonEnableStatChangeGroup,
                        ciscoEnvMonStatChangeNotifGroup }

        VARIATION        ciscoEnvMonVoltageStatusDescr
            ACCESS       not-implemented
            DESCRIPTION  "Object not supported on the platform."

        VARIATION        ciscoEnvMonVoltageStatusValue
            ACCESS       not-implemented
            DESCRIPTION  "Object not supported on the platform."

        VARIATION        ciscoEnvMonVoltageThresholdLow
            ACCESS       not-implemented
            DESCRIPTION  "Object not supported on the platform."

        VARIATION        ciscoEnvMonVoltageThresholdHigh
            ACCESS       not-implemented
            DESCRIPTION  "Object not supported on the platform."

        VARIATION        ciscoEnvMonVoltageLastShutdown
            ACCESS       not-implemented
            DESCRIPTION  "Object not supported on the platform."

        VARIATION        ciscoEnvMonVoltageState
            ACCESS       not-implemented
            DESCRIPTION  "Object not supported on the platform."

        VARIATION        ciscoEnvMonEnableVoltageNotification
            ACCESS       not-implemented
            DESCRIPTION  "Object not supported on the platform."

        VARIATION        ciscoEnvMonVoltageNotification
            ACCESS       not-implemented
            DESCRIPTION  "Object not supported on the platform."

        VARIATION        ciscoEnvMonVoltStatusChangeNotif
            ACCESS       not-implemented
            DESCRIPTION  "Object not supported on the platform."

        VARIATION        ciscoEnvMonTemperatureLastShutdown
            ACCESS       not-implemented
            DESCRIPTION  "Object not supported on the platform."

    ::= { ciscoEnvMonCapability 5 }

ciscoEnvMonCapV12R04TP37xx AGENT-CAPABILITIES
    PRODUCT-RELEASE   "Cisco IOS 12.4T on c37xx devices."
    STATUS            current
    DESCRIPTION       "Cisco Environmental Monitor MIB capabilities."

    SUPPORTS          CISCO-ENVMON-MIB
        INCLUDES      { ciscoEnvMonMIBGroupRev,
                        ciscoEnvMonMIBNotifGroup,
                        ciscoEnvMonMIBMiscNotifGroup }

        VARIATION        ciscoEnvMonTemperatureStatusValue
            ACCESS       not-implemented
            DESCRIPTION  "Object not supported on the platform."

        VARIATION        ciscoEnvMonTemperatureThreshold
            ACCESS       not-implemented
            DESCRIPTION  "Object not supported on the platform."

        VARIATION        ciscoEnvMonTemperatureLastShutdown
            ACCESS       not-implemented
            DESCRIPTION  "Object not supported on the platform."

        VARIATION        ciscoEnvMonVoltageStatusDescr
            ACCESS       not-implemented
            DESCRIPTION  "Object not supported on the platform."
                
        VARIATION        ciscoEnvMonVoltageStatusValue
            ACCESS       not-implemented
            DESCRIPTION  "Object not supported on the platform."
                
        VARIATION        ciscoEnvMonVoltageThresholdLow
            ACCESS       not-implemented
            DESCRIPTION  "Object not supported on the platform."

        VARIATION        ciscoEnvMonVoltageThresholdHigh
            ACCESS       not-implemented
            DESCRIPTION  "Object not supported on the platform."

        VARIATION        ciscoEnvMonVoltageLastShutdown
            ACCESS       not-implemented
            DESCRIPTION  "Object not supported on the platform."

        VARIATION        ciscoEnvMonVoltageState
            ACCESS       not-implemented
            DESCRIPTION  "Object not supported on the platform."

        VARIATION        ciscoEnvMonAlarmContacts
            ACCESS       not-implemented
            DESCRIPTION  "Object not supported on the platform."

        VARIATION        ciscoEnvMonShutdownNotification
            ACCESS       not-implemented
            DESCRIPTION  "Object not supported on the platform."

        VARIATION        ciscoEnvMonVoltageNotification
            ACCESS       not-implemented
            DESCRIPTION  "Object not supported on the platform."

    ::= { ciscoEnvMonCapability 6 }

ciscoEnvMonCapV12R04TP28xx AGENT-CAPABILITIES
    PRODUCT-RELEASE   "Cisco IOS 12.4T on c28xx devices."
    STATUS            current
    DESCRIPTION       "Cisco Environmental Monitor MIB capabilities."

    SUPPORTS          CISCO-ENVMON-MIB
        INCLUDES      { ciscoEnvMonMIBGroupRev,
                        ciscoEnvMonMIBNotifGroup,
                        ciscoEnvMonMIBMiscNotifGroup }

        VARIATION        ciscoEnvMonVoltageStatusDescr
            ACCESS       not-implemented
            DESCRIPTION  "Object not supported on the platform."
                
        VARIATION        ciscoEnvMonVoltageStatusValue
            ACCESS       not-implemented
            DESCRIPTION  "Object not supported on the platform."
                
        VARIATION        ciscoEnvMonVoltageThresholdLow
            ACCESS       not-implemented
            DESCRIPTION  "Object not supported on the platform."

        VARIATION        ciscoEnvMonVoltageThresholdHigh
            ACCESS       not-implemented
            DESCRIPTION  "Object not supported on the platform."

        VARIATION        ciscoEnvMonVoltageLastShutdown
            ACCESS       not-implemented
            DESCRIPTION  "Object not supported on the platform."

        VARIATION        ciscoEnvMonVoltageState
            ACCESS       not-implemented
            DESCRIPTION  "Object not supported on the platform."

        VARIATION        ciscoEnvMonAlarmContacts
            ACCESS       not-implemented
            DESCRIPTION  "Object not supported on the platform."
        
        VARIATION        ciscoEnvMonRedundantSupplyNotification
            ACCESS       not-implemented
            DESCRIPTION  "Object not supported on the platform."

        VARIATION        ciscoEnvMonVoltageNotification
            ACCESS       not-implemented
            DESCRIPTION  "Object not supported on the platform."

        VARIATION        ciscoEnvMonTemperatureLastShutdown
            ACCESS       not-implemented
            DESCRIPTION  "Object not supported on the platform."

    ::= { ciscoEnvMonCapability 7 }

ciscoEnvMonCapV12R04TP26xx AGENT-CAPABILITIES
    PRODUCT-RELEASE   "Cisco IOS 12.4T on c26xx devices."
    STATUS            current
    DESCRIPTION       "Cisco Environmental Monitor MIB capabilities."

    SUPPORTS          CISCO-ENVMON-MIB
        INCLUDES      { ciscoEnvMonMIBGroupRev,
                        ciscoEnvMonMIBNotifGroup,
                        ciscoEnvMonMIBMiscNotifGroup }

        VARIATION        ciscoEnvMonTemperatureStatusValue
            ACCESS       not-implemented
            DESCRIPTION  "Object not supported on the platform."

        VARIATION        ciscoEnvMonTemperatureThreshold
            ACCESS       not-implemented
            DESCRIPTION  "Object not supported on the platform."

        VARIATION        ciscoEnvMonTemperatureLastShutdown
            ACCESS       not-implemented
            DESCRIPTION  "Object not supported on the platform."

        VARIATION        ciscoEnvMonVoltageStatusDescr
            ACCESS       not-implemented
            DESCRIPTION  "Object not supported on the platform."
                
        VARIATION        ciscoEnvMonVoltageStatusValue
            ACCESS       not-implemented
            DESCRIPTION  "Object not supported on the platform."
                
        VARIATION        ciscoEnvMonVoltageThresholdLow
            ACCESS       not-implemented
            DESCRIPTION  "Object not supported on the platform."

        VARIATION        ciscoEnvMonVoltageThresholdHigh
            ACCESS       not-implemented
            DESCRIPTION  "Object not supported on the platform."

        VARIATION        ciscoEnvMonVoltageLastShutdown
            ACCESS       not-implemented
            DESCRIPTION  "Object not supported on the platform."

        VARIATION        ciscoEnvMonVoltageState
            ACCESS       not-implemented
            DESCRIPTION  "Object not supported on the platform."

        VARIATION        ciscoEnvMonAlarmContacts
            ACCESS       not-implemented
            DESCRIPTION  "Object not supported on the platform."

        VARIATION        ciscoEnvMonShutdownNotification
            ACCESS       not-implemented
            DESCRIPTION  "Object not supported on the platform."

        VARIATION        ciscoEnvMonVoltageNotification
            ACCESS       not-implemented
            DESCRIPTION  "Object not supported on the platform."
        
        VARIATION        ciscoEnvMonFanNotification
            ACCESS       not-implemented
            DESCRIPTION  "Object not supported on the platform."

    ::= { ciscoEnvMonCapability 8 }

ciscoEnvMonCapV12R04TPIAD243x AGENT-CAPABILITIES
    PRODUCT-RELEASE   "Cisco IOS 12.4T on IAD243x devices."
    STATUS            current
    DESCRIPTION       "Cisco Environmental Monitor MIB capabilities."

    SUPPORTS          CISCO-ENVMON-MIB
        INCLUDES      { ciscoEnvMonMIBGroupRev,
                        ciscoEnvMonMIBNotifGroup,
                        ciscoEnvMonMIBMiscNotifGroup }

        VARIATION        ciscoEnvMonTemperatureStatusValue
            ACCESS       not-implemented
            DESCRIPTION  "Object not supported on the platform."

        VARIATION        ciscoEnvMonTemperatureThreshold
            ACCESS       not-implemented
            DESCRIPTION  "Object not supported on the platform."

        VARIATION        ciscoEnvMonTemperatureLastShutdown
            ACCESS       not-implemented
            DESCRIPTION  "Object not supported on the platform."

        VARIATION        ciscoEnvMonVoltageStatusDescr
            ACCESS       not-implemented
            DESCRIPTION  "Object not supported on the platform."
                
        VARIATION        ciscoEnvMonVoltageStatusValue
            ACCESS       not-implemented
            DESCRIPTION  "Object not supported on the platform."
                
        VARIATION        ciscoEnvMonVoltageThresholdLow
            ACCESS       not-implemented
            DESCRIPTION  "Object not supported on the platform."

        VARIATION        ciscoEnvMonVoltageThresholdHigh
            ACCESS       not-implemented
            DESCRIPTION  "Object not supported on the platform."

        VARIATION        ciscoEnvMonVoltageLastShutdown
            ACCESS       not-implemented
            DESCRIPTION  "Object not supported on the platform."

        VARIATION        ciscoEnvMonVoltageState
            ACCESS       not-implemented
            DESCRIPTION  "Object not supported on the platform."

        VARIATION        ciscoEnvMonAlarmContacts
            ACCESS       not-implemented
            DESCRIPTION  "Object not supported on the platform."

        VARIATION        ciscoEnvMonShutdownNotification
            ACCESS       not-implemented
            DESCRIPTION  "Object not supported on the platform."

        VARIATION        ciscoEnvMonVoltageNotification
            ACCESS       not-implemented
            DESCRIPTION  "Object not supported on the platform."

    ::= { ciscoEnvMonCapability 9 }

ciscoEnvMonCapV12R04TPVG224 AGENT-CAPABILITIES
    PRODUCT-RELEASE   "Cisco IOS 12.4T on VG224 devices."
    STATUS            current
    DESCRIPTION       "Cisco Environmental Monitor MIB capabilities."

    SUPPORTS          CISCO-ENVMON-MIB
        INCLUDES      { ciscoEnvMonMIBGroupRev,
                        ciscoEnvMonMIBNotifGroup,
                        ciscoEnvMonMIBMiscNotifGroup }

        VARIATION        ciscoEnvMonTemperatureStatusValue
            ACCESS       not-implemented
            DESCRIPTION  "Object not supported on the platform."

        VARIATION        ciscoEnvMonTemperatureThreshold
            ACCESS       not-implemented
            DESCRIPTION  "Object not supported on the platform."

        VARIATION        ciscoEnvMonTemperatureLastShutdown
            ACCESS       not-implemented
            DESCRIPTION  "Object not supported on the platform."

        VARIATION        ciscoEnvMonVoltageStatusDescr
            ACCESS       not-implemented
            DESCRIPTION  "Object not supported on the platform."
                
        VARIATION        ciscoEnvMonVoltageStatusValue
            ACCESS       not-implemented
            DESCRIPTION  "Object not supported on the platform."
                
        VARIATION        ciscoEnvMonVoltageThresholdLow
            ACCESS       not-implemented
            DESCRIPTION  "Object not supported on the platform."

        VARIATION        ciscoEnvMonVoltageThresholdHigh
            ACCESS       not-implemented
            DESCRIPTION  "Object not supported on the platform."

        VARIATION        ciscoEnvMonVoltageLastShutdown
            ACCESS       not-implemented
            DESCRIPTION  "Object not supported on the platform."

        VARIATION        ciscoEnvMonVoltageState
            ACCESS       not-implemented
            DESCRIPTION  "Object not supported on the platform."

        VARIATION        ciscoEnvMonAlarmContacts
            ACCESS       not-implemented
            DESCRIPTION  "Object not supported on the platform."

        VARIATION        ciscoEnvMonShutdownNotification
            ACCESS       not-implemented
            DESCRIPTION  "Object not supported on the platform."

        VARIATION        ciscoEnvMonVoltageNotification
            ACCESS       not-implemented
            DESCRIPTION  "Object not supported on the platform."

    ::= { ciscoEnvMonCapability 10 }

 ciscoEnvMonCapV12R04TP3825 AGENT-CAPABILITIES
    PRODUCT-RELEASE   "Cisco IOS 12.4T on c3825 devices."
    STATUS            current
    DESCRIPTION       "Cisco Environmental Monitor MIB capabilities."

    SUPPORTS          CISCO-ENVMON-MIB
        INCLUDES      { ciscoEnvMonMIBGroupRev,
                        ciscoEnvMonMIBNotifGroup,
                        ciscoEnvMonMIBMiscNotifGroup }

        VARIATION        ciscoEnvMonShutdownNotification
            ACCESS       not-implemented
            DESCRIPTION  "Object not supported on the platform."

        VARIATION        ciscoEnvMonAlarmContacts
            ACCESS       not-implemented
            DESCRIPTION  "Object not supported on the platform."

        VARIATION        ciscoEnvMonTemperatureLastShutdown
            ACCESS       not-implemented
            DESCRIPTION  "Object not supported on the platform."
        
        VARIATION        ciscoEnvMonVoltageLastShutdown
            ACCESS       not-implemented
            DESCRIPTION  "Object not supported on the platform."

        VARIATION        ciscoEnvMonRedundantSupplyNotification   
            ACCESS       not-implemented
            DESCRIPTION  "Object not supported on the platform."

    ::= { ciscoEnvMonCapability 11 }

 ciscoEnvMonCapV12R04TP3845 AGENT-CAPABILITIES
    PRODUCT-RELEASE   "Cisco IOS 12.4T on c3845 devices."
    STATUS            current
    DESCRIPTION       "Cisco Environmental Monitor MIB capabilities."

    SUPPORTS          CISCO-ENVMON-MIB
        INCLUDES      { ciscoEnvMonMIBGroupRev,
                        ciscoEnvMonMIBNotifGroup,
                        ciscoEnvMonMIBMiscNotifGroup }

        VARIATION        ciscoEnvMonShutdownNotification
            ACCESS       not-implemented
            DESCRIPTION  "Object not supported on the platform."

        VARIATION        ciscoEnvMonAlarmContacts
            ACCESS       not-implemented
            DESCRIPTION  "Object not supported on the platform."

        VARIATION        ciscoEnvMonTemperatureLastShutdown
            ACCESS       not-implemented
            DESCRIPTION  "Object not supported on the platform."
        
        VARIATION        ciscoEnvMonVoltageLastShutdown
            ACCESS       not-implemented
            DESCRIPTION  "Object not supported on the platform."

    ::= { ciscoEnvMonCapability 12 }

ciscoEnvMonCapV12R04TP2691 AGENT-CAPABILITIES
    PRODUCT-RELEASE   "Cisco IOS 12.4T on c2691 devices."
    STATUS            current
    DESCRIPTION       "Cisco Environmental Monitor MIB capabilities."

    SUPPORTS          CISCO-ENVMON-MIB
        INCLUDES      { ciscoEnvMonMIBGroupRev,
                        ciscoEnvMonMIBNotifGroup,
                        ciscoEnvMonMIBMiscNotifGroup }

        VARIATION        ciscoEnvMonTemperatureStatusValue
            ACCESS       not-implemented
            DESCRIPTION  "Object not supported on the platform."

        VARIATION        ciscoEnvMonTemperatureThreshold
            ACCESS       not-implemented
            DESCRIPTION  "Object not supported on the platform."

        VARIATION        ciscoEnvMonTemperatureLastShutdown
            ACCESS       not-implemented
            DESCRIPTION  "Object not supported on the platform."

        VARIATION        ciscoEnvMonVoltageStatusDescr
            ACCESS       not-implemented
            DESCRIPTION  "Object not supported on the platform."
                
        VARIATION        ciscoEnvMonVoltageStatusValue
            ACCESS       not-implemented
            DESCRIPTION  "Object not supported on the platform."
                
        VARIATION        ciscoEnvMonVoltageThresholdLow
            ACCESS       not-implemented
            DESCRIPTION  "Object not supported on the platform."

        VARIATION        ciscoEnvMonVoltageThresholdHigh
            ACCESS       not-implemented
            DESCRIPTION  "Object not supported on the platform."

        VARIATION        ciscoEnvMonVoltageLastShutdown
            ACCESS       not-implemented
            DESCRIPTION  "Object not supported on the platform."

        VARIATION        ciscoEnvMonVoltageState
            ACCESS       not-implemented
            DESCRIPTION  "Object not supported on the platform."

        VARIATION        ciscoEnvMonAlarmContacts
            ACCESS       not-implemented
            DESCRIPTION  "Object not supported on the platform."

        VARIATION        ciscoEnvMonShutdownNotification
            ACCESS       not-implemented
            DESCRIPTION  "Object not supported on the platform."

        VARIATION        ciscoEnvMonVoltageNotification
            ACCESS       not-implemented
            DESCRIPTION  "Object not supported on the platform."

            ::= { ciscoEnvMonCapability 13 }

END
