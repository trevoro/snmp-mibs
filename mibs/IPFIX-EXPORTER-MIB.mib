-- extracted from draft-dietz-ipfix-mib-01.txt
-- at Thu Oct 26 06:07:26 2006

   IPFIX-EXPORTER-MIB DEFINITIONS ::= BEGIN

   IMPORTS
       MODULE-IDENTITY, OBJECT-TYPE, Integer32, Unsigned32, mib-2
           FROM SNMPv2-SMI                  -- RFC2578
       TEXTUAL-CONVENTION, DateAndTime, DisplayString, RowStatus,
       TruthValue
           FROM SNMPv2-TC                   -- RFC2579
       MODULE-COMPLIANCE, OBJECT-GROUP
           FROM SNMPv2-CONF                 -- RFC2580
       InterfaceIndexOrZero
           FROM IF-MIB                      -- RFC2863
       InetAddressType, InetAddress, InetAutonomousSystemNumber
           FROM INET-ADDRESS-MIB;           -- RFC3291

   ipfixMIB MODULE-IDENTITY
       LAST-UPDATED "200610231200Z"         -- 23 October 2006
       ORGANIZATION "IETF IP Flow Information Export"
       CONTACT-INFO
           "WG charter:
              http://www.ietf.org/html.charters/ipfix-charter.html

            Mailing Lists:
              General Discussion: ipfix@net.doit.wisc.edu
              To Subscribe: majordomo@net.doit.wisc.edu
              In Body: subscribe ipfix
              Archive: http://ipfix.doit.wisc.edu/archive/

            Editor:
              Thomas Dietz
              NEC Europe Ltd.
              Network Laboratories
              Kurfuersten-Anlage 36
              69115 Heidelberg
              Germany
              Phone: +49 6221 4342-128
              Email: dietz@netlab.nec.de"
       DESCRIPTION
           "The IPFIX MIB defines managed objects for IP flow
            information export.  These objects provide information about
            managed nodes supporting IP flow information export,
            including flow information export capabilities,
            configuration and statistics.  They also allow to configure
            IP flow information export concerning the IP interface at
            which flow information is gathered, the flow selections
            methods used, and the collector to which flow information is
            exported.

            Copyright (C) The Internet Society (2006).  This version
            of this MIB module is part of RFC yyyy;  see the RFC
            itself for full legal notices."
   -- Editor note: check if configuration is really desired
   -- RFC Ed.: replace yyyy with actual RFC number & remove this notice

        --  Revision history

        REVISION     "200610231200Z"         -- 23 October 2006
        DESCRIPTION
            "Initial version, published as RFC yyyy."
   -- RFC Ed.: replace yyyy with actual RFC number & remove this notice

       ::= { mib-2 999 }
   -- 999 to be assigned by IANA.

   -- Textual Conventions

   PsampMethodAvailability ::= TEXTUAL-CONVENTION
       STATUS  current
       DESCRIPTION
           "Used to report the availability of a selection method:

             available(1) - the method is supported and can be used
             notAvailable(2) - the method is not available"
       SYNTAX      INTEGER {
                       available(1),
                       notAvailable(2)
                   }

   -- Top level structure of the MIB

   ipfixExporter       OBJECT IDENTIFIER ::= { ipfixMIB 1 }
   ipfixCollector      OBJECT IDENTIFIER ::= { ipfixMIB 2 }
   ipfixPsampExtension OBJECT IDENTIFIER ::= { ipfixMIB 3 }
   ipfixConformance    OBJECT IDENTIFIER ::= { ipfixMIB 4 }

   ipfixExporterObjects OBJECT IDENTIFIER ::= { ipfixExporter 1 }
   --==================================================================
   -- Reporting Group
   --==================================================================

   ipfixReporting       OBJECT IDENTIFIER ::= { ipfixExporterObjects 1 }

   -- Collector Table +++++++++++++++++++++++++++++++++++++++++++++++++

   ipfixCollectorTable OBJECT-TYPE
       SYNTAX      SEQUENCE OF IpfixCollectorEntry
       MAX-ACCESS  not-accessible
       STATUS      current
       DESCRIPTION
           "This table lists collectors to which reports are exported."
       ::= { ipfixReporting 1 }

   ipfixCollectorEntry OBJECT-TYPE
       SYNTAX      IpfixCollectorEntry
       MAX-ACCESS  not-accessible
       STATUS      current
       DESCRIPTION
           "Defines an entry in the ipfixCollectorTable."
       INDEX { ipfixCollectorIndex }
       ::= { ipfixCollectorTable 1 }

   IpfixCollectorEntry ::= SEQUENCE {
           ipfixCollectorIndex             Integer32,
           ipfixCollectorDstIpAddressType  InetAddressType,
           ipfixCollectorDstIpAddress      InetAddress,
           ipfixCollectorDstProtocol       Integer32,
           ipfixCollectorDstPort           Integer32,
           ipfixCollectorReportsSent       Integer32
       }

   ipfixCollectorIndex OBJECT-TYPE
       SYNTAX      Integer32 (1..2147483647)
       MAX-ACCESS  not-accessible
       STATUS      current
       DESCRIPTION
           "The locally arbitrary, but unique identifier of a collector.

            The value is expected to remain constant at least from one
            re-initialization of the entity's network management system
            to the next re-initialization."
       ::= { ipfixCollectorEntry 1 }

   ipfixCollectorDstIpAddressType OBJECT-TYPE
       SYNTAX      InetAddressType
       MAX-ACCESS  read-create
       STATUS      current
       DESCRIPTION
           "The IP address type of the collector."
       ::= { ipfixCollectorEntry 2 }

   ipfixCollectorDstIpAddress OBJECT-TYPE
       SYNTAX      InetAddress
       MAX-ACCESS  read-create
       STATUS      current
       DESCRIPTION
           "The IP address of the collector."
       ::= { ipfixCollectorEntry 3 }

   ipfixCollectorDstProtocol OBJECT-TYPE
       SYNTAX      Integer32 (0..256)
       MAX-ACCESS  read-create
       STATUS      current
       DESCRIPTION
           "The transport protocol used for exporting sampled packets to
            the collector. The recommended protocols are TCP (6), UDP
            (17) and SCTP (132). The default is SCTP."
       DEFVAL      { 132 }
       ::= { ipfixCollectorEntry 4 }

   ipfixCollectorDstPort OBJECT-TYPE
       SYNTAX      Integer32 (0..65535)
       MAX-ACCESS  read-create
       STATUS      current
       DESCRIPTION
           "The port number of the collector."
       ::= { ipfixCollectorEntry 5 }

   ipfixCollectorReportsSent OBJECT-TYPE
       SYNTAX      Integer32
       MAX-ACCESS  read-only
       STATUS      current
       DESCRIPTION
           "The number of reports sent to the collector."
       ::= { ipfixCollectorEntry 6 }

   -- Collector Group Table +++++++++++++++++++++++++++++++++++++++++++

   ipfixCollectorGroupTable OBJECT-TYPE
       SYNTAX      SEQUENCE OF IpfixCollectorGroupEntry
       MAX-ACCESS  not-accessible
       STATUS      current
       DESCRIPTION
           "This table lists groups of collectors to which flow
            records packets are exported. If flow records are
            exported to only one collector the group consists of
            exactly one collector."
       ::= { ipfixReporting 2 }

   ipfixCollectorGroupEntry OBJECT-TYPE
       SYNTAX      IpfixCollectorGroupEntry
       MAX-ACCESS  not-accessible
       STATUS      current
       DESCRIPTION
           "Defines an entry in the ipfixCollectorGroupTable."
       INDEX { ipfixCollectorGroupIndex, ipfixCollectorIndex }
       ::= { ipfixCollectorGroupTable 1 }

   IpfixCollectorGroupEntry ::= SEQUENCE {
           ipfixCollectorGroupIndex                Integer32
       }

   ipfixCollectorGroupIndex OBJECT-TYPE
       SYNTAX      Integer32 (1..2147483647)
       MAX-ACCESS  not-accessible
       STATUS      current
       DESCRIPTION
           "The locally arbitrary, but unique identifier of a collector
            group.

            The value is expected to remain constant at least from one
            re-initialization of the entity's network management system
            to the next re-initialization."
       ::= { ipfixCollectorGroupEntry 1 }


   -- (Data) Template Table +++++++++++++++++++++++++++++++++++++++++++

   ipfixTemplateTable OBJECT-TYPE
       SYNTAX      SEQUENCE OF IpfixTemplateEntry
       MAX-ACCESS  not-accessible
       STATUS      current
       DESCRIPTION
           "This table lists templates used by the exporter."
       ::= { ipfixReporting 3 }

   ipfixTemplateEntry OBJECT-TYPE
       SYNTAX      IpfixTemplateEntry
       MAX-ACCESS  not-accessible
       STATUS      current
       DESCRIPTION
           "Defines an entry in the ipfixTemplateTable."
       INDEX { ipfixObservationDomainId, ipfixTemplateId,
               ipfixTemplateIndex }
       ::= { ipfixTemplateTable 1 }

   IpfixTemplateEntry ::= SEQUENCE {
           ipfixTemplateId          Integer32,
           ipfixTemplateIndex       Integer32,
           ipfixTemplateFieldId     Integer32,
           ipfixTemplateFieldLength Integer32
       }

   ipfixTemplateId OBJECT-TYPE
       SYNTAX      Integer32 (1..2147483647)
       MAX-ACCESS  not-accessible
       STATUS      current
       DESCRIPTION
           "The unique identifier for the template."
       REFERENCE
           "draft-ietf-ipfix-sample-tech-04.txt, Section 5.1"
   -- Editor Note: get reference right!
       ::= { ipfixTemplateEntry 1 }

   ipfixTemplateIndex OBJECT-TYPE
       SYNTAX      Integer32 (1..2147483647)
       MAX-ACCESS  not-accessible
       STATUS      current
       DESCRIPTION
           "The locally arbitrary, but unique identifier of a field Id
            in the template identified by ipfixTemplateId.

            The value is expected to remain constant at least from one
            re-initialization of the entity's network management system
            to the next re-initialization."
       ::= { ipfixTemplateEntry 2 }

   ipfixTemplateFieldId OBJECT-TYPE
       SYNTAX      Integer32
       MAX-ACCESS  read-only
       STATUS      current
       DESCRIPTION
           "The Field Id at position ipfixTemplateIndex in the template
            ipfixTemplateId. This implicitly gives the data type and
            state values that are exported."
       REFERENCE
           "draft-ietf-ipfix-sample-tech-04.txt, IPFIX/PSAMP INFO MODEL"
   -- Editor Note: get reference right!
       ::= { ipfixTemplateEntry 3 }

   ipfixTemplateFieldLength OBJECT-TYPE
       SYNTAX      Integer32
       MAX-ACCESS  read-only
       STATUS      current
       DESCRIPTION
           "The Length of the Field. Used to indicate if reduced
            encoding or variable length field is used."
       ::= { ipfixTemplateEntry 4 }

   --==================================================================
   -- Instance Group
   --==================================================================

   ipfixInstances       OBJECT IDENTIFIER ::= { ipfixExporterObjects 2 }

   ipfixObservationDomainTable OBJECT-TYPE
       SYNTAX      SEQUENCE OF IpfixObservationDomainEntry
       MAX-ACCESS  not-accessible
       STATUS      current
       DESCRIPTION
           "This table lists the Observation Domains used at
            the managed node."
       ::= { ipfixInstances 1 }

   ipfixObservationDomainEntry OBJECT-TYPE
       SYNTAX      IpfixObservationDomainEntry
       MAX-ACCESS  not-accessible
       STATUS      current
       DESCRIPTION
           "Defines an entry in the ipfixObservationDomainTable."
       INDEX { ipfixObservationDomainId }
       ::= { ipfixObservationDomainTable 1 }

   IpfixObservationDomainEntry ::= SEQUENCE {
           ipfixObservationDomainId         Integer32,
           ipfixInstanceObservationPoint    OBJECT IDENTIFIER,
           ipfixInstanceStartTime           DateAndTime,
           ipfixInstanceStopTime            DateAndTime
       }

   ipfixObservationDomainId OBJECT-TYPE
       SYNTAX      Integer32 (1..2147483647)
       MAX-ACCESS  not-accessible
       STATUS      current
       DESCRIPTION
           "The locally arbitrary, but unique identifier of an
            Observation Domain.
            The value is expected to remain constant at least from one
            re-initialization of the entity's network management system
            to the next re-initialization."
       ::= { ipfixObservationDomainEntry 1 }

   ipfixInstanceObservationPoint OBJECT-TYPE
       SYNTAX      OBJECT IDENTIFIER
       MAX-ACCESS  read-create
       STATUS      current
       DESCRIPTION
           "The point where the packet is observed. If it is e.g, an
            interface it points to the mib-II object of the interface."
       ::= { ipfixObservationDomainEntry 2 }

   ipfixInstanceStartTime OBJECT-TYPE
       SYNTAX      DateAndTime
       MAX-ACCESS  read-create
       STATUS      current
       DESCRIPTION
           "The date and time when exporting for this
            parameter set should start."
       ::= { ipfixObservationDomainEntry 3 }

   ipfixInstanceStopTime OBJECT-TYPE
       SYNTAX      DateAndTime
       MAX-ACCESS  read-create
       STATUS      current
       DESCRIPTION
           "The date and time when exporting for this
            parameter set should stop."
       ::= { ipfixObservationDomainEntry 4 }

   ipfixInstanceTable OBJECT-TYPE
       SYNTAX      SEQUENCE OF IpfixInstanceEntry
       MAX-ACCESS  not-accessible
       STATUS      current
       DESCRIPTION
           "This table lists active instances of packet sampling at
            the managed node."
       ::= { ipfixInstances 2 }

   ipfixInstanceEntry OBJECT-TYPE
       SYNTAX      IpfixInstanceEntry
       MAX-ACCESS  not-accessible
       STATUS      current
       DESCRIPTION
           "Defines an entry in the ipfixInstanceTable."
       INDEX { ipfixInstanceIndex, ipfixObservationDomainId }
       ::= { ipfixInstanceTable 1 }

   IpfixInstanceEntry ::= SEQUENCE {
           ipfixInstanceIndex               Integer32,
           ipfixInstanceTemplateId          Integer32,
           ipfixInstanceCollectorGroupIndex Integer32,
           ipfixInstancePacketsObserved     Integer32,
           ipfixInstancePacketsDropped      Integer32,
           ipfixInstanceProcessId           Integer32,
           ipfixInstanceReportingProcessId  Integer32,
           ipfixInstanceReportsSent         Integer32
       }

   ipfixInstanceIndex OBJECT-TYPE
       SYNTAX      Integer32 (1..2147483647)
       MAX-ACCESS  not-accessible
       STATUS      current
       DESCRIPTION
           "The locally arbitrary, but unique identifier of an
            instance.

            The value is expected to remain constant at least from one
            re-initialization of the entity's network management system
            to the next re-initialization."
       ::= { ipfixInstanceEntry 1 }

   ipfixInstanceTemplateId OBJECT-TYPE
       SYNTAX      Integer32 (1..2147483647)
       MAX-ACCESS  read-create
       STATUS      current
       DESCRIPTION
           "The Id of a template in the template table. This implies
            the knowledge about the method chain from the method chain
            table. Furthermore it links the instance, method chain
            (selector) and template together.

            The identified template is applied to the stream of
            filtered/sampled packets observed after applying the method
            chain at the observation point."
       ::= { ipfixInstanceEntry 2 }

   ipfixInstanceCollectorGroupIndex OBJECT-TYPE
       SYNTAX      Integer32
       MAX-ACCESS  read-create
       STATUS      current
       DESCRIPTION
           "The index of the collector group to which packet reports
            are sent."
       ::= { ipfixInstanceEntry 3 }

   ipfixInstancePacketsObserved OBJECT-TYPE
       SYNTAX      Integer32
       MAX-ACCESS  read-only
       STATUS      current
       DESCRIPTION
           "The number of packets observed at the observation point."
       ::= { ipfixInstanceEntry 4 }

   ipfixInstancePacketsDropped OBJECT-TYPE
       SYNTAX      Integer32
       MAX-ACCESS  read-only
       STATUS      current
       DESCRIPTION
           "The number of packets dropped while filtering/sampling
            packets."
       ::= { ipfixInstanceEntry 5 }

   ipfixInstanceProcessId OBJECT-TYPE
       SYNTAX      Integer32
       MAX-ACCESS  read-only
       STATUS      current
       DESCRIPTION
           "The process id of the metering process used by this
            instance."
       ::= { ipfixInstanceEntry 6 }

   ipfixInstanceReportingProcessId OBJECT-TYPE
       SYNTAX      Integer32
       MAX-ACCESS  read-only
       STATUS      current
       DESCRIPTION
           "The process id of the reporting process used by this
            instance."
       ::= { ipfixInstanceEntry 7 }

   ipfixInstanceReportsSent OBJECT-TYPE
       SYNTAX      Integer32
       MAX-ACCESS  read-only
       STATUS      current
       DESCRIPTION
           "The number of reports on sampled packets sent to the
            collector."
       ::= { ipfixInstanceEntry 8 }


   -- Method Chain Table ++++++++++++++++++++++++++++++++++++++++++++++
   ipfixMethodChainTable OBJECT-TYPE
       SYNTAX      SEQUENCE OF IpfixMethodChainEntry
       MAX-ACCESS  not-accessible
       STATUS      current
       DESCRIPTION
           "This table contains method chains lists and connects them
            to the instances where they are applied to different
            observation points. The filtered/sampled packets are then
            exported."
       ::= { ipfixInstances 4 }

   ipfixMethodChainEntry OBJECT-TYPE
       SYNTAX      IpfixMethodChainEntry
       MAX-ACCESS  not-accessible
       STATUS      current
       DESCRIPTION
           "Defines an entry in the ipfixMethodChainTable."
       INDEX { ipfixInstanceIndex, ipfixMethodChainIndex }
       ::= { ipfixMethodChainTable 1 }

   IpfixMethodChainEntry ::= SEQUENCE {
           ipfixMethodChainIndex           Integer32,
           ipfixMethodChainMethod          OBJECT IDENTIFIER,
           ipfixMethodChainPacketsObserved Integer32,
           ipfixMethodChainPacketsDropped  Integer32
       }

   ipfixMethodChainIndex OBJECT-TYPE
       SYNTAX      Integer32 (1..2147483647)
       MAX-ACCESS  not-accessible
       STATUS      current
       DESCRIPTION
           "The locally arbitrary, but unique identifier of a
            template.

            The value is expected to remain constant at least from one
            re-initialization of the entity's network management system
            to the next re-initialization."
       ::= { ipfixMethodChainEntry 2 }

   ipfixMethodChainMethod OBJECT-TYPE
       SYNTAX      OBJECT IDENTIFIER
       MAX-ACCESS  read-create
       STATUS      current
       DESCRIPTION
           "The method used for the template at a certain position in
            the method chain."
       ::= { ipfixMethodChainEntry 3 }

   ipfixMethodChainPacketsObserved OBJECT-TYPE
       SYNTAX      Integer32
       MAX-ACCESS  read-only
       STATUS      current
       DESCRIPTION
           "The number of packets observed at the method entry point."
       ::= { ipfixMethodChainEntry 4 }

   ipfixMethodChainPacketsDropped OBJECT-TYPE
       SYNTAX      Integer32
       MAX-ACCESS  read-only
       STATUS      current
       DESCRIPTION
           "The number of packets dropped while selecting packets."
       ::= { ipfixMethodChainEntry 5 }

   --==================================================================
   -- Conformance information
   --==================================================================

   ipfixCompliances OBJECT IDENTIFIER ::= { ipfixConformance 1 }
   ipfixGroups      OBJECT IDENTIFIER ::= { ipfixConformance 2 }

   --==================================================================
   -- Compliance statements
   --==================================================================

   ipfixCompliance MODULE-COMPLIANCE
       STATUS  current
       DESCRIPTION
           "An implementation that complies to this module must
            implement the objects defined in the mandatory groups
            ipfixGroupMetering and ipfixGroupReporting. The
            implementation of all other objects depends on the
            implementation of the corresponding functionality in the
            equipment."
       MODULE  -- this module
           MANDATORY-GROUPS {
                              ipfixGroupMetering,
                              ipfixGroupReporting
                            }
           GROUP ipfixGroupStatistics
           DESCRIPTION
               "These objects must be implemented if statistics are
                implemented on the equipment."
       ::= { ipfixCompliances 1 }

   --==================================================================
   -- MIB groupings
   --==================================================================

   ipfixGroupMetering OBJECT-GROUP
       OBJECTS {
                 ipfixTemplateFieldId,
                 ipfixTemplateFieldLength,

                 ipfixMethodChainMethod,

                 ipfixInstanceObservationPoint,
                 ipfixInstanceStartTime,
                 ipfixInstanceStopTime,
                 ipfixInstanceTemplateId,
                 ipfixInstanceCollectorGroupIndex,
                 ipfixInstanceProcessId,
                 ipfixInstanceReportingProcessId
               }
       STATUS  current
       DESCRIPTION
          "All objects that are basic for the metering process. It
           contains a basic metering function (ipfixSelectAll), The
           template definitions needed for the export of data, the
           method chain that fixes the metering functions applied to
           the observation point and several parameters concering
           the export process and the collectors."
       ::= { ipfixGroups 1 }

   ipfixGroupReporting OBJECT-GROUP
       OBJECTS {
                 ipfixCollectorDstIpAddressType,
                 ipfixCollectorDstIpAddress,
                 ipfixCollectorDstProtocol,
                 ipfixCollectorDstPort
               }
       STATUS  current
       DESCRIPTION
          "These objects define the collectors i.e., the destinations
           of the exporting process."
       ::= { ipfixGroups 2 }

   ipfixGroupStatistics OBJECT-GROUP
       OBJECTS {
                 ipfixCollectorReportsSent,

                 ipfixMethodChainPacketsObserved,
                 ipfixMethodChainPacketsDropped,
                 ipfixInstancePacketsObserved,
                 ipfixInstanceReportsSent,
                 ipfixInstancePacketsDropped
               }
       STATUS  current
       DESCRIPTION
          "These objects contain statistical values gathered at
           different points in the metering process."
       ::= { ipfixGroups 3 }

   END

-- 
--    Copyright (C) The Internet Society (2006).  This document is subject
--    to the rights, licenses and restrictions contained in BCP 78, and
--    except as set forth therein, the authors retain all their rights.
-- 
-- 
-- Acknowledgment
-- 
--    Funding for the RFC Editor function is currently provided by the
--    Internet Society.
