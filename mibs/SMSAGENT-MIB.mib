SMSAGENT-MIB DEFINITIONS ::= BEGIN

IMPORTS
    OBJECT-TYPE, Counter            FROM RFC1155-SMI
    Gauge, TimeTicks          FROM RFC1155-SMI
    DisplayString      FROM RFC1213-MIB
	enterprises        FROM RFC1155-SMI;

-- EXPORTS	unisys, unisysOpen;

	unisys      OBJECT IDENTIFIER ::= { enterprises 223 }
	unisysOpen  OBJECT IDENTIFIER ::= { unisys 10 }




-- THIS IS THE MIB DEFINITION FOR UNISYS AGENT 1.3
-- __________________  CONFIGURATION AGENT MIB  __________________

--
-- UNISYS Configuration Agent MIB definition
-- 
-- Copyright (c) 1999 Unisys Corporation. 
-- All rights reserved. 
-- UNISYS PROPRIETARY 
-- 
-- 

cfgAgent        OBJECT IDENTIFIER ::= { unisysOpen 7 }
 
-- CfgAgent MIB
 
cfgAgentVersion OBJECT-TYPE
	SYNTAX  INTEGER
	ACCESS  read-only
	STATUS  mandatory
	DESCRIPTION
			"The internal version number of this SNMP Extension Agent."
	::= { cfgAgent 1 }

cfgAgentRevision OBJECT-TYPE
	SYNTAX  INTEGER
	ACCESS  read-only
	STATUS  mandatory
	DESCRIPTION
			"The internal revision number of this SNMP Extension Agent."
	::= { cfgAgent 2 }

cfgAgentMIBVersion OBJECT-TYPE
	SYNTAX  INTEGER
	ACCESS  read-only
	STATUS  mandatory
	DESCRIPTION
			"The internal version number of the MIB for this SNMP Extension Agent."
	::= { cfgAgent 3 }

cfgAgentMIBRevision OBJECT-TYPE
	SYNTAX  INTEGER
	ACCESS  read-only
	STATUS  mandatory
	DESCRIPTION
			"The internal revision number of the MIB for this SNMP Extension Agent."
	::= { cfgAgent 4 }


-- __________________________  BIOS DEFINITION DATA  _____________________

cfgAgentBIOSVendor OBJECT-TYPE
	SYNTAX  DisplayString
	ACCESS  read-only
	STATUS  mandatory
	DESCRIPTION
			"A description of the system BIOS vendor."
	::= { cfgAgent 5 }

cfgAgentBIOSVersion OBJECT-TYPE
	SYNTAX  DisplayString
	ACCESS  read-only
	STATUS  mandatory
	DESCRIPTION
			"A description of the version of the system vendor's BIOS."
	::= { cfgAgent 6 }

cfgAgentBIOSDate OBJECT-TYPE
	SYNTAX  DisplayString
	ACCESS  read-only
	STATUS  mandatory
	DESCRIPTION
			"The date that the system BIOS was created."
	::= { cfgAgent 7 }

cfgAgentBIOSsROMInKb OBJECT-TYPE
	SYNTAX  INTEGER
	ACCESS  read-only
	STATUS  mandatory
	DESCRIPTION
			"The size of the BIOS read-only memory in kilobytes."
	::= { cfgAgent 8 }

cfgAgentBIOSBusSupport OBJECT-TYPE
	SYNTAX  DisplayString
	ACCESS  read-only
	STATUS  mandatory
	DESCRIPTION
			"The bus interface(s) supported by the system BIOS."
	::= { cfgAgent 9 }

cfgAgentBIOSAddress OBJECT-TYPE
	SYNTAX  INTEGER
	ACCESS  read-only
	STATUS  mandatory
	DESCRIPTION
			"The memory address used to access the system BIOS."
	::= { cfgAgent 10 }

cfgAgentBIOSInterruptId OBJECT-TYPE
	SYNTAX  INTEGER
	ACCESS  read-only
	STATUS  mandatory
	DESCRIPTION
			"The interrupt ID used to access the system BIOS."
	::= { cfgAgent 11 }


-- __________________________  CPU DEFINITION TABLE  _____________________

cfgAgentnCPUs OBJECT-TYPE
	SYNTAX  INTEGER
	ACCESS  read-only
	STATUS  mandatory
	DESCRIPTION
			"The number of CPUs listed in the subsequent CPUs table."
	::= { cfgAgent 12 }

cfgAgentCPUsTbl OBJECT-TYPE
	SYNTAX  SEQUENCE OF CfgAgentCPUEntry
	ACCESS  not-accessible
	STATUS  mandatory
	DESCRIPTION
			"CPU table consisting of a list of system CPUs."
	::= { cfgAgent 13 }

cfgAgentCPUsTblEntry OBJECT-TYPE
	SYNTAX  CfgAgentCPUEntry
	ACCESS  not-accessible
	STATUS  mandatory
	::= { cfgAgentCPUsTbl 1 }

CfgAgentCPUEntry ::= SEQUENCE
	{
	cfgAgentCPUClass  DisplayString,
	cfgAgentCPUName  DisplayString,
	cfgAgentCPUVendor  DisplayString,
	cfgAgentCPUSpeed  INTEGER,
	cfgAgentCPUsCacheInKb  INTEGER,
	cfgAgentCPUState  INTEGER
	}

cfgAgentCPUClass OBJECT-TYPE
	SYNTAX  DisplayString
	ACCESS  read-only
	STATUS  mandatory
	DESCRIPTION
			"The class of central processor (eg: Intel x86)."
	::= { cfgAgentCPUsTblEntry 1 }

cfgAgentCPUName OBJECT-TYPE
	SYNTAX  DisplayString
	ACCESS  read-only
	STATUS  mandatory
	DESCRIPTION
			"The vendor's name for the CPU (eg: 80486)."
	::= { cfgAgentCPUsTblEntry 2 }

cfgAgentCPUVendor OBJECT-TYPE
	SYNTAX  DisplayString
	ACCESS  read-only
	STATUS  mandatory
	DESCRIPTION
			"The vendor of the CPU chipset (eg: Genuine Intel)."
	::= { cfgAgentCPUsTblEntry 3 }

cfgAgentCPUSpeed OBJECT-TYPE
	SYNTAX  INTEGER
	ACCESS  read-only
	STATUS  mandatory
	DESCRIPTION
			"The approximate operating frequency (in MHz) of the CPU chipset."
	::= { cfgAgentCPUsTblEntry 4 }

cfgAgentCPUsCacheInKb OBJECT-TYPE
	SYNTAX  INTEGER
	ACCESS  read-only
	STATUS  mandatory
	DESCRIPTION
			"The size (in kilobytes) of the CPU operational memory cache."
	::= { cfgAgentCPUsTblEntry 5 }

cfgAgentCPUState OBJECT-TYPE
	SYNTAX  INTEGER  { active(1), disabled(2) }
	ACCESS  read-only
	STATUS  mandatory
	DESCRIPTION
			"The current state of the CPU:  active(1), disabled(2)."
	::= { cfgAgentCPUsTblEntry 6 }


-- __________________________  SYSTEM DEFINITION DATA  ___________________

cfgAgentSysName OBJECT-TYPE
	SYNTAX  DisplayString
	ACCESS  read-only
	STATUS  mandatory
	DESCRIPTION
			"The (network) name of this computer."
	::= { cfgAgent 14 }

cfgAgentSysBoardVersion OBJECT-TYPE
	SYNTAX  DisplayString
	ACCESS  read-only
	STATUS  mandatory
	DESCRIPTION
			"The vendor's board version information."
	::= { cfgAgent 15 }

cfgAgentSysUptimeMilSec OBJECT-TYPE
	SYNTAX  INTEGER
	ACCESS  read-only
	STATUS  mandatory
	DESCRIPTION
			"The length of time that this system has been active (in miliseconds)."
	::= { cfgAgent 16 }

cfgAgentSysOS OBJECT-TYPE
	SYNTAX  DisplayString
	ACCESS  read-only
	STATUS  mandatory
	DESCRIPTION
			"The operating system and its version running on this system."
	::= { cfgAgent 17 }

cfgAgentSysnDMAs OBJECT-TYPE
	SYNTAX  INTEGER
	ACCESS  read-only
	STATUS  mandatory
	DESCRIPTION
			"The number of DMA channels available on this system."
	::= { cfgAgent 18 }


-- __________________________  IRQ DEFINITION TABLE  _____________________

cfgAgentnIRQs OBJECT-TYPE
	SYNTAX  INTEGER
	ACCESS  read-only
	STATUS  mandatory
	DESCRIPTION
			"The number of IRQs listed in the subsequent IRQs table."
	::= { cfgAgent 19 }

cfgAgentIRQsTbl OBJECT-TYPE
	SYNTAX  SEQUENCE OF CfgAgentIRQEntry
	ACCESS  not-accessible
	STATUS  mandatory
	DESCRIPTION
			"IRQ table consisting of a list of IRQs allocated on this system."
	::= { cfgAgent 20 }

cfgAgentIRQsTblEntry OBJECT-TYPE
	SYNTAX  CfgAgentIRQEntry
	ACCESS  not-accessible
	STATUS  mandatory
	::= { cfgAgentIRQsTbl 1 }

CfgAgentIRQEntry ::= SEQUENCE
	{
	cfgAgentIRQ  INTEGER,
	cfgAgentIRQOwner  DisplayString,
	cfgAgentIRQBus  DisplayString,
	cfgAgentIRQClass  DisplayString
	}

cfgAgentIRQ OBJECT-TYPE
	SYNTAX  INTEGER
	ACCESS  read-only
	STATUS  mandatory
	DESCRIPTION
			"The allocated IRQ number.
			The agent returns -1 if the IRQ number is not available
			for the corresponding cfgAgentIRQOwner."
	::= { cfgAgentIRQsTblEntry 1 }

cfgAgentIRQOwner OBJECT-TYPE
	SYNTAX  DisplayString
	ACCESS  read-only
	STATUS  mandatory
	DESCRIPTION
			"The name of the device/controller that has allocated this IRQ."
	::= { cfgAgentIRQsTblEntry 2 }

cfgAgentIRQBus OBJECT-TYPE
	SYNTAX  DisplayString
	ACCESS  read-only
	STATUS  mandatory
	DESCRIPTION
			"The bus that the IRQ device/controller uses."
	::= { cfgAgentIRQsTblEntry 3 }

cfgAgentIRQClass OBJECT-TYPE
	SYNTAX  DisplayString
	ACCESS  read-only
	STATUS  mandatory
	DESCRIPTION
			"The class of the device/controller that has allocated this IRQ."
	::= { cfgAgentIRQsTblEntry 4 }


-- __________________________  MEMORY DEFINITION DATA  ___________________

cfgAgentMemSizeInMb OBJECT-TYPE
	SYNTAX  INTEGER
	ACCESS  read-only
	STATUS  mandatory
	DESCRIPTION
			"The size of physical memory on the system in megabytes."
	::= { cfgAgent 21 }

cfgAgentMemType OBJECT-TYPE
	SYNTAX  DisplayString
	ACCESS  read-only
	STATUS  mandatory
	DESCRIPTION
			"A description of the type of memory installed on the system."
	::= { cfgAgent 22 }

cfgAgentMemSpeed OBJECT-TYPE
	SYNTAX  INTEGER
	ACCESS  read-only
	STATUS  mandatory
	DESCRIPTION
			"The operating speed (in MHz) of the memory installed on the system."
	::= { cfgAgent 23 }

cfgAgentMemCacheInKb OBJECT-TYPE
	SYNTAX  INTEGER
	ACCESS  read-only
	STATUS  mandatory
	DESCRIPTION
			"The size of the memory hardware cache in kilobytes."
	::= { cfgAgent 24 }

cfgAgentMemBanks OBJECT-TYPE
	SYNTAX  INTEGER
	ACCESS  read-only
	STATUS  mandatory
	DESCRIPTION
			"The number of memory banks on this system."
	::= { cfgAgent 25 }

cfgAgentMemSpeedSupported OBJECT-TYPE
	SYNTAX  INTEGER
	ACCESS  read-only
	STATUS  mandatory
	DESCRIPTION
			"The supported speed (in MHz) of memory installed on the system."
	::= { cfgAgent 26 }


-- __________________________  I/O DEVICE DEFINITION DATA  _______________

cfgAgentIOKbdType OBJECT-TYPE
	SYNTAX  DisplayString
	ACCESS  read-only
	STATUS  mandatory
	DESCRIPTION
			"The type of keyboard in use on the system."
	::= { cfgAgent 27 }

cfgAgentIOMouseType OBJECT-TYPE
	SYNTAX  DisplayString
	ACCESS  read-only
	STATUS  mandatory
	DESCRIPTION
			"The type of mouse in use on the system."
	::= { cfgAgent 28 }

cfgAgentIOVidType OBJECT-TYPE
	SYNTAX  DisplayString
	ACCESS  read-only
	STATUS  mandatory
	DESCRIPTION
			"The type of display monitor in use on the system."
	::= { cfgAgent 29 }


-- __________________________  SERIAL PORT DEFINITION TABLE  _____________

cfgAgentnSerials OBJECT-TYPE
	SYNTAX  INTEGER
	ACCESS  read-only
	STATUS  mandatory
	DESCRIPTION
			"The number of serial ports listed in the subsequent serial ports table."
	::= { cfgAgent 30 }

cfgAgentSerialsTbl OBJECT-TYPE
	SYNTAX  SEQUENCE OF CfgAgentSerialEntry
	ACCESS  not-accessible
	STATUS  mandatory
	DESCRIPTION
			"Serial port table consisting of a list of serial ports."
	::= { cfgAgent 31 }

cfgAgentSerialsTblEntry OBJECT-TYPE
	SYNTAX  CfgAgentSerialEntry
	ACCESS  not-accessible
	STATUS  mandatory
	::= { cfgAgentSerialsTbl 1 }

CfgAgentSerialEntry ::= SEQUENCE
	{
	cfgAgentSerialPort  INTEGER
	}

cfgAgentSerialPort OBJECT-TYPE
	SYNTAX  INTEGER
	ACCESS  read-only
	STATUS  mandatory
	DESCRIPTION
			"The serial I/O port controller's port address."
	::= { cfgAgentSerialsTblEntry 1 }


-- __________________________  PARALLEL PORT DEFINITION TABLE  ___________

cfgAgentnParallels OBJECT-TYPE
	SYNTAX  INTEGER
	ACCESS  read-only
	STATUS  mandatory
	DESCRIPTION
			"The number of parallel ports listed in the subsequent parallel ports table."
	::= { cfgAgent 32 }

cfgAgentParallelsTbl OBJECT-TYPE
	SYNTAX  SEQUENCE OF CfgAgentParallelEntry
	ACCESS  not-accessible
	STATUS  mandatory
	DESCRIPTION
			"Parallel port table consisting of a list of parallel ports."
	::= { cfgAgent 33 }

cfgAgentParallelsTblEntry OBJECT-TYPE
	SYNTAX  CfgAgentParallelEntry
	ACCESS  not-accessible
	STATUS  mandatory
	::= { cfgAgentParallelsTbl 1 }

CfgAgentParallelEntry ::= SEQUENCE
	{
	cfgAgentParallelPort  INTEGER
	}

cfgAgentParallelPort OBJECT-TYPE
	SYNTAX  INTEGER
	ACCESS  read-only
	STATUS  mandatory
	DESCRIPTION
			"The parallel I/O port controller's port address."
	::= { cfgAgentParallelsTblEntry 1 }


-- __________________________  CONTROLLER DEFINITION TABLE  ______________

cfgAgentnControllers OBJECT-TYPE
	SYNTAX  INTEGER
	ACCESS  read-only
	STATUS  mandatory
	DESCRIPTION
			"The number of controllers listed in the subsequent controllers table."
	::= { cfgAgent 34 }

cfgAgentControllersTbl OBJECT-TYPE
	SYNTAX  SEQUENCE OF CfgAgentControllerEntry
	ACCESS  not-accessible
	STATUS  mandatory
	DESCRIPTION
			"Controller table consisting of a list of controllers."
	::= { cfgAgent 35 }

cfgAgentControllersTblEntry OBJECT-TYPE
	SYNTAX  CfgAgentControllerEntry
	ACCESS  not-accessible
	STATUS  mandatory
	::= { cfgAgentControllersTbl 1 }

CfgAgentControllerEntry ::= SEQUENCE
	{
	cfgAgentControllerType  DisplayString,
	cfgAgentControllerName  DisplayString,
	cfgAgentControllerIRQ  INTEGER
	}

cfgAgentControllerType OBJECT-TYPE
	SYNTAX  DisplayString
	ACCESS  read-only
	STATUS  mandatory
	DESCRIPTION
			"The type of device controller."
	::= { cfgAgentControllersTblEntry 1 }

cfgAgentControllerName OBJECT-TYPE
	SYNTAX  DisplayString
	ACCESS  read-only
	STATUS  mandatory
	DESCRIPTION
			"The controller's device name."
	::= { cfgAgentControllersTblEntry 2 }

cfgAgentControllerIRQ OBJECT-TYPE
	SYNTAX  INTEGER
	ACCESS  read-only
	STATUS  mandatory
	DESCRIPTION
			"The IRQ number used by the device controller.
			The agent returns -1 if the IRQ number is not available
			for the corresponding controller."

	::= { cfgAgentControllersTblEntry 3 }


-- __________________________  SNMP TRAP DESTINATION TABLE  ______________

cfgAgentnTrapDests OBJECT-TYPE
	SYNTAX  INTEGER
	ACCESS  read-only
	STATUS  mandatory
	DESCRIPTION
			"The number of trap destinations listed in the subsequent trap destinations table."
	::= { cfgAgent 36 }

cfgAgentTrapDestsTbl OBJECT-TYPE
	SYNTAX  SEQUENCE OF CfgAgentTrapDestEntry
	ACCESS  not-accessible
	STATUS  mandatory
	DESCRIPTION
			"Trap destinations table consisting of a list of trap destinations."
	::= { cfgAgent 37 }

cfgAgentTrapDestsTblEntry OBJECT-TYPE
	SYNTAX  CfgAgentTrapDestEntry
	ACCESS  not-accessible
	STATUS  mandatory
	::= { cfgAgentTrapDestsTbl 1 }

CfgAgentTrapDestEntry ::= SEQUENCE
	{
	cfgAgentTrapDestId  DisplayString,
	cfgAgentTrapDestIPAddr  DisplayString,
	cfgAgentCommunityString DisplayString
	}

cfgAgentTrapDestId OBJECT-TYPE
	SYNTAX  DisplayString
	ACCESS  read-only
	STATUS  mandatory
	DESCRIPTION
			"The identifier of this trap destination."
	::= { cfgAgentTrapDestsTblEntry 1 }

cfgAgentTrapDestIPAddr OBJECT-TYPE
	SYNTAX  DisplayString
	ACCESS  read-write
	STATUS  mandatory
	DESCRIPTION
			"The IP address of this trap destination."
	::= { cfgAgentTrapDestsTblEntry 2 }

cfgAgentCommunityString OBJECT-TYPE
	SYNTAX  DisplayString
	ACCESS  read-only
	STATUS  mandatory
	DESCRIPTION
			"The community that this trap destination belongs too."
	::= { cfgAgentTrapDestsTblEntry 3 }

-- __________________________  PLATFORM DEFINITION TABLE  ______________

cfgAgentnPlatforms OBJECT-TYPE
	SYNTAX  INTEGER
	ACCESS  read-only
	STATUS  mandatory
	DESCRIPTION
			"The number of OEM Platforms listed in the subsequent table."
	::= { cfgAgent 38 }

cfgAgentPlatforms OBJECT-TYPE
	SYNTAX  SEQUENCE OF CfgAgentPlatformEntry
	ACCESS  not-accessible
	STATUS  mandatory
	DESCRIPTION
			"Platform table consisting of a list of Platform Information from BIOS table."
	::= { cfgAgent 39 }

cfgAgentPlatformTblEntry OBJECT-TYPE
	SYNTAX  CfgAgentPlatformEntry
	ACCESS  not-accessible
	STATUS  mandatory
	::= { cfgAgentPlatforms 1 }

CfgAgentPlatformEntry ::= SEQUENCE
	{
	cfgAgentOEMPlatform  DisplayString,
	cfgAgentProductID  DisplayString
	}

cfgAgentOEMPlatform OBJECT-TYPE
	SYNTAX  DisplayString
	ACCESS  read-only
	STATUS  mandatory
	DESCRIPTION
			"The name of the Platform."
	::= { cfgAgentPlatformTblEntry 1 }

cfgAgentProductID OBJECT-TYPE
	SYNTAX  DisplayString
	ACCESS  read-only
	STATUS  mandatory
	DESCRIPTION
			"The name of the Product ID."
	::= { cfgAgentPlatformTblEntry 2 }


-- __________________________  CONSOLE MGR DEFINITION DATA  ___________________

cfgAgentnConsoleMgr OBJECT-TYPE
	SYNTAX  INTEGER
	ACCESS  read-only
	STATUS  mandatory
	DESCRIPTION
			"The number of esConsoleMgr."
	::= { cfgAgent 40 }

cfgAgentConsoleMgr OBJECT-TYPE
	SYNTAX  SEQUENCE OF CfgAgentConsoleMgrEntry
	ACCESS  not-accessible
	STATUS  mandatory
	DESCRIPTION
			"ConsoleMgr table consisting of a list of ConsoleMgr Information."
	::= { cfgAgent 41 }

cfgAgentConsoleMgrTblEntry OBJECT-TYPE
	SYNTAX  CfgAgentConsoleMgrEntry
	ACCESS  not-accessible
	STATUS  mandatory
	::= { cfgAgentConsoleMgr 1 }

CfgAgentConsoleMgrEntry ::= SEQUENCE
	{
	cfgAgentCMCardIndex  INTEGER,
	cfgAgentCMIPAddress  DisplayString,
	cfgAgentCMHostName   DisplayString,
	cfgAgentCMHardwareVer  DisplayString,
	cfgAgentCMFirmwareVer  DisplayString
	}

cfgAgentCMCardIndex OBJECT-TYPE
	SYNTAX  INTEGER
	ACCESS  read-only
	STATUS  mandatory
	DESCRIPTION
			"The index of the esConsoleMgr table."
	::= { cfgAgentConsoleMgrTblEntry 1 }

cfgAgentCMIPAddress OBJECT-TYPE
	SYNTAX  DisplayString
	ACCESS  read-only
	STATUS  mandatory
	DESCRIPTION
			"The IP address of the esConsoleMgr."
	::= { cfgAgentConsoleMgrTblEntry 2 }

cfgAgentCMHostName OBJECT-TYPE
	SYNTAX  DisplayString
	ACCESS  read-only
	STATUS  mandatory
	DESCRIPTION
			"The host name of the esConsoleMgr."
	::= { cfgAgentConsoleMgrTblEntry 3 }

cfgAgentCMHardwareVer OBJECT-TYPE
	SYNTAX  DisplayString
	ACCESS  read-only
	STATUS  mandatory
	DESCRIPTION
			"The hardware version of the esConsoleMgr."
	::= { cfgAgentConsoleMgrTblEntry 4 }

cfgAgentCMFirmwareVer OBJECT-TYPE
	SYNTAX  DisplayString
	ACCESS  read-only
	STATUS  mandatory
	DESCRIPTION
			"The firmware version of the esConsoleMgr."
	::= { cfgAgentConsoleMgrTblEntry 5 }


-- __________________  NETWORK AGENT MIB  __________________

--
-- UNISYS Network Agent MIB definition
-- 

netAgent        OBJECT IDENTIFIER ::= { unisysOpen 8 }
 
-- NetAgent MIB
 
netAgentVersion OBJECT-TYPE
	SYNTAX  INTEGER
	ACCESS  read-only
	STATUS  mandatory
	DESCRIPTION
			"The internal version number of this SNMP Extension Agent."
	::= { netAgent 1 }

netAgentRevision OBJECT-TYPE
	SYNTAX  INTEGER
	ACCESS  read-only
	STATUS  mandatory
	DESCRIPTION
			"The internal revision number of this SNMP Extension Agent."
	::= { netAgent 2 }

netAgentMIBVersion OBJECT-TYPE
	SYNTAX  INTEGER
	ACCESS  read-only
	STATUS  mandatory
	DESCRIPTION
			"The internal version number of the MIB for this SNMP Extension Agent."
	::= { netAgent 3 }

netAgentMIBRevision OBJECT-TYPE
	SYNTAX  INTEGER
	ACCESS  read-only
	STATUS  mandatory
	DESCRIPTION
			"The internal revision number of the MIB for this SNMP Extension Agent."
	::= { netAgent 4 }

netAgentMachineName OBJECT-TYPE
	SYNTAX  DisplayString
	ACCESS  read-only
	STATUS  mandatory
	DESCRIPTION
			"The network (NetBIOS) name of this computer."
	::= { netAgent 5 }

netAgentLogonServer OBJECT-TYPE
	SYNTAX  DisplayString
	ACCESS  read-only
	STATUS  mandatory
	DESCRIPTION
			"The network domain name that this computer is connected to."
	::= { netAgent 6 }


-- __________________________  NIC DEFINITION TABLE  _____________________

netAgentnNICs OBJECT-TYPE
	SYNTAX  INTEGER
	ACCESS  read-only
	STATUS  mandatory
	DESCRIPTION
			"The number of network interface cards (NIC) listed in the subsequent NIC table."
	::= { netAgent 7 }

netAgentNICsTbl OBJECT-TYPE
	SYNTAX  SEQUENCE OF NetAgentNICEntry
	ACCESS  not-accessible
	STATUS  mandatory
	DESCRIPTION
			"Network interface cards (NIC) table consisting of a list of installed system NICs."
	::= { netAgent 8 }

netAgentNICTblEntry OBJECT-TYPE
	SYNTAX  NetAgentNICEntry
	ACCESS  not-accessible
	STATUS  mandatory
	::= { netAgentNICsTbl 1 }

NetAgentNICEntry ::= SEQUENCE
	{
	netAgentVendorID  DisplayString,
	netAgentMACAddress  DisplayString,
	netAgentFirmwareVersion  INTEGER,
	netAgentFirmwareRevision  INTEGER,
	netAgentControllerType  DisplayString,
	netAgentControllerPort  INTEGER,
	netAgentControllerIRQ  INTEGER,
	netAgentControllerBaseIO  INTEGER,
	netAgentDataSent  INTEGER,
	netAgentDataReceived  INTEGER,
	netAgentNICDriver  DisplayString,
	netAgentDriverName  DisplayString
	}

netAgentVendorID OBJECT-TYPE
	SYNTAX  DisplayString
	ACCESS  read-only
	STATUS  mandatory
	DESCRIPTION
			"The manufacturer's internal network adapter card identification string."
	::= { netAgentNICTblEntry 1 }

netAgentMACAddress OBJECT-TYPE
	SYNTAX  DisplayString
	ACCESS  read-only
	STATUS  mandatory
	DESCRIPTION
			"The network adapter card's unique network address."
	::= { netAgentNICTblEntry 2 }

netAgentFirmwareVersion OBJECT-TYPE
	SYNTAX  INTEGER
	ACCESS  read-only
	STATUS  mandatory
	DESCRIPTION
			"The manufacturer's network adapter card firmware version."
	::= { netAgentNICTblEntry 3 }

netAgentFirmwareRevision OBJECT-TYPE
	SYNTAX  INTEGER
	ACCESS  read-only
	STATUS  mandatory
	DESCRIPTION
			"The manufacturer's network adapter card firmware revision."
	::= { netAgentNICTblEntry 4 }

netAgentControllerType OBJECT-TYPE
	SYNTAX  DisplayString
	ACCESS  read-only
	STATUS  mandatory
	DESCRIPTION
			"The type of PC bus connector used by this network adapter card."
	::= { netAgentNICTblEntry 5 }

netAgentControllerPort OBJECT-TYPE
	SYNTAX  INTEGER
	ACCESS  read-only
	STATUS  mandatory
	DESCRIPTION
			"The controller port number/address used by this network adapter card."
	::= { netAgentNICTblEntry 6 }

netAgentControllerIRQ OBJECT-TYPE
	SYNTAX  INTEGER
	ACCESS  read-only
	STATUS  mandatory
	DESCRIPTION
			"The controller IRQ number used by this network adapter card."
	::= { netAgentNICTblEntry 7 }

netAgentControllerBaseIO OBJECT-TYPE
	SYNTAX  INTEGER
	ACCESS  read-only
	STATUS  mandatory
	DESCRIPTION
			"The controller base IO address used by this network adapter card."
	::= { netAgentNICTblEntry 8 }

netAgentDataSent OBJECT-TYPE
	SYNTAX  INTEGER
	ACCESS  read-only
	STATUS  mandatory
	DESCRIPTION
			"The number of network packets sent by this computer."
	::= { netAgentNICTblEntry 9 }

netAgentDataReceived OBJECT-TYPE
	SYNTAX  INTEGER
	ACCESS  read-only
	STATUS  mandatory
	DESCRIPTION
			"The number of network packets received by this computer."
	::= { netAgentNICTblEntry 10 }

netAgentNICDriver OBJECT-TYPE
	SYNTAX  DisplayString
	ACCESS  read-only
	STATUS  mandatory
	DESCRIPTION
			"The network adapter card's driver specification."
	::= { netAgentNICTblEntry 11 }

netAgentDriverName OBJECT-TYPE
	SYNTAX  DisplayString
	ACCESS  read-only
	STATUS  mandatory
	DESCRIPTION
			"The network adapter card's driver name."
	::= { netAgentNICTblEntry 12 }


-- __________________  SOFTWARE AGENT MIB  __________________

--
-- UNISYS Software Agent MIB definition
-- 

sftAgent        OBJECT IDENTIFIER ::= { unisysOpen 9 }
 
-- sftAgent MIB
 
sftAgentVersion OBJECT-TYPE
	SYNTAX  INTEGER
	ACCESS  read-only
	STATUS  mandatory
	DESCRIPTION
			"The internal version number of this SNMP Extension Agent."
	::= { sftAgent 1 }

sftAgentRevision OBJECT-TYPE
	SYNTAX  INTEGER
	ACCESS  read-only
	STATUS  mandatory
	DESCRIPTION
			"The internal revision number of this SNMP Extension Agent."
	::= { sftAgent 2 }

sftAgentMIBVersion OBJECT-TYPE
	SYNTAX  INTEGER
	ACCESS  read-only
	STATUS  mandatory
	DESCRIPTION
			"The internal version number of the MIB for this SNMP Extension Agent."
	::= { sftAgent 3 }

sftAgentMIBRevision OBJECT-TYPE
	SYNTAX  INTEGER
	ACCESS  read-only
	STATUS  mandatory
	DESCRIPTION
			"The internal revision number of the MIB for this SNMP Extension Agent."
	::= { sftAgent 4 }


-- __________________________  PACKAGE DEFINITION TABLE  _________________

sftAgentnPackages OBJECT-TYPE
	SYNTAX  INTEGER
	ACCESS  read-only
	STATUS  mandatory
	DESCRIPTION
			"The number of Packages listed in the subsequent Packages table."
	::= { sftAgent 5 }

sftAgentPackagesTbl OBJECT-TYPE
	SYNTAX  SEQUENCE OF SftAgentPackageEntry
	ACCESS  not-accessible
	STATUS  mandatory
	DESCRIPTION
			"Package table consisting of a list of uninstallable packages."
	::= { sftAgent 6 }

sftAgentPackagesTblEntry OBJECT-TYPE
	SYNTAX  SftAgentPackageEntry
	ACCESS  not-accessible
	STATUS  mandatory
	::= { sftAgentPackagesTbl 1 }

SftAgentPackageEntry ::= SEQUENCE
	{
	sftAgentPackage  DisplayString
	}

sftAgentPackage OBJECT-TYPE
	SYNTAX  DisplayString
	ACCESS  read-only
	STATUS  mandatory
	DESCRIPTION
			"The name of the package that can be uninstalled."
	::= { sftAgentPackagesTblEntry 1 }


-- __________________________  SERVICE DEFINITION TABLE  _________________

sftAgentnServices OBJECT-TYPE
	SYNTAX  INTEGER
	ACCESS  read-only
	STATUS  mandatory
	DESCRIPTION
			"The number of Services listed in the subsequent Services table."
	::= { sftAgent 7 }

sftAgentServicesTbl OBJECT-TYPE
	SYNTAX  SEQUENCE OF SftAgentServiceEntry
	ACCESS  not-accessible
	STATUS  mandatory
	DESCRIPTION
			"Service table consisting of a list of installed system services."
	::= { sftAgent 8 }

sftAgentServicesTblEntry OBJECT-TYPE
	SYNTAX  SftAgentServiceEntry
	ACCESS  not-accessible
	STATUS  mandatory
	::= { sftAgentServicesTbl 1 }

SftAgentServiceEntry ::= SEQUENCE
	{
	sftAgentService  DisplayString,
	sftAgentServiceStartup  INTEGER,
	sftAgentServiceStatus   INTEGER,
	sftAgentServiceDesired  INTEGER
	}

sftAgentService OBJECT-TYPE
	SYNTAX  DisplayString
	ACCESS  read-only
	STATUS  mandatory
	DESCRIPTION
			"The name of the service that has been installed."
	::= { sftAgentServicesTblEntry 1 }

sftAgentServiceStartup OBJECT-TYPE
	SYNTAX  INTEGER { boot(0), system(1), auto(2), manual(3), disabled(4) }
	ACCESS  read-only
	STATUS  mandatory
	DESCRIPTION
			"The service startup mode: boot(0), system(1), auto(2), manual(3), disabled(4)."
	::= { sftAgentServicesTblEntry 2 }

sftAgentServiceStatus OBJECT-TYPE
	SYNTAX  INTEGER { stopped(1), running(2)}
	ACCESS  read-only
	STATUS  mandatory
	DESCRIPTION
			"The service status: stopped(1), running(2)."
	::= { sftAgentServicesTblEntry 3 }

sftAgentServiceDesired OBJECT-TYPE
	SYNTAX  INTEGER { stopping(1), running(2), ignore(3)}
	ACCESS  read-write
	STATUS  mandatory
	DESCRIPTION
			"The service request: stopping(1), running(2), ignore(3)."
	::= { sftAgentServicesTblEntry 4 }


-- __________________________  DEVICE DEFINITION TABLE  __________________

sftAgentnDevices OBJECT-TYPE
	SYNTAX  INTEGER
	ACCESS  read-only
	STATUS  mandatory
	DESCRIPTION
			"The number of Devices listed in the subsequent Devices table."
	::= { sftAgent 9 }

sftAgentDevicesTbl OBJECT-TYPE
	SYNTAX  SEQUENCE OF SftAgentDeviceEntry
	ACCESS  not-accessible
	STATUS  mandatory
	DESCRIPTION
			"Device table consisting of a list of installed system devices."
	::= { sftAgent 10 }

sftAgentDevicesTblEntry OBJECT-TYPE
	SYNTAX  SftAgentDeviceEntry
	ACCESS  not-accessible
	STATUS  mandatory
	::= { sftAgentDevicesTbl 1 }

SftAgentDeviceEntry ::= SEQUENCE
	{
	sftAgentDevice  DisplayString,
	sftAgentDeviceStartup  INTEGER
	}

sftAgentDevice OBJECT-TYPE
	SYNTAX  DisplayString
	ACCESS  read-only
	STATUS  mandatory
	DESCRIPTION
			"The name of the device that has been installed."
	::= { sftAgentDevicesTblEntry 1 }

sftAgentDeviceStartup OBJECT-TYPE
	SYNTAX  INTEGER { boot(0), system(1), auto(2), manual(3), disabled(4) }
	ACCESS  read-only
	STATUS  mandatory
	DESCRIPTION
			"The device startup mode: boot(0), system(1), auto(2), manual(3), disabled(4)."
	::= { sftAgentDevicesTblEntry 2 }


sftAgentCriticalServices OBJECT-TYPE
	SYNTAX  INTEGER 
	ACCESS  read-only
	STATUS  mandatory
	DESCRIPTION
			"The total number of services in critical state."
	::= { sftAgent 11 }




-- __________________________  TRAP DEFINITIONS  _________________________

sftAgentSvcIndex OBJECT-TYPE
	SYNTAX  INTEGER
	ACCESS  not-accessible
	STATUS  mandatory
	DESCRIPTION
			"Indicates the number (starting from 1) of the unit reported in an alert message."
	::= { sftAgent 99 }

sftAgentSvcStateTrap TRAP-TYPE
	ENTERPRISE sftAgent
	VARIABLES {
	           sftAgentService,
	           sftAgentServiceStatus,
	           sftAgentServiceDesired,
	           sftAgentCriticalServices
	          }
	DESCRIPTION
			"This service state does not match the desired state."
	::= 1


sftAgentSvcStateOkTrap TRAP-TYPE
	ENTERPRISE sftAgent
	VARIABLES {
	           sftAgentService,
	           sftAgentServiceStatus,
	           sftAgentServiceDesired,
	           sftAgentCriticalServices
	          }
	DESCRIPTION
			"The service state is matching the desired state."
	::= 11



-- __________________  STORAGE AGENT MIB  __________________

--
-- UNISYS Storage Agent MIB definition
-- 
 
strAgent        OBJECT IDENTIFIER ::= { unisysOpen 10 }
 
-- StrAgent MIB
 
strAgentVersion OBJECT-TYPE
	SYNTAX  INTEGER
	ACCESS  read-only
	STATUS  mandatory
	DESCRIPTION
			"The internal version number of this SNMP Extension Agent."
	::= { strAgent 1 }

strAgentRevision OBJECT-TYPE
	SYNTAX  INTEGER
	ACCESS  read-only
	STATUS  mandatory
	DESCRIPTION
			"The internal revision number of this SNMP Extension Agent."
	::= { strAgent 2 }

strAgentMIBVersion OBJECT-TYPE
	SYNTAX  INTEGER
	ACCESS  read-only
	STATUS  mandatory
	DESCRIPTION
			"The internal version number of the MIB for this SNMP Extension Agent."
	::= { strAgent 3 }

strAgentMIBRevision OBJECT-TYPE
	SYNTAX  INTEGER
	ACCESS  read-only
	STATUS  mandatory
	DESCRIPTION
			"The internal revision number of the MIB for this SNMP Extension Agent."
	::= { strAgent 4 }


-- __________________________  CONTROLLER DEFINITION TABLE  ______________

strAgentnControllers OBJECT-TYPE
	SYNTAX  INTEGER
	ACCESS  read-only
	STATUS  mandatory
	DESCRIPTION
			"The number of disk controllers listed in the subsequent Controllers table."
	::= { strAgent 5 }

strAgentControllersTbl OBJECT-TYPE
	SYNTAX  SEQUENCE OF StrAgentControllerEntry
	ACCESS  not-accessible
	STATUS  mandatory
	DESCRIPTION
			"Controller table consisting of a list of uninstallable Controllers."
	::= { strAgent 6 }

strAgentControllersTblEntry OBJECT-TYPE
	SYNTAX  StrAgentControllerEntry
	ACCESS  not-accessible
	STATUS  mandatory
	::= { strAgentControllersTbl 1 }

StrAgentControllerEntry ::= SEQUENCE
	{
	strAgentCtlrType  DisplayString,
	strAgentCtlrVendor  DisplayString,
	strAgentCtlrFirmware  DisplayString,
	strAgentCtlrSerialNo  DisplayString,
	strAgentCtlrDMA  INTEGER,
	strAgentCtlrIRQ  INTEGER,
	strAgentCtlrAddress  INTEGER,
	strAgentCtlrIOPort  Gauge
	}

strAgentCtlrType OBJECT-TYPE
	SYNTAX  DisplayString
	ACCESS  read-only
	STATUS  mandatory
	DESCRIPTION
			"The type of the controller:  SCSI or IDE."
	::= { strAgentControllersTblEntry 1 }

strAgentCtlrVendor OBJECT-TYPE
	SYNTAX  DisplayString
	ACCESS  read-only
	STATUS  mandatory
	DESCRIPTION
			"The name of the controller's vendor."
	::= { strAgentControllersTblEntry 2 }

strAgentCtlrFirmware OBJECT-TYPE
	SYNTAX  DisplayString
	ACCESS  read-only
	STATUS  mandatory
	DESCRIPTION
			"The description of the controller's firmware version."
	::= { strAgentControllersTblEntry 3 }

strAgentCtlrSerialNo OBJECT-TYPE
	SYNTAX  DisplayString
	ACCESS  read-only
	STATUS  mandatory
	DESCRIPTION
			"The name of the Controller that can be uninstalled."
	::= { strAgentControllersTblEntry 4 }

strAgentCtlrDMA OBJECT-TYPE
	SYNTAX  INTEGER
	ACCESS  read-only
	STATUS  mandatory
	DESCRIPTION
			"The DMA number used by the controller."
	::= { strAgentControllersTblEntry 5 }

strAgentCtlrIRQ OBJECT-TYPE
	SYNTAX  INTEGER
	ACCESS  read-only
	STATUS  mandatory
	DESCRIPTION
			"The IRQ number used by the controller."
	::= { strAgentControllersTblEntry 6 }

strAgentCtlrAddress OBJECT-TYPE
	SYNTAX  INTEGER
	ACCESS  read-only
	STATUS  mandatory
	DESCRIPTION
			"The memory address used by the controller."
	::= { strAgentControllersTblEntry 7 }

strAgentCtlrIOPort OBJECT-TYPE
	SYNTAX  Gauge
	ACCESS  read-only
	STATUS  mandatory
	DESCRIPTION
			"The I/O port number used by the controller."
	::= { strAgentControllersTblEntry 8 }


-- __________________________  DISK DEFINITION TABLE  ____________________

strAgentnDisks OBJECT-TYPE
	SYNTAX  INTEGER
	ACCESS  read-only
	STATUS  mandatory
	DESCRIPTION
			"The number of Disks listed in the subsequent Disks table."
	::= { strAgent 7 }

strAgentDisksTbl OBJECT-TYPE
	SYNTAX  SEQUENCE OF StrAgentDiskEntry
	ACCESS  not-accessible
	STATUS  mandatory
	DESCRIPTION
			"Disk table consisting of a list of installed system disks."
	::= { strAgent 8 }

strAgentDisksTblEntry OBJECT-TYPE
	SYNTAX  StrAgentDiskEntry
	ACCESS  not-accessible
	STATUS  mandatory
	::= { strAgentDisksTbl 1 }

StrAgentDiskEntry ::= SEQUENCE
	{
	strAgentDiskVendor  DisplayString,
	strAgentDiskDescription  DisplayString,
	strAgentDiskFirmware  DisplayString,
	strAgentDiskPort  INTEGER,
	strAgentDiskBus  INTEGER,
	strAgentDiskLUN  INTEGER,
	strAgentDiskID  INTEGER,
	strAgentDiskSerialNo  DisplayString,
	strAgentDisknSectors  INTEGER,
	strAgentDiskDriveLetters  DisplayString,
	strAgentDiskSizeInMb  INTEGER,
	strAgentDiskState  INTEGER,
	strAgentDiskXfersPerSec  INTEGER,
	strAgentDiskSmartCond  INTEGER
	}

strAgentDiskVendor OBJECT-TYPE
	SYNTAX  DisplayString
	ACCESS  read-only
	STATUS  mandatory
	DESCRIPTION
			"The vendor of this disk device."
	::= { strAgentDisksTblEntry 1 }

strAgentDiskDescription OBJECT-TYPE
	SYNTAX  DisplayString
	ACCESS  read-only
	STATUS  mandatory
	DESCRIPTION
			"A description of the type of device."
	::= { strAgentDisksTblEntry 2 }

strAgentDiskFirmware OBJECT-TYPE
	SYNTAX  DisplayString
	ACCESS  read-only
	STATUS  mandatory
	DESCRIPTION
			"The description of the device's firmware version."
	::= { strAgentDisksTblEntry 3 }

strAgentDiskPort OBJECT-TYPE
	SYNTAX  INTEGER
	ACCESS  read-only
	STATUS  mandatory
	DESCRIPTION
			"The SCSI port this device is attached to."
	::= { strAgentDisksTblEntry 4 }

strAgentDiskBus OBJECT-TYPE
	SYNTAX  INTEGER
	ACCESS  read-only
	STATUS  mandatory
	DESCRIPTION
			"The SCSI bus number on the SCSI port that this device is attached to."
	::= { strAgentDisksTblEntry 5 }

strAgentDiskLUN OBJECT-TYPE
	SYNTAX  INTEGER
	ACCESS  read-only
	STATUS  mandatory
	DESCRIPTION
			"This SCSI device's logical unit number (LUN)."
	::= { strAgentDisksTblEntry 6 }

strAgentDiskID OBJECT-TYPE
	SYNTAX  INTEGER
	ACCESS  read-only
	STATUS  mandatory
	DESCRIPTION
			"This SCSI device's SCSI ID."
	::= { strAgentDisksTblEntry 7 }

strAgentDiskSerialNo OBJECT-TYPE
	SYNTAX  DisplayString
	ACCESS  read-only
	STATUS  mandatory
	DESCRIPTION
			"The vendor's serial number for the device."
	::= { strAgentDisksTblEntry 8 }

strAgentDisknSectors OBJECT-TYPE
	SYNTAX  INTEGER
	ACCESS  read-only
	STATUS  mandatory
	DESCRIPTION
			"The number of sectors (512b) that this device can store."
	::= { strAgentDisksTblEntry 9 }

strAgentDiskDriveLetters OBJECT-TYPE
	SYNTAX  DisplayString
	ACCESS  read-only
	STATUS  mandatory
	DESCRIPTION
			"A list of the drive letters that have storage on this device."
	::= { strAgentDisksTblEntry 10 }

strAgentDiskSizeInMb OBJECT-TYPE
	SYNTAX  INTEGER
	ACCESS  read-only
	STATUS  mandatory
	DESCRIPTION
			"The capacity (in megabytes) of this device."
	::= { strAgentDisksTblEntry 11 }

strAgentDiskState OBJECT-TYPE
	SYNTAX  INTEGER { accessable(1), offline(2) }
	ACCESS  read-only
	STATUS  mandatory
	DESCRIPTION
			"The operational state of the device: accessable(1), off-line(2)."
	::= { strAgentDisksTblEntry 12 }

strAgentDiskXfersPerSec OBJECT-TYPE
	SYNTAX  INTEGER
	ACCESS  read-only
	STATUS  mandatory
	DESCRIPTION
			"the number of disk transfers per second reported by this device."
	::= { strAgentDisksTblEntry 13 }

strAgentDiskSmartCond OBJECT-TYPE
	SYNTAX  INTEGER { unknown(0), safe(1), degraded(2) }
	ACCESS  read-only
	STATUS  mandatory
	DESCRIPTION
			"The SMART condition of the device: unknown(0), safe(1), degraded(2)."
	::= { strAgentDisksTblEntry 14 }


-- __________________________  FLOPPY DEFINITION TABLE  __________________

strAgentnFloppies OBJECT-TYPE
	SYNTAX  INTEGER
	ACCESS  read-only
	STATUS  mandatory
	DESCRIPTION
			"The number of floppy drives listed in the subsequent Floppies table."
	::= { strAgent 9 }

strAgentFloppyTbl OBJECT-TYPE
	SYNTAX  SEQUENCE OF StrAgentFloppyEntry
	ACCESS  not-accessible
	STATUS  mandatory
	DESCRIPTION
			"Floppy table consisting of a list of floppy devices."
	::= { strAgent 10 }

strAgentFloppyTblEntry OBJECT-TYPE
	SYNTAX  StrAgentFloppyEntry
	ACCESS  not-accessible
	STATUS  mandatory
	::= { strAgentFloppyTbl 1 }

StrAgentFloppyEntry ::= SEQUENCE
	{
	strAgentFlopVendor  DisplayString,
	strAgentFlopDescription  DisplayString,
	strAgentFlopFirmware  DisplayString,
	strAgentFlopSerialNo  DisplayString
	}

strAgentFlopVendor OBJECT-TYPE
	SYNTAX  DisplayString
	ACCESS  read-only
	STATUS  mandatory
	DESCRIPTION
			"The vendor information for this floppy drive."
	::= { strAgentFloppyTblEntry 1 }

strAgentFlopDescription OBJECT-TYPE
	SYNTAX  DisplayString
	ACCESS  read-only
	STATUS  mandatory
	DESCRIPTION
			"The vendor's description of this floppy drive."
	::= { strAgentFloppyTblEntry 2 }

strAgentFlopFirmware OBJECT-TYPE
	SYNTAX  DisplayString
	ACCESS  read-only
	STATUS  mandatory
	DESCRIPTION
			"The description and version information from this floppy drive's firmware"
	::= { strAgentFloppyTblEntry 3 }

strAgentFlopSerialNo OBJECT-TYPE
	SYNTAX  DisplayString
	ACCESS  read-only
	STATUS  mandatory
	DESCRIPTION
			"The serial number of this floppy drive."
	::= { strAgentFloppyTblEntry 4 }


-- __________________________  VOLUME DEFINITION TABLE  __________________

strAgentnVolumes OBJECT-TYPE
	SYNTAX  INTEGER
	ACCESS  read-only
	STATUS  mandatory
	DESCRIPTION
			"The number of volumes listed in the subsequent Volumes table."
	::= { strAgent 11 }

strAgentVolumesTbl OBJECT-TYPE
	SYNTAX  SEQUENCE OF StrAgentVolumeEntry
	ACCESS  not-accessible
	STATUS  mandatory
	DESCRIPTION
			"Volume table consisting of a list of installed storage volumes."
	::= { strAgent 12 }

strAgentVolumesTblEntry OBJECT-TYPE
	SYNTAX  StrAgentVolumeEntry
	ACCESS  not-accessible
	STATUS  mandatory
	::= { strAgentVolumesTbl 1 }

StrAgentVolumeEntry ::= SEQUENCE
	{
	strAgentVolDriveLetter  DisplayString,
	strAgentVolDriveLabel  DisplayString,
	strAgentVolFileSystemType  DisplayString,
	strAgentVolCapacityInMb  INTEGER,
	strAgentVolClusterSize  INTEGER,
	strAgentVolPercentUsed  INTEGER,
	strAgentVolThreshold  INTEGER
	}

strAgentVolDriveLetter OBJECT-TYPE
	SYNTAX  DisplayString
	ACCESS  read-only
	STATUS  mandatory
	DESCRIPTION
			"The drive letter that allows access to this storage volume."
	::= { strAgentVolumesTblEntry 1 }

strAgentVolDriveLabel OBJECT-TYPE
	SYNTAX  DisplayString
	ACCESS  read-only
	STATUS  mandatory
	DESCRIPTION
			"The label assigned to this volume (for display purposes)."
	::= { strAgentVolumesTblEntry 2 }

strAgentVolFileSystemType OBJECT-TYPE
	SYNTAX  DisplayString
	ACCESS  read-only
	STATUS  mandatory
	DESCRIPTION
			"The type of file system configured for this volume (eg: FAT, NTFS)."
	::= { strAgentVolumesTblEntry 3 }

strAgentVolCapacityInMb OBJECT-TYPE
	SYNTAX  INTEGER
	ACCESS  read-only
	STATUS  mandatory
	DESCRIPTION
			"The size (in megabytes) of this storage volume."
	::= { strAgentVolumesTblEntry 4 }

strAgentVolClusterSize OBJECT-TYPE
	SYNTAX  INTEGER
	ACCESS  read-only
	STATUS  mandatory
	DESCRIPTION
			"The size of each cluster (storage unit) in sectors (512 bytes)."
	::= { strAgentVolumesTblEntry 5 }

strAgentVolPercentUsed OBJECT-TYPE
	SYNTAX  INTEGER
	ACCESS  read-only
	STATUS  mandatory
	DESCRIPTION
			"The percent of volume storage space used (monitored by the agent)."
	::= { strAgentVolumesTblEntry 6 }

strAgentVolThreshold OBJECT-TYPE
	SYNTAX  INTEGER
	ACCESS  read-write
	STATUS  mandatory
	DESCRIPTION
			"The threshold of volume storage space  (monitored by the agent,if not 100)"
	::= { strAgentVolumesTblEntry 7 }

-- __________________________  THRESHHOLD DEFINITION DATA  _______________

strAgentStateThreshhold OBJECT-TYPE
	SYNTAX  INTEGER
	ACCESS  read-write
	STATUS  mandatory
	DESCRIPTION
			"Indicates whether a drive that goes off-line should cause an alert.  (1 = yes)"
	::= { strAgent 13 }

-- strAgentSpaceThreshhold is replaced by adding a column in the Volume definition table in
-- the UNISYS AGENT version 1.3 and above.
strAgentSpaceThreshhold OBJECT-TYPE
	SYNTAX  INTEGER
	ACCESS  read-write
	STATUS  deprecated
	DESCRIPTION
			"Indicates the maximum disk consumption (%) allowed before an alert is issued.
			This object has been replaced by individual disk volume space thresholds for 
                        strAgent version 1.3 or higher. If the current Unisys Agents returns a -999 value, 
			this object is indicated being obsolete."
	::= { strAgent 14 }


strAgentCriticalVol OBJECT-TYPE
	SYNTAX  INTEGER
	ACCESS  read-only
	STATUS  mandatory
	DESCRIPTION
			"Indicates the total number of volumes in critical state." 	::= { strAgent 15 }


-- __________________________  TRAP DEFINITIONS  _________________________

strAgentIndex OBJECT-TYPE
	SYNTAX  INTEGER
	ACCESS  not-accessible
	STATUS  mandatory
	DESCRIPTION
			"Indicates the number (starting from 1) of the unit reported in an alert message."
	::= { strAgent 99 }

strAgentStateTrap TRAP-TYPE
	ENTERPRISE strAgent
	VARIABLES {
	           strAgentDiskState,
	           strAgentIndex
	          }
	DESCRIPTION
			"The disk drive is no longer accessable (off-line)."
	::= 1

--TRAP NUMBERS 2,12 has been replaced by 4,14 respectively in the 
--UNISYS AGENT version 1.3 and above.
strAgentSpaceTrap TRAP-TYPE
	ENTERPRISE strAgent
	VARIABLES {
	           strAgentVolPercentUsed,
	           strAgentIndex
	          }
	DESCRIPTION
			"The space used on the volume has exceeded the indicated threshhold."
	::= 2

strAgentVolSpaceTrap TRAP-TYPE
	ENTERPRISE strAgent
	VARIABLES {
	           strAgentVolDriveLetter,
	           strAgentVolPercentUsed,
	           strAgentVolThreshold,
	           strAgentCriticalVol 
	          }
	DESCRIPTION
			"The space used on the volume has exceeded the indicated threshhold."
	::= 4

strAgentSmartTrap TRAP-TYPE
	ENTERPRISE strAgent
	VARIABLES {
	           strAgentDiskSmartCond,
	           strAgentIndex
	          }
	DESCRIPTION
			"The condition of the disk drive has degraded.  It should be archived and replaced immediately to avoid data loss due to failure."
	::= 3

strAgentStateOkTrap TRAP-TYPE
	ENTERPRISE strAgent
	VARIABLES {
	           strAgentDiskState,
	           strAgentIndex
	          }
	DESCRIPTION
			"The disk drive is again accessable (on-line)."
	::= 11

strAgentSpaceOkTrap TRAP-TYPE
	ENTERPRISE strAgent
	VARIABLES {
	           strAgentVolPercentUsed,
	           strAgentIndex
	          }
	DESCRIPTION
			"The space used on the volume has returned to an acceptable level."
	::= 12

strAgentVolSpaceOkTrap TRAP-TYPE
	ENTERPRISE strAgent
	VARIABLES {
	           strAgentVolDriveLetter,
	           strAgentVolPercentUsed,
	           strAgentVolThreshold,
	           strAgentCriticalVol 
	          }
	DESCRIPTION
			"The space used on the volume has returned to an acceptable level."
	::= 14

strAgentSmartOKTrap TRAP-TYPE
	ENTERPRISE strAgent
	VARIABLES {
	           strAgentDiskSmartCond,
	           strAgentIndex
	          }
	DESCRIPTION
			"The degraded condition of the disk drive has cleared.  Continue to monitor this drive's performance to ensure the integrity of its data."
	::= 13


-- __________________  SYSTEM STATISTICS AGENT MIB  __________________

--
-- UNISYS System Agent MIB definition
-- 

sysAgent        OBJECT IDENTIFIER ::= { unisysOpen 11 }
 
-- sysAgent MIB
 
sysAgentVersion OBJECT-TYPE
	SYNTAX  INTEGER
	ACCESS  read-only
	STATUS  mandatory
	DESCRIPTION
			"The internal version number of this SNMP Extension Agent."
	::= { sysAgent 1 }

sysAgentRevision OBJECT-TYPE
	SYNTAX  INTEGER
	ACCESS  read-only
	STATUS  mandatory
	DESCRIPTION
			"The internal revision number of this SNMP Extension Agent."
	::= { sysAgent 2 }

sysAgentMIBVersion OBJECT-TYPE
	SYNTAX  INTEGER
	ACCESS  read-only
	STATUS  mandatory
	DESCRIPTION
			"The internal version number of the MIB for this SNMP Extension Agent."
	::= { sysAgent 3 }

sysAgentMIBRevision OBJECT-TYPE
	SYNTAX  INTEGER
	ACCESS  read-only
	STATUS  mandatory
	DESCRIPTION
			"The internal revision number of the MIB for this SNMP Extension Agent."
	::= { sysAgent 4 }

sysAgentCPUCyclesUsed OBJECT-TYPE
	SYNTAX  INTEGER
	ACCESS  read-only
	STATUS  mandatory
	DESCRIPTION
			"The percentage of CPU cycles used."
	::= { sysAgent 5 }

sysAgentPCICyclesUsed OBJECT-TYPE
	SYNTAX  INTEGER
	ACCESS  read-only
	STATUS  mandatory
	DESCRIPTION
			"The percentage of PCI bus cycles used."
	::= { sysAgent 6 }

sysAgentInterrupts OBJECT-TYPE
	SYNTAX  INTEGER
	ACCESS  read-only
	STATUS  mandatory
	DESCRIPTION
			"The number of interrupts processed per second."
	::= { sysAgent 7 }

sysAgentMemorySize OBJECT-TYPE
	SYNTAX  INTEGER
	ACCESS  read-only
	STATUS  mandatory
	DESCRIPTION
			"The size of memory in megabytes."
	::= { sysAgent 8 }

sysAgentMemoryUsed OBJECT-TYPE
	SYNTAX  INTEGER
	ACCESS  read-only
	STATUS  mandatory
	DESCRIPTION
			"The percentage of memory in use."
	::= { sysAgent 9 }

sysAgentPageFaults OBJECT-TYPE
	SYNTAX  INTEGER
	ACCESS  read-only
	STATUS  mandatory
	DESCRIPTION
			"The number of page faults per second."
	::= { sysAgent 10 }

sysAgentPageFaultThreshhold OBJECT-TYPE
	SYNTAX  INTEGER
	ACCESS  read-write
	STATUS  mandatory
	DESCRIPTION
			"The minimum number of page faults per second that will generate an alert."
	::= { sysAgent 11 }

sysAgentMemoryThreshhold OBJECT-TYPE
	SYNTAX  INTEGER
	ACCESS  read-write
	STATUS  mandatory
	DESCRIPTION
			"The minimum amount of memory consumption that will generate an alert."
	::= { sysAgent 12 }

sysAgentCpuThreshhold OBJECT-TYPE
	SYNTAX    INTEGER
	ACCESS      read-write
	STATUS      mandatory
	DESCRIPTION
		 	"The minimum percentage of CPU cycle used that will generate an alert."
	::= { sysAgent  13 }

sysAgentTotalNoCpu OBJECT-TYPE
	SYNTAX    INTEGER
	ACCESS      read-only
	STATUS      mandatory
	DESCRIPTION
		 	"The total number of CPU in the system."
	::= { sysAgent  14 }

sysAgentCPUsTbl OBJECT-TYPE
	SYNTAX  SEQUENCE OF SysAgentCPUEntry
	ACCESS  not-accessible
	STATUS  mandatory
	DESCRIPTION
			"CPU table consisting of a list of system CPUs and cycles used."
	::= { sysAgent 15 }

sysAgentCPUsTblEntry OBJECT-TYPE
	SYNTAX  SysAgentCPUEntry
	ACCESS  not-accessible
	STATUS  mandatory
	::= { sysAgentCPUsTbl 1 }

SysAgentCPUEntry ::= SEQUENCE
	{
	sysAgentCPUIndex  INTEGER,
	sysAgentCPUCycleUsed  INTEGER
	}

sysAgentCPUIndex OBJECT-TYPE
	SYNTAX  INTEGER
	ACCESS  read-only
	STATUS  mandatory
	DESCRIPTION
			"The index number of the CPU in the system."
	::= { sysAgentCPUsTblEntry 1 }

sysAgentCPUCycleUsed OBJECT-TYPE
	SYNTAX  INTEGER
	ACCESS  read-only
	STATUS  mandatory
	DESCRIPTION
			"The percentage of CPU cycles used by each CPU in the system."
	::= { sysAgentCPUsTblEntry 2 }




-- __________________________  TRAP DEFINITIONS  _________________________

sysAgentIndex OBJECT-TYPE
	SYNTAX  INTEGER
	ACCESS  not-accessible
	STATUS  mandatory
	DESCRIPTION
			"Indicates the number (starting from 1) of the unit reported in an alert message.  (Not used in this agent.)"
	::= { sysAgent 99 }

--TRAP NUMBERS 1,2,3,11,12,13 has been replaced by 4,5,6,14,15,16 respectively in the 
--UNISYS AGENT version 1.3 and above.

sysAgentMemTrap TRAP-TYPE
	ENTERPRISE sysAgent
	VARIABLES {
	           sysAgentMemoryUsed,
	           sysAgentIndex
	          }
	DESCRIPTION
			"The percentage of memory in use has exceeded the indicated threshhold."
	::= 1

sysAgentPageTrap TRAP-TYPE
	ENTERPRISE sysAgent
	VARIABLES {
	           sysAgentPageFaults,
	           sysAgentIndex
	          }
	DESCRIPTION
			"The number of page faults has exceeded the indicated threshhold."
	::= 2

sysAgentCpuTrap TRAP-TYPE
	ENTERPRISE sysAgent
	VARIABLES {
		   sysAgentCpuCycleUsed,
		   sysAgentIndex
		  }
	DESCRIPTION
			"The percentage of CPU Cycle used has exceeded the indicated threshold."
	::= 3

sysAgentMemoryTrap TRAP-TYPE
	ENTERPRISE sysAgent
	VARIABLES {
	           sysAgentMemoryUsed,
	          sysAgentMemoryThreshhold
	          }
	DESCRIPTION
			"The percentage of memory in use has exceeded the indicated threshhold."
	::= 4

sysAgentPageFaultTrap TRAP-TYPE
	ENTERPRISE sysAgent
	VARIABLES {
	           sysAgentPageFaults,
	           sysAgentPageFaultThreshhold
	          }
	DESCRIPTION
			"The number of page faults has exceeded the indicated threshhold."
	::= 5

sysAgentProcessorTrap TRAP-TYPE
	ENTERPRISE sysAgent
	VARIABLES {
		   sysAgentCpuCycleUsed,
		   sysAgentCpuThreshhold
		  }
	DESCRIPTION
			"The percentage of CPU Cycle used has exceeded the indicated threshold."
	::= 6

sysAgentMemOkTrap TRAP-TYPE
	ENTERPRISE sysAgent
	VARIABLES {
	           sysAgentMemoryUsed,
	           sysAgentIndex
	          }
	DESCRIPTION
			"The percentage of memory in use has returned to an accecptable level."
	::= 11

sysAgentPageOkTrap TRAP-TYPE
	ENTERPRISE sysAgent
	VARIABLES {
	           sysAgentPageFaults,
	           sysAgentIndex
	          }
	DESCRIPTION
			"The number of page faults has returned to an accecptable level."
	::= 12

sysAgentCpuOKTrap TRAP-TYPE
	ENTERPRISE sysAgent
	VARIABLES {
		   sysAgentCpuCycleUsed,
		   sysAgentIndex
		  }
	DESCRIPTION
			"The percentage of CPU Cycle used has returned to an acceptable level."
	::= 13



sysAgentMemoryOkTrap TRAP-TYPE
	ENTERPRISE sysAgent
	VARIABLES {
	           sysAgentMemoryUsed,
	           sysAgentMemoryThreshhold
	          }
	DESCRIPTION
			"The percentage of memory in use has returned to an accecptable level."
	::= 14

sysAgentPageFaultOkTrap TRAP-TYPE
	ENTERPRISE sysAgent
	VARIABLES {
	           sysAgentPageFaults,
	            sysAgentPageFaultThreshhold
	          }
	DESCRIPTION
			"The number of page faults has returned to an accecptable level."
	::= 15

sysAgentProcessorOKTrap TRAP-TYPE
	ENTERPRISE sysAgent
	VARIABLES {
		   sysAgentCpuCycleUsed,
		   sysAgentCpuThreshhold
		  }
	DESCRIPTION
			"The percentage of CPU Cycle used has returned to an acceptable level."
	::= 16


END
