--
-- 
--	INTEL CORPORATION PROPRIETARY INFORMATION
--
--	This software is supplied under the terms of a license agreement or
--	comment "nondisclosure agreement with Intel Corporation and may not be copied
--	or disclosed except in accordance with the terms of that agreement.
--
--	Copyright (c) 1999 Intel Corporation. All Rights Reserved.
--
--
--
--

	MIB-INTEL-OSPF DEFINITIONS ::= BEGIN

	IMPORTS
		Counter, IpAddress
			FROM RFC1155-SMI
		OBJECT-TYPE
			FROM RFC-1212

		mib2ext
			FROM INTEL-GEN-MIB;


	ospf OBJECT IDENTIFIER ::= { mib2ext 40 }


	--
	-- The IP OSPF routing table 
	--

	ospfIpRouteTable OBJECT-TYPE
		SYNTAX  SEQUENCE OF OspfIpRouteEntry
		ACCESS  not-accessible
		STATUS  optional
		DESCRIPTION
			"This entity's IP OSPF Routing table."
		::= { ospf 1 }

	ospfIpRouteEntry OBJECT-TYPE
		SYNTAX  OspfIpRouteEntry
		ACCESS  not-accessible
		STATUS  optional
		DESCRIPTION
			"A route to a particular destination."
		INDEX   { 
			  ospfIpRouteChassis, 
			  ospfIpRouteModule, 
			  ospfIpRouteInst, 
			  ospfIpRouteDest, 
			  ospfIpRouteMask,
			  ospfIpRouteIfIndex,
			  ospfIpRouteNextHop 
			}
		::= { ospfIpRouteTable 1 }

	OspfIpRouteEntry ::=
		SEQUENCE {
		ospfIpRouteChassis
			INTEGER,
		ospfIpRouteModule
			INTEGER,
		ospfIpRouteInst
			INTEGER,
		ospfIpRouteDest
			IpAddress,
		ospfIpRouteMask
			IpAddress,
		ospfIpRouteIfIndex
			INTEGER,
		ospfIpRouteNextHop
			IpAddress,
		ospfIpRoutePref
			INTEGER,
		ospfIpRouteCost
			INTEGER,
		ospfIpRouteState
			INTEGER,
		ospfIpRouteAge
			INTEGER,
		ospfIpRouteProtoType
			INTEGER
		}

	ospfIpRouteChassis OBJECT-TYPE
		SYNTAX  INTEGER
		ACCESS  read-only
		STATUS  optional
		DESCRIPTION
			"Chassis number in stack that contains the module."
		::= { ospfIpRouteEntry 1 }

	ospfIpRouteModule OBJECT-TYPE
		SYNTAX  INTEGER
		ACCESS  read-only
		STATUS  optional
		DESCRIPTION
			"Module number in the chassis."
		::= { ospfIpRouteEntry 2 }

	ospfIpRouteInst OBJECT-TYPE
		SYNTAX  INTEGER
		ACCESS  read-only
		STATUS  optional
		DESCRIPTION
			"OSPF routing table instance number."
		::= { ospfIpRouteEntry 3 }

	ospfIpRouteDest OBJECT-TYPE
		SYNTAX  IpAddress
		ACCESS  read-only
		STATUS  optional
		DESCRIPTION
			"The destination IP address of this route."
		::= { ospfIpRouteEntry 4 }

	ospfIpRouteMask OBJECT-TYPE
		SYNTAX  IpAddress
		ACCESS  read-only
		STATUS  optional
		DESCRIPTION
			"Indicate the mask to be logical-ANDed with the
			destination address before being compared to the
			value in the ospfIpRouteDest field."
		::= { ospfIpRouteEntry 5 }

	ospfIpRouteIfIndex OBJECT-TYPE
		SYNTAX  INTEGER
		ACCESS  read-only
		STATUS  optional
		DESCRIPTION
			"The interface that the frame is forwarded on."
		::= { ospfIpRouteEntry 6 }

	ospfIpRouteNextHop OBJECT-TYPE
		SYNTAX  IpAddress
		ACCESS  read-only
		STATUS  optional
		DESCRIPTION
			"The IP address of the next hop of this route."
		::= { ospfIpRouteEntry 7 }

	ospfIpRoutePref OBJECT-TYPE
		SYNTAX  INTEGER
		ACCESS  read-only
		STATUS  optional
		DESCRIPTION
			"The preference value for this route."
		::= { ospfIpRouteEntry 8 }

	ospfIpRouteCost OBJECT-TYPE
		SYNTAX  INTEGER
		ACCESS  read-only
		STATUS  optional
		DESCRIPTION
			"The OSPF routing cost for this route."
		::= { ospfIpRouteEntry 9 }

        ospfIpRouteState OBJECT-TYPE
		SYNTAX  INTEGER {
			active(1),
			inactive(2),
			dead(3)
		}
		ACCESS  read-write
		STATUS  optional
		DESCRIPTION
			"The current state of the route."
		::= { ospfIpRouteEntry 10 }

	ospfIpRouteAge OBJECT-TYPE
		SYNTAX  INTEGER
		ACCESS  read-only
		STATUS  optional
		DESCRIPTION
			"The number of seconds since this route was last 
			updated or otherwise detemined to be correct."
		::= { ospfIpRouteEntry 11 }

	ospfIpRouteProtoType OBJECT-TYPE
		SYNTAX  INTEGER {
			intraArea(1),
			interArea(2),
			ext1(3),
			ext2(4),
			type3Discard(5),
			type7Discard(6),
			other(7)
		}
		ACCESS  read-only
		STATUS  optional
		DESCRIPTION
			"The OSPF protocol type."
		::= { ospfIpRouteEntry 12 }


	--
	-- The OSPF counters table 
	--


	ospfIfCntTable OBJECT-TYPE
		SYNTAX  SEQUENCE OF OspfIfCntEntry
		ACCESS  not-accessible
		STATUS  optional
		DESCRIPTION
			"OSPF counters table."
		::= { ospf 2 }

	ospfIfCntEntry OBJECT-TYPE
		SYNTAX  OspfIfCntEntry
		ACCESS  not-accessible
		STATUS  optional
		DESCRIPTION
			"The OSPF counters for the interface."
		INDEX   { 
			  ospfCntChassis,
			  ospfCntModule,
			  ospfCntIfIpAddress,
			  ospfCntAddressLessIf
			}
		::= { ospfIfCntTable 1 }

	OspfIfCntEntry ::=
		SEQUENCE {
		ospfCntChassis
			INTEGER,
		ospfCntModule
			INTEGER,
		ospfCntIfIpAddress
			IpAddress,
		ospfCntAddressLessIf
			INTEGER,
		ospfCntBadVer
			Counter,
		ospfCntBadAreaId
			Counter,
		ospfCntMaskMismatch
			Counter,
		ospfCntAuthMismatch
			Counter,
		ospfCntAuthFail
			Counter,
		ospfCntExtOptMismatch
			Counter,
		ospfCntNSSAOptMismatch
			Counter,
		ospfCntNBMANeighbor
			Counter,
		ospfCntVirtNeighbor
			Counter,
		ospfCntHelloMismatch
			Counter,
		ospfCntDeadMismatch
			Counter,
		ospfCntBadType
			Counter,
		ospfCntBadChksum
			Counter,
		ospfCntBadLen
			Counter,
		ospfCntTooShort
			Counter,
		ospfCntDRPktMismatch
			Counter,
		ospfCntMulticastVL
			Counter,
		ospfCntDestAddr
			Counter,
		ospfCntOwnAddr
			Counter,
		ospfCntHelloTx
			Counter,
		ospfCntHelloRx
			Counter,
		ospfCntLSReqTx
			Counter,
		ospfCntLSUpdateTx
			Counter,
		ospfCntLSAckTx
			Counter,
		ospfCntLSReqRx
			Counter,
		ospfCntLSUpdateRx
			Counter,
		ospfCntLSAckRx
			Counter
		}


	ospfCntChassis OBJECT-TYPE
		SYNTAX  INTEGER
		ACCESS  read-only
		STATUS  optional
		DESCRIPTION
			"Chassis number in stack that contains the module."
		::= { ospfIfCntEntry 1 }

	ospfCntModule OBJECT-TYPE
		SYNTAX  INTEGER
		ACCESS  read-only
		STATUS  optional
		DESCRIPTION
			"Module number in the chassis."
		::= { ospfIfCntEntry 2 }

	ospfCntIfIpAddress OBJECT-TYPE
		SYNTAX	IpAddress
		ACCESS	read-only
		STATUS	optional
		DESCRIPTION
			"The IP address of this OSPF interface."
		::= { ospfIfCntEntry 3 }

	ospfCntAddressLessIf OBJECT-TYPE
		SYNTAX	INTEGER
		ACCESS	read-only
		STATUS	optional
		DESCRIPTION
			"This variable takes the value 0 on interfaces
			 with IP addresses, and the corresponding value of
			 ifIndex for interfaces having no IP address."
		::= { ospfIfCntEntry 4 }
	
	ospfCntBadVer OBJECT-TYPE
		SYNTAX	Counter
		ACCESS	read-write
		STATUS	optional
		DESCRIPTION
			"The number of Bad OSPF Version configuration errors."
		::= { ospfIfCntEntry 5 }
	
	ospfCntBadAreaId OBJECT-TYPE
		SYNTAX	Counter
		ACCESS	read-write
		STATUS	optional
		DESCRIPTION
			"The number of Bad Area Id configuration errors."
		::= { ospfIfCntEntry 6 }
	
	ospfCntMaskMismatch OBJECT-TYPE
		SYNTAX	Counter
		ACCESS	read-write
		STATUS	optional
		DESCRIPTION
			"The number of Net Mask Mismatch configuration errors."
		::= { ospfIfCntEntry 7 }
	
	ospfCntAuthMismatch OBJECT-TYPE
		SYNTAX	Counter
		ACCESS	read-write
		STATUS	optional
		DESCRIPTION
			"The number of Authentication Type Mismatch configuration errors."
		::= { ospfIfCntEntry 8 }
	
	ospfCntAuthFail OBJECT-TYPE
		SYNTAX	Counter
		ACCESS	read-write
		STATUS	optional
		DESCRIPTION
			"The number of Authentication Failure configuration errors."
		::= { ospfIfCntEntry 9 }
	
	ospfCntExtOptMismatch OBJECT-TYPE
		SYNTAX	Counter
		ACCESS	read-write
		STATUS	optional
		DESCRIPTION
			"The number of External Option Mismatch configuration errors."
		::= { ospfIfCntEntry 10 }
	
	ospfCntNSSAOptMismatch OBJECT-TYPE
		SYNTAX	Counter
		ACCESS	read-write
		STATUS	optional
		DESCRIPTION
			"The number of NSSA Option Mismatch configuration errors."
		::= { ospfIfCntEntry 11 }
	
	ospfCntNBMANeighbor OBJECT-TYPE
		SYNTAX	Counter
		ACCESS	read-write
		STATUS	optional
		DESCRIPTION
			"The number of Unknown NBMA Neighbour configuration errors."
		::= { ospfIfCntEntry 12 }
	
	ospfCntVirtNeighbor OBJECT-TYPE
		SYNTAX	Counter
		ACCESS	read-write
		STATUS	optional
		DESCRIPTION
			"The number of Unknown Virtual Neighbour configuration errors."
		::= { ospfIfCntEntry 13 }
	
	ospfCntHelloMismatch OBJECT-TYPE
		SYNTAX	Counter
		ACCESS	read-write
		STATUS	optional
		DESCRIPTION
			"The number of Hello Interval Mismatch configuration errors."
		::= { ospfIfCntEntry 14 }
	
	ospfCntDeadMismatch OBJECT-TYPE
		SYNTAX	Counter
		ACCESS	read-write
		STATUS	optional
		DESCRIPTION
			"The number of Dead Interval Mismatch configuration errors."
		::= { ospfIfCntEntry 15 }
	
	ospfCntBadType OBJECT-TYPE
		SYNTAX	Counter
		ACCESS	read-write
		STATUS	optional
		DESCRIPTION
			"The number of Bad Packet Type errors."
		::= { ospfIfCntEntry 16 }
	
	ospfCntBadChksum OBJECT-TYPE
		SYNTAX	Counter
		ACCESS	read-write
		STATUS	optional
		DESCRIPTION
			"The number of Bad Packet Checksum errors."
		::= { ospfIfCntEntry 17 }
	
	ospfCntBadLen OBJECT-TYPE
		SYNTAX	Counter
		ACCESS	read-write
		STATUS	optional
		DESCRIPTION
			"The number of Bad Packet Length errors."
		::= { ospfIfCntEntry 18 }
	
	ospfCntTooShort OBJECT-TYPE
		SYNTAX	Counter
		ACCESS	read-write
		STATUS	optional
		DESCRIPTION
			"The number of Packet Too Short errors."
		::= { ospfIfCntEntry 19 }
	
	ospfCntDRPktMismatch OBJECT-TYPE
		SYNTAX	Counter
		ACCESS	read-write
		STATUS	optional
		DESCRIPTION
			"The number of DR-destined packets received on non-DR interfaces."
		::= { ospfIfCntEntry 20 }
	
	ospfCntMulticastVL OBJECT-TYPE
		SYNTAX	Counter
		ACCESS	read-write
		STATUS	optional
		DESCRIPTION
			"The number of OSPF multicast-destined packets received on VL."
		::= { ospfIfCntEntry 21 }
	
	ospfCntDestAddr OBJECT-TYPE
		SYNTAX	Counter
		ACCESS	read-write
		STATUS	optional
		DESCRIPTION
			"The number of unknown destination addresses received on the interface."
		::= { ospfIfCntEntry 22 }
	
	ospfCntOwnAddr OBJECT-TYPE
		SYNTAX	Counter
		ACCESS	read-write
		STATUS	optional
		DESCRIPTION
			"The number of ow ip source addresses received on the interface."
		::= { ospfIfCntEntry 23 }
	
	ospfCntHelloTx OBJECT-TYPE
		SYNTAX	Counter
		ACCESS	read-write
		STATUS	optional
		DESCRIPTION
			"The number of Hello packets send on the interface"
		::= { ospfIfCntEntry 24 }
	
	ospfCntHelloRx OBJECT-TYPE
		SYNTAX	Counter
		ACCESS	read-write
		STATUS	optional
		DESCRIPTION
			"The number of Hello packets received on the interface"
		::= { ospfIfCntEntry 25 }

	ospfCntLSReqTx OBJECT-TYPE
		SYNTAX	Counter
		ACCESS	read-write
		STATUS	optional
		DESCRIPTION
			"The number of Link State requests send on the interface"
		::= { ospfIfCntEntry 26 }
	
	ospfCntLSUpdateTx OBJECT-TYPE
		SYNTAX	Counter
		ACCESS	read-write
		STATUS	optional
		DESCRIPTION
			"The number of Link State updates send on the interface"
		::= { ospfIfCntEntry 27 }
	
	ospfCntLSAckTx OBJECT-TYPE
		SYNTAX	Counter
		ACCESS	read-write
		STATUS	optional
		DESCRIPTION
			"The number of Link State acks send on the interface"
		::= { ospfIfCntEntry 28 }
	
	ospfCntLSReqRx OBJECT-TYPE
		SYNTAX	Counter
		ACCESS	read-write
		STATUS	optional
		DESCRIPTION
			"The number of Link State requests received on the interface"
		::= { ospfIfCntEntry 29 }
	
	ospfCntLSUpdateRx OBJECT-TYPE
		SYNTAX	Counter
		ACCESS	read-write
		STATUS	optional
		DESCRIPTION
			"The number of Link State updates received on the interface"
		::= { ospfIfCntEntry 30 }
	
	ospfCntLSAckRx OBJECT-TYPE
		SYNTAX	Counter
		ACCESS	read-write
		STATUS	optional
		DESCRIPTION
			"The number of Link State acks received on the interface"
		::= { ospfIfCntEntry 31 }
	
	END
