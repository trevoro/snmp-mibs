Wellfleet-SMDS-MIB DEFINITIONS ::= BEGIN

-- Created by mdl2asn version 3.1
-- Creation date: Wed Aug 30 16:47:39 EDT 1995


    IMPORTS

      Counter
        FROM RFC1155-SMI
      OBJECT-TYPE
        FROM RFC-1212
      wfWanGroup
        FROM Wellfleet-COMMON-MIB;


    wfSmdsCircuitTable OBJECT-TYPE
        SYNTAX	SEQUENCE OF WfSmdsCircuitEntry
        ACCESS	not-accessible
        STATUS	mandatory
        DESCRIPTION
                "The Wellfleet SMDS Circuit Record"
        ::= { wfWanGroup 3 }

    wfSmdsCircuitEntry OBJECT-TYPE
        SYNTAX	WfSmdsCircuitEntry
        ACCESS	not-accessible
        STATUS	mandatory
        DESCRIPTION
                "per Wellfleet circuit SMDS configuration parameters and
                counters"
        INDEX	{ wfSmdsCircuitID }
        ::= { wfSmdsCircuitTable 1 }

    WfSmdsCircuitEntry ::= SEQUENCE {
    	    wfSmdsCircuitDelete
    		INTEGER,
    	    wfSmdsCircuitDisable
    		INTEGER,
    	    wfSmdsCircuitState
    		INTEGER,
    	    wfSmdsCircuitID
    		INTEGER,
    	    wfSmdsCircuitIndivAddr
    		OCTET STRING,
    	    wfSmdsCircuitGroupAddr
    		OCTET STRING,
    	    wfSmdsCircuitArpAddr
    		OCTET STRING,
    	    wfSmdsCircuitDisableHrtbtPoll
    		INTEGER,
    	    wfSmdsCircuitHrtbtPollInterval
    		INTEGER,
    	    wfSmdsCircuitHrtbtPollDownCount
    		INTEGER,
    	    wfSmdsCircuitDisableNetMgmt
    		INTEGER,
    	    wfSmdsCircuitSipL3ReceivedIndividualDAs
    		Counter,
    	    wfSmdsCircuitSipL3ReceivedGAs
    		Counter,
    	    wfSmdsCircuitSipL3SentIndividualDAs
    		Counter,
    	    wfSmdsCircuitSipL3SentGAs
    		Counter,
    	    wfSmdsCircuitSipL3VersionSupport
    		INTEGER,
    	    wfSmdsCircuitDisableAddrVerify
    		INTEGER,
    	    wfSmdsCircuitAddrVerifyDiscards
    		Counter
        }

    wfSmdsCircuitDelete OBJECT-TYPE
        SYNTAX	INTEGER {
    		    created(1),
    		    deleted(2)
    		}
        ACCESS	read-write
        STATUS	mandatory
        DESCRIPTION
                "create/delete parameter, dflt = created"
        DEFVAL	{ created }
        ::= { wfSmdsCircuitEntry 1 }

    wfSmdsCircuitDisable OBJECT-TYPE
        SYNTAX	INTEGER {
    		    enabled(1),
    		    disabled(2)
    		}
        ACCESS	read-write
        STATUS	mandatory
        DESCRIPTION
                "enable/disable parameter, dflt = enabled"
        DEFVAL	{ enabled }
        ::= { wfSmdsCircuitEntry 2 }

    wfSmdsCircuitState OBJECT-TYPE
        SYNTAX	INTEGER {
    		    up(1),
    		    down(2),
    		    init(3),
    		    notpresent(4)
    		}
        ACCESS	read-only
        STATUS	mandatory
        DESCRIPTION
                "SMDS state variable, Up, Down Init, Not Present"
        DEFVAL	{ notpresent }
        ::= { wfSmdsCircuitEntry 3 }

    wfSmdsCircuitID OBJECT-TYPE
        SYNTAX	INTEGER(1..1023)
        ACCESS	read-only
        STATUS	mandatory
        DESCRIPTION
                "cct number for this instance"
        ::= { wfSmdsCircuitEntry 4 }

    wfSmdsCircuitIndivAddr OBJECT-TYPE
        SYNTAX	OCTET STRING
        ACCESS	read-write
        STATUS	mandatory
        DESCRIPTION
                "SMDS E.164 Individual address for this Wellfleet
                circuit - must be 8 octets long"
        ::= { wfSmdsCircuitEntry 5 }

    wfSmdsCircuitGroupAddr OBJECT-TYPE
        SYNTAX	OCTET STRING
        ACCESS	read-write
        STATUS	mandatory
        DESCRIPTION
                "SMDS E.164 Group address for this Wellfleet
                circuit - must be 8 octets long"
        ::= { wfSmdsCircuitEntry 6 }

    wfSmdsCircuitArpAddr OBJECT-TYPE
        SYNTAX	OCTET STRING
        ACCESS	read-write
        STATUS	mandatory
        DESCRIPTION
                "SMDS E.164 ARP address for this Wellfleet
                circuit - must be 8 octets long"
        ::= { wfSmdsCircuitEntry 7 }

    wfSmdsCircuitDisableHrtbtPoll OBJECT-TYPE
        SYNTAX	INTEGER {
    		    enabled(1),
    		    disabled(2)
    		}
        ACCESS	read-write
        STATUS	mandatory
        DESCRIPTION
                "determine use of DXI heartbeat poll"
        DEFVAL	{ disabled }
        ::= { wfSmdsCircuitEntry 8 }

    wfSmdsCircuitHrtbtPollInterval OBJECT-TYPE
        SYNTAX	INTEGER(6..2147483647)
        ACCESS	read-write
        STATUS	mandatory
        DESCRIPTION
                "heartbeat polling messages get sent every this many
                seconds - we don't want the polling interval to be
                less than or equal to the unacknowledgment timer, which
                is 5 seconds"
        DEFVAL	{ 10 }
        ::= { wfSmdsCircuitEntry 9 }

    wfSmdsCircuitHrtbtPollDownCount OBJECT-TYPE
        SYNTAX	INTEGER(1..2147483647)
        ACCESS	read-write
        STATUS	mandatory
        DESCRIPTION
                "if this many consecutive heartbeat polling messages
                go unacknowledged, log an event declaring the line
                down"
        DEFVAL	{ 3 }
        ::= { wfSmdsCircuitEntry 10 }

    wfSmdsCircuitDisableNetMgmt OBJECT-TYPE
        SYNTAX	INTEGER {
    		    enabled(1),
    		    disabled(2)
    		}
        ACCESS	read-write
        STATUS	mandatory
        DESCRIPTION
                "determine use of LMI network management"
        DEFVAL	{ disabled }
        ::= { wfSmdsCircuitEntry 11 }

    wfSmdsCircuitSipL3ReceivedIndividualDAs OBJECT-TYPE
        SYNTAX	Counter
        ACCESS	read-only
        STATUS	mandatory
        DESCRIPTION
                "The total number of individually addressed SIP Level 3 PDUs
                received from the remote system across the SNI. The total
                includes only unerrored L3PDUs."
        ::= { wfSmdsCircuitEntry 12 }

    wfSmdsCircuitSipL3ReceivedGAs OBJECT-TYPE
        SYNTAX	Counter
        ACCESS	read-only
        STATUS	mandatory
        DESCRIPTION
                "The total number of group addressed SIP Level 3 PDUs
                received from the remote system across the SNI.  The
                total includes only unerrored L3PDUs."
        ::= { wfSmdsCircuitEntry 13 }

    wfSmdsCircuitSipL3SentIndividualDAs OBJECT-TYPE
        SYNTAX	Counter
        ACCESS	read-only
        STATUS	mandatory
        DESCRIPTION
                "The number of individually addressed SIP Level 3 PDUs
                that have been sent by this system across the SNI."
        ::= { wfSmdsCircuitEntry 14 }

    wfSmdsCircuitSipL3SentGAs OBJECT-TYPE
        SYNTAX	Counter
        ACCESS	read-only
        STATUS	mandatory
        DESCRIPTION
                "The number of group addressed SIP L3PDUs that have been
                sent by this system across the SNI."
        ::= { wfSmdsCircuitEntry 15 }

    wfSmdsCircuitSipL3VersionSupport OBJECT-TYPE
        SYNTAX	INTEGER {
    		    version(1)
    		}
        ACCESS	read-only
        STATUS	mandatory
        DESCRIPTION
                "A value which indicates the version(s) of SIP
                that this interface supports.  The value is a sum.
                This sum initially takes the value zero.  For each
                version, V, that this interface supports, 2 raised
                to (V - 1) is added to the sum. For example, a
                port supporting versions 1 and 2 would have a
                value of (2^(1-1)+2^(2-1))=3.  The
                SipL3VersionSupport is effectively a bit mask with
                Version 1 equal to the least significant bit (LSB)."
        DEFVAL	{ version }
        ::= { wfSmdsCircuitEntry 16 }

    wfSmdsCircuitDisableAddrVerify OBJECT-TYPE
        SYNTAX	INTEGER {
    		    enabled(1),
    		    disabled(2)
    		}
        ACCESS	read-write
        STATUS	mandatory
        DESCRIPTION
                "This object enables/disables verification checking
                of destination addresses in received packets."
        DEFVAL	{ disabled }
        ::= { wfSmdsCircuitEntry 17 }

    wfSmdsCircuitAddrVerifyDiscards OBJECT-TYPE
        SYNTAX	Counter
        ACCESS	read-only
        STATUS	mandatory
        DESCRIPTION
                "This is the count of SMDS PDUs discarded due to
                mismatched group or individual addresses"
        ::= { wfSmdsCircuitEntry 18 }

    END  -- Wellfleet-SMDS-MIB
