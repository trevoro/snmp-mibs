-- *****************************************************************************
-- Unisphere-Data-ADDRESS-POOL-MIB
--
-- Unisphere Networks Enterprise MIB
-- Address Pool MIB
--
-- Copyright (c) 1999 Redstone Communications, Incorporated.
-- Copyright (c) 1999, 2002 Unisphere Networks, Incorporated.
-- All Rights Reserved.
-- *****************************************************************************

Unisphere-Data-ADDRESS-POOL-MIB DEFINITIONS ::= BEGIN

IMPORTS
    MODULE-IDENTITY, OBJECT-TYPE, Integer32, IpAddress, NOTIFICATION-TYPE
        FROM SNMPv2-SMI
    RowStatus, TruthValue
        FROM SNMPv2-TC
    MODULE-COMPLIANCE, OBJECT-GROUP, NOTIFICATION-GROUP
        FROM SNMPv2-CONF
    usdRouterName
        FROM Unisphere-Data-ROUTER-MIB
    usDataMibs
        FROM Unisphere-Data-MIBs;

usdAddressPoolMIB MODULE-IDENTITY
    LAST-UPDATED "200205061838Z"  -- 06-May-02 02:38 PM EDT
    ORGANIZATION "Unisphere Networks, Inc."
    CONTACT-INFO
        "       Unisphere Networks, Inc.
        Postal: 10 Technology Park Road
                Westford, MA 01886
                USA
        Tel:    +1 978 589 5800
        E-mail: mib@UnisphereNetworks.com"
    DESCRIPTION
        "The Address Pool MIB for the Unisphere Networks enterprise."
    -- Revision History
    REVISION    "200205061838Z"  -- 06-May-02 02:38 PM EDT  - RX 3.3
    DESCRIPTION
        "Added usdAddressPoolProfileTable to support an address pool with
        multiple address ranges."
    REVISION    "200105021157Z"  -- 02-May-01 07:57 AM EDT  - RX 3.2
    DESCRIPTION
        "Added pool exhaustion variables and notifications for high pool
        utilization and pool exhaustion."
    REVISION    "200104271500Z"  -- 27-Apr-01 11:00 AM EDT  - RX 3.0
    DESCRIPTION
        "Fixed range on usdAddressPoolNextPoolIndex."
    REVISION      "9906010000Z"  -- 01-Jun-99               - RX 1.3
    DESCRIPTION
        "Initial version of this MIB module."
    ::= { usDataMibs 21 }


-- +++++++++++++++++++++++++++++++++++++++++++++++++++++++++++++++++++++++++++++
-- Textual conventions
-- +++++++++++++++++++++++++++++++++++++++++++++++++++++++++++++++++++++++++++++
-- No textual conventions are defined in this MIB.


-- +++++++++++++++++++++++++++++++++++++++++++++++++++++++++++++++++++++++++++++
-- Managed object groups
-- +++++++++++++++++++++++++++++++++++++++++++++++++++++++++++++++++++++++++++++
usdAddressPoolObjects       OBJECT IDENTIFIER ::= {usdAddressPoolMIB 1}
usdAddressPool              OBJECT IDENTIFIER ::= {usdAddressPoolObjects 1}

-- +++++++++++++++++++++++++++++++++++++++++++++++++++++++++++++++++++++++++++++
-- Managed objects for Address Pools
-- +++++++++++++++++++++++++++++++++++++++++++++++++++++++++++++++++++++++++++++
usdAddressPoolTable OBJECT-TYPE
    SYNTAX      SEQUENCE OF UsdAddressPoolEntry
    MAX-ACCESS  not-accessible
    STATUS      current
    DESCRIPTION
        "A table of IP address pool configuration entries."
    ::= { usdAddressPool 1 }

usdAddressPoolEntry OBJECT-TYPE
    SYNTAX      UsdAddressPoolEntry
    MAX-ACCESS  not-accessible
    STATUS      current
    DESCRIPTION
        "An entry describing an IP address pool configuration."
    INDEX     { usdAddressPoolIndex }
    ::= { usdAddressPoolTable 1 }

UsdAddressPoolEntry ::= SEQUENCE {
    usdAddressPoolIndex                 Integer32,
    usdAddressPoolName                  OCTET STRING,
    usdAddressPoolRowStatus             RowStatus,
    usdAddressPoolStart                 IpAddress,
    usdAddressPoolEnd                   IpAddress,
    usdAddressPoolSize                  Integer32,
    usdAddressPoolInUse                 Integer32,
    usdAddressPoolHighUtilThreshold     Integer32,
    usdAddressPoolAbatedUtilThreshold   Integer32,
    usdAddressPoolUtilPct               INTEGER,
    usdAddressPoolTrapEnable            TruthValue }

usdAddressPoolIndex OBJECT-TYPE
    SYNTAX      Integer32 (1..2147483647)
    MAX-ACCESS  not-accessible
    STATUS      current
    DESCRIPTION
        "An arbitrary integer index that distinguishes this address pool."
    ::= { usdAddressPoolEntry 1 }

usdAddressPoolRowStatus OBJECT-TYPE
    SYNTAX      RowStatus
    MAX-ACCESS  read-create
    STATUS      current
    DESCRIPTION
        "Controls creation/deletion of address pools.
        
        Only value 'active' will be observed with GET.
        Only values 'createAndGo' and 'destroy' are supported for SET.

        Once created, entry content cannot be modified except by deleting and
        recreating an entry with the same index."
    ::= { usdAddressPoolEntry 2 }

usdAddressPoolName OBJECT-TYPE
    SYNTAX      OCTET STRING (SIZE(1..16))
    MAX-ACCESS  read-create
    STATUS      current
    DESCRIPTION
        "The name of this address pool.  Represents textual information taken
        from the NVT ASCII graphics character set (codes 32 through 126)."
    REFERENCE
        "RFC 854: NVT ASCII character set."
    ::= { usdAddressPoolEntry 3 }

usdAddressPoolStart OBJECT-TYPE
    SYNTAX      IpAddress
    MAX-ACCESS  read-create
    STATUS      deprecated
    DESCRIPTION
        "The starting IP address for the range of addresses comprising this
        pool."
    ::= { usdAddressPoolEntry 4 }

usdAddressPoolEnd OBJECT-TYPE
    SYNTAX      IpAddress
    MAX-ACCESS  read-create
    STATUS      deprecated
    DESCRIPTION
        "The ending IP address for the range of addresses comprising this pool."
    ::= { usdAddressPoolEntry 5 }

usdAddressPoolSize OBJECT-TYPE
    SYNTAX      Integer32
    MAX-ACCESS  read-only
    STATUS      deprecated
    DESCRIPTION
        "The number of addresses available in this pool."
    ::= { usdAddressPoolEntry 6 }

usdAddressPoolInUse OBJECT-TYPE
    SYNTAX      Integer32
    MAX-ACCESS  read-only
    STATUS      deprecated
    DESCRIPTION
        "The number of addresses currently allocated from this pool."
    ::= { usdAddressPoolEntry 7 }

usdAddressPoolHighUtilThreshold  OBJECT-TYPE
    SYNTAX      Integer32 (1..100)
    MAX-ACCESS  read-create
    STATUS      current
    DESCRIPTION
        "The value of address pool utilization, where if reached for the first
        time, will generate a high address pool utilization event to the
        management entity on this system.
 
        The value of this object must be greater than the value of
        usdAddressPoolAbatedUtilThreshold."
    DEFVAL { 85 }
    ::= { usdAddressPoolEntry 8 }

usdAddressPoolAbatedUtilThreshold OBJECT-TYPE 
    SYNTAX      Integer32 (1..100)
    MAX-ACCESS  read-create
    STATUS      current
    DESCRIPTION
        "The value of address pool utilization that is used to determine when to
        generate an abated address pool utilization event notification to the
        management entity on this system.

        The value of this object must be less than the value of the
        usdAddressPoolHighUtilThreshold.

        The abated address pool utilization event is sent once if the high
        address pool utilization threshold is reached and utilization falls to
        the value of this object."
    DEFVAL    { 75 }
    ::= { usdAddressPoolEntry 9 }

usdAddressPoolUtilPct OBJECT-TYPE
    SYNTAX      INTEGER (1..100)
    MAX-ACCESS  read-only
    STATUS      current 
    DESCRIPTION
        "The current address utilization for this pool."
    ::= { usdAddressPoolEntry 10 }
    
usdAddressPoolTrapEnable OBJECT-TYPE
    SYNTAX      TruthValue
    MAX-ACCESS  read-create
    STATUS      current
    DESCRIPTION
        "The configuration setting for address pool notifications.  Setting this
        object to enable(1) will enable the sending of usdAddressPool event
        notifications to the management entity on this device.  Setting this
        object to false(2) will disable event notification reports."
    ::= { usdAddressPoolEntry 11 }
 

--
-- Address pool profile table.
--
usdAddressPoolProfileTable OBJECT-TYPE
    SYNTAX      SEQUENCE OF UsdAddressPoolProfileEntry
    MAX-ACCESS  not-accessible
    STATUS      current
    DESCRIPTION
        "A table of IP address pool profile entries."
    ::= { usdAddressPool 3 }

usdAddressPoolProfileEntry OBJECT-TYPE
    SYNTAX      UsdAddressPoolProfileEntry
    MAX-ACCESS  not-accessible
    STATUS      current
    DESCRIPTION
        "An IP address pool profile entry."
    INDEX     { usdAddressPoolIndex,
                usdAddressPoolProfileIndex }
    ::= { usdAddressPoolProfileTable 1 }

UsdAddressPoolProfileEntry ::= SEQUENCE { 
    usdAddressPoolProfileIndex      Integer32,
    usdAddressPoolProfileRowStatus  RowStatus,
    usdAddressPoolProfileStart      IpAddress,
    usdAddressPoolProfileEnd        IpAddress,
    usdAddressPoolProfileSize       Integer32,
    usdAddressPoolProfileInUse      Integer32 }

usdAddressPoolProfileIndex OBJECT-TYPE
    SYNTAX      Integer32 (1..2147483647)
    MAX-ACCESS  not-accessible
    STATUS      current
    DESCRIPTION
        "A monotonically increasing integer for the sole purpose of indexing
        entries within the named address pool."
    ::= { usdAddressPoolProfileEntry 1 }

usdAddressPoolProfileRowStatus OBJECT-TYPE
    SYNTAX      RowStatus
    MAX-ACCESS  read-create
    STATUS      current
    DESCRIPTION
        "Controls creation/deletion of address pools.
        
        Only value 'active' will be observed with GET.
        Only values 'createAndGo' and 'destroy' are supported for SET.

        Once created, entry content cannot be modified except by deleting and
        recreating an entry with the same index."
    ::= { usdAddressPoolProfileEntry 2 }

usdAddressPoolProfileStart OBJECT-TYPE
    SYNTAX      IpAddress
    MAX-ACCESS  read-create
    STATUS      current
    DESCRIPTION
        "The starting IP address for the range of addresses comprising this
        pool."
    ::= { usdAddressPoolProfileEntry 3 }

usdAddressPoolProfileEnd OBJECT-TYPE
    SYNTAX      IpAddress
    MAX-ACCESS  read-create
    STATUS      current
    DESCRIPTION
        "The ending IP address for the range of addresses comprising this pool."
    ::= { usdAddressPoolProfileEntry 4 }

usdAddressPoolProfileSize OBJECT-TYPE
    SYNTAX      Integer32
    MAX-ACCESS  read-only
    STATUS      current
    DESCRIPTION
        "The number of addresses available in this pool."
    ::= { usdAddressPoolProfileEntry 5 }

usdAddressPoolProfileInUse OBJECT-TYPE
    SYNTAX Integer32
    MAX-ACCESS read-only
    STATUS current
    DESCRIPTION
        "The number of addresses currently allocated from this pool."
    ::= { usdAddressPoolProfileEntry 6 }


--
-- usdAddressPoolIndex selection for creating new address pools 
--
usdAddressPoolNextPoolIndex OBJECT-TYPE
    SYNTAX      Integer32 (0..2147483647)
    MAX-ACCESS  read-only
    STATUS      current
    DESCRIPTION
        "Coordinate usdAddressPoolIndex value allocation for entries in
        usdAddressPoolTable.

        A GET of this object returns the next available usdAddressPoolIndex value
        to be used to create an entry in the associated usdAddressPoolTable; or
        zero, if no valid usdAddressPoolIndex is available.  This object returns
        a value of zero when it is the lexicographic successor of a varbind
        presented in an SNMP GETNEXT or GETBULK request, for which circumstance
        it is assumed that a new index allocation is unintended.

        Successive GETs will return different values, thus avoiding collisions
        among cooperating management clients seeking to create table entries
        simultaneously."
    ::= { usdAddressPool 2 }


-- +++++++++++++++++++++++++++++++++++++++++++++++++++++++++++++++++++++++++++++
-- Notification control objects
-- +++++++++++++++++++++++++++++++++++++++++++++++++++++++++++++++++++++++++++++
-- No notifications are defined in this MIB.  Placeholder follows.
-- usdAddressPoolTrapControl      OBJECT IDENTIFIER ::= { usdAddressPoolMIB 2 }

-- +++++++++++++++++++++++++++++++++++++++++++++++++++++++++++++++++++++++++++++
-- Notifications
-- +++++++++++++++++++++++++++++++++++++++++++++++++++++++++++++++++++++++++++++
-- The following two OBJECT IDENTIFIERS are used to define SNMPv2 
-- Notifications that are easily translated into SNMPv1 Traps.

usdAddressPoolTraps            OBJECT IDENTIFIER ::= { usdAddressPoolMIB 3 }
usdAddressPoolTrapPrefix       OBJECT IDENTIFIER ::= { usdAddressPoolTraps 0 }

usdAddressPoolHighAddrUtil NOTIFICATION-TYPE
    OBJECTS {
        usdRouterName,
        usdAddressPoolName,
        usdAddressPoolSize,
        usdAddressPoolInUse,
        usdAddressPoolUtilPct }
    STATUS      current
    DESCRIPTION
        "Reports address pool utilization has reached the configured high
        utilization threshold."
    ::= { usdAddressPoolTrapPrefix 1 }

usdAddressPoolAbatedAddrUtil NOTIFICATION-TYPE
    OBJECTS {
        usdRouterName,
        usdAddressPoolName,
        usdAddressPoolSize,
        usdAddressPoolInUse,
        usdAddressPoolUtilPct }
    STATUS      current
    DESCRIPTION
        "Reports address pool utilization has fallen to the configured abated
        threshold level."
    ::= { usdAddressPoolTrapPrefix 2 }

usdAddressPoolNoAddresses NOTIFICATION-TYPE
    OBJECTS {
        usdRouterName,
        usdAddressPoolName,
        usdAddressPoolSize }
    STATUS      current
    DESCRIPTION
        "Reports address pool has exhausted its supply of addresses.  This trap
        is issued every time a request is made to allocate an address from a
        fully utilized pool."
    ::= { usdAddressPoolTrapPrefix 3 }


-- ++++++++++++++++++++++++++++++++++++++++++++++++++++++++++++++++++++++
-- Conformance information
-- ++++++++++++++++++++++++++++++++++++++++++++++++++++++++++++++++++++++
usdAddressPoolMIBConformance
             OBJECT IDENTIFIER ::= { usdAddressPoolMIB 4 }
usdAddressPoolMIBCompliances
             OBJECT IDENTIFIER ::= { usdAddressPoolMIBConformance 1 }
usdAddressPoolMIBGroups
             OBJECT IDENTIFIER ::= { usdAddressPoolMIBConformance 2 }

--
-- compliance statements
--
usdAddressPoolCompliance MODULE-COMPLIANCE
    STATUS      obsolete
    DESCRIPTION
        "Obsolete compliance statement for systems providing local address
        pools.  This statement became obsolete when pool exhaustion variables
        and notifications were added."
    MODULE   -- this module
    MANDATORY-GROUPS {
        usdAddressPoolGroup }
    ::= { usdAddressPoolMIBCompliances 1 }                             -- RX 1.3

usdAddressPoolCompliance2 MODULE-COMPLIANCE
    STATUS      obsolete
    DESCRIPTION
        "Obsolete compliance statement for systems providing local address
        pools.  This statement became obsolete when support was added for
        address pools with multiple address ranges."
    MODULE   -- this module
    MANDATORY-GROUPS {
        usdAddressPoolGroup2,
        usdAddressPoolTrapGroup }
    ::= { usdAddressPoolMIBCompliances 2 }                             -- RX 3.2

usdAddressPoolCompliance3 MODULE-COMPLIANCE
    STATUS      current
    DESCRIPTION
        "The compliance statement for systems providing local address pools."
    MODULE   -- this module
    MANDATORY-GROUPS {
        usdAddressPoolGroup3,
        usdAddressPoolTrapGroup }
    ::= { usdAddressPoolMIBCompliances 3 }                             -- RX 3.3


--
-- units of conformance
--
usdAddressPoolGroup OBJECT-GROUP
    OBJECTS {
        usdAddressPoolRowStatus,
        usdAddressPoolName,
        usdAddressPoolStart,
        usdAddressPoolEnd,
        usdAddressPoolSize,
        usdAddressPoolInUse,
        usdAddressPoolNextPoolIndex }
    STATUS      obsolete
    DESCRIPTION
        "Obsolete collection of objects providing management of local address
        pools.  This group became obsolete when pool exhaustion variables and
        notifications were added."
    ::= { usdAddressPoolMIBGroups 1 }

usdAddressPoolGroup2 OBJECT-GROUP
    OBJECTS {
        usdAddressPoolRowStatus,
        usdAddressPoolName,
        usdAddressPoolStart,
        usdAddressPoolEnd,
        usdAddressPoolSize,
        usdAddressPoolInUse,
        usdAddressPoolNextPoolIndex,
        usdAddressPoolHighUtilThreshold,
        usdAddressPoolAbatedUtilThreshold,
        usdAddressPoolUtilPct,
        usdAddressPoolTrapEnable }
    STATUS      deprecated
    DESCRIPTION
        "The basic collection of objects providing management of local address
        pools.  This group was deprecated when support was added for address
        pools with multiple address ranges."
    ::= { usdAddressPoolMIBGroups 2 }

usdAddressPoolTrapGroup NOTIFICATION-GROUP
    NOTIFICATIONS {
        usdAddressPoolHighAddrUtil,
        usdAddressPoolAbatedAddrUtil,
        usdAddressPoolNoAddresses }
    STATUS      current
    DESCRIPTION
        "The notifications providing alarms for high pool utilization and pool
        exhaustion of local address pools."
    ::= { usdAddressPoolMIBGroups 3 }

usdAddressPoolGroup3 OBJECT-GROUP
    OBJECTS {
        usdAddressPoolRowStatus,
        usdAddressPoolName,
        usdAddressPoolNextPoolIndex,
        usdAddressPoolHighUtilThreshold,
        usdAddressPoolAbatedUtilThreshold,
        usdAddressPoolUtilPct,
        usdAddressPoolTrapEnable,
        usdAddressPoolProfileRowStatus,
        usdAddressPoolProfileStart,
        usdAddressPoolProfileEnd,
        usdAddressPoolProfileSize,
        usdAddressPoolProfileInUse }
    STATUS      current
    DESCRIPTION
        "The basic collection of objects providing management of local address
        pools."
    ::= { usdAddressPoolMIBGroups 4 }

END
