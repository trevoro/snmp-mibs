-- *****************************************************************
-- Moxa Active Ethernet I/O Server MIB
--
-- 11-04-2009
--
-- Copyright (c) 2005 by Moxa Networking Co., Ltd.
-- All rights reserved.
-- *****************************************************************

MOXA-IO-E2210-MIB DEFINITIONS ::= BEGIN
    IMPORTS
	TRAP-TYPE FROM RFC-1215
        enterprises, Unsigned32, Integer32, MODULE-IDENTITY, OBJECT-TYPE FROM SNMPv2-SMI;
   
-- 1.3.6.1.4.1.8691.10.2210
    e2210   MODULE-IDENTITY
    LAST-UPDATED "200911041600Z"
    ORGANIZATION "Moxa Networking,Inc."
    CONTACT-INFO
            "Postal: Moxa Networking,Inc.
             Fl.4, No.135,Lane 235,Pao-Chiao Rd.
             Shing Tien City,Taipei,Taiwan,R.O.C
             Tel: +866-2-89191230 "
    DESCRIPTION
            "The MIB module for Moxa ioLogik Active Ethernet I/O specific information." 
    REVISION "200911041600Z"
    DESCRIPTION
            "Updated version of this MIB."
           ::= { e2000 2210 }    -- 1.3.6.1.4.1.8691.10.2210

-- 1.3.6.1.4.1.8691
    moxa OBJECT IDENTIFIER ::= { enterprises 8691 }

-- 1.3.6.1.4.1.8691.10
    e2000 OBJECT IDENTIFIER ::= { moxa 10 }

-- 1.3.6.1.4.1.8691.10.2210.1
    totalChannelNumber OBJECT-TYPE
        SYNTAX Integer32 (1..20)
        MAX-ACCESS read-only
        STATUS current
        DESCRIPTION
            "Total I/O channels."
        ::= { e2210 1 }

-- 1.3.6.1.4.1.8691.10.2210.2
    serverModel OBJECT-TYPE
        SYNTAX OCTET STRING
        MAX-ACCESS read-only
        STATUS current
        DESCRIPTION
            "The I/O server model."
        ::= { e2210 2 }

-- 1.3.6.1.4.1.8691.10.2210.3
    systemTime OBJECT-TYPE
        SYNTAX Integer32
        MAX-ACCESS read-only
        STATUS current
        DESCRIPTION
            "I/O server up time (in seconds)."
        ::= { e2210 3 }

-- 1.3.6.1.4.1.8691.10.2210.4
    firmwareVersion OBJECT-TYPE
        SYNTAX OCTET STRING
        MAX-ACCESS read-only
        STATUS current
        DESCRIPTION
            "The firmware version."
        ::= { e2210 4 }

----------------------------------------------------------------
-- I/O
-- 1.3.6.1.4.1.8691.10.2210.10          
    e2210monitor OBJECT IDENTIFIER ::= { e2210 10 }
----------------------------------------------------------------
-- DI channel
diTable OBJECT-TYPE
        SYNTAX          SEQUENCE OF DiEntry
        MAX-ACCESS      not-accessible
        STATUS          current
        DESCRIPTION     
            "The DI channel monitor table"
        ::= { e2210monitor 1 }

diEntry OBJECT-TYPE
        SYNTAX          DiEntry
        MAX-ACCESS      not-accessible
        STATUS          current
        DESCRIPTION     
            "The DI channel monitor item"
        INDEX { diIndex }
        ::= { diTable 1 }

DiEntry ::= 
        SEQUENCE {
                diIndex     Integer32,
                diType      Integer32,
                diMode      Integer32,
                diStatus    Unsigned32,
                diFilter    Integer32,
                diTrigger   Integer32,
                diCntStart  Integer32   
                 }

diIndex OBJECT-TYPE
        SYNTAX          Integer32  (0..11)
		MAX-ACCESS 		not-accessible
        STATUS          current
        DESCRIPTION     
            "The channel DI index."
        ::= { diEntry 1 }   
        
diType OBJECT-TYPE
        SYNTAX          Integer32  (0)
        MAX-ACCESS      read-only
        STATUS          current
        DESCRIPTION     "The channel DI type. 0=DI, 1=DO"
        ::= { diEntry 2 }
        
diMode OBJECT-TYPE
        SYNTAX          Integer32  (0..1)
        MAX-ACCESS      read-write
        STATUS          current
        DESCRIPTION     "The channel DI mode. 0=DI, 1=Event Counter"
        ::= { diEntry 3 }
        
diStatus OBJECT-TYPE
        SYNTAX          Unsigned32 (0..4294967295)
        MAX-ACCESS      read-only
        STATUS          current
        DESCRIPTION     "The channel DI status. 0=Off, 1=On in DI mode or N=Count in counter mode"
        ::= { diEntry 4 }
        
diFilter OBJECT-TYPE
        SYNTAX          Integer32  (1..2000)
        MAX-ACCESS      read-write
        STATUS          current
        DESCRIPTION     "The channel DI counter filter. unit=0.5ms"
        ::= { diEntry 5 }

diTrigger OBJECT-TYPE
        SYNTAX          Integer32  (0..1)
        MAX-ACCESS      read-write
        STATUS          current
        DESCRIPTION     "The channel DI counter trigger level. 0=L2H, 1=H2L"
        ::= { diEntry 6 }

diCntStart OBJECT-TYPE
        SYNTAX          Integer32 (0..1)
        MAX-ACCESS      read-write
        STATUS          current
        DESCRIPTION     "The channel DI counter start/stop. 0=stop, 1=start"
        ::= { diEntry 7 }
----------------------------------------------------------------        
-- do-00
doTable OBJECT-TYPE
        SYNTAX          SEQUENCE OF DOEntry
        MAX-ACCESS      not-accessible
        STATUS          current
        DESCRIPTION     "The DO channel monitor table"
        ::= { e2210monitor 2 }

doEntry OBJECT-TYPE
        SYNTAX          DOEntry
        MAX-ACCESS      not-accessible
        STATUS          current
        DESCRIPTION     "The DO channel monitor item"
        INDEX { doIndex }
        ::= { doTable 1 }

DOEntry ::= SEQUENCE {
                    doIndex         Integer32,
                    doType          Integer32,
                    doMode          Integer32,
                    doStatus        Unsigned32,
                    doLowWidth      Integer32,
                    doHighWidth     Integer32,
                    doPulseStart    Integer32
                     }

doIndex OBJECT-TYPE
        SYNTAX          Integer32 (0..7)
		MAX-ACCESS 		not-accessible
        STATUS          current
        DESCRIPTION     "The channel DO index."
        ::= { doEntry 1 }

doType OBJECT-TYPE
        SYNTAX          Integer32 (1)
        MAX-ACCESS      read-only
        STATUS          current
        DESCRIPTION     "The channel DO type. 0=DI, DO=1"
        ::= { doEntry 2 }
        
doMode OBJECT-TYPE
        SYNTAX          Integer32 (0..1)
        MAX-ACCESS      read-write
        STATUS          current
        DESCRIPTION     "The channel DO mode. 0=DO, 1=Pulse Output"
        ::= { doEntry 3 }
        
doStatus OBJECT-TYPE
        SYNTAX          Unsigned32 (0..4294967295)
        MAX-ACCESS      read-write
        STATUS          current
        DESCRIPTION     "The channel DO status. 0=Off, 1=On in DO mode or N=Count in pulse mode"
        ::= { doEntry 4 }
        
doLowWidth OBJECT-TYPE
        SYNTAX          Integer32 (1..2000)
        MAX-ACCESS      read-write
        STATUS          current
        DESCRIPTION     "The channel DO signal low width. unit=0.5ms"
        ::= { doEntry 5 }
        
doHighWidth OBJECT-TYPE
        SYNTAX          Integer32 (1..2000)
        MAX-ACCESS      read-write
        STATUS          current
        DESCRIPTION     "The channel DO signal high width. unit=0.5ms"
        ::= { doEntry 6 }

doPulseStart OBJECT-TYPE
        SYNTAX          Integer32 (0..1)
        MAX-ACCESS      read-write
        STATUS          current
        DESCRIPTION     "The channel DO pulse start/stop. 0=stop, 1=start"
        ::= { doEntry 7 }
----------------------------------------------------------------
-- Click&Go
-- 1.3.6.1.4.1.8691.10.2210.10.4
	logicSettings OBJECT IDENTIFIER ::= { e2210monitor 4 }

----------------------------------------------------------------
irTable OBJECT-TYPE
			SYNTAX 			SEQUENCE OF IrEntry
			MAX-ACCESS 		not-accessible
			STATUS 			current
			DESCRIPTION		"Table of internal registers"
			::= { logicSettings 1 }
                         
irEntry OBJECT-TYPE
		SYNTAX			IrEntry
		MAX-ACCESS 		not-accessible
		STATUS 			current
		DESCRIPTION		"Table of internal registers"
		INDEX { irIndex }
		::= { irTable 1 }

IrEntry ::= SEQUENCE {
		irIndex		    Integer32,
		irName			OCTET STRING,
		irValue		    Integer32
}                  

irIndex OBJECT-TYPE
		SYNTAX 			Integer32 (0..23)
		MAX-ACCESS 		read-only
		STATUS 			current
		DESCRIPTION		"The internal register index."
		::= { irEntry 1 }

irName OBJECT-TYPE
		SYNTAX 			OCTET STRING (SIZE (0..19))
		MAX-ACCESS 		read-write
		STATUS 			current
		DESCRIPTION		"The internal register description."
		::= { irEntry 2 }

irValue OBJECT-TYPE
		SYNTAX 			Integer32(0..255)
		MAX-ACCESS 		read-write
		STATUS 			current
		DESCRIPTION		"The internal register working value."
		::= { irEntry 3 }
     
                         
----------------------------------------------------------------
---------------------------------------------------------------
-- DI TRAP
-- 1.3.6.1.4.1.8691.10.2210.11
    diChannelTrap OBJECT IDENTIFIER ::= { e2210 11 }

----------------------------------------------------------------
diChannel0 TRAP-TYPE
    ENTERPRISE      e2210
    DESCRIPTION     "The channel di-00 status. 0=Off, 1=On in DI mode or N=Count in counter mode"
    ::= 1

diChannel1 TRAP-TYPE
    ENTERPRISE      e2210
    DESCRIPTION     "The channel di-01 status. 0=Off, 1=On in DI mode or N=Count in counter mode"
    ::= 2

diChannel2 TRAP-TYPE
    ENTERPRISE      e2210
    DESCRIPTION     "The channel di-02 status. 0=Off, 1=On in DI mode or N=Count in counter mode"
    ::= 3

diChannel3 TRAP-TYPE
    ENTERPRISE      e2210
    DESCRIPTION     "The channel di-03 status. 0=Off, 1=On in DI mode or N=Count in counter mode"
    ::= 4

diChannel4 TRAP-TYPE
    ENTERPRISE      e2210
    DESCRIPTION     "The channel di-04 status. 0=Off, 1=On in DI mode or N=Count in counter mode"
    ::= 5

diChannel5 TRAP-TYPE
    ENTERPRISE      e2210
    DESCRIPTION     "The channel di-05 status. 0=Off, 1=On in DI mode or N=Count in counter mode"
    ::= 6

diChannel6 TRAP-TYPE
    ENTERPRISE      e2210
    DESCRIPTION     "The channel di-06 status. 0=Off, 1=On in DI mode or N=Count in counter mode"
    ::= 7

diChannel7 TRAP-TYPE
    ENTERPRISE      e2210
    DESCRIPTION     "The channel di-07 status. 0=Off, 1=On in DI mode or N=Count in counter mode"
    ::= 8

diChannel8 TRAP-TYPE
    ENTERPRISE      e2210
    DESCRIPTION     "The channel di-08 status. 0=Off, 1=On in DI mode or N=Count in counter mode"
    ::= 9

diChannel9 TRAP-TYPE
    ENTERPRISE      e2210
    DESCRIPTION     "The channel di-09 status. 0=Off, 1=On in DI mode or N=Count in counter mode"
    ::= 10

diChannel10 TRAP-TYPE
    ENTERPRISE      e2210
    DESCRIPTION     "The channel di-10 status. 0=Off, 1=On in DI mode or N=Count in counter mode"
    ::= 11

diChannel11 TRAP-TYPE
    ENTERPRISE      e2210
    DESCRIPTION     "The channel di-11 status. 0=Off, 1=On in DI mode or N=Count in counter mode"
    ::= 12


----------------------------------------------------------------
-- DO TRAP
-- 1.3.6.1.4.1.8691.10.2210.12
    doChannelTrap OBJECT IDENTIFIER ::= { e2210 12 }

----------------------------------------------------------------
doChannel0 TRAP-TYPE
    ENTERPRISE      e2210
    DESCRIPTION     "The channel do-00 status. 0=Off, 1=On in DO mode or N=Count in pulse mode"
    ::= 1

doChannel1 TRAP-TYPE
    ENTERPRISE      e2210
    DESCRIPTION     "The channel do-01 status. 0=Off, 1=On in DO mode or N=Count in pulse mode"
    ::= 2

doChannel2 TRAP-TYPE
    ENTERPRISE      e2210
    DESCRIPTION     "The channel do-02 status. 0=Off, 1=On in DO mode or N=Count in pulse mode"
    ::= 3

doChannel3 TRAP-TYPE
    ENTERPRISE      e2210
    DESCRIPTION     "The channel do-03 status. 0=Off, 1=On in DO mode or N=Count in pulse mode"
    ::= 4

doChannel4 TRAP-TYPE
    ENTERPRISE      e2210
    DESCRIPTION     "The channel do-04 status. 0=Off, 1=On in DO mode or N=Count in pulse mode"
    ::= 5

doChannel5 TRAP-TYPE
    ENTERPRISE      e2210
    DESCRIPTION     "The channel do-05 status. 0=Off, 1=On in DO mode or N=Count in pulse mode"
    ::= 6

doChannel6 TRAP-TYPE
    ENTERPRISE      e2210
    DESCRIPTION     "The channel do-06 status. 0=Off, 1=On in DO mode or N=Count in pulse mode"
    ::= 7

doChannel7 TRAP-TYPE
    ENTERPRISE      e2210
    DESCRIPTION     "The channel do-07 status. 0=Off, 1=On in DO mode or N=Count in pulse mode"
    ::= 8

----------------------------------------------------------------
-- Message TRAP
-- 1.3.6.1.4.1.8691.10.2210.13
	messageTrap OBJECT IDENTIFIER ::= { e2210 13 }

----------------------------------------------------------------
activeMessageTrap TRAP-TYPE
	ENTERPRISE 		e2210
	DESCRIPTION 	"The SNMP trap with active message"
	::= 1

END
