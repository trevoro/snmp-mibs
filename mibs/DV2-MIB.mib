--___________________________________________________________________________
--
-- Title: GDC DV2 MIB.
-- Date : January 1997
-- Version:  4.30

--
-- Boot Area
--
--
-- This ASN file comprises two major areas. The BOOT area is used for the boot
-- strap code and this comprises a subset of the total file. The area which is
-- only used for the boot code is marked with comments.
--
-- Description Fields
--
--
-- The description fields have three functions in this MIB definition:-
--
--   . They are used to provide the "pop-up" help messages for the DV2 switch
--     code.
--
--   . They are available for use by the NMS to display help information for the
--     elements.
--
--   . They describe the actual MIB elements.
--
--  
--
--___________________________________________________________________________
-- Revision History     :
-- NOTE:
-- Please maintain this section in reverse chronological order. Be
-- specific as to where the changes are made but do not place markers
-- (search patterns) in the file.
-- Please have an MR for all changes and clear all changes through
-- Dave Danenberg (or a proxy for him) before putting changes into
-- a build.
--
--       Date   Engineer     AR #       Description
-- ==========================================================================
--      06-Mar-98 J. Turner  AR-NONE: Make mpro/slave ".asn" compatible. Add "eth", "qtlim"
--                              "not-ready", "INTEGER" for gauge, link-3. Billing and OAM
--                              are uneffected. Make qeDocTunClp entry #31 to match Slave MIB
--			        definition. QeDoc only in slave.
-- #13  05-Mar-98 J. Turner   AR4953 Update: Add "none" to slot0PhyLstChngPrevLnkStat
--                              define. Also add DEFVAL{  } to new variables.
--      03-05-98  M. Apergis  AR5330 :  Rename NTM state machine states from
--					acquisition to acquisition-wide-band, and from
--					reference-out-of-range to acquisition-narrow-band
-- #11  19-Feb-98 J. Turner   AR4954 : Fixed clockAlarm trap variable list sequence.
--	02/16/98  N. Walker   AR5194  added j2QualClock
--      13-Feb-98 J. Turner   AR4953 : Add INTEGER description, more comments.
--      12-Feb-98 J. Turner   AR4953 : Correct slot0PhyLstChngPrevLnkStat and
-- 				slot0PhyLstChngLnkNum table order.
--
-- #10  06-Feb-98 J. Turner   AR4954 : Create SysClkAlarmErr variable. Include in
--                              clockAlarm trap with primary and secondary info
--                              and inService variables.
-- 			      AR4951 : Create limTypeStatus variable. Include in
--			      	lim-fault and lim-oper traps.
--			      AR4953 : Create slot0PhyLstChngPrevLnkStat and
-- 				slot0PhyLstChngLnkNum variables. Include in the
--				linkChanged trap.
--	1/22/98  A.S.Arvind   DT related svcCellRateTable & svcTrafficTable
--	1/22/98  A.S.Arvind   DT related JH port of ubr(0)
--	12/23/97  A. Lorenzo	AR5094
--		  Modified oamVcaBlockSize & oamVcbBlockSize to
--		  oamVcaPMBlockSize & oamVcbPMBlockSize.
--      12-11-97  N. Walker
--		  Added CRC counter for J2 LIM
--    06-Nov-97   J. Turner  AR none?
-- 		  Add ipas(149) and ipap(150) to slot0PhyType entry lists
--	11-05-97  T.Pandolfe - Added trap types for AIS/RDI Received
--	10-27-97  A. Lorenzo - Added tables oamVcaTable and oamVcbTable
-- 		  for OAM configuration. Also modified table
--		  oamLoopbackTable to add oamLoopbackLocId.
--    15-Oct-97   J. Turner  AR 4167
--                Add Y2K changes, deprecate DateTimeString usage and replace
--		  with DateAndTime convention. Add "M2" suffix to replaced MIBs.
--     10-07-97   A.S.Arvind Retry Period  Added svcRetryPeriod in svc group
--      9-25-97   A.S.Arvind/D.Garg AR4321/4322 minor spelling fix & again
--                made HalfConCnt READ-ONLY
--	5-21-97	  D. Mathur added OamDisable Mib element AR4331
--      5-20-97   D. Santoli  AR 1610
--                Removed SIZE (8) from pdh E3 trail trace PhysAddress objects.
--
--      5-20-97   M. Beauchemin
--		  Added DQ7 trap for flash access problem
--		  AR3918
--      5-05-97	  W. Emery
--                Added sdhCIdleCell
--                Ref:  AR 4356, CTR 960307
--
--      4-24-97   Y. Wang
--                AR4418. Obsolete BillLogToDisk.
--                AR4419. Change billLost to read-write access. 
--
--	4-3-97	  R. Anumulapally  AR4352
--		  Added ranges to the following:
--		   fRelConfN391, fRelConfN392, fRelConfN393, fRelConfT391, fRelConfT392.
--		  Renamed dxdoc links A and B to links 0 and 1.
--
--      4-01-97  Y. Cusson
--                Added mpeg LIM MIB information.
--
--      3-25-97   B. Forrest
--                Merged changes in mpro line of devempment
--
--	3-18-97	  N. Walker
--		  changed frdoc back to frac
--
--	3-13-97	  B. Forrest
--                moved the added oids sdhStmSts and sdhAPSOnOff to bottom
--                of table where they belong.
--
--	2-19-97	  M. Beauchemin   added support for mac2 shelf
--
--	2/17/97	  M. Apergis
--		  Changed NTM Config and Status tables for E1 NTM.
--
--      1-29-97   C. Liang
--                Added "routeLoadFail" and "DTLLoadFail" two new traps
--
--      1-28-97   C. Liang
--                Added yet more fields in VC status table
--
--	01-27-97  R. Byczko
--		  Made adjustments to support STS-3c/STM-1 LIM, close cousin to OC3 LIM,
--		  except first is electrical and second is optical.
--
--      1-25-97   C. Liang
--                Added more fields in VC status table
--
--      1-14-97   C. Liang
--                Changed max pt-mpt trees from 10 to 3; max parties from 3 to 10
--
--      1-13-97   C. Liang
--                Obsoleted following objects:
--                pvcForwardCellRateTotal, pvcForwardCellRateAvailable,
--                pvcBackwardCellRateAvailable, svcForwardCellRateTotal,
--                svcForwardCellRateAvailable, svcBackwardCellRateAvailable
--
--      02-12-97  M. Beauchemin
--		  Corrected Sdh table putting sdhStmSts and sdhAPSOnOff last
--
--      01-20-97  J. Wenninger  Made the following changes to support
--				CAS on the DS1 LIM
--				Added signaling states to the ds1V2LimType
--				entry.
--				Added link0 -> link3 to the ds1V2TxClkSel
--				entry.
--      01-31-97  R. Byczko
--                Made adjustments to support STS-3c/STM-1 LIM, close cousin to
--                OC3 LIM, except first is electrical and second is optical.
--
--      12-26-96  M. Apergis
--		  Added "stop" option to sysLkState.
--
--      12-23-96  C. Liang
--                Changed max leaves per tree range from (0..16) to (0..500)
--
--      12-20-96  Y. Wang
--                Add billDirControl object for billing direction control.
--
--      12-2-96   C. Liang
--                Added MIB items for pt-mpt SVC support
--
--      12-20-96  Y. Wang
--                Add billDirControl object for billing direction control.
--
--	12-11-96  E. Zheng
--                Changed pvcForwardCellRateTotal to read-only object (AR 3958)
--                Changed svcForwardCellRateTotal to read-only object (AR 3958)
--
--      12-06-96  P. Cassella
--                Added new Slot0PSUType for MAC2 shelf      
--
--	10-29-96  E. Zheng
--                Changed max pt-pt SVC connections from 500 to 750
--                Changed max Sap connections from 500 to 750
--                Changed max sPvc Id from 500 to 750
--
--      10-26-96  Y. Wang
--                Change DOC card name from frac to frdoc.
--
--	10-21-96  C. Liang
--                Changed default max pt-pt SVC connections from 100 to 25
--
--      10-17-96  C. Liang
--                Added "idle" option to SAP status
--
--      10-07-96  W. Emery
--		  Removed ranges for vidEncBitRate and audBitRate
--                Changed units in DESCRIPTION fields of vidEncBitRate
--                and audBitRate (from Kbps to bps)
--
--      09-25-96  G. McCabe
--		  Edit Cac Mib Descriptions
--
--      09-24-96  M. Beauchemin
--		  changed ACS define from ac to as
--
--      9-09-96   X. Liu
--                Changed SpvcId configuration range from 500 into
--                750 for ACP and ACS
--
--      09-13-96  X. Liu
--                Merged new Mib items for ACP and ACS support from
--		  Continnus/V420H build into CVS
--
--	09-11-96  J. Wenninger
--	          Corrected AR 3439: Changed JT2 to J2, Also changed
--		  "Quality of Clock" to "System Timing Reference"
--
--	09-11-96  J. Wenninger
--	CHANGE:   Added a new entry for SI (SCF) LIM
--
--	09-11-96  P.Cassella
--	CHANGE:   Added a new entry for j2 LIM as well as TRAP definition
--
--      09-05-96  G. McCabe
--                Added Cac Mib items.
--      8-31-96   X. Liu
--                Changed Mib items of memory block ID configurations
--                into 4k, 16k and 64k options.
--
--      08-21-96  P. Cassella          Added Ber for DS1_2C
--                                     search for pkc
--
--      9-03-96   Y. Wang
--                Add local-45Mbps(3), and local-34Mbps(4)
--                to "hssiClockSrc". Change "hssiClockSrc" to read-write
--                Change "hssiType" to read-write.
--
--
--     08-13-96   D. Stack              1.174
--                Added "ceStr3" to indicate Stratum3.
--
--      8-09-96   D. Stack    AR3082
--                Defaulted ceDstSlot and veDstSlot to be -1 so a
--                funky '-' will appear as the slot number
--
--      08-06-96  J. Wojdak            Continuus-9
--                Added CAC/EBT mods.
--
--      7-29-96   C. Liang
--                Changed "sPvcLink" range from 0..3 to 0..15 to support MSCC
--
--      7-25-96   W. Emery    N/A
--                Added vh320 LIM MIB information; made 'video' the
--                only option for veMode
--
--      07-23-96  X. Liu
--                Added Mib items for ACP and ACS support.
--
--	7-22-96   C. Liang
--                Added "svcRestart" to allow a Restart to be sent to the
--                link every time link comes up
--
--      7-22-96   C. Liang
--                Added "svcE164Addr" for each SAP indicating the E164 address
--                of the other side of the link
--
--      7-12-96   C. Liang
--                Disallow SCR Clp0+1 Tagging option
--
--      7-9-96    C. Liang
--                Split usage of cell buffers into "signalling quota" and
--                "IP quota" (non-signalling).
--
--      6-25-96   C. Liang
--                Added new traps "svcQsaalUpDown", "svcQsaalReset" and
--                "svcT309Expiry".
--
--      6-21-96   C. Liang
--                Added "trap on state change" option to SPVC alert config
--
--      6-12-96   X. Liu      N/A        ???
--      CHANGE:   Added xpDiscardCells to
--                Switch Fabric status table.
--
--	6-4-96    C. Liang
--                Integrated SVC 3.1 and MSCC
--
--      05-28-96  G. McCabe
--                Added Cac Mib items.
--
--      5-6-96    X. Liu      N/A        1.153
--      CHANGE:   Added sdhStmSts and sdhAPSOnOff to
--                SDHSonet config table.
--
--	5-6-96	  J. Huang
--		  Added VPI/VPCI Mapping and QoS associated VPCI selection
--		  ELEMENTS: svcVpiMapping & svcQosRoute
--
--      4-3-96    C. Liang
--      CHANGE:   Make "svcHalfConCnt" writable also
--
--      3-27-96   D. Chen
--      CHANGE:   AR 2802: Change ILMI 'connected' state to 'idle'.
--
--      3-18-96   C. Liang
--      CHANGE:   Changed options of "LoadRoutes"
--
--      3-14-96   C. Liang
--      CHANGE:   Changed default value of T308 timer from 15 to 30 seconds
--
--	3-14-96	  M. Khalil  AR2968
--	CHANGE:   Added a new TRAP definition for detection of
--		  duplicate IP address.
--      03-14-96  D. Stack    N/A       1.153
--      CHANGE:   Fixed merge problems
--
--      03-14-96  X. Liu      N/A       1.152
--      CHANGE:   Add MIB element "unknown" for link
--                management connectivity status.
--
--      03-13-96  D. Stack   AR3061      1.151
--	CHANGE:   Removed all ceLeafxxx,veLeafxxx,
--                ceSrcxxx, and veSrcxxx MIB variables
--                as they were confusing to the user.
--                They have been replaced with equivalent
--                variables in dv2ce.c.
--
--      03-13-96  D. Stack   AR3059      1.151
--                Changed enumerations for pvcDirection.
--
--	03-12-96  D. Chen    2725        1.150
--	CHANGE:   Add OAM Statis MIB items to OAM table.
--
--	03-06-96  D. Chen    3011        1.149
--	CHANGE:   Add lmiOnOff to ILMI config table. Also added
--                MIB elements for link mamt.
--
--	03-05-96  D. Chen  2823,         1.148
--	CHANGE:   Added lmiPrefix to ILMI config table.            
--
--	03-05-96  D. Stack   N/A	1.147
--	CHANGE:   Added SRTS status variables cePriVal, ceSecVal,
--                ceClkSel, and ceClkInp.
--
--	03-01-96  S. Hegde/J. Huang
--	CHANGE:	  Added svcSwtch item for UNI31 and IISP
--
--	02-28-96  J. Huang
--	CHANGES:  Added support for multiple signalling
--
--	02-27-96  D. Stack   AR3026     1.145
--	CHANGE:   Since cannot enumerate 0, offset ceSrcLink,
--                veSrcLink, ceDstLink, veDstLink, ceLeafDstLink,
--                veLeafDstLink by 1.
--	CHANGE:   Changed enumerations for ceXhInt and veXhInt,
--                removing warnings and errors from smic.
--
--	02-23-96  D. Stack   N/A        1.144
--	CHANGE:   Added pvcDirection item, which determines if a
--                multicast PVC is to be unidirectional or
--                bidirectional.
--      CHANGE:   Added ceSrcSlot, ceSrcLink, ceSrcVpi, ceSrcVci,
--                ceLeafDstSlot, ceLeafDstLink,	ceLeafDstVpi,
--                ceLeafDstVci, ceLeafSrcVpi, ceLeafSrcVci,
--                ceMulticast, ceXhInt, veSrcSlot, veSrcLink, veSrcVpi,
--                veSrcVci, veLeafDstSlot, veLeafDstLink, veLeafDstVpi,
--                veLeafDstVci, veLeafSrcVpi, veLeafSrcVci,
--                veMulticast, veXhInt for support of CE/VE multicast.
--                (see the CE/VE Multicast SAS/SRS for more info)
--
--      1-22-96   J. Chagnon AR2818
--      CHANGE:	Redesigning SF redundancy: Adding the XpInUse (dv2slot0 2)
--		MIB item back in. Was commented out for change on 8/28/95.
--
--	2-7-96    C. Liang
--	CHANGE    Make "svcLoadRoute" multiple options rather than just
--		  "yes" and "no"
--
--	01-31-96  C. Liang
--	CHANGE    Added "svcHalfConnect" trap type;
--		  Added "svcMaxSapConn" & "svcCurSapConn" for implemention
--		  of Max SVC connection on per SAP basis.
--
--	01-25-96  J. Chagnon
--	CHANGE:   Add changes to take E1 stuff out of NTM MIB
--                Added to slot 0 cfg, S0DOC type.
--                Added traps # 157-162 for NTM
--
--	01-24-96  T. Shanley
--	CHANGE:   Fix syntax problems detected by SMIC compiler.
--
--	1-2-96	C. Liang
--	CHANGE:	  added "slot0SwitchId" and "svcLoadRoute" in supporting
--		  DTL route implementation
--
--	12-13-95  M. Khalil
--	CHANGE:	  changed the default value for ds1V2GappedClk
--		  from no(2), to yes(1).
--		  Fixed Sytax Errors.
--
--      12-13-95  J. Chagnon            1.131
--      CHANGE:   Update NTM card section
--      11/30/95  M. Drost              1.130
--	CHANGE:   Change 'aco' status in alarm handler to 'crit-aco',
--		  'maj-aco' or 'min-aco' for clarity;
--
--	11/15/95  Y. Wang               1.129
--	CHANGE:	  Deprecate lfdoc and hfdoc in slot0PhyType object.
--
--	11/15/95  D. Stack   See below	1.128
--	CHANGE: - Removed vidInSubSmapl (unchangeable) and replaced it
--                with vidInTransMode (same OID and same default values,
--                which should prevent compatibility problems).
--                (MR000000000002368)
--              - Made "full" only option for vidInFrameRate.
--              - Changed options for jpegReset to be "no" and "reset"
--                (MR000000000002438)
--              - Removed unsupported baud rates from jpegSlipSpeed
--                (57600 and 115200) (MR000000000002495)
--              - Made default for vidOutSource "through" (MR000000000002594)
--
--      11/13/95  D. Chen               1.127
--	CHANGE: - Add address format into ILMI control table.
--
--      11/03/95  M. Drost              1.126
--	CHANGE: - Add alarmHandler group.
--		- Comment out ForcedReload trap and noUserFile trap; these are
--		  no longer supported.
--		- Rename the 'greater-than-655-feet' option to 'more-than-655-feet'
--		  under the LineLength options for the ds1Table and ds1V2Table.
--		- Remove slot0SwitchStatus and slot0SetAlarm.  Because these are leaf
--		  objects, they can safely be removed (just table objects cannot be
--		  removed).
--		- Add traps for user status inputs for the new APEX, MAC & MACI chassis.
--
--	10/30/95  Y. Wan
--            1.125
-- 	CHANGE:	  Change slot0PsuType and slot0PhyType
--		  object display.
--
--      10-28-95  Jim Chagnon         1.124
--      FEATURE : Add NTM Card group in System Clocks section
--
--      10/26/95  D. Chen             1.123
--      CHANGE    Change default ILMI vci to 10 from 16.
--
--      10/20/95  M. Libby
--      CHANGE:   Added default values for HSSI table.
--
--      10/20/95  Y. Wang              1.120
--      FEATURE:  Add enabling of SVC billing and SVC/PVC billing
--		  to billingControl object.
--		  Add billTag to billing table.
--		  Add billRecordControl, billLost, billLinks and
--		  billTrapControl to billing group.
--		  Add block-invalid(3) to billValid entry.
--
--      10/18/95  M. Libby             1.119
--      CHANGE:   Added LOS defect/alarm/trap to HSSI Table.
--                Added DTC/DCE (Not) Ready traps.
--
--      10/16/95  D. Chen              1.118
--      CHANGE:   Add dv2Lmi group.
--
--      10/10/95  M. Libby
--      CHANGE:   Made changes to the HSSI DLIM Table.
--
--      10/03/95  Y. Wang              1.115 & 1.116
--      CHANGE:   Change MAC to atm-switch in slot0PsuType object
--
--      09/28/95  C. Liang             1.114
--      CHANGE:   Added new objects in pvcTable to support multicast PVC
--
--      09/27/95  D. Chen              1.113
--      CHANGE:   Add 'physical loopback detected' to loopback
--                test result.
--
--      09/26/95  Y. Wang              1.112
--	CHANGE:	Remove dv2 from slot0PhyType object and
--              Change APEX to ATM-SWITCH in slot0PsuType
--              object for generic user interface of MIB display.
--
--      09/18/95  D. Chen              1.111
--      CHANGE:   Add dv2OAM group
--
--      09/16/95  M. Khalil
--      CHANGE:   Re-arranged dv2DS group so that oids appear in
--                increasing numerical order. It has to be this
--                way because snmp-get-next uses binary search
--                to search generated tables which means that
--                the oids have to be sorted.
--
-- 	09/14/95  M. Drost              1.109
--	CHANGE: Remove mods from rev 1.104; although these mibs were
--		not supported until 4.0, they were physically present
--		in 3.2 and therefore in the 3.2 config files.  To make
--		the desired change, the existing DS3-2C and E3 DLIM tables
--		are being depricated and new tables added.
--
--      09/13/95  Y. Wang               1.107 & 1.108
--	CHANGE:	Change billingControl object to include:
--                      stop-billing-process(1),
--		        start-SPVC-billing-process(2),
--                      start-PVC-billing-process(3),
--                      start-SPVC-PVC-billing-process(4),
--		        delete-all-billing-records(5)
--
--    	09/12/95  M. Drost              1.104
--	CHANGE:	  Removed the unipolar/bipolar user configurable from
--		  the DS3 and E3 DLIM tables.  These tables are new
--		  to 4.0, so removals should be allowed.
--
--      9/9/97    M. Khalil
--      CHANGE    Added new value for Tunnel State.
--
--  	09/07/95  Drost/Filippon 	1.103
--	CHANGE:	  Fix syntax errors.
--
--      9/7/95    Y. Wang               1.102
--                Change BillLogToDisk to read-only.
--
--	9/7/95    J. Huang		1.101
--	CHANGE	  save mac address in slot0 physical table for
--		  redundent slot0
--
--	9/1/95	  J. Huang		1.100
--	CHANGE	  Added trap for Out of Link Resource
--
--      08/29/95  Y. Wang               1.99
--      CHANGE:   Move pdhPLCPLpbkTimeout from pdhPLCPEntry 12 to
--                pdhPLCPEntry 14 for compatibility.
--                Change BillLogDisk from read-only to not-accessible.
--
--	8/29/95	  J. Huang		1.98
--	CHANGE:	  Low priority overbook implementation
--
--      08/29/95  Y. Wang               1.97
--      CHANGE:   Change revision history
--
--      08/29/95  Y. Wang               1.96
--      CHANGE:   Change BillLogToDisk status to obsolete.
--                We no longer need to implement this object.
--
--	08/28/95  J. Huang		1.94
--	CHANGE:	  1.
--		  Switch fabric redundency MIB. Deleted old xpInUse group.
--		  Modified xpToUse to include the xp status.
--		  2.
--		  Added link resource overbook factor to be used to by CAC.
--
-- 	08/25/95  M. Libby              1.93
--	CHANGE:   JPEG changes.  Added load configuration and changed the names
--		  for the file download.  Also, removed send configuration item.
--
-- 	08/22/95  M. Drost              1.92
--	CHANGE:   Mods to some of the SDH traps - some were sending the
--		  defect oid instead of the alarm oid.
--
--     08/18/95   D. Stack   n/a        1.91
--      CHANGE:   Changed default value of veCDV to 31 and
--                veCDVMax to 62 to prevent card coming up
--                in overflow state.
--      REMOVE:   ceNB and veNB - not used anywhere.
--
--     8/17/95  MD/ML                   1.90
--      Change    Add clockActiveRef to indicate timing source switches.
--                Add "unknown" status to the pdhPLCPChipType and make it
--                the default.
--
--     8/12/95  C. Liang   810654,810997,811142,811156  1.89
--      Change    - Allow policing to be turned off on per SPVC basis
--                - Allow policing to be turned off on per SAP basis
--                - Allow CDV Tolerance size to be configurable
--                - Allow interface to be either NETWORK or USER
--                - Changed "best-effort" to be of value 5, instead of 0.
--                - Changed "svcHiLo' to be 1 or 2, instead of 0 and 1.
--
--     08/12/95   M. Drost              1.88
--	CHANGE:   Break previous SDH status table into 2 new status tables;
--		  there was too much information to display on one screen, and
--		  it looked horrible!
--
--     08/10/95   M. Drost/A. Filippone 1.87
--	CHANGE:   Comment out obsolete traps and add new traps for LIM alarms.
--		  Add LOCD alarm to pdhPLCP table.
--
--	8/10/95	  J. Huang		1.86
--      CHANGE:	  Changed VP/VC ranges in SVC resource table as read only
--
--     08/07/95   D. Stack   n/a        1.85
--	REMOVE:   Took out ceLIM and veLIM - all that was
--                displayed was a number for the LIM ID and it
--                confused users.  No compatibility problem in
--                that versions with these were engineering
--                internal releases only.  (As a side effect,
--                all ce/ve OIDs following these have been
--                decremented by 1.)
--
--     08/07/95   M. Drost              1.84
--	CHANGE:   Fixes to previous revision to follow MIB change rules.
--
--     08/05/95	  Y. Wang  CTR#950617   1.83
--	CHANGE:   Add pdhPLCPLpbkTimeout to pdhPLCPTable
--		  Add sdhCLpbkTimeout to sdhCTable
--                Add dlimLpbkTimeout to dv2ds
--      FEATURE:  The changes enable recovery of management communications
--                after loopback times out.
--
--     08/05/95	  M. Drost              1.82
--	CHANGE:   Cosmetic changes to DS1 line length selection names; Expand on
--		  DS3-2C loopback choices.
--
--      8/3/95    C. Liang   #811015    1.81
--      CHANGE    Added "Best effort" option to QOS class in sPvcTable
--
--      8/3/95    C. Liang   #811204    1.80
--      CHANGE    Added "svcQ93bStatClr" and "svcQsaalStatClr" in
--                svcQ93bStatTable and svcQsaalStatTable, so
--                Q.93B and Q.SAAL statistics can be cleared.
--
--     07/28/95   M. Drost/M. Libby     1.78
--	CHANGE:   Rename local link clocking to PLCP clocking.
--		  Add solim version 0 for the pre-clocking LIMs.
--		  Add Chip version to PDH MIB.
--
--     07/21/95   M. Drost/M. Libby   	1.77
--	CHANGE:   Add Excessive BER defect/alarm to various LIM MIBs.
--		  Add ds1TxClkSel to old ds1 DLIM.
--		  Add gaps to new DLIM mibs to allow for future additions
--		   in the appropriate sections.
--
--      7/19/95   C. Liang   n/a         1.76
--      CHANGE:   Changed "svcLink" to "svcHiLo" in SvcResourceTable to indicate
--                SAP VPI/VCI to start from low or high number. The use of
--                "svcLink" has become obselete.
--
--     07/17/95   D. Stack  N/A		1.75
--	CHANGE:	  Changed ceEnable/veEnable to have a restart option.
--                Added ceStatReset/veStatReset between
--                  ceStatPortNo/veStatPortNo and ceStatTxState/veStatTxState,
--                  enabling the user to reset CE/VE counts.  This pushed all
--                  status items down one entry.
--                Removed jpeg as an option for ceMode.
--                Made jpeg the only option for veMode and made it read-only.
--
--      07/19/95  M. Drost              1.74
--	CHANGE:   -Rename DS3 Clear framing to M23
--
--	07/17/95  M. Drost/M. Libby     1.73
--	CHANGE:  -Rename PLCP Mode selections
--		 -Add jpegReset and jpegSWRev
--
--      07/17/95  J. Chagnon             1.72
--      CHANGE:   Add disable into slot0touse again
--
--      07/06/95  M. Khalil		1.71
--      CHANGE:   added new mib variable (slot0IntIPMask) for the internal
--	          subnet.
--
--	07/12/95  J. Huang		1.70
--	CHANGE:	  Changed name of PVC restart to PVC wait
--     07/10/95   M. Drost               1.69
--	CHANGE:   Incorporate gaps into PDH mibs to allow for future configurables
--		  to be added after the existing configuraables without changing
--		  the oids of the status items.
--
--     07/06/95   M. Drost               1.67/1.68
--      CHANGE:   Change idle cell selection in the pdhPLCPTable; Rearrange entries
--		  in pdhPLCPTable, pdhDS3Table, and pdhE3Table to make it more
--		  user friendly.  These are new entries, they have not been released
--		  yet, so can be rearranged!
--		  - Change naming of ds1V2Coding enumerations.
--
--	7/6/95    D. Stack   N/A         1.66
--	CHANGE:   Added ceCDVMax/veCDVMax, reflecting max value in FIFO
--		    before overflow.
--		  Swapped ceStatTxState and ceStatRxState such that
--		    Tx is transmitting to LIM, Rx is receiving from
--		    LIM.  Also changed states of ceStatRxState.
--		  Changed ceTxCnt, ceRxCnt, ceOflCnt, ceDisCnt, ceInvCnt,
--		    ceResCnt, ce FifoLvlCnt, and ceUflCnt from integers
--		    to counters.  Performed same change for ve counterparts.
--		  Changed descrpition of ceNB/veNB to indicate it is for
--		    GDC use only and made it default to NO.  (User playing
--		    with this will have no effect)
--
--	6/29/95   D. Stack   N/A         1.63
--      CHANGE:   Added ceFifoLvlCnt, ceUflCnt, veFifoLvlCnt, veUflCnt.
--                  These are used to track the level of the FIFO and
--                  the number of underflow seconds.
--                Also changed coOflCnt and veOflCnt to reflect only
--                  overflow seconds (previously also included underflow)
--
--      6/19/95  M. Khalil               1.62
--
--      CHANGE   : Added internalReset trap to indicate that a software restart
--                 due to an internal error.
--
--
--	6/29/95   D. Stack               1.62
--
--	Change:   Added Traps for AAL1 fault & recovery intended for
--		  DV2CE and DV2VE
--
--      6/29/95   Drost                  1.61
--		  Added performance parameters; misc traps
--
--      6/27/95   Drost/Libby            1.60
-- 	CHANGE:   Added misc traps: LIM Fault/Operational, PSU Absent,
--		  Switch Fabric
--		   redundant swap, excessive Bit Error Rate Active/Clear;
--		  Added soLimDesc to SOLIM DLIM;
--		  Added PLCP clocking selections;
--		  Added Reconfig entires to all DLIM tables
--
--      6/26/95   Drost/Libby/Johnson    1.59
--	CHANGE:	  Added new PDH support (to eventually replace old plpp),
--                MJLIM support, Full Feature Clocking (to replace dv2clocks),
--
--	6/22/95	  J. Huang               1.58
--	CHANGE:	  Added PVC restart state
--
--	06/19/95  D. Stack   N/A         1.57
--	CHANGE:   Add dv2VE group based on dv2CE group
--
--      06/21/95  Z. Iqbal/M. Khalil     1.56
--      CHANGE:   Add Added 2 traps restart040 and alcTxError
--  		  and moved e1-2C-LOS-SET and e1-2C-LOS-CLR
--	  	  to the end of the trap section.
--
--      06/15/95  J. Chagnon             1.55
--      CHANGE:   Add disable into slot0touse
--
--	06/01/95  D. Stack/T Johnson  	 1.54
--      CHANGE:   Add ds1_2c and ds1_4c support
--                Deprecated ds1V2LimClkSel, ds1V2LimClkStat
--                ceErrCnt to ceOflCnt
--                Descriptions for ceOflCnt, ceDisCnt, and ceInvCnt,
--                  and ceResCnt to refer to number of errored Seconds.
--                Swapped order of fifokick and narrowband in
--                 ceStatRxState to keep in step with dv2CE changes.
--
--       5/31/95  T. Johnson N/A          1.53
--                Add dv2CE group
--                Add dv2ce to Slot0PhyType
--                Add vjlim and e1_4c to Slot0PhyDlim
--                Add defects/alarms/counts to e1Table
--                Add e1-2C LOS Traps
--
--       5/30/95  Y. Wang    N/A          1.52
--       CHANGE:  Change trap name from bill25%full and
--                bill75%full to bill25pstfull and bill75pstfull.
--       5/30/95  Y. Wang    N/A          1.51
--       FEATURE: Modify revision history
--                Add traps bill25%full and bill75%full
--                Add billCLP1OutC and billCLP1Out
--                for billing feature. This revision is
--                built on the top of revision 1.49.
--
--       5/30/95  Y. Wang    N/A          1.50
--       FEATURE: Ignore this revision,
--
--       5/20/95  Y. Wang    N/A          1.49
--       FEATURE: Add revision history
--
--       5/10/95  Y. Wang    0811076      1.45
--       SYMPTOM: Negative display of cell counters & cell rates.
--       FIX:     All the MIBs that should be counters and gauges
--                are redefined.

--       5/23/95 J. Chagnon N/A          1.48
--       FEATURE Add disabled status to slot0inuse
--
--       5/22/95 J. Chagnon N/A          1.47
--       FEATURE Add slot0redmode to dv2slot0 group (17).
--               Add traps #76 and #77 for coming into service.
--
--       5/8/95  C. Liang    N/A        1.44
--       CHANGE: Changed the object "sPvcNextTry" in the sPvcTable
--               to "sPvcConnectTime". The use of "sPvcNextTry"
--               has become obslete, so it is changed to be the
--               connection time in ms in establishing a call.
--               This is part of SPVC software performance
--               enhancement.
--
--       4/26/95 D. Stack   N/A          1.42 (ignore 1.41)
--       CHANGE: Changed ranges for fraPStatDlci, FrbPStatDlci,
--               fraPConfigDlci, frbPConfigDlci to be (16..511)
--               to reduce memory usage on the 302.  Also,
--               removed reference to difference between MS and
--               MP ranges, as the above changes remove that
--               difference.
--
--       4/17/95 M. Drost   0810317      1.40
--       CHANGE: Enumerate the sdhSPathLabel variable.
--
--       4/12/95 D. Kreitner 811043      1.39
--
--       FEATURE : reference new E3 LIM as E3-2C
--       CHANGE  : Correct E3 & E1 to *-2C for
--		   appropriate entries.
--
--       4/10/95 J. Chagnon              1.38
--
--       FEATURE : Add revision history section
--       CHANGE  : Add revision history section
--
--       4/7/95  C. Liang    811014      1.37
--
--       FEATURE : Add alert cfg when a call clears
--       CHANGE  : Modify sPvcAlertFailures section and other
--                 small changes.
--
--       3/24/95 W. Penn                 1.36
--
--       SYMPTOM : Does not comply with ATM Forum Requirements
--       FIX     : Add plppV2FrmFmt - display far end's framing
--
--       FEATURE : Add additional diagnostic capability
--       CHANGE  : Add plppV2CTxAIS - Enable framer to xmit AIS
--
--       FEATURE : Add additional status
--       CHANGE  : Add plppV2SDs3LPBK - DS3 framer is in loopback
--                 Add plppV2SLOC - Receive loss of cell delineation
--                 Add plppV2SRxIDL - Idle is being received
--
--       3/23/95 C. Liang    810970      1.35
--
--       SYMPTOM : When a call is active the called party cannot
--                 terminate the call.
--       CAUSE   : Not implemented properly.
--       FIX     : In svcStatus, eliminate awaiting-clear.

--       3/20/95 C. Liang                1.34
--
--       SYMPTOM : 501 SPVCs allowed. Should only be 500.
--       CAUSE   : Implementation problem
--       FIX     : Changed sPvcId range from (0..500) to (1..500)
--
--       3/17/95 D. Kreitner             1.33
--
--       FEATURE : Add traps for E3-2C LCD
--       CHANGE  : Added trap types e3RecLCD and e3ClrLCD.
--
--       3/09/95 Penn/Khalil             1.32
--
--       SYMPTOM : Syntax problems
--       CAUSE   : It's been this way for a while.
--       FIX     : In PlppV2CEntry, put a comma after INTEGER
--                 In PlppV2Ds3FrmFmt, PlppV2SDs3FEACTxmt and ds3V2TxClksel,
--                   replace underscores with hyphens.
--                 In PlppCEntry, remove the "2".
--
-- GDCARC's APEX-DV2 switch Enterprise MIB
--_____________________________________________________________________________

-- Notes - 9-30-94
-- When using doitall, the following changes needed to be made:
-- Uncomment 'FROM groups.asn'
-- Comment out the following declarations:
--	E164
--	E164SUB
--	DateTimeString
--	Hex
--	Q93bCauseDiag
-- netcomm         OBJECT IDENTIFIER ::= { enterprises 251 }
-- products        OBJECT IDENTIFIER ::= { netcomm 1 }  Enterprise MIBs for specific products
-- dv2             OBJECT IDENTIFIER ::= { products 1 }  D2 ATM switch
-- Change all instances of Q93bCauseDiag to q93bCauseDiag.
--
-- This should make doitall work.
--
-- Mark Libby
--_____________________________________________________________________________
--
--
--
DV2-MIB DEFINITIONS ::= BEGIN

IMPORTS
--		FROM groups.asn
--	dv2
--		FROM GROUPS

	enterprises, IpAddress, Counter, Gauge
		FROM RFC1155-SMI
	DisplayString, PhysAddress
		FROM RFC1213-MIB
	TRAP-TYPE
		FROM RFC-1215
	OBJECT-TYPE
		FROM RFC-1212;


--___________________________________________________________________________

netcomm         OBJECT IDENTIFIER ::= { enterprises 251 }
products        OBJECT IDENTIFIER ::= { netcomm 1 }  -- Enterprise MIBs for specific products
dv2             OBJECT IDENTIFIER ::= { products 1 }  -- D2 ATM switch
dv2System	OBJECT IDENTIFIER ::= { dv2 1 }	-- System information
dv2Slot0	OBJECT IDENTIFIER ::= { dv2 2 }	-- Slot zero system information
dv2Trace	OBJECT IDENTIFIER ::= { dv2 3 } -- trace toggles
dv2SlipLine	OBJECT IDENTIFIER ::= { dv2 4 } -- slip configuration
dv2StaticRoute	OBJECT IDENTIFIER ::= { dv2 5 } -- static routing table
-- dv2Clocks to be depricated in a later build - replaced by dv2SystemClocks
dv2Clocks	OBJECT IDENTIFIER ::= { dv2 6 } -- dv2 clock source group
-- dv2Q93n		OBJECT IDENTIFIER ::= { dv2 7 }
-- q93n configuration
dv2VcDoc	OBJECT IDENTIFIER ::= { dv2 8 } -- vc doc channel config
dv2FrRelay	OBJECT IDENTIFIER ::= { dv2 9 } -- frame relay config/status group
dv2VcStatus	OBJECT IDENTIFIER ::= { dv2 10 } -- VC Status Table
dv2PLPP		OBJECT IDENTIFIER ::= { dv2 11 } -- PLPP status & configuration
dv2LocalFibre	OBJECT IDENTIFIER ::= { dv2 12 } -- Local Fibre status and configuration
dv2DS		OBJECT IDENTIFIER ::= { dv2 13 } -- DS type DLIM
dv2Billing	OBJECT IDENTIFIER ::= { dv2 14 } -- Billing Table
dv2QeDoc	OBJECT IDENTIFIER ::= { dv2 15 } -- QEDOC
dv2SDH		OBJECT IDENTIFIER ::= { dv2 16 } -- SDH
dv2Pvc		OBJECT IDENTIFIER ::= { dv2 17 } -- Permanent virtual circuit group
dv2Svc		OBJECT IDENTIFIER ::= { dv2 18 } -- Switched virtual circuit group
dv2CE		OBJECT IDENTIFIER ::= { dv2 19 } -- Circuit emulation group
dv2VE		OBJECT IDENTIFIER ::= { dv2 20 } -- Circuit emulation group for dv2VE
dv2SystemClocks	OBJECT IDENTIFIER ::= { dv2 21 } -- dv2 system clock driver group
-- Groups suported by the M-JPEG LIM card, for now tie this to the DV2 MIB definition
mjlimSlipLine	OBJECT IDENTIFIER ::= { dv2 22 } -- M-JPEG LIM Slip Configuration
mjlimSystem	OBJECT IDENTIFIER ::= { dv2 23 } -- M-JPEG LIM System Information
vidInCfg	OBJECT IDENTIFIER ::= { dv2 24 } -- M-JPEG LIM Video Input Configuration Information
vidOutCfg	OBJECT IDENTIFIER ::= { dv2 25 } -- M-JPEG LIM Video Output Configuration Information
vidInSta	OBJECT IDENTIFIER ::= { dv2 26 } -- M-JPEG LIM Video Input Status Information
vidOutSta	OBJECT IDENTIFIER ::= { dv2 27 } -- M-JPEG LIM Video Output Status Information
audInCfg	OBJECT IDENTIFIER ::= { dv2 28 } -- M-JPEG LIM Audio Input Configuration Information
audOutCfg	OBJECT IDENTIFIER ::= { dv2 29 } -- M-JPEG LIM Audio Output Configuration Information
audInSta	OBJECT IDENTIFIER ::= { dv2 30 } -- M-JPEG LIM Audio Input Status Information
audOutSta	OBJECT IDENTIFIER ::= { dv2 31 } -- M-JPEG LIM Audio Output Status Information
dataCfg		OBJECT IDENTIFIER ::= { dv2 32 } -- M-JPEG LIM Data Channel Configuration Information
dataSta		OBJECT IDENTIFIER ::= { dv2 33 } -- M-JPEG LIM Data Channel Status Information
mjlimControl	OBJECT IDENTIFIER ::= { dv2 34 } -- M-JPEG LIM DSP Transfer Control
dv2PDH          OBJECT IDENTIFIER ::= { dv2 35 } -- PDH
dv2Oam          OBJECT IDENTIFIER ::= { dv2 36 } -- OAM
dv2Lmi          OBJECT IDENTIFIER ::= { dv2 37 } -- Interim local management interface (LMI)
dv2AlarmHandler OBJECT IDENTIFIER ::= { dv2 38 } -- Alarm Handler
dv2Cac          OBJECT IDENTIFIER ::= { dv2 39 } -- CAC Handler
dv2MS2FRAC      OBJECT IDENTIFIER ::= { dv2 40 } -- FRAC
dv2aal5         OBJECT IDENTIFIER ::= { dv2 41 } -- aal5 part of FRAC
vhsystem        OBJECT IDENTIFIER ::= { dv2 42 } -- VHsystem
vhcontrol       OBJECT IDENTIFIER ::= { dv2 43 } -- VHcontrol
vhmgmt          OBJECT IDENTIFIER ::= { dv2 44 } -- VHmanagement
-- dv2SCE       OBJECT IDENTIFIER ::= { dv2 45 }  SCE
-- dv2LimMpeg   OBJECT IDENTIFIER ::= { dv2 46 }  MPEG LIMs

--___________________________________________________________________________
-- Specific type definitions

VirtualCircuitIdentifier ::= INTEGER (0..65535)
VirtualPathIdentifier    ::= INTEGER (0..4095)

-- Q93B addressing

-- These Three definitions are commented out only for NMS3000 parsing
-- first 2 octets are length, rest is 16 decimal digits
E164 ::= OCTET STRING (SIZE (2..10))

-- first 2 octets are length,
E164SUB ::= OCTET STRING (SIZE (2..22))

Q93bCauseDiag ::= OCTET STRING (SIZE (4))

-- A hex number, passed as an integer but displayed as a hex number.
-- This Line is commented out only for NMS3000 parsing
Hex ::= INTEGER (0..65535)

-- The previous date/time definition, DateTimeSTring, has been replaced
-- with the DateAndTime TEXTUAL-CONVENTION which is represented by 8 octets
-- with the following meanings:     (Y2K)

-- octet 0 - year(2 bytes), 0-65535.
-- octet 2 - month, 1 to 12.
-- octet 3 - day of the month, 1 to 31.
-- octet 4 - hours, 0 to 23.
-- octet 5 - minutes, 0 to 59.
-- octet 6 - seconds, 0 to 59.
-- octet 7 - deci-seconds, 0-9.

-- Any octet can have the value 255, indicating it is not being used or has no
-- meaning for the device.

-- This Line is commented out only for NMS3000 parsing
DateTimeString ::= OCTET STRING (SIZE (8))
--DateAndTime ::= OCTET STRING (SIZE (8))
-- This line is included to define DateAndTime to the parser.  The two
-- definitions has the same number of octets.

-- Must set till parser is updated.......!      (Y2K)
DateAndTime ::= DateTimeString 

--___________________________________________________________________________

-- ********************** Start of boot area ****************

-- The system information group.

--___________________________________________________________________________

sysMemEnd OBJECT-TYPE
	SYNTAX	Hex
	ACCESS	read-only
	STATUS	mandatory
	DESCRIPTION
	"The current end of run-time allocated memory."
	::= { dv2System 1 }

--                              Y2K change : deprecated
--sysLastResetTime OBJECT-TYPE
--	SYNTAX	DateTimeString
--	ACCESS	read-only
--	STATUS	deprecated
--	DESCRIPTION
--	"Date and time board was last reset."
--	::= { dv2System 2 }
--
--                              Y2K change : deprecated
--sysCurrentTime OBJECT-TYPE
--	SYNTAX	DateTimeString
--	ACCESS	read-write
--	STATUS	deprecated
--	DESCRIPTION
--	"Current date and time in the form dd Mon yyyy  hh:mm:ss.
--	For example:-
--	15 Aug 1994  10:12:21"
--	::= { dv2System 3 }

sysInitialMemB OBJECT-TYPE
	SYNTAX INTEGER
	ACCESS read-only
	STATUS mandatory
	DESCRIPTION
	"initial number of memory items."
	::= { dv2System 4 }

sysCurrentMemB OBJECT-TYPE
	SYNTAX INTEGER
	ACCESS read-only
	STATUS mandatory
	DESCRIPTION
	"Current number of memory items."
	::= { dv2System 5 }

sysInitialSema OBJECT-TYPE
	SYNTAX INTEGER
	ACCESS read-only
	STATUS mandatory
	DESCRIPTION
	"Initial number of semaphores."
	::= { dv2System 6 }

sysCurrentSema OBJECT-TYPE
	SYNTAX INTEGER
	ACCESS read-only
	STATUS mandatory
	DESCRIPTION
	"Current number of semaphores."
	::= { dv2System 7 }

sysInitialQItems OBJECT-TYPE
	SYNTAX INTEGER
	ACCESS read-only
	STATUS mandatory
	DESCRIPTION
	"Initial number of queue items."
	::= { dv2System 8 }

sysCurrentQItems OBJECT-TYPE
	SYNTAX INTEGER
	ACCESS read-only
	STATUS mandatory
	DESCRIPTION
	"Current number of queue items."
	::= { dv2System 9 }

sysInitialQs OBJECT-TYPE
	SYNTAX INTEGER
	ACCESS read-only
	STATUS mandatory
	DESCRIPTION
	"Initial number of queues."
	::= { dv2System 10 }

sysCurrentQs OBJECT-TYPE
	SYNTAX INTEGER
	ACCESS read-only
	STATUS mandatory
	DESCRIPTION
	"Current number of queues."
	::= { dv2System 11 }

sysInitialPorts OBJECT-TYPE
	SYNTAX INTEGER
	ACCESS read-only
	STATUS mandatory
	DESCRIPTION
	"Initial number of ports."
	::= { dv2System 12 }

sysCurrentPorts OBJECT-TYPE
	SYNTAX INTEGER
	ACCESS read-only
	STATUS mandatory
	DESCRIPTION
	"Current number of ports."
	::= { dv2System 13 }

sysDefaultCellMode OBJECT-TYPE
	SYNTAX INTEGER {
		no(1),
		yes(2)
	}
	ACCESS read-only
	STATUS mandatory
	DESCRIPTION
	"This flag indicates whether the cell interface is operating in default mode. If yes(2) then this indicates that the daughter card processor is not running its correct code."
	::= { dv2System 14 }


------------------------------------------------------------------------
-- link table for the slot

sysLinkTable OBJECT-TYPE
	SYNTAX SEQUENCE OF SysLinkEntry
	ACCESS not-accessible
	STATUS mandatory
	DESCRIPTION
	"This table contains information about each link on this slot controller."
	::= { dv2System 15 }

sysLinkEntry OBJECT-TYPE
	SYNTAX	SysLinkEntry
	ACCESS	not-accessible
	STATUS	mandatory
        INDEX   { sysLkLinkNo }
	::= { sysLinkTable 1 }

SysLinkEntry ::=
	SEQUENCE {
		sysLkLinkNo
			INTEGER,
		sysLkKillLink
			INTEGER,
		sysLkState
			INTEGER,
		sysLkTxCells
			Counter,
		sysLkRxCells
			Counter,
		sysLkTxRate
			Gauge,
		sysLkRxRate
			Gauge,
		sysLkTxMaxRate
			Gauge,
		sysLkRxMaxRate
			Gauge,
		sysLkResetStats
			INTEGER,
		sysLkClockSrc
			INTEGER,
		sysLkResetResrc
            		INTEGER,
		sysLKEgCLPThreshold
		    INTEGER,
		sysLKIgCLPThreshold
		    INTEGER,
		sysLKEgEFCIThreshold
		    INTEGER,
		sysLKIgEFCIThreshold
		    INTEGER,
		sysLKEgLogBuffer
		    INTEGER,
		sysLKIgLogBuffer
		    INTEGER,
		sysLKEgFIFODepth
		    INTEGER,
		sysLKIgFIFODepth
		    INTEGER,
		sysLKEgMemBlockId
		    INTEGER,
		sysLKIgMemBlockId
		    INTEGER
}

sysLkLinkNo OBJECT-TYPE
	SYNTAX INTEGER (0..3)
	ACCESS read-only
	STATUS mandatory
	DESCRIPTION
	"The link number on the slot"
	::= { sysLinkEntry 1 }

sysLkKillLink OBJECT-TYPE
	SYNTAX INTEGER {
		no(1),
		restart(2)
	}
	ACCESS read-write
	STATUS mandatory
	DESCRIPTION
	"Set to restart(2) to kill this link"
	::= { sysLinkEntry 2 }

sysLkState OBJECT-TYPE
	SYNTAX INTEGER {
		up(1),
		down(2),
		stop(3)
	}
	ACCESS read-only
	STATUS mandatory
	DESCRIPTION
	"Status of the link"
	::= { sysLinkEntry 3 }

sysLkTxCells OBJECT-TYPE
	SYNTAX Counter
	ACCESS read-only
	STATUS mandatory
	DESCRIPTION
	"Number of cells sent from link"
	::= { sysLinkEntry 4 }

sysLkRxCells OBJECT-TYPE
	SYNTAX Counter
	ACCESS read-only
	STATUS mandatory
	DESCRIPTION
	"Number of cells received to link"
	::= { sysLinkEntry 5 }


sysLkTxRate OBJECT-TYPE
	SYNTAX Gauge
	ACCESS read-only
	STATUS mandatory
	DESCRIPTION
	"Cells per second sent from link"
	::= { sysLinkEntry 6 }

sysLkRxRate OBJECT-TYPE
	SYNTAX Gauge
	ACCESS read-only
	STATUS mandatory
	DESCRIPTION
	"Cells per second received to link"
	::= { sysLinkEntry 7 }

sysLkTxMaxRate OBJECT-TYPE
	SYNTAX Gauge
	ACCESS read-only
	STATUS mandatory
	DESCRIPTION
	"Maximum cells per second transmitted from link"
	::= { sysLinkEntry 8 }

sysLkRxMaxRate OBJECT-TYPE
	SYNTAX Gauge
	ACCESS read-only
	STATUS mandatory
	DESCRIPTION
	"Maximum cells per second received to link"
	::= { sysLinkEntry 9 }

sysLkResetStats OBJECT-TYPE
	SYNTAX INTEGER	{
		no(1),
		yes(2)
	}
	ACCESS read-write
	STATUS mandatory
	DESCRIPTION
	"Set to yes(2) to reset the link statistics"
	::= { sysLinkEntry 10 }

sysLkClockSrc OBJECT-TYPE
	SYNTAX INTEGER	{
		normal(1),
		low-quality(2),
		high-quality(3),
		loop-timed(4),
		local(5)
	}
	ACCESS read-write
	STATUS mandatory
	DESCRIPTION
	"This specifies where the link obtains its clock"
	::= { sysLinkEntry 11 }

sysLkResetResrc OBJECT-TYPE
	SYNTAX INTEGER	{
		no(1),
		yes(2)
	}
	ACCESS read-write
	STATUS mandatory
	DESCRIPTION
	"Set to yes(2) to reset the link resources"
	::= { sysLinkEntry 12 }

sysLKEgCLPThreshold OBJECT-TYPE
        SYNTAX INTEGER (0..63)
        ACCESS  read-write
        STATUS  mandatory
        DESCRIPTION
        "Transmit CLP1 threshold"
        DEFVAL { 0 }
        ::= { sysLinkEntry 13 }

sysLKIgCLPThreshold OBJECT-TYPE
        SYNTAX INTEGER (0..63)
        ACCESS  read-write
        STATUS  mandatory
        DESCRIPTION
        "Receive CLP1 threshold"
        DEFVAL { 0 }
        ::= { sysLinkEntry 14 }

sysLKEgEFCIThreshold OBJECT-TYPE
        SYNTAX INTEGER (0..63)
        ACCESS  read-write
        STATUS  mandatory
        DESCRIPTION
        "Transmit EFCI threshold"
        DEFVAL { 0 }
        ::= { sysLinkEntry 15 }

sysLKIgEFCIThreshold OBJECT-TYPE
        SYNTAX INTEGER (0..63)
        ACCESS  read-write
        STATUS  mandatory
        DESCRIPTION
        "Receive EFCI threshold"
        DEFVAL { 0 }
        ::= { sysLinkEntry 16 }

sysLKEgLogBuffer OBJECT-TYPE
        SYNTAX INTEGER (0..63)
        ACCESS  read-write
        STATUS  mandatory
        DESCRIPTION
        "Transmit logic buffer size"
        DEFVAL { 1 }
        ::= { sysLinkEntry 17 }

sysLKIgLogBuffer OBJECT-TYPE
        SYNTAX INTEGER (0..63)
        ACCESS  read-write
        STATUS  mandatory
        DESCRIPTION
        "Receive logic buffer size"
        DEFVAL { 1 }
        ::= { sysLinkEntry 18 }

sysLKEgFIFODepth OBJECT-TYPE
        SYNTAX INTEGER
        ACCESS read-only
        STATUS  mandatory
        DESCRIPTION
        "Transmit FIFO Depth"
        ::= { sysLinkEntry 19 }

sysLKIgFIFODepth OBJECT-TYPE
        SYNTAX INTEGER
        ACCESS read-only
        STATUS  mandatory
        DESCRIPTION
        "Receive FIFO Depth"
        ::= { sysLinkEntry 20 }

sysLKEgMemBlockId OBJECT-TYPE
        SYNTAX INTEGER {
                mem-4k(4),
                mem-16k(16),
                mem-64k(63)
                }
        ACCESS read-only
        STATUS  mandatory
        DESCRIPTION
        "Transmit Memory Block ID"
        ::= { sysLinkEntry 21 }

sysLKIgMemBlockId OBJECT-TYPE
        SYNTAX INTEGER {
                mem-4k(4),
                mem-16k(16),
                mem-64k(63)
                }
        ACCESS read-only
        STATUS  mandatory
        DESCRIPTION
        "Receive Memory Block ID"
        ::= { sysLinkEntry 22 }

sysDbTable OBJECT-TYPE
	SYNTAX SEQUENCE OF SysDbEntry
	ACCESS not-accessible
	STATUS mandatory
	DESCRIPTION
	"This table contains information about the internal buffer pool on the slot controller."
	::= { dv2System 16 }

sysDbEntry OBJECT-TYPE
	SYNTAX	SysDbEntry
	ACCESS	not-accessible
	STATUS	mandatory
        INDEX   { sysDbIndex }
	::= { sysDbTable 1 }

SysDbEntry ::=
	SEQUENCE {
		sysDbIndex
			INTEGER,
		sysDbSize
			INTEGER,
		sysDbInitial
			INTEGER,
		sysDbCurrent
			INTEGER
}

sysDbIndex OBJECT-TYPE
	SYNTAX INTEGER (0..10)
	ACCESS read-only
	STATUS mandatory
	DESCRIPTION
	"Buffer class number"
	::= { sysDbEntry 1 }

sysDbSize OBJECT-TYPE
	SYNTAX INTEGER {
		buff16(16),
		buff128(128),
		buff368(368),
		buff1600(1600),
		cells(48),
		signal-quota(1),
		ip-quota(2)
	}
	ACCESS read-only
	STATUS mandatory
	DESCRIPTION
	"Five classes of buffers are used:- 16, 128, 368 and 1600 bytes plus 48 bytes for cells."
	::= { sysDbEntry 2 }

sysDbInitial OBJECT-TYPE
	SYNTAX INTEGER
	ACCESS read-only
	STATUS mandatory
	DESCRIPTION
	"This is the initial number of buffers available."
	::= { sysDbEntry 3 }

sysDbCurrent OBJECT-TYPE
	SYNTAX INTEGER
	ACCESS read-only
	STATUS mandatory
	DESCRIPTION
	"This is the current number of buffers available."
	::= { sysDbEntry 4 }

sysAuthenticateTable OBJECT-TYPE
	SYNTAX SEQUENCE OF SysAuthenticateEntry
	ACCESS not-accessible
	STATUS mandatory
	DESCRIPTION
	"Table containing all the authentication tuples for this agent."
	::= { dv2System 17 }


sysAuthenticateEntry OBJECT-TYPE
	SYNTAX	SysAuthenticateEntry
	ACCESS	not-accessible
	STATUS	mandatory
	DESCRIPTION
	"An authentication tuple. A PDU from the ipaddress specified that contains
	 the community, will have access to this MIB."
        INDEX   { sysAuIndex }
	::= { sysAuthenticateTable 1 }


SysAuthenticateEntry ::=
	SEQUENCE {
		sysAuIndex
			INTEGER,
		sysAuIpaddress
			IpAddress,
		sysAuCommunity
			DisplayString,
		sysAuAccess
			INTEGER,
		sysAuSendTraps
			INTEGER,
		sysAuValidity
			INTEGER
}

sysAuIndex OBJECT-TYPE
	SYNTAX INTEGER (0..2147483647)
	ACCESS read-write
	STATUS mandatory
	DESCRIPTION
	"Index, identifying each entry in the authentication table."
	::= { sysAuthenticateEntry 1 }

sysAuIpaddress OBJECT-TYPE
	SYNTAX IpAddress
	ACCESS read-write
	STATUS mandatory
	DESCRIPTION
	"The network address of the manager that has authentication access to this agent."
	::= { sysAuthenticateEntry 2 }

sysAuCommunity OBJECT-TYPE
	SYNTAX DisplayString
	ACCESS read-write
	STATUS mandatory
	DESCRIPTION
	"The SNMP community for which the ipaddress is authenticated."
	::= { sysAuthenticateEntry 3 }

sysAuAccess OBJECT-TYPE
	SYNTAX INTEGER {
		readOnly(1),
		readWrite(3)
	}
	ACCESS read-write
	STATUS mandatory
	DESCRIPTION
	"Access permission for this ipaddress/community tuple.
	 Write access is required for performing SNMP sets."
	::= { sysAuthenticateEntry 4 }

sysAuSendTraps	OBJECT-TYPE
	SYNTAX INTEGER {
		send-all(1),
		send-none(2)
	}
	ACCESS read-write
	STATUS mandatory
	DESCRIPTION
	"Set to send-none(2) to prevent traps being sent to this host."
	::= { sysAuthenticateEntry 5 }

sysAuValidity OBJECT-TYPE
	SYNTAX INTEGER {
		valid(1),
		invalid(2)
	}
	ACCESS read-write
	STATUS mandatory
	DESCRIPTION
	"Set to invalid(2) to delete this row."
	::= { sysAuthenticateEntry 6 }

------------------------------------------------------------------------
-- Continuation of Base System Group

sysLastTrapMessage OBJECT-TYPE
	SYNTAX DisplayString (SIZE (0..70))
	ACCESS read-only
	STATUS mandatory
	DESCRIPTION
	"This is used to contain the last trap string sent."
	::= { dv2System 18 }

sysConfigChanged OBJECT-TYPE
	SYNTAX INTEGER {
		no(1),
		yes(2)
	}
	ACCESS read-write
	STATUS mandatory
	DESCRIPTION
	"This indicates that a new <config.cfg> file is available.
	 This should not be set by the user."
	::= { dv2System 19 }

sysConfigFile OBJECT-TYPE
	SYNTAX INTEGER {
		no-action(1),
		read(2),
		write(3)
	}
	ACCESS read-write
	STATUS mandatory
	DESCRIPTION
	"Set to read(2) to re-read the <config.cfg> file. Set to write(3) to write
	 the existing configuration to <config.cfg>."
	::= { dv2System 20 }

sysCompileTime OBJECT-TYPE
	SYNTAX	DisplayString
	ACCESS	read-only
	STATUS	mandatory
	DESCRIPTION
	"Date and time of link in the form dd Mon yyyy  hh:mm:ss.
	For example:-
	15 Aug 1994  10:12:21"
	::= { dv2System 21 }

slotNumber	OBJECT-TYPE
	SYNTAX  INTEGER (0..15)
	ACCESS	read-only
	STATUS  mandatory
	DESCRIPTION
	"Slot Number"
	::= { dv2System 22}

--                              Y2K change : use DateAndTime convention
sysLastResetTimeM2 OBJECT-TYPE
	SYNTAX	DateAndTime          
	ACCESS	read-only
	STATUS	mandatory
	DESCRIPTION
	"Date and time board was last reset."
	::= { dv2System 23 }

--                              Y2K change : use DateAndTime convention
sysCurrentTimeM2 OBJECT-TYPE
	SYNTAX	DateAndTime
	ACCESS	read-write
	STATUS	mandatory
	DESCRIPTION
	"Current date and time in the form dd Mon yyyy  hh:mm:ss.
	For example:-
	15 Aug 1994  10:12:21"
	::= { dv2System 24 }

--                                      new variable #10, #13
limTypeStatus  OBJECT-TYPE
	SYNTAX	INTEGER {
		unknown(1),
		compatible(2),
		not-compatible(3)
	}
	ACCESS	read-only
	STATUS	mandatory
	DESCRIPTION
	"Describes whether the lim and the DOC card are compatible."
	DEFVAL { unknown }
	::= { dv2System 25 }

--___________________________________________________________________________

-- The dv2slot0 group

slot0IntIp OBJECT-TYPE
	SYNTAX	IpAddress
	ACCESS	read-only
	STATUS	mandatory
	DESCRIPTION
	"IP address of SLOT 0 for ATM interface."
	::= { dv2Slot0 1 }

slot0XpInUse	OBJECT-TYPE
	SYNTAX	INTEGER {
		unknown(3),
		main-in-service(1),
		standby-in-service(2)
	}
	ACCESS	read-only
	STATUS	mandatory
	DESCRIPTION
	"The current Switch Fabric in Service"
	DEFVAL { unknown }
	::= { dv2Slot0 2 }


slot0XpToUse	OBJECT-TYPE
	SYNTAX	INTEGER {
		auto(3),
		main(1),
		standby(2),
		not-applicable(4)
	}
	ACCESS	read-write
	STATUS	mandatory
	DESCRIPTION
	"This indicates the switch fabric card you want the switch to use."
	DEFVAL	{ auto }
	::= { dv2Slot0 3 }


slot0StandbyXp	OBJECT-TYPE
	SYNTAX	INTEGER {
		no(2),
		yes(1)
	}
	ACCESS	read-write
	STATUS	mandatory
	DESCRIPTION
	"Set to yes(1) to enable standby switch fabric."
	::= { dv2Slot0 4 }

slot0PsuTable OBJECT-TYPE
	SYNTAX SEQUENCE OF Slot0PsuEntry
	ACCESS not-accessible
	STATUS mandatory
	DESCRIPTION
	""
	::= { dv2Slot0 5 }

slot0PsuEntry OBJECT-TYPE
	SYNTAX	Slot0PsuEntry
	ACCESS	not-accessible
	STATUS	mandatory
        INDEX   { slot0PsuIndex }
	::= { slot0PsuTable 1 }

Slot0PsuEntry ::=
	SEQUENCE {
		slot0PsuIndex
			INTEGER,
		slot0PsuFault
			INTEGER,
		slot0PsuTestFault
			INTEGER,
		slot0PsuVoltage
			INTEGER,
		slot0PsuTemp
			INTEGER,
		slot0PsuFanASpeed
			INTEGER,
		slot0PsuFanBSpeed
			INTEGER,
		slot0PsuFanCSpeed
			INTEGER,
		slot0PsuReset
			INTEGER,
		slot0PsuType
			INTEGER,
		slot0PsuFanFail
			INTEGER,
		slot0PsuTooHot
			INTEGER,
 		slot0PsuFrontTooHot
 			INTEGER
}

slot0PsuIndex OBJECT-TYPE
	SYNTAX INTEGER (0..3)
	ACCESS read-only
	STATUS mandatory
	DESCRIPTION
	"Power-supply number."
	::= { slot0PsuEntry 1 }

slot0PsuFault OBJECT-TYPE
	SYNTAX INTEGER {
		absent(3),	-- This power supply is not fitted.
		ok(1),		-- This power supply is OK.
		fault(2)	-- This power supply has a fault. Temperature or fan speed.
	}
	ACCESS read-only
	STATUS mandatory
	DESCRIPTION
	"If fault(2) then this indicates a fault condition in the power-supply."
	::= { slot0PsuEntry 2 }

slot0PsuTestFault OBJECT-TYPE
	SYNTAX INTEGER {
-- Fix test fault status'; they were previously reversed.  A value of 1 in
-- this field indicates psu okay, a value of 2 indicates a test fault. 
--		yes(1),		 Test on this power supply is in progress.
--		no(2)		 Test not in progress.
		no(1),		-- Test not in progress.
		yes(2),		-- Test on this power supply is in progress.
		not-applicable(3)  -- TestFault not applicable
	}
	ACCESS read-only
	STATUS mandatory
	DESCRIPTION
	"If set to yes(1) the control button on the PSU module has been set to test fault mode."
	::= { slot0PsuEntry 3 }

slot0PsuVoltage OBJECT-TYPE
	SYNTAX INTEGER
	ACCESS read-only
	STATUS mandatory
	DESCRIPTION
	"This is a the voltage generated by the power-supply in millivolts."
	::= { slot0PsuEntry 4 }

slot0PsuTemp OBJECT-TYPE
	SYNTAX INTEGER
	ACCESS read-only
	STATUS mandatory
	DESCRIPTION
	"This is the temperature of the power-supply module in degrees celsius."
	::= { slot0PsuEntry 5 }

slot0PsuFanASpeed OBJECT-TYPE
	SYNTAX INTEGER
	ACCESS read-only
	STATUS mandatory
	DESCRIPTION
	"This is the rotation speed of FAN A in RPM."
	::= { slot0PsuEntry 6 }

slot0PsuFanBSpeed OBJECT-TYPE
	SYNTAX INTEGER
	ACCESS read-only
	STATUS mandatory
	DESCRIPTION
	"This is the rotation speed of FAN B in RPM."
	::= { slot0PsuEntry 7 }

slot0PsuFanCSpeed OBJECT-TYPE
	SYNTAX INTEGER
	ACCESS read-only
	STATUS mandatory
	DESCRIPTION
	"This is the rotation speed of FAN C in RPM."
	::= { slot0PsuEntry 8 }

slot0PsuReset OBJECT-TYPE
	SYNTAX INTEGER {
		no(1),
		yes(2),
		not-applicable(3)
	}
	ACCESS read-write
	STATUS mandatory
	DESCRIPTION
	"If set to yes(2) then the power-supply module is returned to its initial state."
	::= { slot0PsuEntry 9 }

slot0PsuType OBJECT-TYPE
	SYNTAX INTEGER {
		v1-ATM-SWITCH(1),
		v2-ATM-SWITCH(2),
		v3-ATM-SWITCH(3),
		v4-ATM-SWITCH(4),
		v5-ATM-SWITCH(5)
	}
	ACCESS read-only
	STATUS mandatory
	DESCRIPTION
	"Shows the type of PSU fitted into switch."
	::= { slot0PsuEntry 10 }

slot0PsuFanFail OBJECT-TYPE
	SYNTAX INTEGER {
		no(1),
		yes(2)
	}
	ACCESS read-only
	STATUS mandatory
	DESCRIPTION
	"Set to yes(2) if the fan fails."
	::= { slot0PsuEntry 11 }

slot0PsuTooHot OBJECT-TYPE
	SYNTAX INTEGER {
		no(1),
		yes(2),
		not-applicable(3)
	}
	ACCESS read-only
	STATUS mandatory
	DESCRIPTION
	"Set to yes(2) if the PSU is too hot"
	::= { slot0PsuEntry 12 }

slot0PsuFrontTooHot OBJECT-TYPE
	SYNTAX INTEGER {
		no(1),
		yes(2),
		not-applicable(3)
	}
	ACCESS read-only
	STATUS mandatory
	DESCRIPTION
	"Set to yes(2) if the Front is too hot"
	::= { slot0PsuEntry 13 }

--___________________________________________________________________________

-- The Physical Layout table

slot0PhyTable OBJECT-TYPE
	SYNTAX SEQUENCE OF Slot0PhyEntry
	ACCESS not-accessible
	STATUS mandatory
	DESCRIPTION
	"This table summarises the hardware installed in the switch."
	::= { dv2Slot0 6 }

slot0PhyEntry OBJECT-TYPE
	SYNTAX	Slot0PhyEntry
	ACCESS	not-accessible
	STATUS	mandatory
        INDEX   { slot0PhySlotNo }
	::= { slot0PhyTable 1 }

Slot0PhyEntry ::=
	SEQUENCE {
		slot0PhySlotNo
			INTEGER,
		slot0PhyName
			DisplayString,
		slot0PhyType
			INTEGER,
		slot0PhyDlim
			INTEGER,
		slot0PhySwVer
			DisplayString,
		slot0PhyState
			INTEGER,
		slot0PhyReset
			INTEGER,
		slot0PhyReqState
			INTEGER,
--                              Y2K change : deprecated
--		slot0PhyChangeTime
--			DateTimeString,
		slot0PhyStateChange
			INTEGER,
		slot0PhyLinkedSlot
			INTEGER,
		slot0PhyLink0State
			INTEGER,
		slot0PhyLink1State
			INTEGER,
		slot0PhyLink2State
			INTEGER,
		slot0PhyLink3State
			INTEGER,
		slot0PhySlotSerNo
			DisplayString,
		slot0PhySlotHwVerNo
			DisplayString,
		slot0PhyDocSerNo
			DisplayString,
		slot0PhyDocHwVerNo
			DisplayString,
		slot0PhyMacAddress
			PhysAddress,
--                              Y2K change : added,  use DateAndTime convention
		slot0PhyChangeTimeM2
			DateAndTime,
--                                                 #10 new variables
		slot0PhyLstChngLnkNum
			INTEGER,
		slot0PhyLstChngPrevLnkStat
			INTEGER
}

slot0PhySlotNo OBJECT-TYPE
	SYNTAX INTEGER (0..15)
	ACCESS read-only
	STATUS mandatory
	DESCRIPTION
	"This is the slot number in the switch."
	::= { slot0PhyEntry 1 }

slot0PhyName OBJECT-TYPE
	SYNTAX DisplayString
	ACCESS read-write
	STATUS mandatory
	DESCRIPTION
	"This is a mnemonic name for the slot."
	::= { slot0PhyEntry 2 }

slot0PhyType OBJECT-TYPE
	SYNTAX INTEGER	{
		unknown(1),	-- 0x01
		dxdoc(128),	-- 0x80
		qedoc(129),	-- 0x81
		vcdoc(130),	-- 0x82
--		lfdoc(131),	 0x83
--		hfdoc(132),	 0x84
		cp(133),	-- 0x85
		cl(134),	-- 0x86
		cs(135),	-- 0x87
		hp(136),	-- 0x88
		hl(137),	-- 0x89
		hs(138),	-- 0x8a
		ce(139),	-- 0x8b
		ve(140),	-- 0x8c
		chfrc(141),     -- 0x8d
		eth(142),       -- 0x8e
		frac(143),      -- 0x8f
	        trdoc(144),     -- 0x90
		sce(145),       -- 0x91
		dv2ap(146),     -- 0x92
		dv2as(147),     -- 0x93
		vsm(148),	-- 0x94
		ipas(149),	-- 0x95
		ipap(150)	-- 0x96
        }
	ACCESS read-only
	STATUS mandatory
	DESCRIPTION
	"This enumerated type defines the type of card fitted in the slot."
	::= { slot0PhyEntry 3 }

slot0PhyDlim	OBJECT-TYPE
	SYNTAX INTEGER {
		unknown(1),
		dx21(2),
		dx27(3),
		d2G703(4),
		d8G703(5),
		d34G703(6),
		dAUI(7),
		dlfLIM(8),
		dds1(9),
		dds3(10),
		dhssi(11),
		dsolim(12),
		ds3-2c(13),
		e3-2c(14),
		e1-dual(15),
		e1-quad(16),
		ds1-dual(17),
		ds1-quad(18),
 		jpeg(19),
		j2-dual(20),
		j2-quad(21),
		vh320(22),
		si-dual(23),
		si-quad(24),
		delim(25),
                mpg2v(26),
		qtlim(27)
	}
	ACCESS read-write
	STATUS mandatory
	DESCRIPTION
	"This is the type of DLIM fitted to the slot."
	::= { slot0PhyEntry 4 }

slot0PhySwVer OBJECT-TYPE
	SYNTAX DisplayString
	ACCESS read-only
	STATUS mandatory
	DESCRIPTION
	"Version of the software running on this slot controller."
	::= { slot0PhyEntry 5 }

slot0PhyState OBJECT-TYPE
	SYNTAX INTEGER {
		absent(1),		-- no card fitted
		bootmode(2),
		active(3),
		shutdown(4),
		shadow(5)
	}
	ACCESS read-only
	STATUS mandatory
	DESCRIPTION
	"The state of the slot, -(1) indicates no card fitted."
	::= { slot0PhyEntry 6 }

slot0PhyReset OBJECT-TYPE
	SYNTAX INTEGER {
		no(1),
		yes(2)
	}
	ACCESS read-write
	STATUS mandatory
	DESCRIPTION
	"Setting to yes(2) will reset the slot - use with care"
	::= { slot0PhyEntry 7 }

slot0PhyReqState OBJECT-TYPE
	SYNTAX INTEGER {
		normal(1),
		shutdown(2),
		main(3),
		shadow(4)
	}
	ACCESS read-write
	STATUS mandatory
	DESCRIPTION
	"Setting to shutdown(2) will stop the slot running. The slot should only be set to main(3) or shadow(4) if the slot is operating in hardware redundant mode with an adjacent slot."
	::= { slot0PhyEntry 8 }

--                              Y2K change : deprecated
--slot0PhyChangeTime OBJECT-TYPE
--	SYNTAX DateTimeString
--	ACCESS read-only
--	STATUS deprecated
--	DESCRIPTION
--	"Last date and time link changed state."
--	::= { slot0PhyEntry 9 }

slot0PhyStateChange OBJECT-TYPE
	SYNTAX INTEGER {
		no(2),
		yes(1)
	}
	ACCESS read-only
	STATUS mandatory
	DESCRIPTION "Indicates link has changed state."
	::= { slot0PhyEntry 10 }

slot0PhyLinkedSlot OBJECT-TYPE
	SYNTAX INTEGER (0..15)
	ACCESS read-write
	STATUS mandatory
	DESCRIPTION "This is used in hardware redundancy mode. If set to 0 then there is no associated slot. Otherwise the value is the slot number that will be used if this slot fails."
	::= { slot0PhyEntry 11 }

slot0PhyLink0State OBJECT-TYPE
	SYNTAX INTEGER {
		stop(4),
		up(1),
		down(2),
		off(3),
		reset(5)
	}
	ACCESS read-only
	STATUS mandatory
	DESCRIPTION
	"This contains link 0 status."
	::= { slot0PhyEntry 12 }

slot0PhyLink1State OBJECT-TYPE
	SYNTAX INTEGER {
		stop(4),
		up(1),
		down(2),
		off(3),
		reset(5)
	}
	ACCESS read-only
	STATUS mandatory
	DESCRIPTION
	"This contains link 1 status."
	::= { slot0PhyEntry 13 }

slot0PhyLink2State OBJECT-TYPE
	SYNTAX INTEGER {
		stop(4),
		up(1),
		down(2),
		off(3),
		reset(5)
	}
	ACCESS read-only
	STATUS mandatory
	DESCRIPTION
	"This contains link 2 status."
	::= { slot0PhyEntry 14 }

slot0PhyLink3State OBJECT-TYPE
	SYNTAX INTEGER {
		stop(4),
		up(1),
		down(2),
		off(3),
		reset(5)
	}
	ACCESS read-only
	STATUS mandatory
	DESCRIPTION
	"This contains link 3 status."
	::= { slot0PhyEntry 15 }

slot0PhySlotSerNo OBJECT-TYPE
	SYNTAX DisplayString
	ACCESS read-only
	STATUS mandatory
	DESCRIPTION "Serial number of the slot controller."
	::= { slot0PhyEntry 16 }

slot0PhySlotHwVerNo OBJECT-TYPE
	SYNTAX DisplayString
	ACCESS read-only
	STATUS mandatory
	DESCRIPTION "Hardware version number and revision of the slot controller."
	::= { slot0PhyEntry 17 }

slot0PhyDocSerNo OBJECT-TYPE
	SYNTAX DisplayString
	ACCESS read-only
	STATUS mandatory
	DESCRIPTION "Serial number of the DOC."
	::= { slot0PhyEntry 18 }

slot0PhyDocHwVerNo OBJECT-TYPE
	SYNTAX DisplayString
	ACCESS read-only
	STATUS mandatory
	DESCRIPTION "Hardware version number and revision of the DOC."
	::= { slot0PhyEntry 19 }

slot0PhyMacAddress OBJECT-TYPE
	SYNTAX PhysAddress
	ACCESS read-write
	STATUS mandatory
	DESCRIPTION "MAC address of the slot."
	::= { slot0PhyEntry 20 }

--                              Y2K change : use DateAndTime convention
slot0PhyChangeTimeM2 OBJECT-TYPE
	SYNTAX DateAndTime
	ACCESS read-only
	STATUS mandatory
	DESCRIPTION
	"Last date and time link changed state."
	::= { slot0PhyEntry 21 }

--				New variable to identify the effected link, #10, #12, #13
slot0PhyLstChngLnkNum OBJECT-TYPE
	SYNTAX INTEGER {
		link-0(1),
		link-1(2),
		link-2(3),
		link-3(4),
		none(5)
	}
	ACCESS read-only
	STATUS mandatory
	DESCRIPTION
	"Holds the link number of the last link status to change."
	DEFVAL { none }
	::= { slot0PhyEntry 22 }

--				New variable for previous link state, #10, #13
slot0PhyLstChngPrevLnkStat OBJECT-TYPE
	SYNTAX INTEGER {
		up(1),
		down(2),
		off(3),
		stop(4),
		reset(5),
		none(6)
	}
	ACCESS read-only
	STATUS mandatory
	DESCRIPTION
	"Holds the previous link state of the last link number whose status changed."
	DEFVAL { none }
	::= { slot0PhyEntry 23 }


-- slot0LastTrapMessage Deprecated
--
-- slot0LastTrapMessage OBJECT-TYPE
--	SYNTAX deprecated
--	ACCESS read-only
--	STATUS mandatory
--	DESCRIPTION
--	"This is used to contain the last trap string sent."
--	::= { dv2Slot0 7 }

slot0MaxUpSlots OBJECT-TYPE
	SYNTAX INTEGER
	ACCESS read-only
	STATUS mandatory
	DESCRIPTION
	"The maximum number of slots that have been up."
	::= { dv2Slot0 7 }

slot0CurrentUpSlots OBJECT-TYPE
	SYNTAX INTEGER
	ACCESS read-only
	STATUS mandatory
	DESCRIPTION
	"The number of slots currently up."
	::= { dv2Slot0 8 }

slot0IsStandbySlot0 OBJECT-TYPE
	SYNTAX INTEGER {
		unknown(5),
		not-applicable(4),
		no(1),
		yes(2),
		not-ready(6)
	}
	ACCESS read-only
	STATUS mandatory
	DESCRIPTION
	"Set to yes(2) if there is a redundant slot 0 available."
	::= { dv2Slot0 9 }

slot0TftpToStandby OBJECT-TYPE
	SYNTAX INTEGER {
		yes(2),
		no(1)
	}
	ACCESS read-write
	STATUS mandatory
	DESCRIPTION
	"Set to no(2) to stop files being transferred to the out of service slot0 automatically when they are changed."
	::= { dv2Slot0 10 }

slot0MibBroadcast OBJECT-TYPE
	SYNTAX INTEGER {
		none(1),
		snmp-Authentication(2)
	}
	ACCESS read-write
	STATUS mandatory
	DESCRIPTION
	"Broadcasts particular tables to all other slots."
	::= { dv2Slot0 11 }

--slot0SwitchStatus OBJECT-TYPE
--	SYNTAX INTEGER {
--		s00(1),
--		s01(2),
--		s10(3),
--		s11(4)
--	}
--	ACCESS read-only
--	STATUS mandatory
--	DESCRIPTION
--	"Shows the status of the PSU control switches."
--	::= { dv2Slot0 12 }
--
--slot0SetAlarm OBJECT-TYPE
--	SYNTAX INTEGER {
--		none(1),
--		minor-alarm(2),
--		major-alarm(3),
--		critical-alarm(4)
--	}
--	ACCESS read-write
--	STATUS mandatory
--	DESCRIPTION
--	"Set the alarm status of the PSU."
--	::= { dv2Slot0 13 }

slot0Address OBJECT-TYPE
	SYNTAX E164
	ACCESS read-write
	STATUS mandatory
	DESCRIPTION
	"The E.164 address of the switch."
	::= { dv2Slot0 14 }

slot0InUse OBJECT-TYPE
	SYNTAX	INTEGER {
		unknown(5),
		main-in-service(1),
		standby-in-service(2),
		main-out-of-service(3),
		standby-out-of-service(4),
		main-disabled(6),
		standby-disabled(7)
	}
	ACCESS	read-only
	STATUS	mandatory
	DESCRIPTION
	"The Slot 0 card Redundancy Status."
	::= { dv2Slot0 15 }

slot0ToUse OBJECT-TYPE
	SYNTAX	INTEGER {
		auto(3),
		main(1),
		standby(2),
		not-applicable(4),
		disable(5)
	}
	ACCESS	read-write
	STATUS	mandatory
	DESCRIPTION
	"This indicates the Slot 0 card you want the switch to use."
	::= { dv2Slot0 16 }

slot0redmode OBJECT-TYPE
	SYNTAX	INTEGER {
		unknown(4),
		non-redundant(1),
		basic-redundancy(2),
		enhanced-redundancy(3)
	}
	ACCESS	read-only
	STATUS	mandatory
	DESCRIPTION
	"The Slot 0 card Redundancy mode."
	::= { dv2Slot0 17 }

slot0IntIPMask OBJECT-TYPE
	SYNTAX	IpAddress
	ACCESS	read-write
	STATUS	mandatory
	DESCRIPTION
	"IP Mask for Internal Subnet.
	 To reconfigure, Save new configuration and
	 perform then warm Start."
	::= { dv2Slot0 18 }

slot0SwitchId OBJECT-TYPE
	SYNTAX INTEGER (0..255)
	ACCESS  read-write
	STATUS  mandatory
	DESCRIPTION
	"Switch ID for this Apex node"
	DEFVAL { 0 }
	::= { dv2Slot0 19 }

ntms0doc OBJECT-TYPE
	SYNTAX	INTEGER {
		no(1),
		yes(2)
	}
	ACCESS	read-write
	STATUS	mandatory
	DESCRIPTION
	"Signifies that the S0DOC is capable of communicating with an NTM"
	DEFVAL	{ no }
	::= { dv2Slot0 20 }

slot0LecsPrefix OBJECT-TYPE
	SYNTAX E164
	ACCESS read-write
	STATUS mandatory
	DESCRIPTION
	"The NSAP network prefix for LECS."
	::= { dv2Slot0 21 }

slot0LecsESI OBJECT-TYPE
	SYNTAX E164
	ACCESS read-write
	STATUS mandatory
	DESCRIPTION
	"The NSAP ESI for LECS."
	::= { dv2Slot0 22 }


--___________________________________________________________________________
-- clock sourcing group - dv2Clocks
-- to be depricated

clksTxTimingRef OBJECT-TYPE
	SYNTAX INTEGER {
		system-timing-reference(1),
		local-link0(2),
		local-link1(3),
		local-oscillator(4)
	}
	ACCESS read-write
	STATUS mandatory
	DESCRIPTION
	"Transmit Timing Reference"
	::= { dv2Clocks 1 }

clksSysRefSlotNum OBJECT-TYPE
	SYNTAX INTEGER (0..15)
	ACCESS read-write
	STATUS mandatory
	DESCRIPTION
	"System Timing Reference Slot Number"
	::= { dv2Clocks 2 }

clksSysRefLinkNum OBJECT-TYPE
	SYNTAX INTEGER {
		link0(1),
		link1(2),
		none(3)
	}
	ACCESS read-write
	STATUS mandatory
	DESCRIPTION
	"System Timing Reference Link Number"
	::= { dv2Clocks 3 }


clksSysRefError OBJECT-TYPE
	SYNTAX INTEGER {
		slot0(1),
		slot1(2),
		slot2(3),
		slot3(4),
		slot4(5),
		slot5(6),
		slot6(7),
		slot7(8),
		slot8(9),
		slot9(10),
		slot10(11),
		slot11(12),
		slot12(13),
		slot13(14),
		slot14(15),
		slot15(16),
		none(17)
	}
	ACCESS read-only
	STATUS mandatory
	DESCRIPTION
	"System Timing Error"
	::= { dv2Clocks 4 }



--___________________________________________________________________________
-- clock sourcing group - dv2SystemClocks
--

autoRevert OBJECT-TYPE
	SYNTAX INTEGER {
		no(1),
		yes(2)
	}
	ACCESS read-write
	STATUS mandatory
	DESCRIPTION
	"Automatic Revert after Timing Source Recovery"
	DEFVAL { no }
	::= { dv2SystemClocks 1 }

revertTimer OBJECT-TYPE
	SYNTAX INTEGER (5..60)
	ACCESS read-write
	STATUS mandatory
	DESCRIPTION
	"Revert Timer in Seconds"
	DEFVAL { 30 }
	::= { dv2SystemClocks 2 }

forceRevert OBJECT-TYPE
	SYNTAX INTEGER {
	    no(1),
	    yes(2)
 	}
	ACCESS read-write
	STATUS mandatory
	DESCRIPTION
	"Force Immediate Revert"
	DEFVAL { no }
	::= { dv2SystemClocks 3 }


forceSecondary OBJECT-TYPE
	SYNTAX INTEGER {
	    no(1),
	    yes(2)
	}
	ACCESS read-write
	STATUS mandatory
	DESCRIPTION
	"Force Secondary Source Timing"
	DEFVAL { no }
	::= { dv2SystemClocks 4 }

alarmStatus OBJECT-TYPE
	SYNTAX INTEGER {
	    clear(1),
	    minor(2),
	    major(3)
	}
	ACCESS read-only
	STATUS mandatory
	DESCRIPTION
	"Timing Alarm Status"
	DEFVAL { clear }
	::= { dv2SystemClocks 5 }

inService OBJECT-TYPE
	SYNTAX INTEGER {
	    none(1),
	    pri-line(2),
	    pri-internal(3),
	    pri-stratum3(4),
	    pri-external(5),
	    sec-line(6),
	    sec-internal(7),
	    sec-stratum3(8),
	    sec-external(9),
	    pri-plcp(10),
	    sec-plcp(11)
	}
	ACCESS read-only
	STATUS mandatory
	DESCRIPTION
	"Card in Service"
	DEFVAL { pri-internal }
	::= { dv2SystemClocks 6 }

primaryClockTable	OBJECT-TYPE
	SYNTAX SEQUENCE OF PrimaryEntry
	ACCESS not-accessible
	STATUS mandatory
	::= { dv2SystemClocks 7 }

primaryEntry OBJECT-TYPE
              SYNTAX  PrimaryEntry
              ACCESS  not-accessible
              STATUS  mandatory
	      INDEX  { pIndex  }
              ::= { primaryClockTable 1 }

PrimaryEntry	::=
	SEQUENCE {
	        pIndex
		        INTEGER,
		pValidSource
			INTEGER,
		pOnOffLine
			INTEGER,
		pSlotNumber
			INTEGER,
		pSysRefSelect
			INTEGER,
		pActiveTimingSource
			INTEGER,
		pInputLineOk
			INTEGER,
		pSysRefTimingOk
			INTEGER
}

pIndex OBJECT-TYPE
	SYNTAX INTEGER
	ACCESS read-only
	STATUS mandatory
	DESCRIPTION
	"Entry Index"
	::= { primaryEntry 1 }

pValidSource OBJECT-TYPE
	SYNTAX INTEGER {
	    no(1),
	    yes(2)
        }
	ACCESS read-only
	STATUS mandatory
	DESCRIPTION
	"Valid Timing Source"
	DEFVAL { no }
	::= { primaryEntry 2 }

pOnOffLine OBJECT-TYPE
	SYNTAX INTEGER {
	    on(1),
 	    off(2)
        }
	ACCESS read-write
	STATUS mandatory
	DESCRIPTION
	"On / Off line Toggle"
	DEFVAL { off }
	::= { primaryEntry 3 }

pSlotNumber OBJECT-TYPE
	SYNTAX INTEGER (0..15)
	ACCESS read-write
	STATUS mandatory
	DESCRIPTION
	"Primary Source Slot Number"
	DEFVAL { 0 }
	::= { primaryEntry 4 }

pSysRefSelect OBJECT-TYPE
	SYNTAX INTEGER {
	    link0(1),
	    link1(2),
	    link2(3),
	    link3(4),
	    local-oscillator(5)
 	}
	ACCESS read-write
	STATUS mandatory
	DESCRIPTION
	"System Reference Select"
	DEFVAL { local-oscillator }
	::= { primaryEntry 5 }


pActiveTimingSource OBJECT-TYPE
	SYNTAX INTEGER {
	    line(1),
	    internal(2),
	    plcp(3)
        }
	ACCESS read-only
	STATUS mandatory
	DESCRIPTION
	"Active Timing Reference"
	DEFVAL { internal }
	::= { primaryEntry 6 }


pInputLineOk OBJECT-TYPE
	SYNTAX INTEGER {
	    no(1),
	    yes(2)
	}
	ACCESS read-only
	STATUS mandatory
	DESCRIPTION
	"Input Line OK"
	DEFVAL { no }
	::= { primaryEntry 7 }

pSysRefTimingOk OBJECT-TYPE
	SYNTAX INTEGER {
	    no(1),
	    yes(2)
	}
	ACCESS read-only
	STATUS mandatory
	DESCRIPTION
	"System Reference Timing OK"
	DEFVAL { no }
	::= { primaryEntry 8 }

secondaryClockTable	OBJECT-TYPE
	SYNTAX SEQUENCE OF SecondaryEntry
	ACCESS not-accessible
	STATUS mandatory
	::= { dv2SystemClocks 8 }

secondaryEntry OBJECT-TYPE
              SYNTAX  SecondaryEntry
              ACCESS  not-accessible
              STATUS  mandatory
	      INDEX  { sIndex }
              ::= { secondaryClockTable 1 }

SecondaryEntry	::=
	SEQUENCE {
	        sIndex
		        INTEGER,
		sValidSource
			INTEGER,
		sOnOffLine
			INTEGER,
		sSlotNumber
			INTEGER,
		sSysRefSelect
			INTEGER,
		sActiveTimingSource
			INTEGER,
		sInputLineOk
			INTEGER,
		sSysRefTimingOk
			INTEGER
}
sIndex OBJECT-TYPE
	SYNTAX INTEGER
	ACCESS read-only
	STATUS mandatory
	DESCRIPTION
	"Entry Index"
	::= { secondaryEntry 1 }

sValidSource OBJECT-TYPE
	SYNTAX INTEGER {
	    no(1),
	    yes(2)
        }
	ACCESS read-only
	STATUS mandatory
	DESCRIPTION
	"Valid Timing Source"
	DEFVAL { no }
	::= { secondaryEntry 2 }

sOnOffLine OBJECT-TYPE
	SYNTAX INTEGER {
	    on(1),
 	    off(2)
        }
	ACCESS read-write
	STATUS mandatory
	DESCRIPTION
	"On / Off line Toggle"
	DEFVAL { off }
	::= { secondaryEntry 3 }

sSlotNumber OBJECT-TYPE
	SYNTAX INTEGER (0..15)
	ACCESS read-write
	STATUS mandatory
	DESCRIPTION
	"Secondary Source Slot Number"
	DEFVAL { 0 }
	::= { secondaryEntry 4 }

sSysRefSelect OBJECT-TYPE
	SYNTAX INTEGER {
	    link0(1),
	    link1(2),
	    link2(3),
	    link3(4),
	    local-oscillator(5)
 	}
	ACCESS read-write
	STATUS mandatory
	DESCRIPTION
	"System Reference Select"
	DEFVAL { local-oscillator }
	::= { secondaryEntry 5 }


sActiveTimingSource OBJECT-TYPE
	SYNTAX INTEGER {
	    line(1),
	    internal(2),
	    plcp(3)
        }
	ACCESS read-only
	STATUS mandatory
	DESCRIPTION
	"Active Timing Reference"
	DEFVAL { internal }
	::= { secondaryEntry 6 }


sInputLineOk OBJECT-TYPE
	SYNTAX INTEGER {
	    no(1),
	    yes(2)
	}
	ACCESS read-only
	STATUS mandatory
	DESCRIPTION
	"Input Line OK"
	DEFVAL { no }
	::= { secondaryEntry 7 }

sSysRefTimingOk OBJECT-TYPE
	SYNTAX INTEGER {
	    no(1),
	    yes(2)
	}
	ACCESS read-only
	STATUS mandatory
	DESCRIPTION
	"System Reference Timing OK"
	DEFVAL { no }
	::= { secondaryEntry 8 }

str3Configured OBJECT-TYPE
	SYNTAX INTEGER {
	    no(1),
	    yes(2)
	}
	ACCESS read-only
	STATUS mandatory
	DESCRIPTION
	"CAT Card present"
	DEFVAL { no }
	::= { dv2SystemClocks 9 }

pCATcontrolTable	OBJECT-TYPE
	SYNTAX SEQUENCE OF PCATcontrolEntry
	ACCESS not-accessible
	STATUS mandatory
	::= { dv2SystemClocks 10 }

pCATcontrolEntry OBJECT-TYPE
              SYNTAX  PCATcontrolEntry
              ACCESS  not-accessible
              STATUS  mandatory
	      INDEX  { pccIndex  }
              ::= { pCATcontrolTable 1 }

PCATcontrolEntry	::=
	SEQUENCE {
	        pccIndex
		        INTEGER,
		pccatlimtype
			INTEGER,
                pccatsendcode
			INTEGER,
		pccatactivate
			INTEGER,
		pccatsendconfig
			INTEGER,
		pccatbytestransferred
			INTEGER,
		pccatfilexferstat
			INTEGER,
		pcatforcesecext
			INTEGER,
		pcatforcesecstr3
			INTEGER,
		pcatcommand
			INTEGER,
		pcatplaceholder1
			INTEGER,
		pcatplaceholder2
			INTEGER,
		pcconoffline
			INTEGER
}

pccIndex OBJECT-TYPE
	SYNTAX INTEGER
	ACCESS read-only
	STATUS mandatory
	DESCRIPTION
	"Entry Index"
	::= { pCATcontrolEntry 1 }

pccatlimtype OBJECT-TYPE
	SYNTAX INTEGER {
	    none(1),
	    t1(2),
            e1(3)
        }
	ACCESS read-write
	STATUS mandatory
	DESCRIPTION
	"Type of CAT LIM"
	DEFVAL { t1 }
	::= { pCATcontrolEntry 2 }

pccatsendcode OBJECT-TYPE
	SYNTAX INTEGER {
	    no(1),
	    yes(2)
        }
	ACCESS read-write
	STATUS mandatory
	DESCRIPTION
	"Send code to NTM LIM"
	DEFVAL { no }
	::= { pCATcontrolEntry 3 }

pccatactivate OBJECT-TYPE
	SYNTAX INTEGER {
	    no(1),
	    yes(2)
        }
	ACCESS read-write
	STATUS mandatory
	DESCRIPTION
	"Activate NTM Code"
	DEFVAL { no }
	::= { pCATcontrolEntry 4 }

pccatsendconfig OBJECT-TYPE
	SYNTAX INTEGER {
	    no(1),
	    yes(2)
        }
	ACCESS read-write
	STATUS mandatory
	DESCRIPTION
	"Send Configuration to NTM LIM"
	DEFVAL { no }
	::= { pCATcontrolEntry 5 }

pccatbytestransferred OBJECT-TYPE
	SYNTAX INTEGER
	ACCESS read-only
	STATUS mandatory
	DESCRIPTION
	"Code bytes transferred to NTM LIM"
	::= { pCATcontrolEntry 6 }


pccatfilexferstat OBJECT-TYPE
	SYNTAX	INTEGER  { idle(1), start(2), continue(3), end(4), ack(5), aborted(6), error(7) }
	ACCESS read-only
	STATUS mandatory
	DESCRIPTION
	"File transfer status as reported by Slot 0"
	::= { pCATcontrolEntry 7 }

pcatforcesecext OBJECT-TYPE
	SYNTAX INTEGER {
	    no(1),
	    yes(2)
        }
	ACCESS read-write
	STATUS mandatory
	DESCRIPTION
	"Force the secondary external"
	DEFVAL { no }
	::= { pCATcontrolEntry 8 }


pcatforcesecstr3 OBJECT-TYPE
	SYNTAX INTEGER {
	    no(1),
	    yes(2)
        }
	ACCESS read-write
	STATUS mandatory
	DESCRIPTION
	"Force the secondary stratum 3"
	DEFVAL { no }
	::= { pCATcontrolEntry 9 }

pcatcommand OBJECT-TYPE
	SYNTAX INTEGER {
	    none(1),
	    revert(2)
        }
	ACCESS read-only
	STATUS mandatory
	DESCRIPTION
	"Internal Use"
	DEFVAL { none }
	::= { pCATcontrolEntry 10 }


pcatplaceholder1 OBJECT-TYPE
	SYNTAX INTEGER {
	    na(1)
        }
	ACCESS read-only
	STATUS mandatory
	DESCRIPTION
	"Placeholder for future MIB changes"
	DEFVAL { na }
	::= { pCATcontrolEntry 11 }


pcatplaceholder2 OBJECT-TYPE
	SYNTAX INTEGER {
	    na(1)
        }
	ACCESS read-only
	STATUS mandatory
	DESCRIPTION
	"Placeholder for future MIB changes"
	DEFVAL { na }
	::= { pCATcontrolEntry 12 }

pcconoffline OBJECT-TYPE
	SYNTAX INTEGER {
	    offline(1),
	    online(2)
        }
	ACCESS read-write
	STATUS mandatory
	DESCRIPTION
	"Put NTM LIM on or offline"
	DEFVAL { offline }
	::= { pCATcontrolEntry 13 }

-- CAT Secondary Control

sCATcontrolTable	OBJECT-TYPE
	SYNTAX SEQUENCE OF SCATcontrolEntry
	ACCESS not-accessible
	STATUS mandatory
	::= { dv2SystemClocks 11 }

sCATcontrolEntry OBJECT-TYPE
              SYNTAX  SCATcontrolEntry
              ACCESS  not-accessible
              STATUS  mandatory
	      INDEX  { sccIndex  }
              ::= { sCATcontrolTable 1 }

SCATcontrolEntry	::=
	SEQUENCE {
	        sccIndex
		        INTEGER,
		sccatlimtype
			INTEGER,
                sccatsendcode
			INTEGER,
		sccatactivate
			INTEGER,
		sccatsendconfig
			INTEGER,
		sccatbytestransferred
			INTEGER,
		sccatfilexferstat
			INTEGER,
		scatcommand
			INTEGER,
		scatplaceholder1
			INTEGER,
		scatplaceholder2
			INTEGER,
		scconoffline
			INTEGER
}
sccIndex OBJECT-TYPE
	SYNTAX INTEGER
	ACCESS read-only
	STATUS mandatory
	DESCRIPTION
	"Entry Index"
	::= { sCATcontrolEntry 1 }

sccatlimtype OBJECT-TYPE
	SYNTAX INTEGER {
	    none(1),
	    t1(2),
            e1(3)
        }
	ACCESS read-write
	STATUS mandatory
	DESCRIPTION
	"Type of NTM LIM"
	DEFVAL { t1 }
	::= { sCATcontrolEntry 2 }

sccatsendcode OBJECT-TYPE
	SYNTAX INTEGER {
	    no(1),
	    yes(2)
        }
	ACCESS read-write
	STATUS mandatory
	DESCRIPTION
	"Download code to NTM LIM"
	DEFVAL { no }
	::= { sCATcontrolEntry 3 }

sccatactivate OBJECT-TYPE
	SYNTAX INTEGER {
	    no(1),
	    yes(2)
        }
	ACCESS read-write
	STATUS mandatory
	DESCRIPTION
	"Activate NTM Code"
	DEFVAL { no }
	::= { sCATcontrolEntry 4 }

sccatsendconfig OBJECT-TYPE
	SYNTAX INTEGER {
	    no(1),
	    yes(2)
        }
	ACCESS read-write
	STATUS mandatory
	DESCRIPTION
	"Download Configuration to NTM LIM"
	DEFVAL { no }
	::= { sCATcontrolEntry 5 }

sccatbytestransferred OBJECT-TYPE
	SYNTAX INTEGER
	ACCESS read-only
	STATUS mandatory
	DESCRIPTION
	"Code bytes transferred to NTM LIM"
	::= { sCATcontrolEntry 6 }

sccatfilexferstat OBJECT-TYPE
	SYNTAX	INTEGER  { idle(1), start(2), continue(3), end(4), ack(5), aborted(6), error(7) }
	ACCESS read-only
	STATUS mandatory
	DESCRIPTION
	"File transfer status as reported by Slot 0"
	::= { sCATcontrolEntry 7 }

scatcommand OBJECT-TYPE
	SYNTAX INTEGER {
	    none(1),
	    revert(2)
        }
	ACCESS read-only
	STATUS mandatory
	DESCRIPTION
	"Internal Use"
	DEFVAL { none }
	::= { sCATcontrolEntry 8 }


scatplaceholder1 OBJECT-TYPE
	SYNTAX INTEGER {
	    na(1)
        }
	ACCESS read-only
	STATUS mandatory
	DESCRIPTION
	"Placeholder for future MIB changes"
	DEFVAL { na }
	::= { sCATcontrolEntry 9 }


scatplaceholder2 OBJECT-TYPE
	SYNTAX INTEGER {
	    na(1)
        }
	ACCESS read-only
	STATUS mandatory
	DESCRIPTION
	"Placeholder for future MIB changes"
	DEFVAL { na }
	::= { sCATcontrolEntry 10 }

scconoffline OBJECT-TYPE
	SYNTAX INTEGER {
	    offline(1),
	    online(2)
        }
	ACCESS read-write
	STATUS mandatory
	DESCRIPTION
	"Put NTM LIM on or offline"
	DEFVAL { offline }
	::= { sCATcontrolEntry 11 }

-- CAT Primary Status

pCATstatusTable		OBJECT-TYPE
	SYNTAX SEQUENCE OF PCATstatusEntry
	ACCESS not-accessible
	STATUS mandatory
	::= { dv2SystemClocks 12 }

pCATstatusEntry OBJECT-TYPE
              SYNTAX  PCATstatusEntry
              ACCESS  not-accessible
              STATUS  mandatory
	      INDEX  { pscIndex  }
              ::= { pCATstatusTable 1 }

PCATstatusEntry	::=
	SEQUENCE {
	        pscIndex
		        INTEGER,
		pscatlimtype
			INTEGER,
                psCATFFrevision
                        DisplayString,
                psCATBootrevision
                        DisplayString,
                psCATHWrevision
                        INTEGER,
		pscatfilestatus
			INTEGER,
                psCATfilerevision
                        DisplayString,
		pscatmode
			INTEGER,
		pscaterrorcode
			INTEGER,
		pscatplaceholder1
			INTEGER,
		pscatplaceholder2
			INTEGER
}

pscIndex OBJECT-TYPE
	SYNTAX INTEGER
	ACCESS read-only
	STATUS mandatory
	DESCRIPTION
	"Entry Index"
	::= { pCATstatusEntry 1 }

pscatlimtype OBJECT-TYPE
	SYNTAX INTEGER {
	    none(1),
	    t1(2),
            e1(3)
        }
	ACCESS read-only
	STATUS mandatory
	DESCRIPTION
	"Type of NTM LIM detected"
	DEFVAL { none }
	::= { pCATstatusEntry 2 }

psCATFFrevision OBJECT-TYPE
	SYNTAX DisplayString
	ACCESS read-only
	STATUS mandatory
	DESCRIPTION "NTM LIM Code Revision"
	::= { pCATstatusEntry 3 }

psCATBootrevision OBJECT-TYPE
	SYNTAX DisplayString
	ACCESS read-only
	STATUS mandatory
	DESCRIPTION "NTM LIM Boot Revision"
	::= { pCATstatusEntry 4 }


pscatfilestatus OBJECT-TYPE
	SYNTAX INTEGER {
	    na(1),
	    not-present(2),
            present(3)
        }
	ACCESS read-only
	STATUS mandatory
	DESCRIPTION
	"Flash file status"
	DEFVAL { na }
	::= { pCATstatusEntry 5 }


psCATfilerevision OBJECT-TYPE
	SYNTAX DisplayString
	ACCESS read-only
	STATUS mandatory
	DESCRIPTION "NTM LIM file Revision"
	::= { pCATstatusEntry 6 }

psCATHWrevision OBJECT-TYPE
	SYNTAX INTEGER
	ACCESS read-only
	STATUS mandatory
	DESCRIPTION "NTM LIM Hardware Revision"
	::= { pCATstatusEntry 7 }


pscatmode OBJECT-TYPE
	SYNTAX INTEGER {
            no-card(3),
	    boot(1),
	    full-feature-offline(2),
            unknown(4),
	    full-feature-in-dnld(5),
	    boot-in-dnld(6),
	    full-feature-online(7)
        }
	ACCESS read-only
	STATUS mandatory
	DESCRIPTION
	"Operating Mode of NTM LIM"
	DEFVAL { no-card }
	::= { pCATstatusEntry 8 }

pscaterrorcode OBJECT-TYPE
	SYNTAX INTEGER {
	    none(1),
            bad-config(3),
            no-code(4),
	    no-config(5),
	    download-ok(6),
	    download-fail(7)
        }
	ACCESS read-only
	STATUS mandatory
	DESCRIPTION
	"NTM LIM Error Code"
	DEFVAL { none }
	::= { pCATstatusEntry 9 }


pscatplaceholder1 OBJECT-TYPE
	SYNTAX INTEGER {
	    na(1)
        }
	ACCESS read-only
	STATUS mandatory
	DESCRIPTION
	"Placeholder for future MIB changes"
	DEFVAL { na }
	::= { pCATstatusEntry 10 }


pscatplaceholder2 OBJECT-TYPE
	SYNTAX INTEGER {
	    na(1)
        }
	ACCESS read-only
	STATUS mandatory
	DESCRIPTION
	"Placeholder for future MIB changes"
	DEFVAL { na }
	::= { pCATstatusEntry 11 }

-- CAT Secondary Status

sCATstatusTable		OBJECT-TYPE
	SYNTAX SEQUENCE OF SCATstatusEntry
	ACCESS not-accessible
	STATUS mandatory
	::= { dv2SystemClocks 13 }

sCATstatusEntry OBJECT-TYPE
              SYNTAX  SCATstatusEntry
              ACCESS  not-accessible
              STATUS  mandatory
	      INDEX  { sscIndex  }
              ::= { sCATstatusTable 1 }

SCATstatusEntry	::=
	SEQUENCE {
	        sscIndex
		        INTEGER,
		sscatlimtype
			INTEGER,
                ssCATFFrevision
                        DisplayString,
                ssCATBootrevision
                        DisplayString,
		sscatfilestatus
			INTEGER,
                ssCATfilerevision
                        DisplayString,
                ssCATHWrevision
                        INTEGER,
		sscatmode
			INTEGER,
		sscaterrorcode
			INTEGER,
		sscatplaceholder1
			INTEGER,
		sscatplaceholder2
			INTEGER
}

sscIndex OBJECT-TYPE
	SYNTAX INTEGER
	ACCESS read-only
	STATUS mandatory
	DESCRIPTION
	"Entry Index"
	::= { sCATstatusEntry 1 }

sscatlimtype OBJECT-TYPE
	SYNTAX INTEGER {
	    none(1),
	    t1(2),
            e1(3)
        }
	ACCESS read-only
	STATUS mandatory
	DESCRIPTION
	"Type of NTM LIM"
	DEFVAL { none }
	::= { sCATstatusEntry 2 }

ssCATFFrevision OBJECT-TYPE
	SYNTAX DisplayString
	ACCESS read-only
	STATUS mandatory
	DESCRIPTION "NTM LIM Code Revision"
	::= { sCATstatusEntry 3 }

ssCATBootrevision OBJECT-TYPE
	SYNTAX DisplayString
	ACCESS read-only
	STATUS mandatory
	DESCRIPTION "NTM LIM Boot Revision"
	::= { sCATstatusEntry 4 }


sscatfilestatus OBJECT-TYPE
	SYNTAX INTEGER {
	    na(1),
	    not-present(2),
            present(3)
        }
	ACCESS read-only
	STATUS mandatory
	DESCRIPTION
	"Flash file status"
	DEFVAL { na }
	::= { sCATstatusEntry 5 }


ssCATfilerevision OBJECT-TYPE
	SYNTAX DisplayString
	ACCESS read-only
	STATUS mandatory
	DESCRIPTION "NTM LIM file Revision"
	::= { sCATstatusEntry 6 }

ssCATHWrevision OBJECT-TYPE
	SYNTAX INTEGER
	ACCESS read-only
	STATUS mandatory
	DESCRIPTION "NTM LIM Hardware Revision"
	::= { sCATstatusEntry 7 }


sscatmode OBJECT-TYPE
	SYNTAX INTEGER {
	    no-card(3),
	    boot(1),
	    full-feature-offline(2),
            unknown(4),
	    full-feature-in-dnld(5),
	    boot-in-dnld(6),
	    full-feature-online(7)
        }
	ACCESS read-only
	STATUS mandatory
	DESCRIPTION
	"Operating mode of NTM LIM"
	DEFVAL { no-card }
	::= { sCATstatusEntry 8 }

sscaterrorcode OBJECT-TYPE
	SYNTAX INTEGER {
	    none(1),
	    no-cat(2),
            bad-config(3),
            no-code(4),
	    no-config(5),
	    download-ok(6),
	    download-fail(7)
        }
	ACCESS read-only
	STATUS mandatory
	DESCRIPTION
	"NTM LIM Error Code"
	DEFVAL { none }
	::= { sCATstatusEntry 9 }



sscatplaceholder1 OBJECT-TYPE
	SYNTAX INTEGER {
	    na(1)
        }
	ACCESS read-only
	STATUS mandatory
	DESCRIPTION
	"Placeholder for future MIB changes"
	DEFVAL { na }
	::= { sCATstatusEntry 10 }


sscatplaceholder2 OBJECT-TYPE
	SYNTAX INTEGER {
	    na(1)
        }
	ACCESS read-only
	STATUS mandatory
	DESCRIPTION
	"Placeholder for future MIB changes"
	DEFVAL { na }
	::= { sCATstatusEntry 11 }

-- CAT Primary Stratum 3 Config

pCATStratum3ConfigTable		OBJECT-TYPE
	SYNTAX SEQUENCE OF PCATStratum3ConfigEntry
	ACCESS not-accessible
	STATUS mandatory
	::= { dv2SystemClocks 14 }

pCATStratum3ConfigEntry OBJECT-TYPE
              SYNTAX  PCATStratum3ConfigEntry
              ACCESS  not-accessible
              STATUS  mandatory
	      INDEX  { ps3cIndex  }
              ::= { pCATStratum3ConfigTable 1 }

PCATStratum3ConfigEntry	::=
	SEQUENCE {
	        ps3cIndex
		        INTEGER,
                pcatstr3listener
                        INTEGER,
                pcatstr3oscillator
                        INTEGER,
                pcatstr3forcesecondary
                        INTEGER,
		pcatstr3reconfigure
			INTEGER
}

ps3cIndex OBJECT-TYPE
	SYNTAX INTEGER
	ACCESS read-only
	STATUS mandatory
	DESCRIPTION
	"Entry Index"
	::= { pCATStratum3ConfigEntry 1 }

pcatstr3listener OBJECT-TYPE
	SYNTAX INTEGER {
	    external(1),
	    line(2)
        }
	ACCESS read-write
	STATUS mandatory
	DESCRIPTION
	"Configures Stratum 3 Reference"
	DEFVAL { external }
	::= { pCATStratum3ConfigEntry 2 }

pcatstr3oscillator OBJECT-TYPE
	SYNTAX INTEGER {
	    external-or-line(1),
	    internal(2)
        }
	ACCESS read-write
	STATUS mandatory
	DESCRIPTION
	"Configures Stratum 3 Mode"
	DEFVAL { external-or-line }
	::= { pCATStratum3ConfigEntry 3 }

pcatstr3forcesecondary OBJECT-TYPE
	SYNTAX INTEGER {
	    no(1),
	    yes(2)
        }
	ACCESS read-write
	STATUS mandatory
	DESCRIPTION
	"Disables Stratum 3 Driver on Primary NTM LIM only"
	DEFVAL { no }
	::= { pCATStratum3ConfigEntry 4 }


pcatstr3reconfigure OBJECT-TYPE
	SYNTAX INTEGER {
	    no(1),
	    yes(2)
        }
	ACCESS read-write
	STATUS mandatory
	DESCRIPTION
	"Re-configure Primary Stratum 3"
	DEFVAL { no }
	::= { pCATStratum3ConfigEntry 5 }

-- CAT Secondary Stratum 3 Config

sCATStratum3ConfigTable		OBJECT-TYPE
	SYNTAX SEQUENCE OF SCATStratum3ConfigEntry
	ACCESS not-accessible
	STATUS mandatory
	::= { dv2SystemClocks 15 }

sCATStratum3ConfigEntry OBJECT-TYPE
              SYNTAX  SCATStratum3ConfigEntry
              ACCESS  not-accessible
              STATUS  mandatory
	      INDEX  { ss3cIndex  }
              ::= { sCATStratum3ConfigTable 1 }

SCATStratum3ConfigEntry	::=
	SEQUENCE {
	        ss3cIndex
		        INTEGER,
                scatstr3listener
                        INTEGER,
                scatstr3oscillator
                        INTEGER,
		scatstr3reconfigure
			INTEGER
}

ss3cIndex OBJECT-TYPE
	SYNTAX INTEGER
	ACCESS read-only
	STATUS mandatory
	DESCRIPTION
	"Entry Index"
	::= { sCATStratum3ConfigEntry 1 }

scatstr3listener OBJECT-TYPE
	SYNTAX INTEGER {
	    external(1),
	    line(2)
        }
	ACCESS read-write
	STATUS mandatory
	DESCRIPTION
	"Configures Stratum 3 Reference"
	DEFVAL { external }
	::= { sCATStratum3ConfigEntry 2 }

scatstr3oscillator OBJECT-TYPE
	SYNTAX INTEGER {
	    external-or-line(1),
	    internal(2)
        }
	ACCESS read-write
	STATUS mandatory
	DESCRIPTION
	"Configures Stratum 3 Mode"
	DEFVAL { external-or-line }
	::= { sCATStratum3ConfigEntry 3 }

scatstr3reconfigure OBJECT-TYPE
	SYNTAX INTEGER {
	    no(1),
	    yes(2)
        }
	ACCESS read-write
	STATUS mandatory
	DESCRIPTION
	"Re-configure Secondary Stratum 3"
	DEFVAL { no }
	::= { sCATStratum3ConfigEntry 4 }

-- CAT Primary Stratum 3 Status

pCATStratum3StatusTable	OBJECT-TYPE
	SYNTAX SEQUENCE OF PCATStratum3StatusEntry
	ACCESS not-accessible
	STATUS mandatory
	::= { dv2SystemClocks 16 }

pCATStratum3StatusEntry OBJECT-TYPE
              SYNTAX  PCATStratum3StatusEntry
              ACCESS  not-accessible
              STATUS  mandatory
	      INDEX  { ps3sIndex  }
              ::= { pCATStratum3StatusTable 1 }

PCATStratum3StatusEntry	::=
	SEQUENCE {
	        ps3sIndex
		        INTEGER,
                pcatstr3listenerstatus
                        INTEGER,
                pcatstr3driverstatus
                        INTEGER,
                pcatstr3oscstatus
                        INTEGER
}

ps3sIndex OBJECT-TYPE
	SYNTAX INTEGER
	ACCESS read-only
	STATUS mandatory
	DESCRIPTION
	"Entry Index"
	::= { pCATStratum3StatusEntry 1 }

pcatstr3listenerstatus OBJECT-TYPE
	SYNTAX INTEGER {
	    listening-to-Primary(1),
	    listening-to-Secondary(2),
            no-input(3)
        }
	ACCESS read-only
	STATUS mandatory
	DESCRIPTION
	"What the Stratum 3 is referencing to"
	DEFVAL { no-input }
	::= { pCATStratum3StatusEntry 2 }

pcatstr3driverstatus OBJECT-TYPE
	SYNTAX INTEGER {
	    enabled-online(1),
            disabled-offline(2),
            fault(3)
        }
	ACCESS read-only
	STATUS mandatory
	DESCRIPTION
	"What the Stratum 3 output is driving"
	DEFVAL { fault }
	::= { pCATStratum3StatusEntry 3 }

pcatstr3oscstatus OBJECT-TYPE
	SYNTAX INTEGER {
	    idle(1),
	    acquisition-wide-band(2),
            locked-in-range(3),
            acquisition-narrow-band(4),
            holdover(5),
            internal(6)
        }
	ACCESS read-only
	STATUS mandatory
	DESCRIPTION
	"Stratum 3 oscillator status"
	DEFVAL { idle }
	::= { pCATStratum3StatusEntry 4 }

-- CAT Secondary Stratum 3 Status

sCATStratum3StatusTable	OBJECT-TYPE
	SYNTAX SEQUENCE OF SCATStratum3StatusEntry
	ACCESS not-accessible
	STATUS mandatory
	::= { dv2SystemClocks 17 }

sCATStratum3StatusEntry OBJECT-TYPE
              SYNTAX  SCATStratum3StatusEntry
              ACCESS  not-accessible
              STATUS  mandatory
	      INDEX  { ss3sIndex  }
              ::= { sCATStratum3StatusTable 1 }

SCATStratum3StatusEntry	::=
	SEQUENCE {
	        ss3sIndex
		        INTEGER,
                scatstr3listenerstatus
                        INTEGER,
                scatstr3driverstatus
                        INTEGER,
                scatstr3oscstatus
                        INTEGER
}

ss3sIndex OBJECT-TYPE
	SYNTAX INTEGER
	ACCESS read-only
	STATUS mandatory
	DESCRIPTION
	"Entry Index"
	::= { sCATStratum3StatusEntry 1 }

scatstr3listenerstatus OBJECT-TYPE
	SYNTAX INTEGER {
	    listening-to-Primary(1),
	    listening-to-secondary(2),
            no-input(3)
        }
	ACCESS read-only
	STATUS mandatory
	DESCRIPTION
	"What the Stratum 3 Listener is referencing"
	DEFVAL { no-input }
	::= { sCATStratum3StatusEntry 2 }

scatstr3driverstatus OBJECT-TYPE
	SYNTAX INTEGER {
	    enabled-online(1),
            disabled-offline(2),
            fault(3)
        }
	ACCESS read-only
	STATUS mandatory
	DESCRIPTION
	"What the Stratum 3 output is driving"
	DEFVAL { fault }
	::= { sCATStratum3StatusEntry 3 }

scatstr3oscstatus OBJECT-TYPE
	SYNTAX INTEGER {
	    idle(1),
	    acquisition-wide-band(2),
            locked-in-range(3),
            acquisition-narrow-band(4),
            holdover(5),
            internal(6)
        }
	ACCESS read-only
	STATUS mandatory
	DESCRIPTION
	"Stratum 3 oscillator status"
	DEFVAL { idle }
	::= { sCATStratum3StatusEntry 4 }

-- CAT Primary BITS configuration

pCATBitsConfigTable OBJECT-TYPE
	SYNTAX SEQUENCE OF PCATBitsConfigEntry
	ACCESS not-accessible
	STATUS mandatory
	::= { dv2SystemClocks 18 }

pCATBitsConfigEntry OBJECT-TYPE
              SYNTAX  PCATBitsConfigEntry
              ACCESS  not-accessible
              STATUS  mandatory
	      INDEX  { pbcIndex  }
              ::= { pCATBitsConfigTable 1 }

PCATBitsConfigEntry	::=
	SEQUENCE {
	        pbcIndex
		        INTEGER,
                pbcds1V2TxLineLn
                        INTEGER,
		pbcplaceholder1
		        INTEGER,
                pbcV2FRMRMode
                        INTEGER,
                pbcds1V2Coding
                        INTEGER,
                pbcV2Lb
                        INTEGER,
		pbcclrperf
			INTEGER,
		pbcreconfigure
			INTEGER
}

pbcIndex OBJECT-TYPE
	SYNTAX INTEGER
	ACCESS read-only
	STATUS mandatory
	DESCRIPTION
	"Entry Index"
	::= { pCATBitsConfigEntry 1 }

pbcds1V2TxLineLn   OBJECT-TYPE
        SYNTAX  INTEGER
        {
		feet-0-110(1),
                feet-110-220(2),
                feet-220-330(3),
                feet-330-440(4),
                feet-440-550(5),
                feet-550-660(6),
                more-than-655-ft(7),
		na(8)
        }
        ACCESS  read-write
        STATUS  mandatory
        DESCRIPTION
        "Select transmit line length"
        DEFVAL { na }
        ::= { pCATBitsConfigEntry 2 }


pbcplaceholder1	OBJECT-TYPE
	SYNTAX	INTEGER
	{
		na(1)
	}
	ACCESS	read-write
	STATUS	mandatory
	DESCRIPTION
	"Future Use"
        DEFVAL { na }
	::= { pCATBitsConfigEntry 3 }


pbcV2FRMRMode   OBJECT-TYPE
        SYNTAX  INTEGER
        {
                none(1),
                sf(2),
                esf(3)
        }
        ACCESS  read-write
        STATUS  mandatory
        DESCRIPTION
        "DS1 Framing options."
        DEFVAL { none }
        ::= { pCATBitsConfigEntry 4 }

pbcds1V2Coding     OBJECT-TYPE
        SYNTAX  INTEGER
        {
               na(3),
               ami(2),
               b8zs-t1(1)
        }
        ACCESS  read-write
        STATUS  mandatory
        DESCRIPTION
        "T1 Line Code"
        DEFVAL { na }
        ::= { pCATBitsConfigEntry 5 }

pbcV2Lb OBJECT-TYPE
        SYNTAX  INTEGER
        {
          none(1),
          line-loopback(2),
          local-loopback(3)
        }
        ACCESS  read-write
        STATUS  mandatory
        DESCRIPTION
        "Loopback Selection DS1 "
        DEFVAL { none }
        ::= { pCATBitsConfigEntry 6 }

pbcclrperf	OBJECT-TYPE
	SYNTAX	INTEGER
	{
		no(1),
		yes(2)
	}
	ACCESS	read-write
	STATUS	mandatory
	DESCRIPTION
	"Clear the Performance Counters"
        DEFVAL { no }
	::= { pCATBitsConfigEntry 7 }


pbcreconfigure	OBJECT-TYPE
	SYNTAX	INTEGER
	{
		no(1),
		yes(2)
	}
	ACCESS	read-write
	STATUS	mandatory
	DESCRIPTION
	"Re-configure Primary External"
        DEFVAL { no }
	::= { pCATBitsConfigEntry 9 }

-- CAT Secondary BITS configuration

sCATBitsConfigTable OBJECT-TYPE
	SYNTAX SEQUENCE OF SCATBitsConfigEntry
	ACCESS not-accessible
	STATUS mandatory
	::= { dv2SystemClocks 19 }

sCATBitsConfigEntry OBJECT-TYPE
              SYNTAX  SCATBitsConfigEntry
              ACCESS  not-accessible
              STATUS  mandatory
	      INDEX  { sbcIndex  }
              ::= { sCATBitsConfigTable 1 }

SCATBitsConfigEntry	::=
	SEQUENCE {
	        sbcIndex
		        INTEGER,
                sbcds1V2TxLineLn
                        INTEGER,
                sbcplaceholder1
		        INTEGER,
		sbcV2FRMRMode
                        INTEGER,
                sbcds1V2Coding
                        INTEGER,
                sbcV2Lb
                        INTEGER,
		sbcclrperf
			INTEGER,
		sbcreconfigure
			INTEGER
}

sbcIndex OBJECT-TYPE
	SYNTAX INTEGER 
	ACCESS read-only
	STATUS mandatory
	DESCRIPTION
	"Entry Index"
	::= { sCATBitsConfigEntry 1 }

sbcds1V2TxLineLn   OBJECT-TYPE
        SYNTAX  INTEGER
        {
		feet-0-110(1),
                feet-110-220(2),
                feet-220-330(3),
                feet-330-440(4),
                feet-440-550(5),
                feet-550-660(6),
                more-than-655-ft(7),
		na(8)
        }
        ACCESS  read-write
        STATUS  mandatory
        DESCRIPTION
        "Select transmit line length"
        DEFVAL { na }
        ::= { sCATBitsConfigEntry 2 }


sbcplaceholder1	OBJECT-TYPE
	SYNTAX	INTEGER
	{
		na(1)
	}
	ACCESS	read-write
	STATUS	mandatory
	DESCRIPTION
	"Future Use"
        DEFVAL { na }
	::= { sCATBitsConfigEntry 3 }


sbcV2FRMRMode   OBJECT-TYPE
        SYNTAX  INTEGER
        {
                none(1),
                sf(2),
                esf(3)
        }
        ACCESS  read-write
        STATUS  mandatory
        DESCRIPTION
        "DS1 Framing options."
        DEFVAL { none }
        ::= { sCATBitsConfigEntry 4 }

sbcds1V2Coding     OBJECT-TYPE
        SYNTAX  INTEGER
        {
               na(3),
               ami(2),
               b8zs(1)
        }
        ACCESS  read-write
        STATUS  mandatory
        DESCRIPTION
        "T1 Line Coding"
        DEFVAL { na }
        ::= { sCATBitsConfigEntry 5 }

sbcV2Lb OBJECT-TYPE
        SYNTAX  INTEGER
        {
          none(1),
          line-loopback(2),
          local-loopback(3)
        }
        ACCESS  read-write
        STATUS  mandatory
        DESCRIPTION
        "Loopback Selection"
        DEFVAL { none }
        ::= { sCATBitsConfigEntry 6 }

sbcclrperf	OBJECT-TYPE
	SYNTAX	INTEGER
	{
		no(1),
		yes(2)
	}
	ACCESS	read-write
	STATUS	mandatory
	DESCRIPTION
	"Clear the Performance Counters"
        DEFVAL { no }
	::= { sCATBitsConfigEntry 7 }

sbcreconfigure	OBJECT-TYPE
	SYNTAX	INTEGER
	{
		no(1),
		yes(2)
	}
	ACCESS	read-write
	STATUS	mandatory
	DESCRIPTION
	"Re-configure Secondary External"
        DEFVAL { no }
	::= { sCATBitsConfigEntry 8 }

-- CAT Primary BITS Status

pCATBitsStatusTable      OBJECT-TYPE
        SYNTAX  SEQUENCE OF PCATBitsStatusEntry
        ACCESS  not-accessible
        STATUS  mandatory
        DESCRIPTION
        "Ds1/E1 Bits Status Table"
        ::= { dv2SystemClocks 20 }

pCATBitsStatusEntry      OBJECT-TYPE
        SYNTAX  PCATBitsStatusEntry
        ACCESS  not-accessible
        STATUS  mandatory
        INDEX   { pbsIndex }
        ::= { pCATBitsStatusTable 1 }

PCATBitsStatusEntry ::=
        SEQUENCE {
                pbsIndex
                        INTEGER,
		pbslineok
			INTEGER,
		pbsV2RxAIS
			INTEGER,
		pbsV2RxLOS
			INTEGER,
		pbsV2RxOOF
			INTEGER,
		pbsV2RxBER
			INTEGER,
		pbsV2RxOOFCnt
			INTEGER,
		pbsV2RxBERCnt
			INTEGER,
		pbsV2RxLOSCnt
			INTEGER,
		pbsV2LCVCnt
			INTEGER
}

pbsIndex  OBJECT-TYPE
        SYNTAX  INTEGER 
        ACCESS  read-only
        STATUS  mandatory
        DESCRIPTION
        "Entry Index"
        ::= { pCATBitsStatusEntry 1 }


pbslineok   OBJECT-TYPE
        SYNTAX INTEGER {
                no(1),
                yes(2),
		na(3)
        }
        ACCESS read-only
        STATUS mandatory
        DESCRIPTION
        "Is the line OK"
        ::= { pCATBitsStatusEntry 2 }

pbsV2RxAIS   OBJECT-TYPE
        SYNTAX INTEGER {
                no(1),
                yes(2),
		na(3)
        }
        ACCESS read-only
        STATUS mandatory
        DESCRIPTION
        "Receive DS1 AIS(Blue)Alarm status."
        ::= { pCATBitsStatusEntry 3 }

pbsV2RxLOS   OBJECT-TYPE
        SYNTAX INTEGER {
                no(1),
                yes(2)
        }
        ACCESS read-only
        STATUS mandatory
        DESCRIPTION
        "Receive DS1 LOS status."
        ::= { pCATBitsStatusEntry 4 }

pbsV2RxOOF   OBJECT-TYPE
        SYNTAX INTEGER {
                no(1),
                yes(2),
		na(3)
        }
        ACCESS read-only
        STATUS mandatory
        DESCRIPTION
        "Receive DS1 OOF status."
        ::= { pCATBitsStatusEntry 5 }

pbsV2RxBER   OBJECT-TYPE
        SYNTAX INTEGER {
                no(1),
                yes(2),
		na(3)
        }
        ACCESS read-only
        STATUS mandatory
        DESCRIPTION
        "Receive DS1 BER status."
        ::= { pCATBitsStatusEntry 6 }

pbsV2RxOOFCnt   OBJECT-TYPE
        SYNTAX INTEGER
        ACCESS read-only
        STATUS mandatory
        DESCRIPTION
        "Receive DS1 OOF count."
        ::= { pCATBitsStatusEntry 7 }

pbsV2RxBERCnt   OBJECT-TYPE
        SYNTAX INTEGER
        ACCESS read-only
        STATUS mandatory
        DESCRIPTION
        "Receive DS1 BEE count."
        ::= { pCATBitsStatusEntry 8 }

pbsV2RxLOSCnt   OBJECT-TYPE
        SYNTAX INTEGER
        ACCESS read-only
        STATUS mandatory
        DESCRIPTION
        "Receive DS1 LOS count."
        ::= { pCATBitsStatusEntry 9 }

pbsV2LCVCnt   OBJECT-TYPE
        SYNTAX INTEGER
        ACCESS read-only
        STATUS mandatory
        DESCRIPTION
        "Receive DS1 LCV count."
        ::= { pCATBitsStatusEntry 10 }

-- CAT Secondary BITS Status

sCATBitsStatusTable      OBJECT-TYPE
        SYNTAX  SEQUENCE OF SCATBitsStatusEntry
        ACCESS  not-accessible
        STATUS  mandatory
        DESCRIPTION
        "Ds1/E1 Bits Status Table"
        ::= { dv2SystemClocks 21 }

sCATBitsStatusEntry      OBJECT-TYPE
        SYNTAX  SCATBitsStatusEntry
        ACCESS  not-accessible
        STATUS  mandatory
        INDEX   { sbsIndex }
        ::= { sCATBitsStatusTable 1 }

SCATBitsStatusEntry ::=
        SEQUENCE {
                sbsIndex
                        INTEGER,
		sbslineok
			INTEGER,
		sbsV2RxAIS
			INTEGER,
		sbsV2RxLOS
			INTEGER,
		sbsV2RxOOF
			INTEGER,
		sbsV2RxBER
			INTEGER,
		sbsV2RxOOFCnt
			INTEGER,
		sbsV2RxBERCnt
			INTEGER,
		sbsV2RxLOSCnt
			INTEGER,
		sbsV2LCVCnt
			INTEGER
}

sbsIndex  OBJECT-TYPE
        SYNTAX  INTEGER 
        ACCESS  read-only
        STATUS  mandatory
        DESCRIPTION
        "Entry Index"
        ::= { sCATBitsStatusEntry 1 }


sbslineok   OBJECT-TYPE
        SYNTAX INTEGER {
                no(1),
                yes(2),
		na(3)
        }
        ACCESS read-only
        STATUS mandatory
        DESCRIPTION
        "Is the line OK"
        ::= { sCATBitsStatusEntry 2 }

sbsV2RxAIS   OBJECT-TYPE
        SYNTAX INTEGER {
                no(1),
                yes(2),
		na(3)
        }
        ACCESS read-only
        STATUS mandatory
        DESCRIPTION
        "Receive DS1 AIS(Blue)Alarm status."
        ::= { sCATBitsStatusEntry 3 }

sbsV2RxLOS   OBJECT-TYPE
        SYNTAX INTEGER {
                no(1),
                yes(2)
        }
        ACCESS read-only
        STATUS mandatory
        DESCRIPTION
        "Receive DS1 LOS status."
        ::= { sCATBitsStatusEntry 4 }

sbsV2RxOOF   OBJECT-TYPE
        SYNTAX INTEGER {
                no(1),
                yes(2),
		na(3)
        }
        ACCESS read-only
        STATUS mandatory
        DESCRIPTION
        "Receive DS1 OOF status."
        ::= { sCATBitsStatusEntry 5 }

sbsV2RxBER   OBJECT-TYPE
        SYNTAX INTEGER {
                no(1),
                yes(2),
		na(3)
        }
        ACCESS read-only
        STATUS mandatory
        DESCRIPTION
        "Receive DS1 BER  status."
        ::= { sCATBitsStatusEntry 6 }


sbsV2RxOOFCnt   OBJECT-TYPE
        SYNTAX INTEGER
        ACCESS read-only
        STATUS mandatory
        DESCRIPTION
        "Receive DS1 OOF Counts."
        ::= { sCATBitsStatusEntry 7 }

sbsV2RxBERCnt   OBJECT-TYPE
        SYNTAX INTEGER
        ACCESS read-only
        STATUS mandatory
        DESCRIPTION
        "Receive DS1 BEE Counts."
        ::= { sCATBitsStatusEntry 8 }

sbsV2RxLOSCnt   OBJECT-TYPE
        SYNTAX INTEGER
        ACCESS read-only
        STATUS mandatory
        DESCRIPTION
        "Receive DS1/E1 LOS Counts."
        ::= { sCATBitsStatusEntry 9 }

sbsV2LCVCnt   OBJECT-TYPE
        SYNTAX INTEGER
        ACCESS read-only
        STATUS mandatory
        DESCRIPTION
        "Receive DS1 AIS Counts."
        ::= { sCATBitsStatusEntry 10 }

-- CAT Primary Derived T1 configuration

pCATDerConfigTable OBJECT-TYPE
	SYNTAX SEQUENCE OF PCATDerConfigEntry
	ACCESS not-accessible
	STATUS mandatory
	::= { dv2SystemClocks 22 }

pCATDerConfigEntry OBJECT-TYPE
              SYNTAX  PCATDerConfigEntry
              ACCESS  not-accessible
              STATUS  mandatory
	      INDEX  { pdcIndex  }
              ::= { pCATDerConfigTable 1 }

PCATDerConfigEntry	::=
	SEQUENCE {
	        pdcIndex
		        INTEGER,
                pdcds1V2TxLineLn
                        INTEGER,
                pdcplaceholder1
		        INTEGER,
		pdcV2FRMRMode
                        INTEGER,
                pdcds1V2Coding
                        INTEGER,
                pdcV2Lb
                        INTEGER,
		pdcclrperf
			INTEGER,
		pdcreconfigure
			INTEGER
}

pdcIndex OBJECT-TYPE
	SYNTAX INTEGER 
	ACCESS read-only
	STATUS mandatory
	DESCRIPTION
	"Entry Index"
	::= { pCATDerConfigEntry 1 }

pdcds1V2TxLineLn   OBJECT-TYPE
        SYNTAX  INTEGER
        {
		feet-0-110(1),
                feet-110-220(2),
                feet-220-330(3),
                feet-330-440(4),
                feet-440-550(5),
                feet-550-660(6),
                more-than-655-ft(7),
		na(8)
        }
        ACCESS  read-write
        STATUS  mandatory
        DESCRIPTION
        "Select transmit line length"
        DEFVAL { na }
        ::= { pCATDerConfigEntry 2 }

pdcplaceholder1	OBJECT-TYPE
	SYNTAX	INTEGER
	{
		na(1)
	}
	ACCESS	read-write
	STATUS	mandatory
	DESCRIPTION
	"Future Use"
        DEFVAL { na }
	::= { pCATDerConfigEntry 3 }



pdcV2FRMRMode   OBJECT-TYPE
        SYNTAX  INTEGER
        {
                none(1),
                sf(2),
                esf(3)
        }
        ACCESS  read-write
        STATUS  mandatory
        DESCRIPTION
        "DS1 Framing options."
        DEFVAL { none }
        ::= { pCATDerConfigEntry 4 }

pdcds1V2Coding     OBJECT-TYPE
        SYNTAX  INTEGER
        {
		na(3),
                ami(2),
               b8zs(1)
        }
        ACCESS  read-write
        STATUS  mandatory
        DESCRIPTION
        "Line Code"
        DEFVAL { na }
        ::= { pCATDerConfigEntry 5 }

pdcV2Lb OBJECT-TYPE
        SYNTAX  INTEGER
        {
          none(1),
          line-lpbk(2),
          local-loopback(3)
        }
        ACCESS  read-write
        STATUS  mandatory
        DESCRIPTION
        "Loopback Selection "
        ::= { pCATDerConfigEntry 6 }

pdcclrperf	OBJECT-TYPE
	SYNTAX	INTEGER
	{
		no(1),
		yes(2)
	}
	ACCESS	read-write
	STATUS	mandatory
	DESCRIPTION
	"Clear the performance counters"
        DEFVAL { no }
	::= { pCATDerConfigEntry 7 }


pdcreconfigure	OBJECT-TYPE
	SYNTAX	INTEGER
	{
		no(1),
		yes(2)
	}
	ACCESS	read-write
	STATUS	mandatory
	DESCRIPTION
	"Re-configure Primary Line"
        DEFVAL { no }
	::= { pCATDerConfigEntry 8 }

-- CAT Secondary Derived T1 configuration

sCATDerConfigTable OBJECT-TYPE
	SYNTAX SEQUENCE OF SCATDerConfigEntry
	ACCESS not-accessible
	STATUS mandatory
	::= { dv2SystemClocks 23 }

sCATDerConfigEntry OBJECT-TYPE
              SYNTAX  SCATDerConfigEntry
              ACCESS  not-accessible
              STATUS  mandatory
	      INDEX  { sdcIndex  }
              ::= { sCATDerConfigTable 1 }

SCATDerConfigEntry	::=
	SEQUENCE {
	        sdcIndex
		        INTEGER,
                sdcds1V2TxLineLn
                        INTEGER,
                sdcplaceholder1
		        INTEGER,
		sdcV2FRMRMode
                        INTEGER,
                sdcds1V2Coding
                        INTEGER,
                sdcV2Lb
                        INTEGER,
		sdcclrperf
			INTEGER,
		sdcreconfigure
			INTEGER
}

sdcIndex OBJECT-TYPE
	SYNTAX INTEGER 
	ACCESS read-only
	STATUS mandatory
	DESCRIPTION
	"Entry Index"
	::= { sCATDerConfigEntry 1 }

sdcds1V2TxLineLn   OBJECT-TYPE
        SYNTAX  INTEGER
        {
		feet-0-110(1),
                feet-110-220(2),
                feet-220-330(3),
                feet-330-440(4),
                feet-440-550(5),
                feet-550-660(6),
                more-than-655-ft(7),
		na(8)
        }
        ACCESS  read-write
        STATUS  mandatory
        DESCRIPTION
        "Select transmit line length"
        DEFVAL { na }
        ::= { sCATDerConfigEntry 2 }


sdcplaceholder1	OBJECT-TYPE
	SYNTAX	INTEGER
	{
		na(1)
	}
	ACCESS	read-write
	STATUS	mandatory
	DESCRIPTION
	"Future Use"
        DEFVAL { na }
	::= { sCATDerConfigEntry 3 }


sdcV2FRMRMode   OBJECT-TYPE
        SYNTAX  INTEGER
        {
                none(1),
                sf(2),
                esf(3)
        }
        ACCESS  read-write
        STATUS  mandatory
        DESCRIPTION
        "DS1 Framing options."
        DEFVAL { none }
        ::= { sCATDerConfigEntry 4 }

sdcds1V2Coding     OBJECT-TYPE
        SYNTAX  INTEGER
        {
		na(3),
                ami(2),
               b8zs(1)
        }
        ACCESS  read-write
        STATUS  mandatory
        DESCRIPTION
        "Line Coding"
        DEFVAL { na }
        ::= { sCATDerConfigEntry 5 }

sdcV2Lb OBJECT-TYPE
        SYNTAX  INTEGER
        {
          none(1),
          line-lpbk(2),
          local-loopback(3)
        }
        ACCESS  read-write
        STATUS  mandatory
        DESCRIPTION
        "Loopback Selection DS1"
        ::= { sCATDerConfigEntry 6 }

sdcclrperf	OBJECT-TYPE
	SYNTAX	INTEGER
	{
		no(1),
		yes(2)
	}
	ACCESS	read-write
	STATUS	mandatory
	DESCRIPTION
	"Clear the Performance Counters"
        DEFVAL { no }
	::= { sCATDerConfigEntry 7 }



sdcreconfigure	OBJECT-TYPE
	SYNTAX	INTEGER
	{
		no(1),
		yes(2)
	}
	ACCESS	read-write
	STATUS	mandatory
	DESCRIPTION
	"Re-configure Secondary Line"
        DEFVAL { no }
	::= { sCATDerConfigEntry 8 }

-- CAT Primary  T1/E1 Derived Status

pCATDerStatusTable      OBJECT-TYPE
        SYNTAX  SEQUENCE OF PCATDerStatusEntry
        ACCESS  not-accessible
        STATUS  mandatory
        DESCRIPTION
        "Ds1/E1 Derived Status Table"
        ::= { dv2SystemClocks 24 }

pCATDerStatusEntry      OBJECT-TYPE
        SYNTAX  PCATDerStatusEntry
        ACCESS  not-accessible
        STATUS  mandatory
        INDEX   { pdsIndex }
        ::= { pCATDerStatusTable 1 }

PCATDerStatusEntry ::=
        SEQUENCE {
                pdsIndex
                        INTEGER,
                pdslineok
                        INTEGER,
                pdsV2TxReference
                        INTEGER,
		pdsV2RxAIS
			INTEGER,
		pdsV2RxLOS
			INTEGER,
		pdsV2RxOOF
			INTEGER,
		pdsV2RxBER
			INTEGER,
		pdsV2RxOOFCnt
			INTEGER,
		pdsV2RxBERCnt
			INTEGER,
		pdsV2RxLOSCnt
			INTEGER ,
		pdsV2LCVCnt
			INTEGER
}

pdsIndex  OBJECT-TYPE
        SYNTAX  INTEGER 
        ACCESS  read-only
        STATUS  mandatory
        DESCRIPTION
        "Entry Index"
        ::= { pCATDerStatusEntry 1 }


pdslineok   OBJECT-TYPE
        SYNTAX INTEGER {
                no(1),
                yes(2),
		na(3)
        }
        ACCESS read-only
        STATUS mandatory
        DESCRIPTION
        "Is the line OK"
        ::= { pCATDerStatusEntry 2 }

pdsV2TxReference   OBJECT-TYPE
        SYNTAX INTEGER {
                no-input(1),
                primary-valid(2),
                secondary-valid(3)
        }
        ACCESS read-only
        STATUS mandatory
        DESCRIPTION
        "Transmit Reference Status"
        ::= { pCATDerStatusEntry 3 }


pdsV2RxAIS   OBJECT-TYPE
        SYNTAX INTEGER {
                no(1),
                yes(2),
		na(3)
        }
        ACCESS read-only
        STATUS mandatory
        DESCRIPTION
        "Receive DS1 AIS(Blue)Alarm status."
        ::= { pCATDerStatusEntry 4 }

pdsV2RxLOS   OBJECT-TYPE
        SYNTAX INTEGER {
                no(1),
                yes(2),
		na(3)
        }
        ACCESS read-only
        STATUS mandatory
        DESCRIPTION
        "Receive DS1 LOS status."
        ::= { pCATDerStatusEntry 5 }

pdsV2RxOOF   OBJECT-TYPE
        SYNTAX INTEGER {
                no(1),
                yes(2),
		na(3)
        }
        ACCESS read-only
        STATUS mandatory
        DESCRIPTION
        "Receive DS1 OOF status."
        ::= { pCATDerStatusEntry 6 }

pdsV2RxBER   OBJECT-TYPE
        SYNTAX INTEGER {
                no(1),
                yes(2),
		na(3)
        }
        ACCESS read-only
        STATUS mandatory
        DESCRIPTION
        "Receive DS1 BER status."
        ::= { pCATDerStatusEntry 7 }

pdsV2RxOOFCnt   OBJECT-TYPE
        SYNTAX INTEGER
        ACCESS read-only
        STATUS mandatory
        DESCRIPTION
        "Receive DS1 OOF count."
        ::= { pCATDerStatusEntry 8 }

pdsV2RxBERCnt   OBJECT-TYPE
        SYNTAX INTEGER
        ACCESS read-only
        STATUS mandatory
        DESCRIPTION
        "Receive DS1 BEE count."
        ::= { pCATDerStatusEntry 9 }

pdsV2RxLOSCnt   OBJECT-TYPE
        SYNTAX INTEGER
        ACCESS read-only
        STATUS mandatory
        DESCRIPTION
        "Receive DS1 LOS count."
        ::= { pCATDerStatusEntry 10 }

pdsV2LCVCnt   OBJECT-TYPE
        SYNTAX INTEGER
        ACCESS read-only
        STATUS mandatory
        DESCRIPTION
        "Receive DS1 AIS count."
        ::= { pCATDerStatusEntry 11 }

-- CAT Secondary Derived Status

sCATDerStatusTable      OBJECT-TYPE
        SYNTAX  SEQUENCE OF SCATDerStatusEntry
        ACCESS  not-accessible
        STATUS  mandatory
        DESCRIPTION
        "Ds1/E1 Derived Status Table"
        ::= { dv2SystemClocks 25 }

sCATDerStatusEntry      OBJECT-TYPE
        SYNTAX  SCATDerStatusEntry
        ACCESS  not-accessible
        STATUS  mandatory
        INDEX   { sdsIndex }
        ::= { sCATDerStatusTable 1 }

SCATDerStatusEntry ::=
        SEQUENCE {
                sdsIndex
                        INTEGER,
                sdslineok
                        INTEGER,
                sdsV2TxReference
                        INTEGER,
		sdsV2RxAIS
			INTEGER,
		sdsV2RxLOS
			INTEGER,
		sdsV2RxOOF
			INTEGER,
		sdsV2RxBER
			INTEGER,
		sdsV2RxOOFCnt
			INTEGER,
		sdsV2RxBERCnt
			INTEGER,
		sdsV2RxLOSCnt
			INTEGER,
		sdsV2LCVCnt
			INTEGER
}

sdsIndex  OBJECT-TYPE
        SYNTAX  INTEGER 
        ACCESS  read-only
        STATUS  mandatory
        DESCRIPTION
        "Entry Index"
        ::= { sCATDerStatusEntry 1 }


sdslineok   OBJECT-TYPE
        SYNTAX INTEGER {
                no(1),
                yes(2),
		na(3)
        }
        ACCESS read-only
        STATUS mandatory
        DESCRIPTION
        "Is the line OK"
        ::= { sCATDerStatusEntry 2 }

sdsV2TxReference   OBJECT-TYPE
        SYNTAX INTEGER {
                no-input(1),
                primary-valid(2),
                secondary-valid(3)
        }
        ACCESS read-only
        STATUS mandatory
        DESCRIPTION
        "Transmit Reference Status"
        ::= { sCATDerStatusEntry 3 }

sdsV2RxAIS   OBJECT-TYPE
        SYNTAX INTEGER {
                no(1),
                yes(2),
		na(3)
        }
        ACCESS read-only
        STATUS mandatory
        DESCRIPTION
        "Receive DS1 AIS(Blue)Alarm status."
        ::= { sCATDerStatusEntry 4 }

sdsV2RxLOS   OBJECT-TYPE
        SYNTAX INTEGER {
                no(1),
                yes(2),
		na(3)
        }
        ACCESS read-only
        STATUS mandatory
        DESCRIPTION
        "Receive DS1 LOS status."
        ::= { sCATDerStatusEntry 5 }

sdsV2RxOOF   OBJECT-TYPE
        SYNTAX INTEGER {
                no(1),
                yes(2),
		na(3)
        }
        ACCESS read-only
        STATUS mandatory
        DESCRIPTION
        "Receive DS1 OOF status."
        ::= { sCATDerStatusEntry 6 }

sdsV2RxBER   OBJECT-TYPE
        SYNTAX INTEGER {
                no(1),
                yes(2),
		na(3)
        }
        ACCESS read-only
        STATUS mandatory
        DESCRIPTION
        "Receive DS1 BER status."
        ::= { sCATDerStatusEntry 7 }

sdsV2RxOOFCnt   OBJECT-TYPE
        SYNTAX INTEGER
        ACCESS read-only
        STATUS mandatory
        DESCRIPTION
        "Receive DS1 OOF count."
        ::= { sCATDerStatusEntry 8 }

sdsV2RxBERCnt   OBJECT-TYPE
        SYNTAX INTEGER
        ACCESS read-only
        STATUS mandatory
        DESCRIPTION
        "Receive DS1 BEE count."
        ::= { sCATDerStatusEntry 9 }

sdsV2RxLOSCnt   OBJECT-TYPE
        SYNTAX INTEGER
        ACCESS read-only
        STATUS mandatory
        DESCRIPTION
        "Receive DS1 LOS count."
        ::= { sCATDerStatusEntry 10 }

sdsV2LCVCnt   OBJECT-TYPE
        SYNTAX INTEGER
        ACCESS read-only
        STATUS mandatory
        DESCRIPTION
        "Receive DS1 AIS count."
        ::= { sCATDerStatusEntry 11 }

--                                New variable for clockAlarm trap #10, #13
sysClkAlarmErr   OBJECT-TYPE
        SYNTAX INTEGER {
		none(1),
		sEClinePRI-ok(2),
		pRIlineSEC-ok(3),
		pRIlineSECoffline(4),
		pRIoscSECoffline(5),
 		sEClinePRIoffline(6),
		sECoscPRIoffline(7),
		pRIlineSECline(8),
		pRIosc(9),
		sECosc(10),
		pRIoscSECosc(11),
		pRIoscSECline(12),
		pRIlineSECosc(13),
		no-valid-error(14)
        }
        ACCESS read-only
        STATUS mandatory
        DESCRIPTION
        "Defines the error type for the current clock alarm"
	DEFVAL { none }
	::= { dv2SystemClocks 26 }


--___________________________________________________________________________
-- The dv2 trace flags information group.

traceIp OBJECT-TYPE
	SYNTAX	INTEGER	{
		no(1),
		yes(2)
	}
	ACCESS	read-write
	STATUS	mandatory
	DESCRIPTION
	"Toggle for IP trace flag."
	::= { dv2Trace 1 }

traceUdp OBJECT-TYPE
	SYNTAX	INTEGER	{
		no(1),
		yes(2)
	}
	ACCESS	read-write
	STATUS	mandatory
	DESCRIPTION
	"Toggle for UDP trace flag."
	::= { dv2Trace 2 }

traceTcp OBJECT-TYPE
	SYNTAX	INTEGER	{
		no(1),
		yes(2)
	}
	ACCESS	read-write
	STATUS	mandatory
	DESCRIPTION
	"Toggle for TCP trace flag."
	::= { dv2Trace 3 }

traceSnmp OBJECT-TYPE
	SYNTAX	INTEGER	{
		no(1),
		yes(2)
	}
	ACCESS	read-write
	STATUS	mandatory
	DESCRIPTION
	"Toggle for SNMP trace flag."
	::= { dv2Trace 4 }


traceCat OBJECT-TYPE
	SYNTAX	INTEGER	{
		no(1),
		yes(2)
	}
	ACCESS	read-write
	STATUS	mandatory
	DESCRIPTION
	"Toggle for CAT trace flag."
 	DEFVAL { no }
	::= { dv2Trace 5 }

--___________________________________________________________________________
-- The dv2 SLIP configuration.

slipIp OBJECT-TYPE
	SYNTAX	IpAddress
	ACCESS	read-write
	STATUS	mandatory
	DESCRIPTION
	"IP address of SLIP line."
	::= { dv2SlipLine 1 }

slipMask OBJECT-TYPE
	SYNTAX	IpAddress
	ACCESS	read-write
	STATUS	mandatory
	DESCRIPTION
	"Mask for SLIP line."
	::= { dv2SlipLine 2 }

slipRemoteIp OBJECT-TYPE
	SYNTAX	IpAddress
	ACCESS	read-write
	STATUS	mandatory
	DESCRIPTION
	"IP address of remote end of SLIP line."
	::= { dv2SlipLine 3 }

slipSpeed OBJECT-TYPE
	SYNTAX	INTEGER	{
		baud2400(1),
		baud4800(2),
		baud9600(3),
		baud19200(4),
		baud38400(5),
		baud57600(6),
		baud115200(7)
	}
	ACCESS	read-write
	STATUS	mandatory
	DESCRIPTION
	"Baud rate of SLIP serial line."
	::= { dv2SlipLine 4 }


--___________________________________________________________________________
-- The VC DOC channel table config

vcDocTable OBJECT-TYPE
	SYNTAX SEQUENCE OF VcDocEntry
	ACCESS not-accessible
	STATUS mandatory
	DESCRIPTION
	""
	::= { dv2VcDoc 1 }

vcDocEntry OBJECT-TYPE
	SYNTAX	VcDocEntry
	ACCESS	not-accessible
	STATUS	mandatory
        INDEX   { vcDocLinkNo }
	::= { vcDocTable 1 }

VcDocEntry ::=
	SEQUENCE {
		vcDocLinkNo
			INTEGER,
		vcDocEnable
			INTEGER,
		vcDocVpi
			VirtualPathIdentifier,
		vcDocVci
			VirtualCircuitIdentifier,
		vcDocLinkSpeed
			INTEGER,
		vcDocCLines
			INTEGER,
		vcDocFifoSize
			INTEGER,
		vcDocLowWater
			INTEGER,
		vcDocHighWater
			INTEGER,
		vcDocTestMode
			INTEGER,
		vcDocTestVal
			Hex,
		vcDocPriority
			INTEGER,
		vcDocSuba
			INTEGER,
		vcDocSaddr
			INTEGER,
		vcDocClockFix
			INTEGER
}

vcDocLinkNo OBJECT-TYPE
	SYNTAX INTEGER (0..127)
	ACCESS read-only
	STATUS mandatory
	DESCRIPTION
	"This is the target link number for the PVC."
	::= { vcDocEntry 1 }

vcDocEnable OBJECT-TYPE
	SYNTAX INTEGER {
			yes(1),
			no(2)
		}
	ACCESS read-write
	STATUS mandatory
	DESCRIPTION
	"Setting to yes(1) enables the VCDOC channel."
	::= { vcDocEntry 2 }

vcDocVpi OBJECT-TYPE
	SYNTAX VirtualPathIdentifier
	ACCESS read-only
	STATUS mandatory
	DESCRIPTION
	"VPI of the VC being used for cell transfers."
	::= { vcDocEntry 3 }

vcDocVci OBJECT-TYPE
	SYNTAX VirtualCircuitIdentifier
	ACCESS read-only
	STATUS mandatory
	DESCRIPTION
	"VCI of the VC being used for cell transfers."
	::= { vcDocEntry 4 }

vcDocLinkSpeed OBJECT-TYPE
	SYNTAX INTEGER {
			s32kbps(64),
			s64kbps(128),
			s128kbps(192),
			s256kbps(224),
			s512kbps(240),
			s1024kbps(248),
			s2048kbps(252)
		}
	ACCESS read-write
	STATUS mandatory
	DESCRIPTION
	"This sets the speed at which the link is to run."
	::= { vcDocEntry 5 }

vcDocCLines OBJECT-TYPE
	SYNTAX INTEGER {
			process(1),
			ignore(2)
		}
	ACCESS read-write
	STATUS mandatory
	DESCRIPTION
	"This sets how control lines should be processed. If Ignore(2) is set then the port is always online."
	::= { vcDocEntry 6 }

vcDocFifoSize OBJECT-TYPE
	SYNTAX INTEGER (10..100)
	ACCESS read-write
	STATUS mandatory
	DESCRIPTION
	"This is the size of the software emulated FIFO."
	::= { vcDocEntry 7 }

vcDocLowWater OBJECT-TYPE
	SYNTAX INTEGER (0..50)
	ACCESS read-write
	STATUS mandatory
	DESCRIPTION
	"This is the point at which the transmit clock is switched to low frequency. This must be between 0 and FIFO Size/2"
	::= { vcDocEntry 8 }

vcDocHighWater OBJECT-TYPE
	SYNTAX INTEGER (5..100)
	ACCESS read-write
	STATUS mandatory
	DESCRIPTION
	"This is the point at which the transmit clock is switched to high frequency. This must be between FIFO size and FIFO Size/2"
	::= { vcDocEntry 9 }


vcDocTestMode OBJECT-TYPE
	SYNTAX INTEGER {
		normal(1),
		local-loop(2),
		cable-loop(3),
		remote-loop(4),
		pattern-send(5)
	}
	ACCESS read-write
	STATUS mandatory
	DESCRIPTION
	"This is the type of self-test to perform with the VC DOC."
	::= { vcDocEntry 10 }

vcDocTestVal OBJECT-TYPE
	SYNTAX Hex
	ACCESS read-write
	STATUS mandatory
	DESCRIPTION
	"This is the test value to use when doing the pattern-send test."
	::= { vcDocEntry 11 }

vcDocPriority OBJECT-TYPE
	SYNTAX INTEGER (0..1)
	ACCESS read-only
	STATUS mandatory
	DESCRIPTION
	"This indicates that cells will be sent with the priority bit set."
	::= { vcDocEntry 12 }

vcDocSuba OBJECT-TYPE
	SYNTAX INTEGER (0..3)
	ACCESS read-only
	STATUS mandatory
	DESCRIPTION
	"This is the target link number for the VC."
	::= { vcDocEntry 13 }

vcDocSaddr OBJECT-TYPE
	SYNTAX INTEGER (0..15)
	ACCESS read-only
	STATUS mandatory
	DESCRIPTION
	"This is the target slot number for the VC."
	::= { vcDocEntry 14 }

vcDocClockFix OBJECT-TYPE
	SYNTAX INTEGER
	{
		no(1),
		yes(2)
	}
	ACCESS read-write
	STATUS mandatory
	DESCRIPTION
	"If yes(2) then the clock will not be varied to maintain the size of the send FIFO."
	::= { vcDocEntry 15 }

--___________________________________________________________________________
-- The VC DOC channel table status

vcStatTable OBJECT-TYPE
	SYNTAX SEQUENCE OF VcStatEntry
	ACCESS not-accessible
	STATUS mandatory
	DESCRIPTION
	"This is a two row table that contains status information about the VCDOC."
	::= { dv2VcDoc 2 }

vcStatEntry OBJECT-TYPE
	SYNTAX	VcStatEntry
	ACCESS	not-accessible
	STATUS	mandatory
        INDEX   { vcStatPortNo }
	::= { vcStatTable 1 }

VcStatEntry ::=
	SEQUENCE {
		vcStatPortNo
			INTEGER,
		vcStatRxState
			INTEGER,
		vcStatTxState
			INTEGER,
		vcStatFifoCount
			INTEGER,
		vcStatOFlow
			INTEGER,
		vcStatUFlow
			INTEGER,
		vcStatReSync
			INTEGER,
		vcStatInvented
			INTEGER,
		vcStatRxCells
			Counter,
		vcStatTxCells
			Counter,
		vcStatRxSeqNo
			INTEGER,
		vcStatTxSeqNo
			INTEGER,
		vcStatLastError
			INTEGER,
		vcStatLastCompare
			INTEGER,
		vcStatTestErrors
			INTEGER
}

vcStatPortNo OBJECT-TYPE
	SYNTAX INTEGER (0..1)
	ACCESS read-only
	STATUS mandatory
	DESCRIPTION
	"This is the originating port number for the PVC"
	::= { vcStatEntry 1 }

vcStatRxState OBJECT-TYPE
	SYNTAX INTEGER {
			up(1),
			down(2)
		}
	ACCESS read-only
	STATUS mandatory
	DESCRIPTION
	"This indicates whether control lines are high at the other end of the link."
	::= { vcStatEntry 2 }

vcStatTxState OBJECT-TYPE
	SYNTAX INTEGER {
			up(1),
			down(2)
		}
	ACCESS read-only
	STATUS mandatory
	DESCRIPTION
	"This indicates whether the local control lines are high."
	::= { vcStatEntry 3 }

vcStatFifoCount OBJECT-TYPE
	SYNTAX INTEGER
	ACCESS read-only
	STATUS mandatory
	DESCRIPTION
	"This indicates the number of cells waiting in the FIFO."
	::= { vcStatEntry 4 }


vcStatOFlow OBJECT-TYPE
	SYNTAX INTEGER
	ACCESS read-only
	STATUS mandatory
	DESCRIPTION
	"Number of Overflows."
	::= { vcStatEntry 5 }

vcStatUFlow OBJECT-TYPE
	SYNTAX INTEGER
	ACCESS read-only
	STATUS mandatory
	DESCRIPTION
	"Number of Underflows."
	::= { vcStatEntry 6 }

vcStatReSync OBJECT-TYPE
	SYNTAX INTEGER
	ACCESS read-only
	STATUS mandatory
	DESCRIPTION
	"This is the number of times a sequence number resync has been required."
	::= { vcStatEntry 7 }

vcStatInvented OBJECT-TYPE
	SYNTAX INTEGER
	ACCESS read-only
	STATUS mandatory
	DESCRIPTION
	"Number of invented cells."
	::= { vcStatEntry 8 }

vcStatRxCells OBJECT-TYPE
	SYNTAX Counter
	ACCESS read-only
	STATUS mandatory
	DESCRIPTION
	"Received cells count."
	::= { vcStatEntry 9 }

vcStatTxCells OBJECT-TYPE
	SYNTAX Counter
	ACCESS read-only
	STATUS mandatory
	DESCRIPTION
	"Transmitted cells count."
	::= { vcStatEntry 10 }

vcStatRxSeqNo OBJECT-TYPE
	SYNTAX INTEGER
	ACCESS read-only
	STATUS mandatory
	DESCRIPTION
	"Receive current sequence number."
	::= { vcStatEntry 11 }

vcStatTxSeqNo OBJECT-TYPE
	SYNTAX INTEGER
	ACCESS read-only
	STATUS mandatory
	DESCRIPTION
	"Transmit current sequence number."
	::= { vcStatEntry 12 }

vcStatLastError OBJECT-TYPE
	SYNTAX INTEGER
	ACCESS read-only
	STATUS mandatory
	DESCRIPTION
	"Last error type."
	::= { vcStatEntry 13 }


vcStatLastCompare OBJECT-TYPE
	SYNTAX INTEGER
	ACCESS read-only
	STATUS mandatory
	DESCRIPTION
	"Last compare value."
	::= { vcStatEntry 14 }

vcStatTestErrors OBJECT-TYPE
	SYNTAX INTEGER
	ACCESS read-only
	STATUS mandatory
	DESCRIPTION
	"Number of test errors detected."
	::= { vcStatEntry 15 }

--___________________________________________________________________________

-- frame Relay Overall Status Table

fRelayStatTable	OBJECT-TYPE
	SYNTAX SEQUENCE OF FRelayStatEntry
	ACCESS not-accessible
	STATUS mandatory
	DESCRIPTION
	"This contains the overall status information for the frame relay links."
	::= { dv2FrRelay 1 }

fRelayStatEntry	OBJECT-TYPE
	SYNTAX FRelayStatEntry
	ACCESS not-accessible
	STATUS mandatory
	INDEX { fRelStatLinkNo }
	::= { fRelayStatTable 1 }

FRelayStatEntry ::=
	SEQUENCE {
		fRelStatLinkNo
			INTEGER,
		fRelStatLocSeq
			INTEGER,
		fRelStatLocAck
			INTEGER,
		fRelStatLocState
			INTEGER,
		fRelStatLocStartT
			INTEGER,
		fRelStatLocErrThr
			Counter,
		fRelStatLocMec
			Counter,
		fRelStatLocPoll
			Counter,
		fRelStatRemSeq
			INTEGER,
		fRelStatRemAck
			INTEGER,
		fRelStatRemState
			INTEGER,
		fRelStatRemStartT
			INTEGER,
		fRelStatRemErrThr
			Counter,
		fRelStatRemMec
			Counter,
		fRelStatRemPoll
			Counter
	}

fRelStatLinkNo OBJECT-TYPE
	SYNTAX	INTEGER (0..1)
	ACCESS	read-only
	STATUS	mandatory
	DESCRIPTION
	"Local send sequence."
	::= { fRelayStatEntry  1 }

fRelStatLocSeq OBJECT-TYPE
	SYNTAX	INTEGER
	ACCESS	read-only
	STATUS	mandatory
	DESCRIPTION
	"Local send sequence."
	::= { fRelayStatEntry  2 }

fRelStatLocAck OBJECT-TYPE
	SYNTAX	INTEGER
	ACCESS	read-only
	STATUS	mandatory
	DESCRIPTION
	"Local ack sequence."
	::= { fRelayStatEntry 3 }

fRelStatLocState OBJECT-TYPE
	SYNTAX	INTEGER {
		up(1),
		down(2)
	}
	ACCESS	read-only
	STATUS	mandatory
	DESCRIPTION
	"Local state of link."
	::= { fRelayStatEntry 4 }

fRelStatLocStartT OBJECT-TYPE
	SYNTAX	INTEGER
	ACCESS	read-only
	STATUS	mandatory
	DESCRIPTION
	"Local start time for poll."
	::= { fRelayStatEntry 5 }

fRelStatLocErrThr OBJECT-TYPE
	SYNTAX	Counter
	ACCESS	read-only
	STATUS	mandatory
	DESCRIPTION
	"Local error threshold Counter."
	::= { fRelayStatEntry 6 }

fRelStatLocMec OBJECT-TYPE
	SYNTAX	Counter
	ACCESS	read-only
	STATUS	mandatory
	DESCRIPTION
	"Local monitored events Counter."
	::= { fRelayStatEntry 7 }

fRelStatLocPoll OBJECT-TYPE
	SYNTAX	Counter
	ACCESS	read-only
	STATUS	mandatory
	DESCRIPTION
	"Local poll Counter for DTE."
	::= { fRelayStatEntry 8 }

fRelStatRemSeq OBJECT-TYPE
	SYNTAX	INTEGER
	ACCESS	read-only
	STATUS	mandatory
	DESCRIPTION
	"Remote send sequence."
	::= { fRelayStatEntry 9 }

fRelStatRemAck OBJECT-TYPE
	SYNTAX	INTEGER
	ACCESS	read-only
	STATUS	mandatory
	DESCRIPTION
	"Remote ack sequence."
	::= { fRelayStatEntry 10 }

fRelStatRemState OBJECT-TYPE
	SYNTAX	INTEGER {
		up(1),
		down(2)
	}
	ACCESS	read-only
	STATUS	mandatory
	DESCRIPTION
	"Remote state of link."
	::= { fRelayStatEntry 11 }

fRelStatRemStartT OBJECT-TYPE
	SYNTAX	INTEGER
	ACCESS	read-only
	STATUS	mandatory
	DESCRIPTION
	"Remote start time for poll."
	::= { fRelayStatEntry 12 }

fRelStatRemErrThr OBJECT-TYPE
	SYNTAX	Counter
	ACCESS	read-only
	STATUS	mandatory
	DESCRIPTION
	"Remote error threshold Counter."
	::= { fRelayStatEntry 13 }

fRelStatRemMec OBJECT-TYPE
	SYNTAX	Counter
	ACCESS	read-only
	STATUS	mandatory
	DESCRIPTION
	"Remote monitored events Counter."
	::= { fRelayStatEntry 14 }

fRelStatRemPoll OBJECT-TYPE
	SYNTAX	Counter
	ACCESS	read-only
	STATUS	mandatory
	DESCRIPTION
	"Remote poll Counter for DTE."
	::= { fRelayStatEntry 15 }

--___________________________________________________________________________

-- frame Relay Overall Configuration Table

fRelayConfTable OBJECT-TYPE
	SYNTAX SEQUENCE OF FRelayConfEntry
	ACCESS not-accessible
	STATUS mandatory
	DESCRIPTION
	"This table contains the overall configuration for the frame relay links."
	::= { dv2FrRelay 2 }

fRelayConfEntry OBJECT-TYPE
	SYNTAX FRelayConfEntry
	ACCESS not-accessible
	STATUS mandatory
	INDEX { fRelConfLinkNo }
	::= { fRelayConfTable 1 }

FRelayConfEntry ::=
	SEQUENCE {
		fRelConfLinkNo
			INTEGER,
		fRelConfLinkEnab
			INTEGER,
		fRelConfLinkMode
			INTEGER,
		fRelConfLinkSpeed
			INTEGER,
		fRelConfLinkCline
			INTEGER,
		fRelConfLinkType
			INTEGER,
		fRelConfN391
			INTEGER,
		fRelConfN392
			INTEGER,
		fRelConfN393
			INTEGER,
		fRelConfT391
			INTEGER,
		fRelConfT392
			INTEGER
}


fRelConfLinkNo OBJECT-TYPE
	SYNTAX	INTEGER  (0..1)
	ACCESS	read-only
	STATUS	mandatory
	DESCRIPTION
	"Number of the link to configure."
	::= { fRelayConfEntry 1 }

fRelConfLinkEnab OBJECT-TYPE
	SYNTAX	INTEGER {
		yes(1),
		no(2)
	}
	ACCESS	read-write
	STATUS	mandatory
	DESCRIPTION
	"Set to yes(1) to enable the link."
	::= { fRelayConfEntry  2 }

fRelConfLinkMode OBJECT-TYPE
	SYNTAX	INTEGER {
		ansi(1),
		lmi(2),
		transport(3),
                dxi(4)
	}
	ACCESS	read-write
	STATUS	mandatory
	DESCRIPTION
	"frame mode."
	::= { fRelayConfEntry  3 }

fRelConfLinkSpeed OBJECT-TYPE
	SYNTAX	INTEGER {
		s48kbps(48),
		s56kbps(77),
		s64kbps(100),
		s72kbps(117),
		s128kbps(177),
		s153k6bps(191),
		s256kbps(217),
		s307k2bps(223),
		s614k4bps(240),
		s819k2bps(244),
		s1Mbps(246),
		s2Mbps(251),
		s3Mbps(253),
		s5Mbps(254),
		s10Mbps(255)
	}
	ACCESS	read-write
	STATUS	mandatory
	DESCRIPTION
	"Local speed of link."
	::= { fRelayConfEntry  4 }

fRelConfLinkCline OBJECT-TYPE
	SYNTAX	INTEGER {
		yes(1),
		no(2)
	}
	ACCESS	read-write
	STATUS	mandatory
	DESCRIPTION
	"Set to no(2) to disable control line processing."
	::= { fRelayConfEntry  5 }

fRelConfLinkType OBJECT-TYPE
	SYNTAX	INTEGER {
		user(1),
		network(2),
		nni(3)
	}
	ACCESS	read-write
	STATUS	mandatory
	DESCRIPTION
	"Type of link."
	::= { fRelayConfEntry  6 }

fRelConfN391 OBJECT-TYPE
	SYNTAX	INTEGER (1..255)
	ACCESS	read-write
	STATUS	mandatory
	DESCRIPTION
	"Poll count."
	::= { fRelayConfEntry  7 }

fRelConfN392 OBJECT-TYPE
	SYNTAX	INTEGER (1..10)
	ACCESS	read-write
	STATUS	mandatory
	DESCRIPTION
	"Threshold."
	::= { fRelayConfEntry  8 }

fRelConfN393 OBJECT-TYPE
	SYNTAX	INTEGER (1..10)
	ACCESS	read-write
	STATUS	mandatory
	DESCRIPTION
	"Monitored events."
	::= { fRelayConfEntry  9 }

fRelConfT391 OBJECT-TYPE
	SYNTAX	INTEGER (5..30)
	ACCESS	read-write
	STATUS	mandatory
	DESCRIPTION
	"Poll period."
	::= { fRelayConfEntry  10 }

fRelConfT392 OBJECT-TYPE
	SYNTAX	INTEGER (5..30)
	ACCESS	read-write
	STATUS	mandatory
	DESCRIPTION
	"Poll timeout."
	::= { fRelayConfEntry  11 }

--___________________________________________________________________________
-- The Frame Relay Link A Status (fra)

fraPStatTable OBJECT-TYPE
	SYNTAX SEQUENCE OF FraPStatEntry
	ACCESS not-accessible
	STATUS mandatory
	DESCRIPTION
	"This shows the status of the frame relay PVCs for link 0."
	::= { dv2FrRelay 3 }

fraPStatEntry OBJECT-TYPE
	SYNTAX	FraPStatEntry
	ACCESS	not-accessible
	STATUS	mandatory
        INDEX   { fraPStatDlci }
	::= { fraPStatTable 1 }

FraPStatEntry ::=
	SEQUENCE {
		fraPStatDlci
			INTEGER,
		fraPStatRxBCnt
			Counter,
		fraPStatTxBCnt
			Counter,
		fraPStatRxFCnt
			Counter,
		fraPStatTxFCnt
			Counter,
		fraPStatRxBRate
			Gauge,
		fraPStatTxBRate
			Gauge,
		fraPStatRxFRate
			Gauge,
		fraPStatTxFRate
			Gauge,
		fraPStatDERxF
			Counter,
		fraPStatDisRxF
			Counter,
		fraPStatPvcStat
			Hex,
		fraPStatLinkState
			Hex,
		fraPStatLocSeq
			INTEGER,
		fraPStatLocAck
			INTEGER,
		fraPStatLocStat
			INTEGER,
		fraPStatLocStartT
			INTEGER,
		fraPStatLocErrThr
			Counter,
		fraPStatLocMec
			Counter,
		fraPStatLocPoll
			Counter,
		fraPStatRemSeq
			INTEGER,
		fraPStatRemAck
			INTEGER,
		fraPStatRemStat
			INTEGER,
		fraPStatRemStartT
			INTEGER,
		fraPStatRemErrThr
			Counter,
		fraPStatRemMec
			Counter,
		fraPStatRemPoll
			Counter,
--                              Y2K change : deprecated
--		fraPStatLastChange
--			DateTimeString,
--                              Y2K change : added,  use DateAndTime convention
		fraPStatLastChangeM2
			DateAndTime
}

fraPStatDlci OBJECT-TYPE
	SYNTAX INTEGER (16..511)
	ACCESS read-only
	STATUS mandatory
	DESCRIPTION
	"This is the DLCI for the PVC."
	::= { fraPStatEntry 1 }

fraPStatRxBCnt OBJECT-TYPE
	SYNTAX Counter
	ACCESS read-only
	STATUS mandatory
	DESCRIPTION
	"The number of bytes received."
	::= { fraPStatEntry 2 }

fraPStatTxBCnt OBJECT-TYPE
	SYNTAX Counter
	ACCESS read-only
	STATUS mandatory
	DESCRIPTION
	"The number of bytes transmitted."
	::= { fraPStatEntry 3 }

fraPStatRxFCnt OBJECT-TYPE
	SYNTAX Counter
	ACCESS read-only
	STATUS mandatory
	DESCRIPTION
	"The number of frames received."
	::= { fraPStatEntry 4 }

fraPStatTxFCnt OBJECT-TYPE
	SYNTAX Counter
	ACCESS read-only
	STATUS mandatory
	DESCRIPTION
	"The number of frames transmitted."
	::= { fraPStatEntry 5 }

fraPStatRxBRate OBJECT-TYPE
	SYNTAX Gauge
	ACCESS read-only
	STATUS mandatory
	DESCRIPTION
	"The rate of bytes being received."
	::= { fraPStatEntry 6 }

fraPStatTxBRate OBJECT-TYPE
	SYNTAX Gauge
	ACCESS read-only
	STATUS mandatory
	DESCRIPTION
	"The rate of bytes being transmitted."
	::= { fraPStatEntry 7 }

fraPStatRxFRate OBJECT-TYPE
	SYNTAX Gauge
	ACCESS read-only
	STATUS mandatory
	DESCRIPTION
	"The rate of frames being received."
	::= { fraPStatEntry 8 }

fraPStatTxFRate OBJECT-TYPE
	SYNTAX Gauge
	ACCESS read-only
	STATUS mandatory
	DESCRIPTION
	"The rate of frames being transmitted."
	::= { fraPStatEntry 9 }

fraPStatDERxF OBJECT-TYPE
	SYNTAX Counter
	ACCESS read-only
	STATUS mandatory
	DESCRIPTION
	"The count of discarded eligible received frames."
	::= { fraPStatEntry 10 }

fraPStatDisRxF	OBJECT-TYPE
	SYNTAX Counter
	ACCESS read-only
	STATUS mandatory
	DESCRIPTION
	"The count of discarded received frames."
	::= { fraPStatEntry 11 }

fraPStatPvcStat	OBJECT-TYPE
	SYNTAX Hex
	ACCESS read-only
	STATUS mandatory
	DESCRIPTION
	"The state of the PVC."
	::= { fraPStatEntry 12 }

fraPStatLinkState	OBJECT-TYPE
	SYNTAX Hex
	ACCESS read-only
	STATUS mandatory
	DESCRIPTION
	"The state of the link."
	::= { fraPStatEntry 13 }

fraPStatLocSeq	OBJECT-TYPE
	SYNTAX INTEGER
	ACCESS read-only
	STATUS mandatory
	DESCRIPTION
	"The local send sequence."
	::= { fraPStatEntry 14 }

fraPStatLocAck	OBJECT-TYPE
	SYNTAX INTEGER
	ACCESS read-only
	STATUS mandatory
	DESCRIPTION
	"The local acknowledge number."
	::= { fraPStatEntry 15 }

fraPStatLocStat	OBJECT-TYPE
	SYNTAX INTEGER
	ACCESS read-only
	STATUS mandatory
	DESCRIPTION
	"The local state of the link."
	::= { fraPStatEntry 16 }

fraPStatLocStartT	OBJECT-TYPE
	SYNTAX INTEGER
	ACCESS read-only
	STATUS mandatory
	DESCRIPTION
	"The local start time for poll."
	::= { fraPStatEntry 17 }

fraPStatLocErrThr	OBJECT-TYPE
	SYNTAX Counter
	ACCESS read-only
	STATUS mandatory
	DESCRIPTION
	"The local error threshold Counter."
	::= { fraPStatEntry 18 }

fraPStatLocMec	OBJECT-TYPE
	SYNTAX Counter
	ACCESS read-only
	STATUS mandatory
	DESCRIPTION
	"The local monitored event Counter."
	::= { fraPStatEntry 19 }

fraPStatLocPoll	OBJECT-TYPE
	SYNTAX Counter
	ACCESS read-only
	STATUS mandatory
	DESCRIPTION
	"The local poll Counter for DTE."
	::= { fraPStatEntry 20 }

fraPStatRemSeq	OBJECT-TYPE
	SYNTAX INTEGER
	ACCESS read-only
	STATUS mandatory
	DESCRIPTION
	"The remote send sequence."
	::= { fraPStatEntry 21 }

fraPStatRemAck	OBJECT-TYPE
	SYNTAX INTEGER
	ACCESS read-only
	STATUS mandatory
	DESCRIPTION
	"The remote acknowledge number."
	::= { fraPStatEntry 22 }

fraPStatRemStat	OBJECT-TYPE
	SYNTAX INTEGER
	ACCESS read-only
	STATUS mandatory
	DESCRIPTION
	"The remote state of the link."
	::= { fraPStatEntry 23 }

fraPStatRemStartT	OBJECT-TYPE
	SYNTAX INTEGER
	ACCESS read-only
	STATUS mandatory
	DESCRIPTION
	"The remote start time for poll."
	::= { fraPStatEntry 24 }

fraPStatRemErrThr	OBJECT-TYPE
	SYNTAX Counter
	ACCESS read-only
	STATUS mandatory
	DESCRIPTION
	"The remote error threshold Counter."
	::= { fraPStatEntry 25 }

fraPStatRemMec	OBJECT-TYPE
	SYNTAX Counter
	ACCESS read-only
	STATUS mandatory
	DESCRIPTION
	"The remote monitored event Counter."
	::= { fraPStatEntry 26 }

fraPStatRemPoll	OBJECT-TYPE
	SYNTAX Counter
	ACCESS read-only
	STATUS mandatory
	DESCRIPTION
	"The remote poll Counter for DTE."
	::= { fraPStatEntry 27 }

--                              Y2K change : deprecated
--fraPStatLastChange	OBJECT-TYPE
--	SYNTAX DateTimeString
--	ACCESS read-only
--	STATUS deprecated
--	DESCRIPTION
--	"The date and time of last state change."
--	::= { fraPStatEntry 28 }

--                              Y2K change : added,  use DateAndTime convention
fraPStatLastChangeM2	OBJECT-TYPE
	SYNTAX DateAndTime
	ACCESS read-only
	STATUS mandatory
	DESCRIPTION
	"The date and time of last state change."
	::= { fraPStatEntry 29 }

--___________________________________________________________________________
-- The Frame Relay Link A Config (fra)

fraPConfigTable OBJECT-TYPE
	SYNTAX SEQUENCE OF FraPConfigEntry
	ACCESS not-accessible
	STATUS mandatory
	DESCRIPTION
	""
	::= { dv2FrRelay 4 }

fraPConfigEntry OBJECT-TYPE
	SYNTAX	FraPConfigEntry
	ACCESS	not-accessible
	STATUS	mandatory
        INDEX   { fraPConfigDlci }
	::= { fraPConfigTable 1 }

FraPConfigEntry ::=
	SEQUENCE {
		fraPConfigDlci
			INTEGER,
		fraPConfigCir
			INTEGER,
		fraPConfigCommitB
			INTEGER,
		fraPConfigExcessB
			INTEGER,
		fraVci
			VirtualCircuitIdentifier,
		fraVpi
			VirtualPathIdentifier,
		fraPConfigPriority
			INTEGER,
		fraPConfigSuba
			INTEGER,
		fraPConfigSaddr
			INTEGER,
		fraPConfigValidity
			INTEGER,
                fraPConfigDxivpi
                        INTEGER,
                fraPConfigDxivci
                        INTEGER,
                fraPConfigDximode
                        INTEGER
}

fraPConfigDlci OBJECT-TYPE
	SYNTAX INTEGER (16..511)
	ACCESS read-write
	STATUS mandatory
	DESCRIPTION
	"This is the DLCI for the PVC."
	::= { fraPConfigEntry 1 }

fraPConfigCir OBJECT-TYPE
	SYNTAX INTEGER
	ACCESS read-write
	STATUS mandatory
	DESCRIPTION
	"The committed information rate."
	::= { fraPConfigEntry 2 }

fraPConfigCommitB OBJECT-TYPE
	SYNTAX INTEGER
	ACCESS read-write
	STATUS mandatory
	DESCRIPTION
	"The committed burst rate."
	::= { fraPConfigEntry 3 }

fraPConfigExcessB OBJECT-TYPE
	SYNTAX INTEGER
	ACCESS read-write
	STATUS mandatory
	DESCRIPTION
	"The excess burst size."
	::= { fraPConfigEntry 4 }

fraVpi OBJECT-TYPE
	SYNTAX VirtualPathIdentifier
	ACCESS read-only
	STATUS mandatory
	DESCRIPTION
	"The VPI for this call."
	::= { fraPConfigEntry 5 }

fraVci OBJECT-TYPE
	SYNTAX VirtualCircuitIdentifier
	ACCESS read-only
	STATUS mandatory
	DESCRIPTION
	"The VCI for the call."
	::= { fraPConfigEntry 6 }

fraPConfigPriority OBJECT-TYPE
	SYNTAX INTEGER
	ACCESS read-only
	STATUS mandatory
	DESCRIPTION
	""
	::= { fraPConfigEntry 7 }

fraPConfigSuba OBJECT-TYPE
	SYNTAX INTEGER
	ACCESS read-only
	STATUS mandatory
	DESCRIPTION
	""
	::= { fraPConfigEntry 8 }


fraPConfigSaddr OBJECT-TYPE
	SYNTAX INTEGER
	ACCESS read-only
	STATUS mandatory
	DESCRIPTION
	""
	::= { fraPConfigEntry 9 }

fraPConfigValidity OBJECT-TYPE
	SYNTAX INTEGER {
		valid(1),
		invalid(2)
	}
	ACCESS read-write
	STATUS mandatory
	DESCRIPTION
	"Provides a way of deleting a row in the table when
	 set to invalid."
	::= { fraPConfigEntry 10 }


fraPConfigDxivpi OBJECT-TYPE
	SYNTAX INTEGER (0..7)
	ACCESS read-write
	STATUS mandatory
	DESCRIPTION
	"This is the VPI for the PVC"
	::= { fraPConfigEntry 11 }


fraPConfigDxivci OBJECT-TYPE
	SYNTAX INTEGER (0..63)
	ACCESS read-write
	STATUS mandatory
	DESCRIPTION
	"This is the VCI for the PVC"
	::= { fraPConfigEntry 12 }

fraPConfigDximode OBJECT-TYPE
	SYNTAX INTEGER {
		no(1),
		yes(2)
	}
	ACCESS read-write
	STATUS mandatory
	DESCRIPTION
	"This flag indicates whether the mode is DXI - in that case the value of DLCI is ignored"
	::= { fraPConfigEntry 13 }

--___________________________________________________________________________
-- The Frame Relay Link B Status (frb)

frbPStatTable OBJECT-TYPE
	SYNTAX SEQUENCE OF FrbPStatEntry
	ACCESS not-accessible
	STATUS mandatory
	DESCRIPTION
	"This table shows statistics about the Frame Relay PVCs for link 1."
	::= { dv2FrRelay 5 }

frbPStatEntry OBJECT-TYPE
	SYNTAX	FrbPStatEntry
	ACCESS	not-accessible
	STATUS	mandatory
        INDEX   { frbPStatDlci }
	::= { frbPStatTable 1 }

FrbPStatEntry ::=
	SEQUENCE {
		frbPStatDlci
			INTEGER,
		frbPStatRxBCnt
			Counter,
		frbPStatTxBCnt
			Counter,
		frbPStatRxFCnt
			Counter,
		frbPStatTxFCnt
			Counter,
		frbPStatRxBRate
			Gauge,
		frbPStatTxBRate
			Gauge,
		frbPStatRxFRate
			Gauge,
		frbPStatTxFRate
			Gauge,
		frbPStatDERxF
			Counter,
		frbPStatDisRxF
			Counter,
		frbPStatPvcStat
			Hex,
		frbPStatLinkState
			Hex,
		frbPStatLocSeq
			INTEGER,
		frbPStatLocAck
			INTEGER,
		frbPStatLocStat
			INTEGER,
		frbPStatLocStartT
			INTEGER,
		frbPStatLocErrThr
			Counter,
		frbPStatLocMec
			Counter,
		frbPStatLocPoll
			Counter,
		frbPStatRemSeq
			INTEGER,
		frbPStatRemAck
			INTEGER,
		frbPStatRemStat
			INTEGER,
		frbPStatRemStartT
			INTEGER,
		frbPStatRemErrThr
			Counter,
		frbPStatRemMec
			Counter,
		frbPStatRemPoll
			Counter,
--                              Y2K change : deprecated
--		frbPStatLastChange
--			DateTimeString,
--                              Y2K change : added,  use DateAndTime convention
		frbPStatLastChangeM2
			DateAndTime
}

frbPStatDlci OBJECT-TYPE
	SYNTAX INTEGER (16..511)
	ACCESS read-only
	STATUS mandatory
	DESCRIPTION
	"This is the DLCI for the PVC."
	::= { frbPStatEntry 1 }

frbPStatRxBCnt OBJECT-TYPE
	SYNTAX Counter
	ACCESS read-only
	STATUS mandatory
	DESCRIPTION
	"The number of bytes received."
	::= { frbPStatEntry 2 }

frbPStatTxBCnt OBJECT-TYPE
	SYNTAX Counter
	ACCESS read-only
	STATUS mandatory
	DESCRIPTION
	"The number of bytes transmitted."
	::= { frbPStatEntry 3 }

frbPStatRxFCnt OBJECT-TYPE
	SYNTAX Counter
	ACCESS read-only
	STATUS mandatory
	DESCRIPTION
	"The number of frames received."
	::= { frbPStatEntry 4 }

frbPStatTxFCnt OBJECT-TYPE
	SYNTAX Counter
	ACCESS read-only
	STATUS mandatory
	DESCRIPTION
	"The number of frames transmitted."
	::= { frbPStatEntry 5 }

frbPStatRxBRate OBJECT-TYPE
	SYNTAX Gauge
	ACCESS read-only
	STATUS mandatory
	DESCRIPTION
	"The rate of bytes being received."
	::= { frbPStatEntry 6 }

frbPStatTxBRate OBJECT-TYPE
	SYNTAX Gauge
	ACCESS read-only
	STATUS mandatory
	DESCRIPTION
	"The rate of bytes being transmitted."
	::= { frbPStatEntry 7 }

frbPStatRxFRate OBJECT-TYPE
	SYNTAX Gauge
	ACCESS read-only
	STATUS mandatory
	DESCRIPTION
	"The rate of frames being received."
	::= { frbPStatEntry 8 }

frbPStatTxFRate OBJECT-TYPE
	SYNTAX Gauge
	ACCESS read-only
	STATUS mandatory
	DESCRIPTION
	"The rate of frames being transmitted."
	::= { frbPStatEntry 9 }

frbPStatDERxF OBJECT-TYPE
	SYNTAX Counter
	ACCESS read-only
	STATUS mandatory
	DESCRIPTION
	"The count of discarded eligible received frames."
	::= { frbPStatEntry 10 }

frbPStatDisRxF	OBJECT-TYPE
	SYNTAX Counter
	ACCESS read-only
	STATUS mandatory
	DESCRIPTION
	"The count of discarded received frames."
	::= { frbPStatEntry 11 }

frbPStatPvcStat	OBJECT-TYPE
	SYNTAX Hex
	ACCESS read-only
	STATUS mandatory
	DESCRIPTION
	"The state of the PVC."
	::= { frbPStatEntry 12 }

frbPStatLinkState	OBJECT-TYPE
	SYNTAX Hex
	ACCESS read-only
	STATUS mandatory
	DESCRIPTION
	"The state of the link."
	::= { frbPStatEntry 13 }

frbPStatLocSeq	OBJECT-TYPE
	SYNTAX INTEGER
	ACCESS read-only
	STATUS mandatory
	DESCRIPTION
	"The local send sequence."
	::= { frbPStatEntry 14 }

frbPStatLocAck	OBJECT-TYPE
	SYNTAX INTEGER
	ACCESS read-only
	STATUS mandatory
	DESCRIPTION
	"The local acknowledge number."
	::= { frbPStatEntry 15 }

frbPStatLocStat	OBJECT-TYPE
	SYNTAX INTEGER
	ACCESS read-only
	STATUS mandatory
	DESCRIPTION
	"The local state of the link."
	::= { frbPStatEntry 16 }

frbPStatLocStartT	OBJECT-TYPE
	SYNTAX INTEGER
	ACCESS read-only
	STATUS mandatory
	DESCRIPTION
	"The local start time for poll."
	::= { frbPStatEntry 17 }

frbPStatLocErrThr	OBJECT-TYPE
	SYNTAX Counter
	ACCESS read-only
	STATUS mandatory
	DESCRIPTION
	"The local error threshold Counter."
	::= { frbPStatEntry 18 }

frbPStatLocMec	OBJECT-TYPE
	SYNTAX Counter
	ACCESS read-only
	STATUS mandatory
	DESCRIPTION
	"The local monitored event Counter."
	::= { frbPStatEntry 19 }

frbPStatLocPoll	OBJECT-TYPE
	SYNTAX Counter
	ACCESS read-only
	STATUS mandatory
	DESCRIPTION
	"The local poll Counter for DTE."
	::= { frbPStatEntry 20 }

frbPStatRemSeq	OBJECT-TYPE
	SYNTAX INTEGER
	ACCESS read-only
	STATUS mandatory
	DESCRIPTION
	"The remote send sequence."
	::= { frbPStatEntry 21 }

frbPStatRemAck	OBJECT-TYPE
	SYNTAX INTEGER
	ACCESS read-only
	STATUS mandatory
	DESCRIPTION
	"The remote acknowledge number."
	::= { frbPStatEntry 22 }

frbPStatRemStat	OBJECT-TYPE
	SYNTAX INTEGER
	ACCESS read-only
	STATUS mandatory
	DESCRIPTION
	"The remote state of the link."
	::= { frbPStatEntry 23 }

frbPStatRemStartT	OBJECT-TYPE
	SYNTAX INTEGER
	ACCESS read-only
	STATUS mandatory
	DESCRIPTION
	"The remote start time for poll."
	::= { frbPStatEntry 24 }

frbPStatRemErrThr	OBJECT-TYPE
	SYNTAX Counter
	ACCESS read-only
	STATUS mandatory
	DESCRIPTION
	"The remote error threshold Counter."
	::= { frbPStatEntry 25 }

frbPStatRemMec	OBJECT-TYPE
	SYNTAX Counter
	ACCESS read-only
	STATUS mandatory
	DESCRIPTION
	"The remote monitored event Counter."
	::= { frbPStatEntry 26 }

frbPStatRemPoll	OBJECT-TYPE
	SYNTAX Counter
	ACCESS read-only
	STATUS mandatory
	DESCRIPTION
	"The remote poll Counter for DTE."
	::= { frbPStatEntry 27 }

--                              Y2K change : deprecated
--frbPStatLastChange	OBJECT-TYPE
--	SYNTAX DateTimeString
--	ACCESS read-only
--	STATUS deprecated
--	DESCRIPTION
--	"The date and time of last state change."
--	::= { frbPStatEntry 28 }

--                              Y2K change : added use DateAndTime Convention
frbPStatLastChangeM2	OBJECT-TYPE
	SYNTAX DateAndTime
	ACCESS read-only
	STATUS mandatory
	DESCRIPTION
	"The date and time of last state change."
	::= { frbPStatEntry 29 }


--___________________________________________________________________________
-- The Frame Relay Link B Config (frb)

frbPConfigTable OBJECT-TYPE
	SYNTAX SEQUENCE OF FrbPConfigEntry
	ACCESS not-accessible
	STATUS mandatory
	DESCRIPTION
	""
	::= { dv2FrRelay 6 }

frbPConfigEntry OBJECT-TYPE
	SYNTAX	FrbPConfigEntry
	ACCESS	not-accessible
	STATUS	mandatory
        INDEX   { frbPConfigDlci }
	::= { frbPConfigTable 1 }

FrbPConfigEntry ::=
	SEQUENCE {
		frbPConfigDlci
			INTEGER,
		frbPConfigCir
			INTEGER,
		frbPConfigCommitB
			INTEGER,
		frbPConfigExcessB
			INTEGER,
		frbVpi
			VirtualPathIdentifier,
		frbVci
			VirtualCircuitIdentifier,
		frbPConfigPriority
			INTEGER,
		frbPConfigSuba
			INTEGER,
		frbPConfigSaddr
			INTEGER,
		frbPConfigValidity
			INTEGER,
                frbPConfigDxivpi
                        INTEGER,
                frbPConfigDxivci
                        INTEGER,
                frbPConfigDximode
                        INTEGER
}

frbPConfigDlci OBJECT-TYPE
	SYNTAX INTEGER (16..511)
	ACCESS read-write
	STATUS mandatory
	DESCRIPTION
	"This is the DLCI for the PVC."
	::= { frbPConfigEntry 1 }

frbPConfigCir OBJECT-TYPE
	SYNTAX INTEGER
	ACCESS read-write
	STATUS mandatory
	DESCRIPTION
	"The committed information rate."
	::= { frbPConfigEntry 2 }

frbPConfigCommitB OBJECT-TYPE
	SYNTAX INTEGER
	ACCESS read-write
	STATUS mandatory
	DESCRIPTION
	"The committed burst rate."
	::= { frbPConfigEntry 3 }

frbPConfigExcessB OBJECT-TYPE
	SYNTAX INTEGER
	ACCESS read-write
	STATUS mandatory
	DESCRIPTION
	"The excess burst size."
	::= { frbPConfigEntry 4 }

frbVpi OBJECT-TYPE
	SYNTAX VirtualPathIdentifier
	ACCESS read-only
	STATUS mandatory
	DESCRIPTION
	"The VPI for this call."
	::= { frbPConfigEntry 5 }

frbVci OBJECT-TYPE
	SYNTAX VirtualCircuitIdentifier
	ACCESS read-only
	STATUS mandatory
	DESCRIPTION
	"The VCI for the call."
	::= { frbPConfigEntry 6 }

frbPConfigPriority OBJECT-TYPE
	SYNTAX INTEGER
	ACCESS read-only
	STATUS mandatory
	DESCRIPTION
	""
	::= { frbPConfigEntry 7 }

frbPConfigSuba OBJECT-TYPE
	SYNTAX INTEGER
	ACCESS read-only
	STATUS mandatory
	DESCRIPTION
	""
	::= { frbPConfigEntry 8 }


frbPConfigSaddr OBJECT-TYPE
	SYNTAX INTEGER
	ACCESS read-only
	STATUS mandatory
	DESCRIPTION
	""
	::= { frbPConfigEntry 9 }

frbPConfigValidity OBJECT-TYPE
	SYNTAX INTEGER {
		valid(1),
		invalid(2)
	}
	ACCESS read-write
	STATUS mandatory
	DESCRIPTION
	"Provides a way of deleting a row in the table when
	 set to invalid."
	::= { frbPConfigEntry 10 }


        frbPConfigDxivpi OBJECT-TYPE
	SYNTAX INTEGER (0..7)
	ACCESS read-write
	STATUS mandatory
	DESCRIPTION
	"This is the VPI for the PVC"
	::= { frbPConfigEntry 11 }


        frbPConfigDxivci OBJECT-TYPE
	SYNTAX INTEGER (0..63)
	ACCESS read-write
	STATUS mandatory
	DESCRIPTION
	"This is the VCI for the PVC"
	::= { frbPConfigEntry 12 }


frbPConfigDximode OBJECT-TYPE
	SYNTAX INTEGER {
		no(1),
		yes(2)
	}
	ACCESS read-write
	STATUS mandatory
	DESCRIPTION
	"This flag indicates whether the mode is DXI - in that case the value of DLCI is ignored"
	::= { frbPConfigEntry 13 }

--___________________________________________________________________________
-- The dv2VcStatus group

vcaTable	OBJECT-TYPE
	SYNTAX SEQUENCE OF VcaEntry
	ACCESS not-accessible
	STATUS mandatory
	DESCRIPTION
	"This table shows detailed status for native ATM slot controller card link A VCs."
	::= { dv2VcStatus 3 }

vcaEntry OBJECT-TYPE
	SYNTAX	VcaEntry
	ACCESS	not-accessible
	STATUS	mandatory
        INDEX   { vcaVpi,
		  vcaVci
		}
	::= { vcaTable 1 }

VcaEntry ::=
	SEQUENCE {
		vcaVpi
			INTEGER,
		vcaVci
			INTEGER,
		vcaTxGCells
			Counter,
		vcaTxGCellsClp1
			Counter,
		vcaRxGCells
			Counter,
		vcaExcessCells
			Counter,
		vcaPeakExceeds
			Counter,
		vcaCellHead
			Hex,
		vcaCellMask
			Hex,
		vcaCellSwitchHead
			Hex,
                vcaStartTime
                        INTEGER,
		vcaBucketControl
			Hex,
		vcaBucket0CV
			Gauge,
		vcaBucket0Max
			Gauge,
		vcaBucket0Inc
			INTEGER,
		vcaBucket1CV
			Gauge,
		vcaBucket1Max
			Gauge,
		vcaBucket1Inc
			INTEGER,
		vcaBucket2CV
			Gauge,
		vcaBucket2Max
			Gauge,
		vcaBucket2Inc
			INTEGER,
		vcaBucket3CV
			Gauge,
		vcaBucket3Max
			Gauge,
		vcaBucket3Inc
			INTEGER,
		vcaType
			INTEGER,
		vcaDstSlot
			INTEGER,
		vcaDstLink
			INTEGER,
		vcaDstVpi
			INTEGER,
		vcaDstVci
			INTEGER,
		vcaInternalVpi
			INTEGER,
		vcaInternalVci
			INTEGER
}

vcaVpi	OBJECT-TYPE
	SYNTAX INTEGER (0..4095)
	ACCESS read-only
	STATUS mandatory
	DESCRIPTION
	"Virtual path identifier for the VC."
	::= { vcaEntry 1 }

vcaVci	OBJECT-TYPE
	SYNTAX INTEGER (0..65535)
	ACCESS read-only
	STATUS mandatory
	DESCRIPTION
	"Virtual channel identifier for the VC."
	::= { vcaEntry 2 }

vcaTxGCells	OBJECT-TYPE
	SYNTAX Counter
	ACCESS read-only
	STATUS mandatory
	DESCRIPTION
	"Number of transmitted good cells CLP0."
	::= { vcaEntry 3 }

vcaTxGCellsClp1	OBJECT-TYPE
	SYNTAX Counter
	ACCESS read-only
	STATUS mandatory
	DESCRIPTION
	"Number of transmitted good cells CLP1."
	::= { vcaEntry 4 }

vcaRxGCells	OBJECT-TYPE
	SYNTAX Counter
	ACCESS read-only
	STATUS mandatory
	DESCRIPTION
	"Number of received good cells."
	::= { vcaEntry 5 }

vcaExcessCells	OBJECT-TYPE
	SYNTAX Counter
	ACCESS read-only
	STATUS mandatory
	DESCRIPTION
	"Number of cells discarded because of bucket overflow."
	::= { vcaEntry 6 }

vcaPeakExceeds	OBJECT-TYPE
	SYNTAX Counter
	ACCESS read-only
	STATUS mandatory
	DESCRIPTION
	"Number of cells discarded because of peak cell rate violation."
	::= { vcaEntry 7 }

vcaCellHead	OBJECT-TYPE
	SYNTAX Hex
	ACCESS read-only
	STATUS mandatory
	DESCRIPTION
	"This value is bitwise OR'd with the cell header."
	::= { vcaEntry 8 }

vcaCellMask	OBJECT-TYPE
	SYNTAX Hex
	ACCESS read-only
	STATUS mandatory
	DESCRIPTION
	"This value is bitwise AND'd with the cell header."
	::= { vcaEntry 9 }

vcaCellSwitchHead	OBJECT-TYPE
	SYNTAX Hex
	ACCESS read-only
	STATUS mandatory
	DESCRIPTION
	"This comprises a tag which is added to the cell before putting into the cell switch and a control byte."
	::= { vcaEntry 10 }

vcaStartTime	OBJECT-TYPE
	SYNTAX INTEGER
	ACCESS read-only
	STATUS mandatory
	DESCRIPTION
	"This is the bucket start time."
	::= { vcaEntry 11 }

vcaBucketControl	OBJECT-TYPE
	SYNTAX Hex
	ACCESS read-only
	STATUS mandatory
	DESCRIPTION
	"This is the bucket control register value."
	::= { vcaEntry 12 }

vcaBucket0CV	OBJECT-TYPE
	SYNTAX Gauge
	ACCESS read-only
	STATUS mandatory
	DESCRIPTION
	"The current value of bucket 0."
	::= { vcaEntry 13 }

vcaBucket0Max	OBJECT-TYPE
	SYNTAX Gauge
	ACCESS read-only
	STATUS mandatory
	DESCRIPTION
	"The maximum value of bucket 0."
	::= { vcaEntry 14 }

vcaBucket0Inc	OBJECT-TYPE
	SYNTAX INTEGER
	ACCESS read-only
	STATUS mandatory
	DESCRIPTION
	"The bucket 0 increment value."
	::= { vcaEntry 15 }

vcaBucket1CV	OBJECT-TYPE
	SYNTAX Gauge
	ACCESS read-only
	STATUS mandatory
	DESCRIPTION
	"The current value of bucket 1."
	::= { vcaEntry 16 }

vcaBucket1Max	OBJECT-TYPE
	SYNTAX Gauge
	ACCESS read-only
	STATUS mandatory
	DESCRIPTION
	"The maximum value of bucket 1."
	::= { vcaEntry 17 }

vcaBucket1Inc	OBJECT-TYPE
	SYNTAX INTEGER
	ACCESS read-only
	STATUS mandatory
	DESCRIPTION
	"The bucket 1 increment value."
	::= { vcaEntry 18 }

vcaBucket2CV	OBJECT-TYPE
	SYNTAX Gauge
	ACCESS read-only
	STATUS mandatory
	DESCRIPTION
	"The current value of bucket 2."
	::= { vcaEntry 19 }

vcaBucket2Max	OBJECT-TYPE
	SYNTAX Gauge
	ACCESS read-only
	STATUS mandatory
	DESCRIPTION
	"The maximum value of bucket 2."
	::= { vcaEntry 20 }

vcaBucket2Inc	OBJECT-TYPE
	SYNTAX INTEGER
	ACCESS read-only
	STATUS mandatory
	DESCRIPTION
	"The bucket 2 increment value."
	::= { vcaEntry 21 }

vcaBucket3CV	OBJECT-TYPE
	SYNTAX Gauge
	ACCESS read-only
	STATUS mandatory
	DESCRIPTION
	"The current value of bucket 3."
	::= { vcaEntry 22 }

vcaBucket3Max	OBJECT-TYPE
	SYNTAX Gauge
	ACCESS read-only
	STATUS mandatory
	DESCRIPTION
	"The maximum value of bucket 3."
	::= { vcaEntry 23 }

vcaBucket3Inc	OBJECT-TYPE
	SYNTAX INTEGER
	ACCESS read-only
	STATUS mandatory
	DESCRIPTION
	"The bucket 3 increment value."
	::= { vcaEntry 24 }

vcaType	OBJECT-TYPE
	SYNTAX INTEGER {
		mgmt-vc(3),
		sr-pp-pvc(2),
		sr-pp-pvp(6),
		sr-mp-bi-pvc(10),
		sr-mp-bi-pvp(14),
		sr-mp-uni-pvc(26),
		sr-mp-uni-pvp(30),
		sr-pp-svc(1),
		sr-pp-svp(5),
		sr-mp-bi-svc(9),
		sr-mp-bi-svp(13),
		sr-mp-uni-svc(25),
		sr-mp-uni-svp(29),
		ds-pp-pvc(34),
		ds-pp-pvp(38),
		ds-mp-bi-pvc(42),
		ds-mp-bi-pvp(46),
		ds-mp-uni-pvc(58),
		ds-mp-uni-pvp(62),
		ds-pp-svc(33),
		ds-pp-svp(37),
		ds-mp-bi-svc(41),
		ds-mp-bi-svp(45),
		ds-mp-uni-svc(57),
		ds-mp-uni-svp(61)
		}
	ACCESS read-only
	STATUS mandatory
	DESCRIPTION
	"Virtual channel type for the VC."
	::= { vcaEntry 25 }

vcaDstSlot	OBJECT-TYPE
	SYNTAX INTEGER
	ACCESS read-only
	STATUS mandatory
	DESCRIPTION
	"slot # this VC is going to"
	::= { vcaEntry 26 }

vcaDstLink	OBJECT-TYPE
	SYNTAX INTEGER
	ACCESS read-only
	STATUS mandatory
	DESCRIPTION
	"link # this VC is going to"
	::= { vcaEntry 27 }

vcaDstVpi	OBJECT-TYPE
	SYNTAX INTEGER
	ACCESS read-only
	STATUS mandatory
	DESCRIPTION
	"VPI this VC is destined for."
	::= { vcaEntry 28 }

vcaDstVci	OBJECT-TYPE
	SYNTAX INTEGER
	ACCESS read-only
	STATUS mandatory
	DESCRIPTION
	"VCI for this VC is destined for."
	::= { vcaEntry 29 }

vcaInternalVpi	OBJECT-TYPE
	SYNTAX INTEGER
	ACCESS read-only
	STATUS mandatory
	DESCRIPTION
	"Internal VPI"
	::= { vcaEntry 30 }

vcaInternalVci	OBJECT-TYPE
	SYNTAX INTEGER
	ACCESS read-only
	STATUS mandatory
	DESCRIPTION
	"Internal VCI"
	::= { vcaEntry 31 }


vcbTable	OBJECT-TYPE
	SYNTAX SEQUENCE OF VcbEntry
	ACCESS not-accessible
	STATUS mandatory
	DESCRIPTION
	"This table shows detailed status for native ATM slot controller card link B VCs."
	::= { dv2VcStatus 4 }

vcbEntry OBJECT-TYPE
	SYNTAX	VcbEntry
	ACCESS	not-accessible
	STATUS	mandatory
        INDEX   { vcbVpi,
		  vcbVci
		}
	::= { vcbTable 1 }

VcbEntry ::=
	SEQUENCE {
		vcbVpi
			INTEGER,
		vcbVci
			INTEGER,
		vcbTxGCells
			Counter,
		vcbTxGCellsClp1
			Counter,
		vcbRxGCells
			Counter,
		vcbExcessCells
			Counter,
		vcbPeakExceeds
			Counter,
		vcbCellHead
			Hex,
		vcbCellMask
			Hex,
		vcbCellSwitchHead
			Hex,
                vcbStartTime
                        INTEGER,
		vcbBucketControl
			Hex,
		vcbBucket0CV
			Gauge,
		vcbBucket0Max
			Gauge,
		vcbBucket0Inc
			INTEGER,
		vcbBucket1CV
			Gauge,
		vcbBucket1Max
			Gauge,
		vcbBucket1Inc
			INTEGER,
		vcbBucket2CV
			Gauge,
		vcbBucket2Max
			Gauge,
		vcbBucket2Inc
			INTEGER,
		vcbBucket3CV
			Gauge,
		vcbBucket3Max
			Gauge,
		vcbBucket3Inc
			INTEGER,
		vcbType
			INTEGER,
		vcbDstSlot
			INTEGER,
		vcbDstLink
			INTEGER,
		vcbDstVpi
			INTEGER,
		vcbDstVci
			INTEGER,
		vcbInternalVpi
			INTEGER,
		vcbInternalVci
			INTEGER
}

vcbVpi	OBJECT-TYPE
	SYNTAX INTEGER (0..4095)
	ACCESS read-only
	STATUS mandatory
	DESCRIPTION
	"Virtual path identifier for the VC."
	::= { vcbEntry 1 }

vcbVci	OBJECT-TYPE
	SYNTAX INTEGER (0..65535)
	ACCESS read-only
	STATUS mandatory
	DESCRIPTION
	"Virtual channel identifier for the VC."
	::= { vcbEntry 2 }

vcbTxGCells	OBJECT-TYPE
	SYNTAX Counter
	ACCESS read-only
	STATUS mandatory
	DESCRIPTION
	"Number of transmitted good cells CLP0."
	::= { vcbEntry 3 }

vcbTxGCellsClp1	OBJECT-TYPE
	SYNTAX Counter
	ACCESS read-only
	STATUS mandatory
	DESCRIPTION
	"Number of transmitted good cells CLP1."
	::= { vcbEntry 4 }

vcbRxGCells	OBJECT-TYPE
	SYNTAX Counter
	ACCESS read-only
	STATUS mandatory
	DESCRIPTION
	"Number of received good cells."
	::= { vcbEntry 5 }

vcbExcessCells	OBJECT-TYPE
	SYNTAX Counter
	ACCESS read-only
	STATUS mandatory
	DESCRIPTION
	"Number of cells discarded because of bucket overflow."
	::= { vcbEntry 6 }

vcbPeakExceeds	OBJECT-TYPE
	SYNTAX Counter
	ACCESS read-only
	STATUS mandatory
	DESCRIPTION
	"Number of cells discarded because of peak cell rate violation."
	::= { vcbEntry 7 }

vcbCellHead	OBJECT-TYPE
	SYNTAX Hex
	ACCESS read-only
	STATUS mandatory
	DESCRIPTION
	"This value is bitwise OR'd with the cell header."
	::= { vcbEntry 8 }

vcbCellMask	OBJECT-TYPE
	SYNTAX Hex
	ACCESS read-only
	STATUS mandatory
	DESCRIPTION
	"This value is bitwise AND'd with the cell header."
	::= { vcbEntry 9 }

vcbCellSwitchHead	OBJECT-TYPE
	SYNTAX Hex
	ACCESS read-only
	STATUS mandatory
	DESCRIPTION
	"This comprises a tag which is added to the cell before putting into the cell switch and a control byte."
	::= { vcbEntry 10 }

vcbStartTime	OBJECT-TYPE
	SYNTAX INTEGER
	ACCESS read-only
	STATUS mandatory
	DESCRIPTION
	"This is the bucket start time."
	::= { vcbEntry 11 }

vcbBucketControl	OBJECT-TYPE
	SYNTAX Hex
	ACCESS read-only
	STATUS mandatory
	DESCRIPTION
	"This is the bucket control register value."
	::= { vcbEntry 12 }

vcbBucket0CV	OBJECT-TYPE
	SYNTAX Gauge
	ACCESS read-only
	STATUS mandatory
	DESCRIPTION
	"The current value of bucket 0."
	::= { vcbEntry 13 }

vcbBucket0Max	OBJECT-TYPE
	SYNTAX Gauge
	ACCESS read-only
	STATUS mandatory
	DESCRIPTION
	"The maximum value of bucket 0."
	::= { vcbEntry 14 }

vcbBucket0Inc	OBJECT-TYPE
	SYNTAX INTEGER
	ACCESS read-only
	STATUS mandatory
	DESCRIPTION
	"The bucket 0 increment value."
	::= { vcbEntry 15 }

vcbBucket1CV	OBJECT-TYPE
	SYNTAX Gauge
	ACCESS read-only
	STATUS mandatory
	DESCRIPTION
	"The current value of bucket 1."
	::= { vcbEntry 16 }

vcbBucket1Max	OBJECT-TYPE
	SYNTAX Gauge
	ACCESS read-only
	STATUS mandatory
	DESCRIPTION
	"The maximum value of bucket 1."
	::= { vcbEntry 17 }

vcbBucket1Inc	OBJECT-TYPE
	SYNTAX INTEGER
	ACCESS read-only
	STATUS mandatory
	DESCRIPTION
	"The bucket 1 increment value."
	::= { vcbEntry 18 }

vcbBucket2CV	OBJECT-TYPE
	SYNTAX Gauge
	ACCESS read-only
	STATUS mandatory
	DESCRIPTION
	"The current value of bucket 2."
	::= { vcbEntry 19 }

vcbBucket2Max	OBJECT-TYPE
	SYNTAX Gauge
	ACCESS read-only
	STATUS mandatory
	DESCRIPTION
	"The maximum value of bucket 2."
	::= { vcbEntry 20 }

vcbBucket2Inc	OBJECT-TYPE
	SYNTAX INTEGER
	ACCESS read-only
	STATUS mandatory
	DESCRIPTION
	"The bucket 2 increment value."
	::= { vcbEntry 21 }

vcbBucket3CV	OBJECT-TYPE
	SYNTAX Gauge
	ACCESS read-only
	STATUS mandatory
	DESCRIPTION
	"The current value of bucket 3."
	::= { vcbEntry 22 }

vcbBucket3Max	OBJECT-TYPE
	SYNTAX Gauge
	ACCESS read-only
	STATUS mandatory
	DESCRIPTION
	"The maximum value of bucket 3."
	::= { vcbEntry 23 }

vcbBucket3Inc	OBJECT-TYPE
	SYNTAX INTEGER
	ACCESS read-only
	STATUS mandatory
	DESCRIPTION
	"The bucket 3 increment value."
	::= { vcbEntry 24 }

vcbType	OBJECT-TYPE
	SYNTAX INTEGER {
		mgmt-vc(3),
		sr-pp-pvc(2),
		sr-pp-pvp(6),
		sr-mp-bi-pvc(10),
		sr-mp-bi-pvp(14),
		sr-mp-uni-pvc(26),
		sr-mp-uni-pvp(30),
		sr-pp-svc(1),
		sr-pp-svp(5),
		sr-mp-bi-svc(9),
		sr-mp-bi-svp(13),
		sr-mp-uni-svc(25),
		sr-mp-uni-svp(29),
		ds-pp-pvc(34),
		ds-pp-pvp(38),
		ds-mp-bi-pvc(42),
		ds-mp-bi-pvp(46),
		ds-mp-uni-pvc(58),
		ds-mp-uni-pvp(62),
		ds-pp-svc(33),
		ds-pp-svp(37),
		ds-mp-bi-svc(41),
		ds-mp-bi-svp(45),
		ds-mp-uni-svc(57),
		ds-mp-uni-svp(61)
		}
	ACCESS read-only
	STATUS mandatory
	DESCRIPTION
	"Virtual channel type for the VC."
	::= { vcbEntry 25 }

vcbDstSlot	OBJECT-TYPE
	SYNTAX INTEGER
	ACCESS read-only
	STATUS mandatory
	DESCRIPTION
	"slot # this VC is going to"
	::= { vcbEntry 26 }

vcbDstLink	OBJECT-TYPE
	SYNTAX INTEGER
	ACCESS read-only
	STATUS mandatory
	DESCRIPTION
	"link # this VC is going to"
	::= { vcbEntry 27 }

vcbDstVpi	OBJECT-TYPE
	SYNTAX INTEGER
	ACCESS read-only
	STATUS mandatory
	DESCRIPTION
	"VPI this VC is destined for."
	::= { vcbEntry 28 }

vcbDstVci	OBJECT-TYPE
	SYNTAX INTEGER
	ACCESS read-only
	STATUS mandatory
	DESCRIPTION
	"VCI for this VC is destined for."
	::= { vcbEntry 29 }

vcbInternalVpi	OBJECT-TYPE
	SYNTAX INTEGER
	ACCESS read-only
	STATUS mandatory
	DESCRIPTION
	"Internal VPI"
	::= { vcbEntry 30 }

vcbInternalVci	OBJECT-TYPE
	SYNTAX INTEGER
	ACCESS read-only
	STATUS mandatory
	DESCRIPTION
	"Internal VCI"
	::= { vcbEntry 31 }


xpStatTable	OBJECT-TYPE
	SYNTAX SEQUENCE OF XpStatEntry
	ACCESS not-accessible
	STATUS mandatory
	DESCRIPTION
	"This table shows status of the switch fabric interface."
	::= { dv2VcStatus 5 }

xpStatEntry OBJECT-TYPE
	SYNTAX	XpStatEntry
	ACCESS	not-accessible
	STATUS	mandatory
        INDEX   { xpIFace }
	::= { xpStatTable 1 }

XpStatEntry ::=
	SEQUENCE {
		xpIFace
			INTEGER,
		xpRXCells
			Counter,
		xpTXCells
			Counter,
		xpBadVpiVci
			Counter,
		xpRxOverflow
			Counter,
		xpTxHighPrOver
			Counter,
		xpTxLowPrOver
			Counter,
		xpInputOverflow
			Counter,
		xpDocErrors
			Counter,
		xpLowPriorityFifo
			Counter,
        xpEgDiscCells
			Counter,
        xpIgDiscCells
			Counter
}

xpIFace	OBJECT-TYPE
	SYNTAX INTEGER (0..1)
	ACCESS read-only
	STATUS mandatory
	DESCRIPTION
	"Switch fabric interface number."
	::= { xpStatEntry 1 }

xpRXCells	OBJECT-TYPE
	SYNTAX Counter
	ACCESS read-only
	STATUS mandatory
	DESCRIPTION
	"Switch fabric received cell count."
	::= { xpStatEntry 2 }

xpTXCells	OBJECT-TYPE
	SYNTAX Counter
	ACCESS read-only
	STATUS mandatory
	DESCRIPTION
	"Switch fabric transmit cell count."
	::= { xpStatEntry 3 }

xpBadVpiVci	OBJECT-TYPE
	SYNTAX Counter
	ACCESS read-only
	STATUS mandatory
	DESCRIPTION
	"Number of cells with bad VCI/VPI received."
	::= { xpStatEntry 4 }

xpRxOverflow	OBJECT-TYPE
	SYNTAX Counter
	ACCESS read-only
	STATUS mandatory
	DESCRIPTION
	"Number of receiver overflows."
	::= { xpStatEntry 5 }

xpTxHighPrOver	OBJECT-TYPE
	SYNTAX Counter
	ACCESS read-only
	STATUS mandatory
	DESCRIPTION
	"Number of transmitted cells with high priority overflow."
	::= { xpStatEntry 6 }

xpTxLowPrOver	OBJECT-TYPE
	SYNTAX Counter
	ACCESS read-only
	STATUS mandatory
	DESCRIPTION
	"Number of transmitted cells with low priority overflow."
	::= { xpStatEntry 7 }

xpInputOverflow	OBJECT-TYPE
	SYNTAX Counter
	ACCESS read-only
	STATUS mandatory
	DESCRIPTION
	"Number of M68302 fabric input overflow cells."
	::= { xpStatEntry 8 }

xpDocErrors	OBJECT-TYPE
	SYNTAX Counter
	ACCESS read-only
	STATUS mandatory
	DESCRIPTION
	"Number of DOC errors."
	::= { xpStatEntry 9 }

xpLowPriorityFifo	OBJECT-TYPE
	SYNTAX Counter
	ACCESS read-only
	STATUS mandatory
	DESCRIPTION
	"Read transmit low priority FIFO count."
	::= { xpStatEntry 10 }

xpEgDiscCells   OBJECT-TYPE
        SYNTAX Counter
        ACCESS read-only
        STATUS mandatory
        DESCRIPTION
        "Read transmit discard cell count."
        ::= { xpStatEntry 11 }

xpIgDiscCells   OBJECT-TYPE
        SYNTAX Counter
        ACCESS read-only
        STATUS mandatory
        DESCRIPTION
        "Read receive discard cell count."
        ::= { xpStatEntry 12 }

--___________________________________________________________________________
--                   The New PDH config/status table
--                 PLCP config/status info from PLPP chip
--___________________________________________________________________________
pdhPLCPTable OBJECT-TYPE
	SYNTAX SEQUENCE OF PdhPLCPEntry
	ACCESS not-accessible
	STATUS mandatory
	DESCRIPTION
	"This table is used for PLCP configuration and status"
	::= { dv2PDH 1 }

pdhPLCPEntry OBJECT-TYPE
	SYNTAX	PdhPLCPEntry
	ACCESS	not-accessible
	STATUS	mandatory
        INDEX   { pdhPLCPLinkNo }
	::= { pdhPLCPTable 1 }

PdhPLCPEntry ::=
	SEQUENCE {
		pdhPLCPLinkNo
			INTEGER,
-- config info
		pdhPLCPLinkEnable
			INTEGER,
		pdhPLCPLinkStatusAffect
			INTEGER,
		pdhPLCPLinkState
			INTEGER,
		pdhPLCPPhyMode
			INTEGER,
		pdhPLCPMode
			INTEGER,
		pdhPLCPScrambler
			INTEGER,
		pdhPLCP0x55
			INTEGER,
		pdhPLCPSmdsMode
			INTEGER,
		pdhPLCPIdleCell
			INTEGER,
		pdhPLCPLoopback
			INTEGER,
		pdhPLCPClear
			INTEGER,
		pdhPLCPReconfig
			INTEGER,
                pdhPLCPLpbkTimeout
                        INTEGER,
-- misc status
		pdhPLCPChipType
			INTEGER,
		pdhPLCPTXclock
			INTEGER,
		pdhPLCPRXclock
			INTEGER,

-- cell stats
		pdhPLCPTXCells
			Counter,
		pdhPLCPRXCells
			Counter,
		pdhPLCPHCSErrs
			Counter,
-- defects
		pdhPLCPLOCDDefect
			INTEGER,
		pdhPLCPYellowDefect
			INTEGER,
		pdhPLCPLOFDefect
			INTEGER,
-- alarm
		pdhPLCPLOCDAlarm
			INTEGER,
		pdhPLCPYellowAlarm
			INTEGER,
		pdhPLCPLOFAlarm
			INTEGER,
-- error counts
		pdhPLCPFrameErrs
			Counter,
		pdhPLCPBIP8Errs
			Counter,
		pdhPLCPFEBEErrs
			Counter,

-- performance parameters
		pdhPLCPES
			Counter,
		pdhPLCPSES
			Counter,
		pdhPLCPUAS
			Counter,
		pdhPLCPFEES
			Counter,
		pdhPLCPFESES
			Counter,
		pdhPLCPFEUAS
			Counter
		 }

pdhPLCPLinkNo	OBJECT-TYPE
	SYNTAX INTEGER (0..1)
	ACCESS read-only
	STATUS mandatory
	DESCRIPTION
	"Link Number"
	::= { pdhPLCPEntry 1 }

pdhPLCPLinkEnable OBJECT-TYPE
	SYNTAX INTEGER {
		enabled(1),
		disabled(2)
	}
	ACCESS read-write
	STATUS mandatory
	DESCRIPTION
	"Enable/Disable Link"
	::= { pdhPLCPEntry 2 }

pdhPLCPLinkStatusAffect  OBJECT-TYPE
	SYNTAX INTEGER
	{
		ignored(2),
		processed(1)
	}
	ACCESS read-write
	STATUS mandatory
	DESCRIPTION
	"Link Status affect on receiving/transmitting"
	::= { pdhPLCPEntry 3 }

pdhPLCPLinkState  OBJECT-TYPE
	SYNTAX INTEGER
	{
		up(1),
		down(2)
	}
	ACCESS read-only
	STATUS mandatory
	DESCRIPTION
	"Current Link State"
	::= { pdhPLCPEntry 4 }

pdhPLCPPhyMode OBJECT-TYPE
	SYNTAX INTEGER
	{
		none(1),
		ds3(2),
		e3(3)
	}
	ACCESS read-write
	STATUS mandatory
	DESCRIPTION
	"The physical framing for link"
	::= { pdhPLCPEntry 5 }


pdhPLCPMode	OBJECT-TYPE
	SYNTAX INTEGER {
		hec-based-delineation(1),
		ds1-PLCP(2),
		ds3-PLCP(3),
		e1-PLCP(4),
		e3-g751-PLCP(5)
	}
	ACCESS read-write
	STATUS mandatory
	DESCRIPTION
	"The PLCP mode for link."
	::= { pdhPLCPEntry 6 }


pdhPLCPScrambler OBJECT-TYPE
	SYNTAX INTEGER {
		enabled(1),
		disabled(2)
	}
	ACCESS read-write
	STATUS mandatory
	DESCRIPTION
	"Enable/Disable scrambling"
	::= { pdhPLCPEntry 7 }

pdhPLCP0x55	OBJECT-TYPE
	SYNTAX INTEGER {
		enabled(1),
		disabled(2)
	}
	ACCESS read-write
	STATUS mandatory
	DESCRIPTION
	"Enable/Disable XORing HCS with 0x55"
	::= { pdhPLCPEntry 8 }

pdhPLCPSmdsMode	OBJECT-TYPE
	SYNTAX INTEGER {
		disabled(2),
		enabled(1)
	}
	ACCESS read-write
	STATUS mandatory
	DESCRIPTION
	"Enable/Disable SMDS mode"
	::= { pdhPLCPEntry 9 }

pdhPLCPIdleCell OBJECT-TYPE
	SYNTAX INTEGER
	{
	   unassigned(1),
	   idle(2)
	}
	ACCESS read-write
	STATUS mandatory
	DESCRIPTION
	"Idle Cell Header Contents"
	::= { pdhPLCPEntry 10 }

pdhPLCPLoopback	OBJECT-TYPE
	SYNTAX INTEGER {
		none(1),
		diagnostic-lpbk(2),
		line-lpbk(3),
		payload-lpbk(4),
		cell-lpbk(5)
	}
	ACCESS read-write
	STATUS mandatory
	DESCRIPTION
	"PLCP Loopback"
	::= { pdhPLCPEntry 11 }

pdhPLCPClear OBJECT-TYPE
	SYNTAX INTEGER
	{
		no(2),
		yes(1)
	}
	ACCESS read-write
	STATUS mandatory
	DESCRIPTION
	"Clear PLCP counts"
	::= { pdhPLCPEntry 12 }

pdhPLCPReconfig OBJECT-TYPE
	SYNTAX INTEGER
	{
		no(2),
		yes(1)
	}
	ACCESS read-write
	STATUS mandatory
	DESCRIPTION
	"Reconfigure link"
	::= { pdhPLCPEntry 13 }

pdhPLCPLpbkTimeout OBJECT-TYPE
	SYNTAX	INTEGER (1..604800)
	ACCESS	read-write
	STATUS	mandatory
	DESCRIPTION
	"This parameter is used to set the loopback timeout in minutes."
	::= { pdhPLCPEntry 14 }

pdhPLCPChipType OBJECT-TYPE
       SYNTAX INTEGER
       {
               plpp(1),
               suni-pdh(2),
               unknown(3)
       }
       ACCESS read-only
       STATUS mandatory
       DESCRIPTION
       "PDH Chip Type"
	DEFVAL { unknown }
       ::= { pdhPLCPEntry 32 }

pdhPLCPTXclock	OBJECT-TYPE
	SYNTAX INTEGER {
		up(1),
		down(2)
	}
	ACCESS read-only
	STATUS mandatory
	DESCRIPTION
	"The state of TX clock for this link."
	::= { pdhPLCPEntry 33 }

pdhPLCPRXclock	OBJECT-TYPE
	SYNTAX INTEGER {
		up(1),
		down(2)
	}
	ACCESS read-only
	STATUS mandatory
	DESCRIPTION
	"The state of RX clock for this link."
	::= { pdhPLCPEntry 34 }

pdhPLCPTXCells	OBJECT-TYPE
	SYNTAX Counter
	ACCESS read-only
	STATUS mandatory
	DESCRIPTION
	"The transmit cells count for this link."
	::= { pdhPLCPEntry 35 }

pdhPLCPRXCells	OBJECT-TYPE
	SYNTAX Counter
	ACCESS read-only
	STATUS mandatory
	DESCRIPTION
	"The receive cells count for this link."
	::= { pdhPLCPEntry 36 }

pdhPLCPHCSErrs	OBJECT-TYPE
	SYNTAX Counter
	ACCESS read-only
	STATUS mandatory
	DESCRIPTION
	"The header checksum error count for this link."
	::= { pdhPLCPEntry 37 }

pdhPLCPLOCDDefect	OBJECT-TYPE
	SYNTAX INTEGER {
		no(2),
		yes(1)
	}
	ACCESS read-only
	STATUS mandatory
	DESCRIPTION
	"Loss of cell delineation Defect"
	::= { pdhPLCPEntry 43 }

pdhPLCPYellowDefect OBJECT-TYPE
	SYNTAX INTEGER {
		no(2),
		yes(1)
	}
	ACCESS read-only
	STATUS mandatory
	DESCRIPTION
	"PLCP Yellow Defect"
	::= { pdhPLCPEntry 44 }

pdhPLCPLOFDefect OBJECT-TYPE
	SYNTAX INTEGER {
		no(2),
		yes(1)
	}
	ACCESS read-only
	STATUS mandatory
	DESCRIPTION
	"PLCP Loss Of Frame Defect"
	::= { pdhPLCPEntry 45 }

pdhPLCPLOCDAlarm	OBJECT-TYPE
	SYNTAX INTEGER {
		no(2),
		yes(1)
	}
	ACCESS read-only
	STATUS mandatory
	DESCRIPTION
	"Loss of cell delineation Alarm"
	::= { pdhPLCPEntry 49 }

pdhPLCPYellowAlarm OBJECT-TYPE
	SYNTAX INTEGER {
		no(2),
		yes(1)
	}
	ACCESS read-only
	STATUS mandatory
	DESCRIPTION
	"PLCP Yellow Alarm"
	::= { pdhPLCPEntry 50 }

pdhPLCPLOFAlarm OBJECT-TYPE
	SYNTAX INTEGER {
		no(2),
		yes(1)
	}
	ACCESS read-only
	STATUS mandatory
	DESCRIPTION
	"PLCP Loss Of Frame Alarm"
	::= { pdhPLCPEntry 51 }


pdhPLCPFrameErrs OBJECT-TYPE
	SYNTAX Counter
	ACCESS read-only
	STATUS mandatory
	DESCRIPTION
	"Number of PLCP frame errors"
	::= { pdhPLCPEntry 56 }

pdhPLCPBIP8Errs	OBJECT-TYPE
	SYNTAX Counter
	ACCESS read-only
	STATUS mandatory
	DESCRIPTION
	"Number of PLCP BIP-8 errors"
	::= { pdhPLCPEntry 57 }

pdhPLCPFEBEErrs	OBJECT-TYPE
	SYNTAX Counter
	ACCESS read-only
	STATUS mandatory
	DESCRIPTION
	"Number of PLCP FEBE errors"
	::= { pdhPLCPEntry 58 }

pdhPLCPES	OBJECT-TYPE
	SYNTAX Counter
	ACCESS read-only
	STATUS mandatory
	DESCRIPTION
	"PLCP Errored Seconds"
	::= { pdhPLCPEntry 63 }

pdhPLCPSES OBJECT-TYPE
	SYNTAX Counter
	ACCESS read-only
	STATUS mandatory
	DESCRIPTION
	"PLCP Severely Errored Seconds"
	::= { pdhPLCPEntry 64 }

pdhPLCPUAS OBJECT-TYPE
	SYNTAX Counter
	ACCESS read-only
	STATUS mandatory
	DESCRIPTION
	"PLCP Unavailable Seconds"
	::= { pdhPLCPEntry 65 }

pdhPLCPFEES	OBJECT-TYPE
	SYNTAX Counter
	ACCESS read-only
	STATUS mandatory
	DESCRIPTION
	"PLCP Far End Errored Seconds"
	::= { pdhPLCPEntry 66 }

pdhPLCPFESES OBJECT-TYPE
	SYNTAX Counter
	ACCESS read-only
	STATUS mandatory
	DESCRIPTION
	"PLCP Far End Severely Errored Seconds"
	::= { pdhPLCPEntry 67 }

pdhPLCPFEUAS OBJECT-TYPE
	SYNTAX Counter
	ACCESS read-only
	STATUS mandatory
	DESCRIPTION
	"PLCP Far End Unavailable Seconds"
	::= { pdhPLCPEntry 68 }

-- ******** DS3 config/status info obtained from PLPP chip ****************
pdhDS3Table OBJECT-TYPE
	SYNTAX SEQUENCE OF PdhDS3Entry
	ACCESS not-accessible
	STATUS mandatory
	DESCRIPTION
	"This table is used for DS3 config/status supplied by the PLPP chip"
	::= { dv2PDH 2 }

pdhDS3Entry OBJECT-TYPE
	SYNTAX	PdhDS3Entry
	ACCESS	not-accessible
	STATUS	mandatory
        INDEX   { pdhDS3LinkNo }
	::= { pdhDS3Table 1 }

PdhDS3Entry ::=
	SEQUENCE {
		pdhDS3TableValid
			INTEGER,
		pdhDS3LinkNo
			INTEGER,
-- config info
		pdhDS3Framer
			INTEGER,
		pdhDS3TxAIS
			INTEGER,
		pdhDS3Clear
			INTEGER,
		pdhDS3Reconfig
			INTEGER,
-- misc status'
		pdhDS3RxFrmFmt
			INTEGER,
		pdhDS3RxIDL
			INTEGER,
		pdhDS3FEACTxmt
			INTEGER,

-- error counts
		pdhDS3Lcvs
			Counter,
		pdhDS3FrameErrs
			Counter,
		pdhDS3ParityErrs
			Counter,
		pdhDS3CbitPrtyErrs
			Counter,
		pdhDS3FEBEErrs
			Counter,

-- defects
		pdhDS3LOSDefect
			INTEGER,
		pdhDS3OOFDefect
			INTEGER,
		pdhDS3AISDefect
			INTEGER,
		pdhDS3YellowDefect
			INTEGER,
		pdhDS3ExBERDefect
			INTEGER,

-- alarms
		pdhDS3LOSAlarm
			INTEGER,
		pdhDS3LOFAlarm
			INTEGER,
		pdhDS3AISAlarm
			INTEGER,
		pdhDS3YellowAlarm
			INTEGER,
		pdhDS3ExBERAlarm
			INTEGER,

-- performance parameters
		pdhDS3LES
			Counter,
		pdhDS3LSES
			Counter,
		pdhDS3ES
			Counter,
		pdhDS3ES2
			Counter,
		pdhDS3SES
			Counter,
		pdhDS3SES2
			Counter,
		pdhDS3AISS
			Counter,
		pdhDS3UAS
			Counter,
		pdhDS3FarEndES
			Counter,
		pdhDS3FarEndSES
			Counter,
		pdhDS3FarEndUAS
			Counter
		 }

pdhDS3TableValid OBJECT-TYPE
	SYNTAX INTEGER
	{
		no(2),
		yes(1)
	}
	ACCESS read-only
	STATUS mandatory
	DESCRIPTION
	"Indicates if table is valid for configured LIM"
	::= { pdhDS3Entry 1 }

pdhDS3LinkNo	OBJECT-TYPE
	SYNTAX INTEGER (0..1)
	ACCESS read-only
	STATUS mandatory
	DESCRIPTION
	"Link Number"
	::= { pdhDS3Entry 2 }


pdhDS3Framer	OBJECT-TYPE
	SYNTAX INTEGER
	{
  		c-bit(1),
	     	m23(2)
	}
	ACCESS read-write
	STATUS mandatory
	DESCRIPTION
	"DS3 framer mode"
	::= { pdhDS3Entry 3 }

pdhDS3TxAIS OBJECT-TYPE
	SYNTAX INTEGER
	{
		no(2),
		yes(1)
	}
	ACCESS read-write
	STATUS mandatory
	DESCRIPTION
	"Transmit AIS"
	::= { pdhDS3Entry 4 }


pdhDS3Clear OBJECT-TYPE
	SYNTAX INTEGER
	{
		yes(1),
		no(2)
	}
	ACCESS read-write
	STATUS mandatory
	DESCRIPTION
	"Clear Button for Counters"
	::= { pdhDS3Entry 5 }

pdhDS3Reconfig OBJECT-TYPE
	SYNTAX INTEGER
	{
		no(2),
		yes(1)
	}
	ACCESS read-write
	STATUS mandatory
	DESCRIPTION
	"Reconfigure link"
	::= { pdhDS3Entry 6 }


pdhDS3RxFrmFmt OBJECT-TYPE
	SYNTAX INTEGER
	{
		c-bit(1),
		clear-channel(2)
	}
	ACCESS read-only
	STATUS mandatory
	DESCRIPTION
	"Receive framing format"
	::= { pdhDS3Entry 26 }

pdhDS3RxIDL	OBJECT-TYPE
	SYNTAX INTEGER
	{
		no(2),
		yes(1)
	}
	ACCESS read-only
	STATUS mandatory
	DESCRIPTION
	"Receive IDLE status"
	::= { pdhDS3Entry 27 }

pdhDS3FEACTxmt		OBJECT-TYPE
	SYNTAX INTEGER {
		   none(7),
   line-loopback-active(6),
 line-loopback-deactive(5),
		ds3-idl(4),
		ds3-ais(3),
		ds3-oof(2),
		ds3-los(1)
	}
	ACCESS read-only
	STATUS mandatory
	DESCRIPTION
	"Code that has been transmitted as a FEAC."
	::= { pdhDS3Entry 28 }

pdhDS3Lcvs	OBJECT-TYPE
	SYNTAX Counter
	ACCESS read-only
	STATUS mandatory
	DESCRIPTION
	"DS3 Line Code Violation count"
	::= { pdhDS3Entry 33 }

pdhDS3FrameErrs	OBJECT-TYPE
	SYNTAX Counter
	ACCESS read-only
	STATUS mandatory
	DESCRIPTION
	"DS3 frame error count"
	::= { pdhDS3Entry 34 }

pdhDS3ParityErrs	OBJECT-TYPE
	SYNTAX Counter
	ACCESS read-only
	STATUS mandatory
	DESCRIPTION
	"DS3 parity error count"
	::= { pdhDS3Entry 35 }

pdhDS3CbitPrtyErrs	OBJECT-TYPE
	SYNTAX Counter
	ACCESS read-only
	STATUS mandatory
	DESCRIPTION
	"DS3 C-bit parity error count"
	::= { pdhDS3Entry 36 }

pdhDS3FEBEErrs	OBJECT-TYPE
	SYNTAX Counter
	ACCESS read-only
	STATUS mandatory
	DESCRIPTION
	"DS3 FEBE error count"
	::= { pdhDS3Entry 37 }

pdhDS3LOSDefect OBJECT-TYPE
	SYNTAX INTEGER
	{
		no(2),
		yes(1)
	}
	ACCESS read-only
	STATUS mandatory
	DESCRIPTION
	"DS3 Loss of Signal Defect"
	::= { pdhDS3Entry 43 }

pdhDS3OOFDefect OBJECT-TYPE
	SYNTAX INTEGER
	{
		no(2),
		yes(1)
	}
	ACCESS read-only
	STATUS mandatory
	DESCRIPTION
	"DS3 Out of Frame Defect"
	::= { pdhDS3Entry 44 }


pdhDS3AISDefect OBJECT-TYPE
	SYNTAX INTEGER
	{
		no(2),
		yes(1)
	}
	ACCESS read-only
	STATUS mandatory
	DESCRIPTION
	"Receive DS3 AIS Defect"
	::= { pdhDS3Entry 45 }

pdhDS3YellowDefect OBJECT-TYPE
	SYNTAX INTEGER
	{
		no(2),
		yes(1)
	}
	ACCESS read-only
	STATUS mandatory
	DESCRIPTION
	"DS3 Yellow Defect"
	::= { pdhDS3Entry 46 }

pdhDS3ExBERDefect OBJECT-TYPE
	SYNTAX INTEGER
	{
		no(2),
		yes(1)
	}
	ACCESS read-only
	STATUS mandatory
	DESCRIPTION
	"Excessive Bit Error Rate Defect"
	::= { pdhDS3Entry 47 }


pdhDS3LOSAlarm OBJECT-TYPE
	SYNTAX INTEGER
	{
		no(2),
		yes(1)
	}
	ACCESS read-only
	STATUS mandatory
	DESCRIPTION
	"DS3 Loss of Signal Alarm"
	::= { pdhDS3Entry 53 }

pdhDS3LOFAlarm OBJECT-TYPE
	SYNTAX INTEGER
	{
		no(2),
		yes(1)
	}
	ACCESS read-only
	STATUS mandatory
	DESCRIPTION
	"DS3 Loss of Frame Defect"
	::= { pdhDS3Entry 54 }


pdhDS3AISAlarm OBJECT-TYPE
	SYNTAX INTEGER
	{
		no(2),
		yes(1)
	}
	ACCESS read-only
	STATUS mandatory
	DESCRIPTION
	"Receive DS3 AIS Defect"
	::= { pdhDS3Entry 55 }

pdhDS3YellowAlarm OBJECT-TYPE
	SYNTAX INTEGER
	{
		no(2),
		yes(1)
	}
	ACCESS read-only
	STATUS mandatory
	DESCRIPTION
	"DS3 Yellow Alarm"
	::= { pdhDS3Entry 56 }

pdhDS3ExBERAlarm OBJECT-TYPE
	SYNTAX INTEGER
	{
		no(2),
		yes(1)
	}
	ACCESS read-only
	STATUS mandatory
	DESCRIPTION
	"Excessive Bit Error Rate Alarm"
	::= { pdhDS3Entry 57 }

pdhDS3LES OBJECT-TYPE
	SYNTAX Counter
	ACCESS read-only
	STATUS mandatory
	DESCRIPTION
	"Line Errored Seconds"
	::= { pdhDS3Entry 63 }

pdhDS3LSES OBJECT-TYPE
	SYNTAX Counter
	ACCESS read-only
	STATUS mandatory
	DESCRIPTION
	"Line Severely Errored Seconds"
	::= { pdhDS3Entry 64 }

pdhDS3ES OBJECT-TYPE
	SYNTAX Counter
	ACCESS read-only
	STATUS mandatory
	DESCRIPTION
	"Errored Seconds"
	::= { pdhDS3Entry 65 }

pdhDS3ES2 OBJECT-TYPE
	SYNTAX Counter
	ACCESS read-only
	STATUS mandatory
	DESCRIPTION
	"Secondary Errored Seconds (C-bit mode only)"
	::= { pdhDS3Entry 66 }

pdhDS3SES OBJECT-TYPE
	SYNTAX Counter
	ACCESS read-only
	STATUS mandatory
	DESCRIPTION
	"Severely Errored Seconds"
	::= { pdhDS3Entry 67 }

pdhDS3SES2 OBJECT-TYPE
	SYNTAX Counter
	ACCESS read-only
	STATUS mandatory
	DESCRIPTION
	"Secondary Severely Errored Seconds (C-bit mode only)"
	::= { pdhDS3Entry 68 }

pdhDS3AISS OBJECT-TYPE
	SYNTAX Counter
	ACCESS read-only
	STATUS mandatory
	DESCRIPTION
	"AIS Seconds"
	::= { pdhDS3Entry 69 }

pdhDS3UAS OBJECT-TYPE
	SYNTAX Counter
	ACCESS read-only
	STATUS mandatory
	DESCRIPTION
	"Unavailable Seconds"
	::= { pdhDS3Entry 70 }

pdhDS3FarEndES OBJECT-TYPE
	SYNTAX Counter
	ACCESS read-only
	STATUS mandatory
	DESCRIPTION
	"Far End Errored Seconds"
	::= { pdhDS3Entry 71 }

pdhDS3FarEndSES OBJECT-TYPE
	SYNTAX Counter
	ACCESS read-only
	STATUS mandatory
	DESCRIPTION
	"Far End Severely Errored Seconds"
	::= { pdhDS3Entry 72 }

pdhDS3FarEndUAS OBJECT-TYPE
	SYNTAX Counter
	ACCESS read-only
	STATUS mandatory
	DESCRIPTION
	"Far End Unavailable Seconds"
	::= { pdhDS3Entry 73 }

-- **************** E3 config/status info obtained from PLPP chip ************
pdhE3Table OBJECT-TYPE
	SYNTAX SEQUENCE OF PdhE3Entry
	ACCESS not-accessible
	STATUS mandatory
	DESCRIPTION
	"This table is used for E3 config/status supplied by the PLPP chip"
	::= { dv2PDH 3 }

pdhE3Entry OBJECT-TYPE
	SYNTAX	PdhE3Entry
	ACCESS	not-accessible
	STATUS	mandatory
        INDEX   { pdhE3LinkNo }
	::= { pdhE3Table 1 }

PdhE3Entry ::=
	SEQUENCE {
		pdhE3TableValid
			INTEGER,
		pdhE3LinkNo
			INTEGER,
		pdhE3Framer
			INTEGER,
		pdhE3Clear
			INTEGER,
		pdhE3Reconfig
			INTEGER,
-- G832 trail trace config stuff
		pdhE3TxmtTimMk
			INTEGER,
		pdhE3PloadTypeLab
			INTEGER,
		pdhE3TxTrlTrcIdLen
			INTEGER,
		pdhE3TxTrcIdUH
			PhysAddress,
		pdhE3TxTrcIdLH
			PhysAddress,
		pdhE3RxExTrcIdUH
			PhysAddress,
		pdhE3RxExTrcIdLH
			PhysAddress,
-- Error counts
		pdhE3FrameErrs
			Counter,
		pdhE3Lcvs
			Counter,
		pdhE3ParityErrs
			Counter,
		pdhE3FEBEErrs
			Counter,
-- Defects
		pdhE3LOSDefect
			INTEGER,
		pdhE3OOFDefect
			INTEGER,
		pdhE3AISDefect
			INTEGER,
		pdhE3FERFDefect
			INTEGER,
		pdhE3ExBERDefect
			INTEGER,
-- Alarms
		pdhE3LOSAlarm
			INTEGER,
		pdhE3LOFAlarm
			INTEGER,
		pdhE3AISAlarm
			INTEGER,
		pdhE3FERFAlarm
			INTEGER,
		pdhE3ExBERAlarm
			INTEGER,

-- Performance Parameters
		pdhE3LES
			Counter,
		pdhE3LSES
			Counter,
		pdhE3ES
			Counter,
		pdhE3SES
			Counter,
		pdhE3AISS
			Counter,
		pdhE3UAS
			Counter,
-- G832 specific entries
		pdhE3RxTrlTrc
			PhysAddress,
		pdhE3RxTrIdMis
			INTEGER,
		pdhE3RxTrIdUnst
			INTEGER,
		pdhE3RxPloadTypeLabMis
			INTEGER,
		pdhE3RxPloadTypeLabUnst
			INTEGER
		 }

pdhE3TableValid OBJECT-TYPE
	SYNTAX INTEGER
	{
		no(2),
		yes(1)
	}
	ACCESS read-only
	STATUS mandatory
	DESCRIPTION
	"Indicates if table is valid for configured LIM"
	::= { pdhE3Entry 1 }

pdhE3LinkNo OBJECT-TYPE
	SYNTAX INTEGER (0..1)
	ACCESS read-only
	STATUS mandatory
	DESCRIPTION
	"Link Number"
	::= { pdhE3Entry 2 }

pdhE3Framer OBJECT-TYPE
	SYNTAX INTEGER
	{
		g832(2),
		g751(1)
	}
	ACCESS read-write
	STATUS mandatory
	DESCRIPTION
	"E3 framer mode"
	::= { pdhE3Entry 3 }

pdhE3Clear OBJECT-TYPE
	SYNTAX INTEGER
	{
		yes(1),
		no(2)
	}
	ACCESS read-write
	STATUS mandatory
	DESCRIPTION
	"Clear Button for Counters"
	::= { pdhE3Entry 4 }

pdhE3Reconfig OBJECT-TYPE
	SYNTAX INTEGER
	{
		no(2),
		yes(1)
	}
	ACCESS read-write
	STATUS mandatory
	DESCRIPTION
	"Reconfigure link"
	::= { pdhE3Entry 5 }

pdhE3TxmtTimMk OBJECT-TYPE
	SYNTAX INTEGER
	{
		yes(1),
		no(2)
	}
	ACCESS read-write
	STATUS mandatory
	DESCRIPTION
	"Set to yes(1) if traceable to primary ref clk."
	::= { pdhE3Entry 6 }

pdhE3PloadTypeLab	OBJECT-TYPE
	SYNTAX INTEGER
	{
		atm(2)
	}
	ACCESS read-write
	STATUS mandatory
	DESCRIPTION
	"Payload type label."
	::= { pdhE3Entry 7 }

pdhE3TxTrlTrcIdLen	OBJECT-TYPE
	SYNTAX INTEGER
	{
		length-16(16)
	}
	ACCESS read-write
	STATUS mandatory
	DESCRIPTION
	"Trail trace length for transmit and expected receive."
	::= { pdhE3Entry 8 }

pdhE3TxTrcIdUH	OBJECT-TYPE
	SYNTAX PhysAddress
	ACCESS read-write
	STATUS mandatory
	DESCRIPTION
	"Transmit trail trace ID upper half."
	::= { pdhE3Entry 9 }

pdhE3TxTrcIdLH	OBJECT-TYPE
	SYNTAX PhysAddress
	ACCESS read-write
	STATUS mandatory
	DESCRIPTION
	"Transmit trail trace ID lower half."
	::= { pdhE3Entry 10 }

pdhE3RxExTrcIdUH	OBJECT-TYPE
	SYNTAX PhysAddress
	ACCESS read-write
	STATUS mandatory
	DESCRIPTION
	"Receive expected trail trace ID upper half."
	::= { pdhE3Entry 11 }

pdhE3RxExTrcIdLH	OBJECT-TYPE
	SYNTAX PhysAddress
	ACCESS read-write
	STATUS mandatory
	DESCRIPTION
	"Receive expected trail trace ID lower half."
	::= { pdhE3Entry 12 }

pdhE3FrameErrs	OBJECT-TYPE
	SYNTAX Counter
	ACCESS read-only
	STATUS mandatory
	DESCRIPTION
	"E3 frame error count"
	::= { pdhE3Entry 32 }

pdhE3Lcvs OBJECT-TYPE
	SYNTAX Counter
	ACCESS read-only
	STATUS mandatory
	DESCRIPTION
	"E3 Line Code Violation count"
	::= { pdhE3Entry 33 }

pdhE3ParityErrs	OBJECT-TYPE
	SYNTAX Counter
	ACCESS read-only
	STATUS mandatory
	DESCRIPTION
	"E3-G832 parity error count"
	::= { pdhE3Entry 34 }

pdhE3FEBEErrs	OBJECT-TYPE
	SYNTAX Counter
	ACCESS read-only
	STATUS mandatory
	DESCRIPTION
	"E3-G832 FEBE error count"
	::= { pdhE3Entry 35 }

pdhE3LOSDefect	OBJECT-TYPE
	SYNTAX INTEGER
	{
		no(2),
		yes(1)
	}
	ACCESS read-only
	STATUS mandatory
	DESCRIPTION
	"LOS Defect"
	::= { pdhE3Entry 41 }

pdhE3OOFDefect	OBJECT-TYPE
	SYNTAX INTEGER
	{
		no(2),
		yes(1)
	}
	ACCESS read-only
	STATUS mandatory
	DESCRIPTION
	"LOF Defect"
	::= { pdhE3Entry 42 }

pdhE3AISDefect OBJECT-TYPE
	SYNTAX INTEGER
	{
		no(2),
		yes(1)
	}
	ACCESS read-only
	STATUS mandatory
	DESCRIPTION
	"AIS Defect"
	::= { pdhE3Entry 43 }


pdhE3FERFDefect	OBJECT-TYPE
	SYNTAX INTEGER
	{
		no(2),
		yes(1)
	}
	ACCESS read-only
	STATUS mandatory
	DESCRIPTION
	"FERF Defect"
	::= { pdhE3Entry 44 }

pdhE3ExBERDefect	OBJECT-TYPE
	SYNTAX INTEGER
	{
		no(2),
		yes(1)
	}
	ACCESS read-only
	STATUS mandatory
	DESCRIPTION
	"Excessive Bit Error Rate Defect"
	::= { pdhE3Entry 45 }

pdhE3LOSAlarm	OBJECT-TYPE
	SYNTAX INTEGER
	{
		no(2),
		yes(1)
	}
	ACCESS read-only
	STATUS mandatory
	DESCRIPTION
	"LOS Alarm"
	::= { pdhE3Entry 51 }

pdhE3LOFAlarm	OBJECT-TYPE
	SYNTAX INTEGER
	{
		no(2),
		yes(1)
	}
	ACCESS read-only
	STATUS mandatory
	DESCRIPTION
	"LOF Alarm"
	::= { pdhE3Entry 52 }

pdhE3AISAlarm OBJECT-TYPE
	SYNTAX INTEGER
	{
		no(2),
		yes(1)
	}
	ACCESS read-only
	STATUS mandatory
	DESCRIPTION
	"AIS Alarm"
	::= { pdhE3Entry 53 }

pdhE3FERFAlarm	OBJECT-TYPE
	SYNTAX INTEGER
	{
		no(2),
		yes(1)
	}
	ACCESS read-only
	STATUS mandatory
	DESCRIPTION
	"FERF Alarm"
	::= { pdhE3Entry 54 }


pdhE3ExBERAlarm	OBJECT-TYPE
	SYNTAX INTEGER
	{
		no(2),
		yes(1)
	}
	ACCESS read-only
	STATUS mandatory
	DESCRIPTION
	"Excessive Bit Error Rate Alarm"
	::= { pdhE3Entry 55 }

pdhE3LES OBJECT-TYPE
	SYNTAX Counter
	ACCESS read-only
	STATUS mandatory
	DESCRIPTION
	"Line Errored Seconds"
	::= { pdhE3Entry 61 }

pdhE3LSES OBJECT-TYPE
	SYNTAX Counter
	ACCESS read-only
	STATUS mandatory
	DESCRIPTION
	"Line Severely Errored Seconds"
	::= { pdhE3Entry 62 }

pdhE3ES OBJECT-TYPE
	SYNTAX Counter
	ACCESS read-only
	STATUS mandatory
	DESCRIPTION
	"Errored Seconds"
	::= { pdhE3Entry 63 }

pdhE3SES OBJECT-TYPE
	SYNTAX Counter
	ACCESS read-only
	STATUS mandatory
	DESCRIPTION
	"Severely Errored Seconds"
	::= { pdhE3Entry 64 }

pdhE3AISS OBJECT-TYPE
	SYNTAX Counter
	ACCESS read-only
	STATUS mandatory
	DESCRIPTION
	"AIS Seconds"
	::= { pdhE3Entry 65 }

pdhE3UAS OBJECT-TYPE
	SYNTAX Counter
	ACCESS read-only
	STATUS mandatory
	DESCRIPTION
	"Unavailable Seconds"
	::= { pdhE3Entry 66 }

pdhE3RxTrlTrc	OBJECT-TYPE
	SYNTAX PhysAddress (SIZE (16))
	ACCESS read-only
	STATUS mandatory
	DESCRIPTION
	"Last received trail trace message."
	::= { pdhE3Entry 76 }

pdhE3RxTrIdMis	OBJECT-TYPE
	SYNTAX INTEGER {
		no(2),
		yes(1)
	}
	ACCESS read-only
	STATUS mandatory
	DESCRIPTION
	"Receive trace id mismatch indication."
	::= { pdhE3Entry 77 }

pdhE3RxTrIdUnst	OBJECT-TYPE
	SYNTAX INTEGER {
		no(2),
		yes(1)
	}
	ACCESS read-only
	STATUS mandatory
	DESCRIPTION
	"Receive trace id unstable indication."
	::= { pdhE3Entry 78 }

pdhE3RxPloadTypeLabMis	OBJECT-TYPE
	SYNTAX INTEGER {
		no(2),
		yes(1)
	}
	ACCESS read-only
	STATUS mandatory
	DESCRIPTION
	"Receive payload type label mismatch indication."
	::= { pdhE3Entry 79 }

pdhE3RxPloadTypeLabUnst	OBJECT-TYPE
	SYNTAX INTEGER {
		no(2),
		yes(1)
	}
	ACCESS read-only
	STATUS mandatory
	DESCRIPTION
	"Receive payload type label unstable indication."
	::= { pdhE3Entry 80 }


--___________________________________________________________________________
-- The PLPP config table

plppCTable OBJECT-TYPE
	SYNTAX SEQUENCE OF PlppCEntry
	ACCESS not-accessible
	STATUS mandatory
	DESCRIPTION
	"This table is used to control PLPP configuration."
	::= { dv2PLPP 1 }

plppCEntry OBJECT-TYPE
	SYNTAX	PlppCEntry
	ACCESS	not-accessible
	STATUS	mandatory
        INDEX   { plppCLinkNo }
	::= { plppCTable 1 }

PlppCEntry ::=
	SEQUENCE {
		plppCLinkNo
			INTEGER,
		plppCLinkEnab
			INTEGER,
		plppCCPLCPMode
			INTEGER,
		plppCDS3Framer
			INTEGER,
		plppCScrambler
			INTEGER,
		plppC0x55
			INTEGER,
		plppCCLine
			INTEGER,
		plppCLoopback
			INTEGER,
--		plppCLoopTimer
--			INTEGER,
--		plppCLoopDiag
--			INTEGER,
--		plppCLoopLine
--			INTEGER,
		plppCSmdsMode
			INTEGER,
		plppCPloadTypeLab
			INTEGER,
		plppCTxTrlTrcIdLen
			INTEGER,
		plppCTxTrcId
			PhysAddress,
		plppCRxExTrcId
			PhysAddress
}


plppCLinkNo	OBJECT-TYPE
	SYNTAX INTEGER (0..1)
	ACCESS read-only
	STATUS mandatory
	DESCRIPTION
	"The link number for this configuration."
	::= { plppCEntry 1 }

plppCLinkEnab	OBJECT-TYPE
	SYNTAX INTEGER {
		yes(1),
		no(2)
	}
	ACCESS read-write
	STATUS mandatory
	DESCRIPTION
	"Set to yes(1) to enable the link."
	::= { plppCEntry 2 }

plppCCPLCPMode	OBJECT-TYPE
	SYNTAX INTEGER {
		none(1),
		e1(2),
		g751-e3(3),
		ds1(4),
		ds3(5),
		g832-e3(6)
	}
	ACCESS read-write
	STATUS mandatory
	DESCRIPTION
	"The PLCP mode for link."
	::= { plppCEntry 3 }

plppCDS3Framer	OBJECT-TYPE
	SYNTAX INTEGER {
		no(2),
		yes(1)
	}
	ACCESS read-write
	STATUS mandatory
	DESCRIPTION
	"Set to yes(1) to enable the DS3 framer mode for this link."
	::= { plppCEntry 4 }

plppCScrambler	OBJECT-TYPE
	SYNTAX INTEGER {
		yes(1),
		no(2)
	}
	ACCESS read-write
	STATUS mandatory
	DESCRIPTION
	"Set to no(2) to disable the scrambler mode for this link."
	::= { plppCEntry 5 }

plppC0x55	OBJECT-TYPE
	SYNTAX INTEGER {
		yes(1),
		no(2)
	}
	ACCESS read-write
	STATUS mandatory
	DESCRIPTION
	"If set to no(2) then HCS is not XORed with 0x55"
	::= { plppCEntry 6 }

plppCCLine	OBJECT-TYPE
	SYNTAX INTEGER {
		processed(1),
		ignored(2)
	}
	ACCESS read-write
	STATUS mandatory
	DESCRIPTION
	"Control line processing for this link."
	::= { plppCEntry 7 }

plppCLoopback	OBJECT-TYPE
	SYNTAX INTEGER {
		no(2),
		yes(1)
	}
	ACCESS read-write
	STATUS mandatory
	DESCRIPTION
	"Set to yes(1) to enable loopback mode for this link."
	::= { plppCEntry 8 }

-- plppCLoopTimer	OBJECT-TYPE
--	SYNTAX INTEGER {
--		no(2),
--		yes(1)
--	}
--	ACCESS read-write
--	STATUS deprecated
--	DESCRIPTION
--	"Set to yes(1) to enable loop timing."
--	::= { plppCEntry 9 }

-- plppCLoopDiag OBJECT-TYPE
--	SYNTAX INTEGER {
--		no(2),
--		yes(1)
--	}
--	ACCESS read-write
--	STATUS deprecated
--	DESCRIPTION
--	"Set to yes(1) to enable diagnostic loopback."
--	::= { plppCEntry 10 }

-- plppCLoopLine OBJECT-TYPE
--	SYNTAX INTEGER {
--		no(2),
--		yes(1)
--	}
--	ACCESS read-write
--	STATUS deprecated
--	DESCRIPTION
--	"Set to yes(1) to enable line loopback."
--	::= { plppCEntry 11 }

plppCSmdsMode	OBJECT-TYPE
	SYNTAX INTEGER {
		no(2),
		yes(1)
	}
	ACCESS read-write
	STATUS mandatory
	DESCRIPTION
	"Set to yes(1) to enable SMDS mode."
	::= { plppCEntry 12 }

plppCPloadTypeLab	OBJECT-TYPE
	SYNTAX INTEGER (0..7)
	ACCESS read-write
	STATUS mandatory
	DESCRIPTION
	"Pay type label."
	::= { plppCEntry 13 }

plppCTxTrlTrcIdLen	OBJECT-TYPE
	SYNTAX INTEGER
	{
		l16(16),
		l64(64)
	}
	ACCESS read-write
	STATUS mandatory
	DESCRIPTION
	"Trail trace length for transmit and expected receive."
	::= { plppCEntry 14 }

plppCTxTrcId	OBJECT-TYPE
	SYNTAX PhysAddress (SIZE (16..64))
	ACCESS read-write
	STATUS mandatory
	DESCRIPTION
	"Transmit trail trace identifier."
	::= { plppCEntry 15 }

plppCRxExTrcId	OBJECT-TYPE
	SYNTAX PhysAddress (SIZE (16..64))
	ACCESS read-write
	STATUS mandatory
	DESCRIPTION
	"Receive expected trail trace identifier."
	::= { plppCEntry 16 }


--___________________________________________________________________________
-- The plpp status table

plppSTable OBJECT-TYPE
	SYNTAX SEQUENCE OF PlppSEntry
	ACCESS not-accessible
	STATUS mandatory
	DESCRIPTION
	"The status table for plpp."
	::= { dv2PLPP 2 }

plppSEntry OBJECT-TYPE
	SYNTAX	PlppSEntry
	ACCESS	not-accessible
	STATUS	mandatory
        INDEX   { plppSLinkNo }
	::= { plppSTable 1 }

PlppSEntry ::=
	SEQUENCE {
		plppSLinkNo
			INTEGER,
		plppSCLines
			INTEGER,
		plppSTXclock
			INTEGER,
		plppSRXclock
			INTEGER,
		plppSTXCells
			Counter,
		plppSRXCells
			Counter,
		plppSHCSErrs
			Counter,
-- 		plppSBadVciPi
--			INTEGER,
--		plppSRXOverflows
--			Counter,
--		plppSXPOverflows
--			Counter,
		plppSFrameErrs
			Counter,
		plppSBIP8Errs
			Counter,
		plppSFEBEErrs
			Counter,
		plppSSPLRStatus
			INTEGER,
		plppSDs3Lcvs
			Counter,
		plppSDs3FrameErrs
			Counter,
		plppSDs3ParityErrs
			Counter,
		plppSDs3CbitPrtyErrs
			Counter,
		plppSDs3FEBEErrs
			Counter,
		plppSDs3RxAIS
			INTEGER,
		plppSDs3RxRedAlarm
			INTEGER,
		plppSDs3RxYellowAlarm
			INTEGER,
		plppSPLCPRxYellowAlarm
			INTEGER,
		plppsRxTrIdMis
			INTEGER,
		plppsRxTrIdUnst
			INTEGER,
		plppsRxPloadTypeLabMis
			INTEGER,
		plppsRxPloadTypeLabUnst
			INTEGER,
		plppsRxTrlTrc
			PhysAddress
}


plppSLinkNo	OBJECT-TYPE
	SYNTAX INTEGER (0..1)
	ACCESS read-only
	STATUS mandatory
	DESCRIPTION
	"The link number for this status."
	::= { plppSEntry 1 }

plppSCLines	OBJECT-TYPE
	SYNTAX INTEGER {
		up(1),
		down(2)
	}
	ACCESS read-only
	STATUS mandatory
	DESCRIPTION
	"The state of control lines for this link."
	::= { plppSEntry 2 }

plppSTXclock	OBJECT-TYPE
	SYNTAX INTEGER {
		up(1),
		down(2)
	}
	ACCESS read-only
	STATUS mandatory
	DESCRIPTION
	"The state of TX clock for this link."
	::= { plppSEntry 3 }

plppSRXclock	OBJECT-TYPE
	SYNTAX INTEGER {
		up(1),
		down(2)
	}
	ACCESS read-only
	STATUS mandatory
	DESCRIPTION
	"The state of RX clock for this link."
	::= { plppSEntry 4 }

plppSTXCells	OBJECT-TYPE
	SYNTAX Counter
	ACCESS read-only
	STATUS mandatory
	DESCRIPTION
	"The transmit cells count for this link."
	::= { plppSEntry 5 }

plppSRXCells	OBJECT-TYPE
	SYNTAX Counter
	ACCESS read-only
	STATUS mandatory
	DESCRIPTION
	"The receive cells count for this link."
	::= { plppSEntry 6 }

plppSHCSErrs	OBJECT-TYPE
	SYNTAX Counter
	ACCESS read-only
	STATUS mandatory
	DESCRIPTION
	"The header checksum error count for this link."
	::= { plppSEntry 7 }

--plppSBadVciPi	OBJECT-TYPE
--	SYNTAX INTEGER
--	ACCESS read-only
--	STATUS deprecated
--	DESCRIPTION
--	"Invalid VPI/VCI cells."
--	::= { plppSEntry 8 }

--plppSRXOverflows	OBJECT-TYPE
--	SYNTAX Counter
--	ACCESS read-only
--	STATUS deprecated
--	DESCRIPTION
--	"Receiver overflows."
--	::= { plppSEntry 9 }

--plppSXPOverflows	OBJECT-TYPE
--	SYNTAX Counter
--	ACCESS read-only
--	STATUS deprecated
--	DESCRIPTION
--	"XP overflows."
--	::= { plppSEntry 10 }


plppSFrameErrs	OBJECT-TYPE
	SYNTAX Counter
	ACCESS read-only
	STATUS mandatory
	DESCRIPTION
	"The frame error count for this link."
	::= { plppSEntry 11 }

plppSBIP8Errs	OBJECT-TYPE
	SYNTAX Counter
	ACCESS read-only
	STATUS mandatory
	DESCRIPTION
	"The BIP-8 error count for this link."
	::= { plppSEntry 12 }

plppSFEBEErrs	OBJECT-TYPE
	SYNTAX Counter
	ACCESS read-only
	STATUS mandatory
	DESCRIPTION
	"The FEBE error count for this link."
	::= { plppSEntry 13 }

plppSSPLRStatus	OBJECT-TYPE
	SYNTAX INTEGER
	ACCESS read-only
	STATUS mandatory
	DESCRIPTION
	"The SPLR Status Register Contents."
	::= { plppSEntry 14 }

plppSDs3Lcvs	OBJECT-TYPE
	SYNTAX Counter
	ACCESS read-only
	STATUS mandatory
	DESCRIPTION
	"The DS3 LCV count for this link."
	::= { plppSEntry 15 }

plppSDs3FrameErrs	OBJECT-TYPE
	SYNTAX Counter
	ACCESS read-only
	STATUS mandatory
	DESCRIPTION
	"The DS3 frame error count for this link."
	::= { plppSEntry 16 }

plppSDs3ParityErrs	OBJECT-TYPE
	SYNTAX Counter
	ACCESS read-only
	STATUS mandatory
	DESCRIPTION
	"The DS3 parity error count for this link."
	::= { plppSEntry 17 }

plppSDs3CbitPrtyErrs	OBJECT-TYPE
	SYNTAX Counter
	ACCESS read-only
	STATUS mandatory
	DESCRIPTION
	"The DS3 control bit parity error count for this link."
	::= { plppSEntry 18 }

plppSDs3FEBEErrs	OBJECT-TYPE
	SYNTAX Counter
	ACCESS read-only
	STATUS mandatory
	DESCRIPTION
	"The DS3 FEBE error count for this link."
	::= { plppSEntry 19 }

plppSDs3RxAIS	OBJECT-TYPE
	SYNTAX INTEGER {
		yes(1),
		no(2)
	}
	ACCESS read-only
	STATUS mandatory
	DESCRIPTION
	"Receive DS3 AIS status."
	::= { plppSEntry 20 }

plppSDs3RxRedAlarm	OBJECT-TYPE
	SYNTAX INTEGER {
		yes(1),
		no(2)
	}
	ACCESS read-only
	STATUS mandatory
	DESCRIPTION
	"Receive DS3 Red Alarm status."
	::= { plppSEntry 21 }

plppSDs3RxYellowAlarm	OBJECT-TYPE
	SYNTAX INTEGER {
		yes(1),
		no(2)
	}
	ACCESS read-only
	STATUS mandatory
	DESCRIPTION
	"Receive DS3 Yellow Alarm status."
	::= { plppSEntry 22 }

plppSPLCPRxYellowAlarm	OBJECT-TYPE
	SYNTAX INTEGER {
		yes(1),
		no(2)
	}
	ACCESS read-only
	STATUS mandatory
	DESCRIPTION
	"Receive PLCP Yellow Alarm status."
	::= { plppSEntry 23 }

plppsRxTrIdMis	OBJECT-TYPE
	SYNTAX INTEGER {
		yes(1),
		no(2)
	}
	ACCESS read-only
	STATUS mandatory
	DESCRIPTION
	"Receive trace id mismatch indication."
	::= { plppSEntry 24 }

plppsRxTrIdUnst	OBJECT-TYPE
	SYNTAX INTEGER {
		yes(1),
		no(2)
	}
	ACCESS read-only
	STATUS mandatory
	DESCRIPTION
	"Receive trace id unstable indication."
	::= { plppSEntry 25 }

plppsRxPloadTypeLabMis	OBJECT-TYPE
	SYNTAX INTEGER {
		yes(1),
		no(2)
	}
	ACCESS read-only
	STATUS mandatory
	DESCRIPTION
	"Receive payload type label mismatch indication."
	::= { plppSEntry 26 }

plppsRxPloadTypeLabUnst	OBJECT-TYPE
	SYNTAX INTEGER {
		yes(1),
		no(2)
	}
	ACCESS read-only
	STATUS mandatory
	DESCRIPTION
	"Receive payload type label unstable indication."
	::= { plppSEntry 27 }

plppsRxTrlTrc	OBJECT-TYPE
	SYNTAX PhysAddress (SIZE (16..64))
	ACCESS read-only
	STATUS mandatory
	DESCRIPTION
	"Last received trail trace message."
	::= { plppSEntry 28 }


--___________________________________________________________________________
-- The PLPP DS3-2C Config table

plppV2CTable OBJECT-TYPE
	SYNTAX SEQUENCE OF PlppV2CEntry
	ACCESS not-accessible
	STATUS mandatory
	DESCRIPTION
	"This table is used to control DS3-2C PLPP configuration."
	::= { dv2PLPP 3 }

plppV2CEntry OBJECT-TYPE
	SYNTAX	PlppV2CEntry
	ACCESS	not-accessible
	STATUS	mandatory
        INDEX   { plppV2CLinkNo }
	::= { plppV2CTable 1 }


PlppV2CEntry ::=
	SEQUENCE {
		plppV2CLinkNo
			INTEGER,
		plppV2CLinkEnab
			INTEGER,
		plppV2CCPLCPMode
			INTEGER,
		plppV2CDS3Framer
			INTEGER,
		plppV2CScrambler
			INTEGER,
		plppV2C0x55
			INTEGER,
		plppV2CLoopback
			INTEGER,
		plppV2CSmdsMode
			INTEGER,
		plppV2CFrmFmt
			INTEGER,
		plppV2CTxAIS
			INTEGER
}
plppV2CLinkNo	OBJECT-TYPE
	SYNTAX INTEGER (0..1)
	ACCESS read-only
	STATUS mandatory
	DESCRIPTION
	"The link number for this configuration."
	::= { plppV2CEntry 1 }

plppV2CLinkEnab	OBJECT-TYPE
	SYNTAX INTEGER {
		yes(1),
		no(2)
	}
	ACCESS read-write
	STATUS mandatory
	DESCRIPTION
	"Set to yes(1) to enable the link."
	::= { plppV2CEntry 2 }

plppV2CCPLCPMode	OBJECT-TYPE
	SYNTAX INTEGER {
		yes(1),
		no(2)
	}
	ACCESS read-write
	STATUS mandatory
	DESCRIPTION
	"Set to yes(1) to enable the PLCP layer mode for this link."
	::= { plppV2CEntry 3 }

plppV2CDS3Framer	OBJECT-TYPE
	SYNTAX INTEGER {
		yes(1),
		no(2)
	}
	ACCESS read-write
	STATUS mandatory
	DESCRIPTION
	"Set to yes(1) to enable the DS3 framer mode for this link."
	::= { plppV2CEntry 4 }

plppV2CScrambler	OBJECT-TYPE
	SYNTAX INTEGER {
		yes(1),
		no(2)
	}
	ACCESS read-write
	STATUS mandatory
	DESCRIPTION
	"Set to no(2) to disable the scrambler mode for this link."
	::= { plppV2CEntry 5 }

plppV2C0x55	OBJECT-TYPE
	SYNTAX INTEGER {
		yes(1),
		no(2)
	}
	ACCESS read-write
	STATUS mandatory
	DESCRIPTION
	"If set to no(2) then HCS is not XORed with 0x55"
	::= { plppV2CEntry 6 }



plppV2CLoopback	OBJECT-TYPE
	SYNTAX INTEGER {
		no(2),
		yes(1)
	}
	ACCESS read-write
	STATUS mandatory
	DESCRIPTION
	"Set to yes(1) to enable loopback mode for this link."
	::= { plppV2CEntry 7 }


plppV2CSmdsMode	OBJECT-TYPE
	SYNTAX INTEGER {
		no(2),
		yes(1)
	}
	ACCESS read-write
	STATUS mandatory
	DESCRIPTION
	"Set to yes(1) to enable SMDS mode."
	::= { plppV2CEntry 8 }


plppV2CFrmFmt	OBJECT-TYPE
	SYNTAX INTEGER {
	     c-bit(1),
	     clear-channel(2)
	}
	ACCESS read-write
	STATUS mandatory
	DESCRIPTION
	"Set to yes(1) to enable C-bit parity framing format."
	::= { plppV2CEntry 9 }


plppV2CTxAIS	OBJECT-TYPE
	SYNTAX INTEGER {
		no(2),
		yes(1)
	}
	ACCESS read-write
	STATUS mandatory
	DESCRIPTION
	"Set to yes(1) to enable framer to Txmt AIS."
	::= { plppV2CEntry 10 }


--___________________________________________________________________________
-- The DS3-2C plpp status table

plppV2STable OBJECT-TYPE
	SYNTAX SEQUENCE OF PlppV2SEntry
	ACCESS not-accessible
	STATUS mandatory
	DESCRIPTION
	"The status table for DS3-2C plpp."
	::= { dv2PLPP 4 }

plppV2SEntry OBJECT-TYPE
	SYNTAX	PlppV2SEntry
	ACCESS	not-accessible
	STATUS	mandatory
        INDEX   { plppV2SLinkNo }
	::= { plppV2STable 1 }

PlppV2SEntry ::=
	SEQUENCE {
		plppV2SLinkNo
			INTEGER,
		plppV2STXclock
			INTEGER,
		plppV2SRXclock
			INTEGER,
		plppV2STXCells
			Counter,
		plppV2SRXCells
			Counter,
		plppV2SHCSErrs
			Counter,
		plppV2SFrameErrs
			Counter,
		plppV2SBIP8Errs
			Counter,
		plppV2SFEBEErrs
			Counter,
		plppV2SSPLRStatus
			INTEGER,
	        plppV2SDs3FrmFmt
			INTEGER,
		plppV2SDs3Lcvs
			Counter,
		plppV2SDs3FrameErrs
			Counter,
		plppV2SDs3ParityErrs
			Counter,
		plppV2SDs3CbitPrtyErrs
			Counter,
		plppV2SDs3FEBEErrs
			Counter,
		plppV2SDs3RxAIS
			INTEGER,
		plppV2SDs3RxRedAlarm
			INTEGER,
		plppV2SDs3RxYellowAlarm
			INTEGER,
		plppV2SPLCPRxYellowAlarm
			INTEGER,
		plppV2SDs3FEACTxmt
			INTEGER,
		plppV2SRxIDL
			INTEGER,
		plppV2SLOC
			INTEGER,
		plppV2SDs3LPBK
			INTEGER
}

plppV2SLinkNo	OBJECT-TYPE
	SYNTAX INTEGER (0..1)
	ACCESS read-only
	STATUS mandatory
	DESCRIPTION
	"The link number for this status."
	::= { plppV2SEntry 1 }

plppV2STXclock	OBJECT-TYPE
	SYNTAX INTEGER {
		up(1),
		down(2)
	}
	ACCESS read-only
	STATUS mandatory
	DESCRIPTION
	"The state of TX clock for this link."
	::= { plppV2SEntry 2 }

plppV2SRXclock	OBJECT-TYPE
	SYNTAX INTEGER {
		up(1),
		down(2)
	}
	ACCESS read-only
	STATUS mandatory
	DESCRIPTION
	"The state of RX clock for this link."
	::= { plppV2SEntry 3 }

plppV2STXCells	OBJECT-TYPE
	SYNTAX Counter
	ACCESS read-only
	STATUS mandatory
	DESCRIPTION
	"The transmit cells count for this link."
	::= { plppV2SEntry 4 }

plppV2SRXCells	OBJECT-TYPE
	SYNTAX Counter
	ACCESS read-only
	STATUS mandatory
	DESCRIPTION
	"The receive cells count for this link."
	::= { plppV2SEntry 5 }

plppV2SHCSErrs	OBJECT-TYPE
	SYNTAX Counter
	ACCESS read-only
	STATUS mandatory
	DESCRIPTION
	"The header checksum error count for this link."
	::= { plppV2SEntry 6 }

plppV2SFrameErrs	OBJECT-TYPE
	SYNTAX Counter
	ACCESS read-only
	STATUS mandatory
	DESCRIPTION
	"The frame error count for this link."
	::= { plppV2SEntry 7 }

plppV2SBIP8Errs	OBJECT-TYPE
	SYNTAX Counter
	ACCESS read-only
	STATUS mandatory
	DESCRIPTION
	"The BIP-8 error count for this link."
	::= { plppV2SEntry 8 }

plppV2SFEBEErrs	OBJECT-TYPE
	SYNTAX Counter
	ACCESS read-only
	STATUS mandatory
	DESCRIPTION
	"The FEBE error count for this link."
	::= { plppV2SEntry 9 }

plppV2SSPLRStatus	OBJECT-TYPE
	SYNTAX INTEGER {
		no(2),
		yes(1)
	}
	ACCESS read-only
	STATUS mandatory
	DESCRIPTION
	"yes(1) indicates a PLCP LOF."
	::= { plppV2SEntry 10 }

plppV2SDs3FrmFmt	OBJECT-TYPE
	SYNTAX INTEGER {
		c-bit(1),
		clear-channel(2)
	}
	ACCESS read-only
	STATUS mandatory
	DESCRIPTION
	"Operate in DS3 C-bit Parity or drop-back to Clear Channel."
	::= { plppV2SEntry 11 }

plppV2SDs3Lcvs	OBJECT-TYPE
	SYNTAX Counter
	ACCESS read-only
	STATUS mandatory
	DESCRIPTION
	"The DS3 LCV count for this link."
	::= { plppV2SEntry 12 }

plppV2SDs3FrameErrs	OBJECT-TYPE
	SYNTAX Counter
	ACCESS read-only
	STATUS mandatory
	DESCRIPTION
	"The DS3 frame error count for this link."
	::= { plppV2SEntry 13 }

plppV2SDs3ParityErrs	OBJECT-TYPE
	SYNTAX Counter
	ACCESS read-only
	STATUS mandatory
	DESCRIPTION
	"The DS3 parity error count for this link."
	::= { plppV2SEntry 14 }

plppV2SDs3CbitPrtyErrs	OBJECT-TYPE
	SYNTAX Counter
	ACCESS read-only
	STATUS mandatory
	DESCRIPTION
	"The DS3 control bit parity error count for this link."
	::= { plppV2SEntry 15 }

plppV2SDs3FEBEErrs	OBJECT-TYPE
	SYNTAX Counter
	ACCESS read-only
	STATUS mandatory
	DESCRIPTION
	"The DS3 FEBE error count for this link."
	::= { plppV2SEntry 16 }

plppV2SDs3RxAIS	OBJECT-TYPE
	SYNTAX INTEGER {
		no(2),
		yes(1)
	}
	ACCESS read-only
	STATUS mandatory
	DESCRIPTION
	"Receive DS3 AIS status."
	::= { plppV2SEntry 17 }

plppV2SDs3RxRedAlarm	OBJECT-TYPE
	SYNTAX INTEGER {
		no(2),
		yes(1)
	}
	ACCESS read-only
	STATUS mandatory
	DESCRIPTION
	"Receive DS3 Red Alarm status."
	::= { plppV2SEntry 18 }

plppV2SDs3RxYellowAlarm	OBJECT-TYPE
	SYNTAX INTEGER {
		yes(1),
		no(2)
	}
	ACCESS read-only
	STATUS mandatory
	DESCRIPTION
	"Receive DS3 Yellow Alarm status."
	::= { plppV2SEntry 19 }

plppV2SPLCPRxYellowAlarm	OBJECT-TYPE
	SYNTAX INTEGER {
		no(2),
		yes(1)
	}
	ACCESS read-only
	STATUS mandatory
	DESCRIPTION
	"Receive PLCP Yellow Alarm status."
	::= { plppV2SEntry 20 }

plppV2SDs3FEACTxmt		OBJECT-TYPE
	SYNTAX INTEGER {
		   none(7),
   line-loopback-active(6),
 line-loopback-deactive(5),
		ds3-idl(4),
		ds3-ais(3),
		ds3-oof(2),
		ds3-los(1)
	}
	ACCESS read-only
	STATUS mandatory
	DESCRIPTION
	"Code that has been transmitted as a FEAC."
	::= { plppV2SEntry 21 }

plppV2SRxIDL	OBJECT-TYPE
	SYNTAX INTEGER {
		no(2),
		yes(1)
	}
	ACCESS read-only
	STATUS mandatory
	DESCRIPTION
	"yes(1) indicates an IDLE has been received."
	::= { plppV2SEntry 22 }

plppV2SLOC	OBJECT-TYPE
	SYNTAX INTEGER {
		no(2),
		yes(1)
	}
	ACCESS read-only
	STATUS mandatory
	DESCRIPTION
	"Receive Loss of cell delineation."
	::= { plppV2SEntry 23 }

plppV2SDs3LPBK	OBJECT-TYPE
	SYNTAX INTEGER {
		no(2),
		yes(1)
	}
	ACCESS read-only
	STATUS mandatory
	DESCRIPTION
	"if yes(1), the DS3 Framer is in loopback."
	::= { plppV2SEntry 24 }

--___________________________________________________________________________
-- The PLPP E1-2C config table

plppE1CTable OBJECT-TYPE
	SYNTAX SEQUENCE OF PlppE1CEntry
	ACCESS not-accessible
	STATUS mandatory
	DESCRIPTION
	"This table to control the E1-2C PLPP configuration."
	::= { dv2PLPP 5 }

plppE1CEntry OBJECT-TYPE
	SYNTAX	PlppE1CEntry
	ACCESS	not-accessible
	STATUS	mandatory
        INDEX   { plppE1CLinkNo }
	::= { plppE1CTable 1 }

PlppE1CEntry ::=
	SEQUENCE {
		plppE1CLinkNo
			INTEGER,
		plppE1CLinkEnab
			INTEGER,
		plppE1CScrambler
			INTEGER,
		plppE1C0x55
			INTEGER,
		plppE1CSmdsMode
			INTEGER,
		plppE1CLpbk
			INTEGER
}

plppE1CLinkNo	OBJECT-TYPE
	SYNTAX INTEGER (0..1)
	ACCESS read-only
	STATUS mandatory
	DESCRIPTION
	"The link number for this configuration."
	::= { plppE1CEntry 1 }

plppE1CLinkEnab	OBJECT-TYPE
	SYNTAX INTEGER {
		yes(1),
		no(2)
	}
	ACCESS read-write
	STATUS mandatory
	DESCRIPTION
	"Set to yes(1) to enable the link."
	::= { plppE1CEntry 2 }

plppE1CScrambler	OBJECT-TYPE
	SYNTAX INTEGER {
		yes(1),
		no(2)
	}
	ACCESS read-write
	STATUS mandatory
	DESCRIPTION
	"Set to no(2) to disable the scrambler mode for this link."
	::= { plppE1CEntry 3 }

plppE1C0x55	OBJECT-TYPE
	SYNTAX INTEGER {
		yes(1),
		no(2)
	}
	ACCESS read-write
	STATUS mandatory
	DESCRIPTION
	"If set to no(2) then HCS is not XORed with 0x55"
	::= { plppE1CEntry 4 }

plppE1CSmdsMode	OBJECT-TYPE
	SYNTAX INTEGER {
		no(2),
		yes(1)
	}
	ACCESS read-write
	STATUS mandatory
	DESCRIPTION
	"Set to yes(1) to enable SMDS mode."
	::= { plppE1CEntry 5 }

plppE1CLpbk	OBJECT-TYPE
	SYNTAX INTEGER {
		no(2),
		yes(1)
	}
	ACCESS read-write
	STATUS mandatory
	DESCRIPTION
	"Set to yes(1) to enable DOC Framer loopback."
	::= { plppE1CEntry 6 }


--___________________________________________________________________________
-- The plpp E1-2C status table

plppE1STable OBJECT-TYPE
	SYNTAX SEQUENCE OF PlppE1SEntry
	ACCESS not-accessible
	STATUS mandatory
	DESCRIPTION
	"The status table for E1-2C plpp."
	::= { dv2PLPP 6 }

plppE1SEntry OBJECT-TYPE
	SYNTAX	PlppE1SEntry
	ACCESS	not-accessible
	STATUS	mandatory
        INDEX   { plppE1SLinkNo }
	::= { plppE1STable 1 }

PlppE1SEntry ::=
	SEQUENCE {
		plppE1SLinkNo
			INTEGER,
		plppE1STXclock
			INTEGER,
		plppE1SRXclock
			INTEGER,
		plppE1STXCells
			Counter,
		plppE1SRXCells
			Counter,
		plppE1SHCSErrs
			Counter,
		plppE1SCRCErrs
			Counter,
		plppE1SFrameErrs
			Counter,
		plppE1SFEBEErrs
			Counter,
		plppE1SLcvs
			Counter,
		plppE1SRxAIS
			INTEGER,
		plppE1SRxOOF
			INTEGER,
		plppE1SRxLOS
			INTEGER,
		plppE1SRxLOF
			INTEGER,
		plppE1SFerf
			INTEGER
}

plppE1SLinkNo	OBJECT-TYPE
	SYNTAX INTEGER (0..1)
	ACCESS read-only
	STATUS mandatory
	DESCRIPTION
	"The link number for this status."
	::= { plppE1SEntry 1 }


plppE1STXclock	OBJECT-TYPE
	SYNTAX INTEGER {
		up(1),
		down(2)
	}
	ACCESS read-only
	STATUS mandatory
	DESCRIPTION
	"The state of TX clock for this link."
	::= { plppE1SEntry 2 }

plppE1SRXclock	OBJECT-TYPE
	SYNTAX INTEGER {
		up(1),
		down(2)
	}
	ACCESS read-only
	STATUS mandatory
	DESCRIPTION
	"The state of RX clock for this link."
	::= { plppE1SEntry 3 }

plppE1STXCells	OBJECT-TYPE
	SYNTAX Counter
	ACCESS read-only
	STATUS mandatory
	DESCRIPTION
	"The transmit cells count for this link."
	::= { plppE1SEntry 4 }

plppE1SRXCells	OBJECT-TYPE
	SYNTAX Counter
	ACCESS read-only
	STATUS mandatory
	DESCRIPTION
	"The receive cells count for this link."
	::= { plppE1SEntry 5 }

plppE1SHCSErrs	OBJECT-TYPE
	SYNTAX Counter
	ACCESS read-only
	STATUS mandatory
	DESCRIPTION
	"The HCS error count for this link."
	::= { plppE1SEntry 6 }

plppE1SCRCErrs	OBJECT-TYPE
	SYNTAX Counter
	ACCESS read-only
	STATUS mandatory
	DESCRIPTION
	"The CRC-4 error count for this link."
	::= { plppE1SEntry 7 }

plppE1SFrameErrs OBJECT-TYPE
	SYNTAX Counter
	ACCESS read-only
	STATUS mandatory
	DESCRIPTION
	"The frame error count for this link."
	::= { plppE1SEntry 8 }

plppE1SFEBEErrs	OBJECT-TYPE
	SYNTAX Counter
	ACCESS read-only
	STATUS mandatory
	DESCRIPTION
	"The FEBE error count for this link."
	::= { plppE1SEntry 9 }

plppE1SLcvs	OBJECT-TYPE
	SYNTAX Counter
	ACCESS read-only
	STATUS mandatory
	DESCRIPTION
	"The E1 LCV count for this link."
	::= { plppE1SEntry 10 }

plppE1SRxAIS	OBJECT-TYPE
	SYNTAX INTEGER {
		no(2),
		yes(1)
	}
	ACCESS read-only
	STATUS mandatory
	DESCRIPTION
	"Receive E1 AIS status."
	::= { plppE1SEntry 11 }


plppE1SRxOOF	OBJECT-TYPE
	SYNTAX INTEGER {
		no(2),
		yes(1)
	}
	ACCESS read-only
	STATUS mandatory
	DESCRIPTION
	"Receive E1 OOF status."
	::= { plppE1SEntry 12 }

plppE1SRxLOS	OBJECT-TYPE
	SYNTAX INTEGER {
		no(2),
		yes(1)
	}
	ACCESS read-only
	STATUS mandatory
	DESCRIPTION
	"Receive E1 LOS status."
	::= { plppE1SEntry 13 }

plppE1SRxLOF	OBJECT-TYPE
	SYNTAX INTEGER {
		no(2),
		yes(1)
	}
	ACCESS read-only
	STATUS mandatory
	DESCRIPTION
	"Receive E1 LOF status."
	::= { plppE1SEntry 14 }

plppE1SFerf	OBJECT-TYPE
	SYNTAX INTEGER {
		no(2),
		yes(1)
	}
	ACCESS read-only
	STATUS mandatory
	DESCRIPTION
	"Receiving a Far-End Receive Failure if yes."
	::= { plppE1SEntry 15 }


--___________________________________________________________________________
-- The PLPP E3-2C config table

plppE3CTable OBJECT-TYPE
	SYNTAX SEQUENCE OF PlppE3CEntry
	ACCESS not-accessible
	STATUS mandatory
	DESCRIPTION
	"This table is used to control the E3-2C PLPP configuration."
	::= { dv2PLPP 7 }

plppE3CEntry OBJECT-TYPE
	SYNTAX	PlppE3CEntry
	ACCESS	not-accessible
	STATUS	mandatory
        INDEX   { plppE3CLinkNo }
	::= { plppE3CTable 1 }

PlppE3CEntry ::=
	SEQUENCE {
		plppE3CLinkNo
			INTEGER,
		plppE3CLinkEnab
			INTEGER,
		plppE3CFramer
			INTEGER,
		plppE3CPLCPMode
			INTEGER,
		plppE3CScrambler
			INTEGER,
		plppE3C0x55
			INTEGER,
		plppE3CLoopback
			INTEGER,
		plppE3CSmdsMode
			INTEGER,
		plppE3CTxmtTimMk
			INTEGER,
		plppE3CPloadTypeLab
			INTEGER,
		plppE3CTxTrlTrcIdLen
			INTEGER,
		plppE3CTxTrcIdUH
			PhysAddress,
		plppE3CTxTrcIdLH
			PhysAddress,
		plppE3CRxExTrcIdUH
			PhysAddress,
		plppE3CRxExTrcIdLH
			PhysAddress
}


plppE3CLinkNo	OBJECT-TYPE
	SYNTAX INTEGER (0..1)
	ACCESS read-only
	STATUS mandatory
	DESCRIPTION
	"The link number for this configuration."
	::= { plppE3CEntry 1 }

plppE3CLinkEnab	OBJECT-TYPE
	SYNTAX INTEGER {
		yes(1),
		no(2)
	}
	ACCESS read-write
	STATUS mandatory
	DESCRIPTION
	"Set to yes(1) to enable the link."
	::= { plppE3CEntry 2 }

plppE3CFramer	OBJECT-TYPE
	SYNTAX INTEGER {
		g832(3),
		g751(2),
		none(1)
	}
	ACCESS read-write
	STATUS mandatory
	DESCRIPTION
	"The E3 framer mode for the link."
	::= { plppE3CEntry 3 }

plppE3CPLCPMode	OBJECT-TYPE
	SYNTAX INTEGER {
		none(1),
		g751(3)
	}
	ACCESS read-write
	STATUS mandatory
	DESCRIPTION
	"The PLCP mode for the link."
	::= { plppE3CEntry 4 }

plppE3CScrambler	OBJECT-TYPE
	SYNTAX INTEGER {
		yes(1),
		no(2)
	}
	ACCESS read-write
	STATUS mandatory
	DESCRIPTION
	"Set to no(2) to disable the scrambler mode for this link."
	::= { plppE3CEntry 5 }

plppE3C0x55	OBJECT-TYPE
	SYNTAX INTEGER {
		yes(1),
		no(2)
	}
	ACCESS read-write
	STATUS mandatory
	DESCRIPTION
	"If set to no(2) then HCS is not XORed with 0x55"
	::= { plppE3CEntry 6 }

plppE3CLoopback	OBJECT-TYPE
	SYNTAX INTEGER {
		no(2),
		yes(1)
	}
	ACCESS read-write
	STATUS mandatory
	DESCRIPTION
	"Set to yes(1) to enable loopback mode for this link."
	::= { plppE3CEntry 7 }


plppE3CSmdsMode	OBJECT-TYPE
	SYNTAX INTEGER {
		no(2),
		yes(1)
	}
	ACCESS read-write
	STATUS mandatory
	DESCRIPTION
	"Set to yes(1) to enable SMDS mode."
	::= { plppE3CEntry 8 }

plppE3CTxmtTimMk OBJECT-TYPE
	SYNTAX INTEGER {
		yes(1),
		no(2)
	}
	ACCESS read-write
	STATUS mandatory
	DESCRIPTION
	"Set to yes(1) if traceable to primary ref clk."
	::= { plppE3CEntry 9 }

plppE3CPloadTypeLab	OBJECT-TYPE
	SYNTAX INTEGER {
		atm(2)
	}
	ACCESS read-write
	STATUS mandatory
	DESCRIPTION
	"Payload type label."
	::= { plppE3CEntry 10 }

plppE3CTxTrlTrcIdLen	OBJECT-TYPE
	SYNTAX INTEGER
	{
		length-16(16)
	}
	ACCESS read-write
	STATUS mandatory
	DESCRIPTION
	"Trail trace length for transmit and expected receive."
	::= { plppE3CEntry 11 }

plppE3CTxTrcIdUH	OBJECT-TYPE
	SYNTAX PhysAddress (SIZE (8))
	ACCESS read-write
	STATUS mandatory
	DESCRIPTION
	"Transmit trail trace ID upper half."
	::= { plppE3CEntry 12 }

plppE3CTxTrcIdLH	OBJECT-TYPE
	SYNTAX PhysAddress (SIZE (8))
	ACCESS read-write
	STATUS mandatory
	DESCRIPTION
	"Transmit trail trace ID lower half."
	::= { plppE3CEntry 13 }

plppE3CRxExTrcIdUH	OBJECT-TYPE
	SYNTAX PhysAddress (SIZE (8))
	ACCESS read-write
	STATUS mandatory
	DESCRIPTION
	"Receive expected trail trace ID upper half."
	::= { plppE3CEntry 14 }

plppE3CRxExTrcIdLH	OBJECT-TYPE
	SYNTAX PhysAddress (SIZE (8))
	ACCESS read-write
	STATUS mandatory
	DESCRIPTION
	"Receive expected trail trace ID lower half."
	::= { plppE3CEntry 15 }


--___________________________________________________________________________
-- The plpp E3-2C status table

plppE3STable OBJECT-TYPE
	SYNTAX SEQUENCE OF PlppE3SEntry
	ACCESS not-accessible
	STATUS mandatory
	DESCRIPTION
	"The E3-2C status table for plpp."
	::= { dv2PLPP 8 }

plppE3SEntry OBJECT-TYPE
	SYNTAX	PlppE3SEntry
	ACCESS	not-accessible
	STATUS	mandatory
        INDEX   { plppE3SLinkNo }
	::= { plppE3STable 1 }

PlppE3SEntry ::=
	SEQUENCE {
		plppE3SLinkNo
			INTEGER,
		plppE3STXclock
			INTEGER,
		plppE3SRXclock
			INTEGER,
		plppE3STXCells
			Counter,
		plppE3SRXCells
			Counter,
		plppE3SHCSErrs
			Counter,
		plppE3SE3FrameErrs
			Counter,
		plppE3SPLCPFrameErrs
			Counter,
		plppE3SBIP8Errs
			Counter,
		plppE3SFEBEErrs
			Counter,
		plppE3SLcvs
			Counter,
		plppE3SLcd
			INTEGER,
		plppE3SRxTrlTrc
			PhysAddress,
		plppE3SRxAIS
			INTEGER,
		plppE3SRxOOF
			INTEGER,
		plppE3SRxLOS
			INTEGER,
		plppE3SRxLOF
			INTEGER,
		plppE3SRxFERF
			INTEGER,
		plppE3SPLCPRxLof
			INTEGER,
		plppE3SPLCPRxYellowAlarm
			INTEGER,
		plppE3SRxTrIdMis
			INTEGER,
		plppE3SRxTrIdUnst
			INTEGER,
		plppE3SRxPloadTypeLabMis
			INTEGER,
		plppE3SRxPloadTypeLabUnst
			INTEGER
}


plppE3SLinkNo	OBJECT-TYPE
	SYNTAX INTEGER (0..1)
	ACCESS read-only
	STATUS mandatory
	DESCRIPTION
	"The link number for this status."
	::= { plppE3SEntry 1 }

plppE3STXclock	OBJECT-TYPE
	SYNTAX INTEGER {
		down(2),
		up(1)
	}
	ACCESS read-only
	STATUS mandatory
	DESCRIPTION
	"The state of TX clock for this link."
	::= { plppE3SEntry 2 }

plppE3SRXclock	OBJECT-TYPE
	SYNTAX INTEGER {
		down(2),
		up(1)
	}
	ACCESS read-only
	STATUS mandatory
	DESCRIPTION
	"The state of RX clock for this link."
	::= { plppE3SEntry 3 }

plppE3STXCells	OBJECT-TYPE
	SYNTAX Counter
	ACCESS read-only
	STATUS mandatory
	DESCRIPTION
	"The transmit cells count for this link."
	::= { plppE3SEntry 4 }

plppE3SRXCells	OBJECT-TYPE
	SYNTAX Counter
	ACCESS read-only
	STATUS mandatory
	DESCRIPTION
	"The receive cells count for this link."
	::= { plppE3SEntry 5 }

plppE3SHCSErrs	OBJECT-TYPE
	SYNTAX Counter
	ACCESS read-only
	STATUS mandatory
	DESCRIPTION
	"The header checksum error count for this link."
	::= { plppE3SEntry 6 }

plppE3SE3FrameErrs	OBJECT-TYPE
	SYNTAX Counter
	ACCESS read-only
	STATUS mandatory
	DESCRIPTION
	"The E3 frame error count for this link."
	::= { plppE3SEntry 7 }

plppE3SPLCPFrameErrs	OBJECT-TYPE
	SYNTAX Counter
	ACCESS read-only
	STATUS mandatory
	DESCRIPTION
	"The PLCP frame error count for this link."
	::= { plppE3SEntry 8 }

plppE3SBIP8Errs	OBJECT-TYPE
	SYNTAX Counter
	ACCESS read-only
	STATUS mandatory
	DESCRIPTION
	"The BIP-8 error count for this link."
	::= { plppE3SEntry 9 }

plppE3SFEBEErrs	OBJECT-TYPE
	SYNTAX Counter
	ACCESS read-only
	STATUS mandatory
	DESCRIPTION
	"The FEBE error count for this link."
	::= { plppE3SEntry 10 }

plppE3SLcvs	OBJECT-TYPE
	SYNTAX Counter
	ACCESS read-only
	STATUS mandatory
	DESCRIPTION
	"The E3 LCV count for this link."
	::= { plppE3SEntry 11 }

plppE3SLcd	OBJECT-TYPE
	SYNTAX INTEGER {
		no(2),
		yes(1)
	}
	ACCESS read-only
	STATUS mandatory
	DESCRIPTION
	"Receive Loss of cell delineation."
	::= { plppE3SEntry 12 }

plppE3SRxTrlTrc	OBJECT-TYPE
	SYNTAX PhysAddress (SIZE (16))
	ACCESS read-only
	STATUS mandatory
	DESCRIPTION
	"Last received trail trace message."
	::= { plppE3SEntry 13 }

plppE3SRxAIS	OBJECT-TYPE
	SYNTAX INTEGER {
		no(2),
		yes(1)
	}
	ACCESS read-only
	STATUS mandatory
	DESCRIPTION
	"Receive E3 AIS status."
	::= { plppE3SEntry 14 }

plppE3SRxOOF	OBJECT-TYPE
	SYNTAX INTEGER {
		no(2),
		yes(1)
	}
	ACCESS read-only
	STATUS mandatory
	DESCRIPTION
	"Receive E3 OOF status."
	::= { plppE3SEntry 15 }

plppE3SRxLOS	OBJECT-TYPE
	SYNTAX INTEGER {
		no(2),
		yes(1)
	}
	ACCESS read-only
	STATUS mandatory
	DESCRIPTION
	"Receive E3 LOS status."
	::= { plppE3SEntry 16 }

plppE3SRxLOF	OBJECT-TYPE
	SYNTAX INTEGER {
		no(2),
		yes(1)
	}
	ACCESS read-only
	STATUS mandatory
	DESCRIPTION
	"Receive E3 LOF status."
	::= { plppE3SEntry 17 }

plppE3SRxFERF	OBJECT-TYPE
	SYNTAX INTEGER {
		no(2),
		yes(1)
	}
	ACCESS read-only
	STATUS mandatory
	DESCRIPTION
	"Receive E3 FERF status."
	::= { plppE3SEntry 18 }

plppE3SPLCPRxLof	OBJECT-TYPE
	SYNTAX INTEGER {
		no(2),
		yes(1)
	}
	ACCESS read-only
	STATUS mandatory
	DESCRIPTION
	"The PLCP Rx LOF for this link."
	::= { plppE3SEntry 19 }

plppE3SPLCPRxYellowAlarm	OBJECT-TYPE
	SYNTAX INTEGER {
		no(2),
		yes(1)
	}
	ACCESS read-only
	STATUS mandatory
	DESCRIPTION
	"Receive PLCP Yellow Alarm status."
	::= { plppE3SEntry 20 }

plppE3SRxTrIdMis	OBJECT-TYPE
	SYNTAX INTEGER {
		no(2),
		yes(1)
	}
	ACCESS read-only
	STATUS mandatory
	DESCRIPTION
	"Receive trace id mismatch indication."
	::= { plppE3SEntry 21 }

plppE3SRxTrIdUnst	OBJECT-TYPE
	SYNTAX INTEGER {
		no(2),
		yes(1)
	}
	ACCESS read-only
	STATUS mandatory
	DESCRIPTION
	"Receive trace id unstable indication."
	::= { plppE3SEntry 22 }

plppE3SRxPloadTypeLabMis	OBJECT-TYPE
	SYNTAX INTEGER {
		no(2),
		yes(1)
	}
	ACCESS read-only
	STATUS mandatory
	DESCRIPTION
	"Receive payload type label mismatch indication."
	::= { plppE3SEntry 23 }

plppE3SRxPloadTypeLabUnst	OBJECT-TYPE
	SYNTAX INTEGER {
		no(2),
		yes(1)
	}
	ACCESS read-only
	STATUS mandatory
	DESCRIPTION
	"Receive payload type label unstable indication."
	::= { plppE3SEntry 24 }




-- ------------------------------------------------------------------------
-- Local Fibre configuration and status

lFibreConfTable OBJECT-TYPE
	SYNTAX SEQUENCE OF LFibreConfEntry
	ACCESS not-accessible
	STATUS mandatory
	DESCRIPTION
	"This table contains configuration information for the LFDOC."
	::= { dv2LocalFibre 1 }

lFibreConfEntry OBJECT-TYPE
	SYNTAX	LFibreConfEntry
	ACCESS	not-accessible
	STATUS	mandatory
        INDEX   { lFibreConfLinkNo }
	::= { lFibreConfTable 1 }

LFibreConfEntry ::=
	SEQUENCE {
		lFibreConfLinkNo
			INTEGER,
		lFibreConfLinkEnab
			INTEGER,
		lFibreConfCLine
			INTEGER,
		lFibreConfLoopback
			INTEGER
}


lFibreConfLinkNo	OBJECT-TYPE
	SYNTAX INTEGER (0..1)
	ACCESS read-only
	STATUS mandatory
	DESCRIPTION
	"The link number for this configuration."
	::= { lFibreConfEntry 1 }

lFibreConfLinkEnab	OBJECT-TYPE
	SYNTAX INTEGER {
		yes(1),
		no(2)
	}
	ACCESS read-write
	STATUS mandatory
	DESCRIPTION
	"Set to yes(1) to enable the link."
	::= { lFibreConfEntry 2 }

lFibreConfCLine	OBJECT-TYPE
	SYNTAX INTEGER {
		processed(1),
		ignored(2)
	}
	ACCESS read-write
	STATUS mandatory
	DESCRIPTION
	"Set to ignored(2) to stop control line processing for this link."
	::= { lFibreConfEntry 3 }

lFibreConfLoopback	OBJECT-TYPE
	SYNTAX INTEGER {
		no(2),
		yes(1)
	}
	ACCESS read-write
	STATUS mandatory
	DESCRIPTION
	"Set to yes(1) to enable loopback mode for this link."
	::= { lFibreConfEntry 4 }

--___________________________________________________________________________
-- The LF link status table

lFibreStatTable OBJECT-TYPE
	SYNTAX SEQUENCE OF LFibreStatEntry
	ACCESS not-accessible
	STATUS mandatory
	DESCRIPTION
	"This table contains status information for the LFDOC"
	::= { dv2LocalFibre 2 }

lFibreStatEntry OBJECT-TYPE
	SYNTAX	LFibreStatEntry
	ACCESS	not-accessible
	STATUS	mandatory
        INDEX   { lFibreStatLinkNo }
	::= { lFibreStatTable 1 }

LFibreStatEntry ::=
	SEQUENCE {
		lFibreStatLinkNo
			INTEGER,
		lFibreStatCLines
			INTEGER,
		lFibreStatHCSErrs
			Counter
}

lFibreStatLinkNo	OBJECT-TYPE
	SYNTAX INTEGER (0..1)
	ACCESS read-only
	STATUS mandatory
	DESCRIPTION
	"The link number for this status."
	::= { lFibreStatEntry 1 }

lFibreStatCLines	OBJECT-TYPE
	SYNTAX INTEGER {
		up(1),
		down(2)
	}
	ACCESS read-only
	STATUS mandatory
	DESCRIPTION
	"The state of control lines for this link."
	::= { lFibreStatEntry 2 }

lFibreStatHCSErrs	OBJECT-TYPE
	SYNTAX Counter
	ACCESS read-only
	STATUS mandatory
	DESCRIPTION
	"The header checksum error count for this link."
	::= { lFibreStatEntry 3 }

--___________________________________________________________________________
-- The DS Group

-- DS1 DLIM

ds1Table	OBJECT-TYPE
	SYNTAX	SEQUENCE OF Ds1Entry
	ACCESS	not-accessible
	STATUS	mandatory
	DESCRIPTION
	"ds1 Status Table"
	::= { dv2DS 1 }

ds1Entry	OBJECT-TYPE
	SYNTAX	Ds1Entry
	ACCESS	not-accessible
	STATUS	mandatory
	INDEX	{ ds1LinkNo }
	::= { ds1Table 1 }

Ds1Entry ::=
	SEQUENCE {
		ds1LinkNo
			INTEGER,
		ds1LineLength
			INTEGER,
		ds1Framing
			INTEGER,
		ds1Coding
			INTEGER,
		ds1Tr
			INTEGER,
		ds1Rt
			INTEGER,
		ds1LOSDefect
			INTEGER,
		ds1AISDefect
			INTEGER,
		ds1OOFDefect
			INTEGER,
		ds1YellowDefect
			INTEGER,
		ds1LOSAlarm
			INTEGER,
		ds1AISAlarm
			INTEGER,
		ds1LOFAlarm
			INTEGER,
		ds1YellowAlarm
			INTEGER,
		ds1PdvCount
			Counter,
		ds1Z16Count
			Counter,
		ds1LcvCount
			Counter,
		ds1BeeCount
			Counter,
		ds1FerCount
			Counter,
		ds1OofCount
			Counter,
		ds1ClrStats
			INTEGER,
		ds1Reconfig
			INTEGER,
		ds1LineES
			Counter,
		ds1LineSES
			Counter,
		ds1ES
			Counter,
		ds1SES
			Counter,
		ds1AISS
			Counter,
		ds1UAS
			Counter,
		ds1TxClkSel
			INTEGER,
		ds1ExBERDefect
			INTEGER,
		ds1ExBERAlarm
			INTEGER

}

ds1LinkNo  OBJECT-TYPE
	SYNTAX	INTEGER (0..3)
	ACCESS	read-only
	STATUS	mandatory
	DESCRIPTION
	"Link number - this is the instance."
	::= { ds1Entry 1 }


ds1LineLength	OBJECT-TYPE
	SYNTAX	INTEGER
	{
		feet-0-110(1),
		feet-110-220(2),
		feet-220-330(3),
		feet-330-440(4),
		feet-440-550(5),
		feet-550-660(6),
		more-than-655-feet(7),
		square(8)
	}
	ACCESS	read-write
	STATUS	mandatory
	DESCRIPTION
	"Length of the line connected to the physical interface."
	::= { ds1Entry 2 }

ds1Framing	OBJECT-TYPE
	SYNTAX	INTEGER
	{
		none(1),
		sf(2),
		t1dm(3),
		slc96(4),
		esf4k(5),
		esf2k-3(6),
		esf2k-1(7)
	}
	ACCESS	read-write
	STATUS	mandatory
	DESCRIPTION
	"T1 Framing type."
	::= { ds1Entry 3 }


ds1Coding	OBJECT-TYPE
	SYNTAX	INTEGER
	{
		b8zs(1),
		ami(2)
	}
	ACCESS	read-write
	STATUS	mandatory
	DESCRIPTION
	"The line code of incoming DS1 signal. ami(2) selects AMI line code."
	::= { ds1Entry 4 }

ds1Tr	OBJECT-TYPE
	SYNTAX	INTEGER
	{
		no(2),
		yes(1)
	}
	ACCESS	read-write
	STATUS	mandatory
	DESCRIPTION
	"Set to yes(1) to enable transmit loop-back."
	::= { ds1Entry 5 }

ds1Rt	OBJECT-TYPE
	SYNTAX	INTEGER
	{
		no(2),
		yes(1)
	}
	ACCESS	read-write
	STATUS	mandatory
	DESCRIPTION
	"Set to yes(1) to enable receive loop-back."
	::= { ds1Entry 6 }

ds1LOSDefect	OBJECT-TYPE
	SYNTAX	INTEGER
	{
		yes(1),
		no(2)
	}
	ACCESS	read-only
	STATUS	mandatory
	DESCRIPTION
	"Loss of Signal Defect"
	::= { ds1Entry 7 }

ds1AISDefect	OBJECT-TYPE
	SYNTAX	INTEGER
	{
		yes(1),
		no(2)
	}
	ACCESS	read-only
	STATUS	mandatory
	DESCRIPTION
	"AIS Defect"
	::= { ds1Entry 8 }

ds1OOFDefect	OBJECT-TYPE
	SYNTAX	INTEGER
	{
		yes(1),
		no(2)
	}
	ACCESS	read-only
	STATUS	mandatory
	DESCRIPTION
	"OOF Defect"
	::= { ds1Entry 9 }

ds1YellowDefect	OBJECT-TYPE
	SYNTAX	INTEGER
	{
		yes(1),
		no(2)
	}
	ACCESS	read-only
	STATUS	mandatory
	DESCRIPTION
	"Yellow Defect"
	::= { ds1Entry 10 }

ds1LOSAlarm	OBJECT-TYPE
	SYNTAX	INTEGER
	{
		yes(1),
		no(2)
	}
	ACCESS	read-only
	STATUS	mandatory
	DESCRIPTION
	"Loss Of Signal alarm"
	::= { ds1Entry 11 }

ds1AISAlarm	OBJECT-TYPE
	SYNTAX	INTEGER
	{
		yes(1),
		no(2)
	}
	ACCESS	read-only
	STATUS	mandatory
	DESCRIPTION
	"AIS alarm"
	::= { ds1Entry 12 }

ds1LOFAlarm	OBJECT-TYPE
	SYNTAX	INTEGER
	{
		yes(1),
		no(2)
	}
	ACCESS	read-only
	STATUS	mandatory
	DESCRIPTION
	"Loss Of Frame alarm"
	::= { ds1Entry 13 }


ds1YellowAlarm	OBJECT-TYPE
	SYNTAX	INTEGER
	{
		yes(1),
		no(2)
	}
	ACCESS	read-only
	STATUS	mandatory
	DESCRIPTION
	"Yellow alarm"
	::= { ds1Entry 14 }

ds1PdvCount	OBJECT-TYPE
	SYNTAX	Counter
	ACCESS	read-only
	STATUS	mandatory
	DESCRIPTION
	"Number of pulse density violations detected."
	::= { ds1Entry 15 }

ds1Z16Count	OBJECT-TYPE
	SYNTAX	Counter
	ACCESS	read-only
	STATUS	mandatory
	DESCRIPTION
	"Number of 16 consecutive zeroes detected."
	::= { ds1Entry 16 }

ds1LcvCount	OBJECT-TYPE
	SYNTAX	Counter
	ACCESS	read-only
	STATUS	mandatory
	DESCRIPTION
	"Number of line code violations detected."
	::= { ds1Entry 17 }

ds1BeeCount	OBJECT-TYPE
	SYNTAX	Counter
	ACCESS	read-only
	STATUS	mandatory
	DESCRIPTION
	"Number of block error events detected."
	::= { ds1Entry 18 }

ds1FerCount	OBJECT-TYPE
	SYNTAX	Counter
	ACCESS	read-only
	STATUS	mandatory
	DESCRIPTION
	"Number of framing bit error events detected."
	::= { ds1Entry 19 }

ds1OofCount	OBJECT-TYPE
	SYNTAX	Counter
	ACCESS	read-only
	STATUS	mandatory
	DESCRIPTION
	"Number of out of frame events detected."
	::= { ds1Entry 20 }

ds1ClrStats  OBJECT-TYPE
	SYNTAX	INTEGER
	{
		no(2),
		yes(1)
	}
	ACCESS	read-write
	STATUS	mandatory
	DESCRIPTION
	"Clear counters"
	DEFVAL { no }
	::= { ds1Entry 21 }

ds1Reconfig  OBJECT-TYPE
	SYNTAX	INTEGER
	{
		no(2),
		yes(1)
	}
	ACCESS	read-write
	STATUS	mandatory
	DESCRIPTION
	"Reconfigure Link"
	DEFVAL { no }
	::= { ds1Entry 22 }

ds1LineES OBJECT-TYPE
        SYNTAX Counter
        ACCESS read-only
        STATUS mandatory
        DESCRIPTION
        "Line Errored Seconds"
        ::= { ds1Entry 23 }

ds1LineSES OBJECT-TYPE
        SYNTAX Counter
        ACCESS read-only
        STATUS mandatory
        DESCRIPTION
        "Line Severely Errored Seconds"
        ::= { ds1Entry 24 }

ds1ES OBJECT-TYPE
        SYNTAX Counter
        ACCESS read-only
        STATUS mandatory
        DESCRIPTION
        "Errored Seconds"
        ::= { ds1Entry 25 }

ds1SES OBJECT-TYPE
        SYNTAX Counter
        ACCESS read-only
        STATUS mandatory
        DESCRIPTION
        "Severely Errored Seconds"
        ::= { ds1Entry 26 }

ds1AISS OBJECT-TYPE
        SYNTAX Counter
        ACCESS read-only
        STATUS mandatory
        DESCRIPTION
        "AIS Seconds"
        ::= { ds1Entry 27 }

ds1UAS OBJECT-TYPE
        SYNTAX Counter
        ACCESS read-only
        STATUS mandatory
        DESCRIPTION
        "Unavailable Seconds"
        ::= { ds1Entry 28 }

ds1TxClkSel	OBJECT-TYPE
	SYNTAX	INTEGER
	{
		local-oscillator(12),
		local-link(13)
	}
	ACCESS	read-write
	STATUS	mandatory
	DESCRIPTION
	"Transmit clock select."
	::= { ds1Entry 29 }

ds1ExBERDefect	OBJECT-TYPE
	SYNTAX	INTEGER
	{
		yes(1),
		no(2)
	}
	ACCESS	read-only
	STATUS	mandatory
	DESCRIPTION
	"Excessive Bit Error Rate Defect"
	::= { ds1Entry 30 }

ds1ExBERAlarm	OBJECT-TYPE
	SYNTAX	INTEGER
	{
		yes(1),
		no(2)
	}
	ACCESS	read-only
	STATUS	mandatory
	DESCRIPTION
	"Excessive Bit Error Rate Alarm"
	::= { ds1Entry 31 }

-- DS3 DLIM

ds3Table	OBJECT-TYPE
	SYNTAX	SEQUENCE OF Ds3Entry
	ACCESS	not-accessible
	STATUS	mandatory
	DESCRIPTION
	"ds3 Status Table"
	::= { dv2DS 2 }

ds3Entry	OBJECT-TYPE
	SYNTAX	Ds3Entry
	ACCESS	not-accessible
	STATUS	mandatory
	INDEX	{ ds3LinkNo }
	::= { ds3Table 1 }

Ds3Entry ::=
	SEQUENCE {
		ds3LinkNo
			INTEGER,
		ds3Lb
			INTEGER,
		ds3Err
			INTEGER,
		ds3RXLos
			INTEGER,
		ds3TXLoc
			INTEGER,
		ds3RXErr
			INTEGER,
		ds3RXAis
			INTEGER,
		ds3TXAis
			INTEGER,
		ds3TXLev
			INTEGER,
		ds3Tr
			INTEGER,
		ds3Rt
			INTEGER,
		ds3Equal
			INTEGER,
		ds3LOSAlarm
			INTEGER,
		ds3Reconfig
			INTEGER
}

ds3LinkNo  OBJECT-TYPE
	SYNTAX	INTEGER (0..3)
	ACCESS	read-only
	STATUS	mandatory
	DESCRIPTION
	"Link number - this is the instance."
	::= { ds3Entry 1 }

ds3Lb	OBJECT-TYPE
	SYNTAX	INTEGER
	{
		yes(1),
		no(2)
	}
	ACCESS	read-only
	STATUS	mandatory
	DESCRIPTION
	"Loop-back mode active."
	::= { ds3Entry 2 }

ds3Err	OBJECT-TYPE
	SYNTAX	INTEGER
	{
		yes(1),
		no(2)
	}
	ACCESS	read-only
	STATUS	mandatory
	DESCRIPTION
	"AIS or BPV detected."
	::= { ds3Entry 3 }

ds3RXLos	OBJECT-TYPE
	SYNTAX	INTEGER
	{
		yes(1),
		no(2)
	}
	ACCESS	read-only
	STATUS	mandatory
	DESCRIPTION
	"Receive loss of signal."
	::= { ds3Entry 4 }

ds3TXLoc	OBJECT-TYPE
	SYNTAX	INTEGER
	{
		yes(1),
		no(2)
	}
	ACCESS	read-only
	STATUS	mandatory
	DESCRIPTION
	"Transmit loss of clock."
	::= { ds3Entry 5 }

ds3RXErr	OBJECT-TYPE
	SYNTAX	INTEGER
	{
		yes(1),
		no(2)
	}
	ACCESS	read-only
	STATUS	mandatory
	DESCRIPTION
	"Receive error detected."
	::= { ds3Entry 6 }

ds3RXAis	OBJECT-TYPE
	SYNTAX	INTEGER
	{
		no(2),
		yes(1)
	}
	ACCESS	read-write
	STATUS	mandatory
	DESCRIPTION
	"Set to yes(1) to generate a receive AIS alarm."
	::= { ds3Entry 7 }


ds3TXAis	OBJECT-TYPE
	SYNTAX	INTEGER
	{
		no(2),
		yes(1)
	}
	ACCESS	read-write
	STATUS	mandatory
	DESCRIPTION
	"Set to yes(1) to transmit an AIS alarm."
	::= { ds3Entry 8 }

ds3TXLev	OBJECT-TYPE
	SYNTAX	INTEGER
	{
		normal(1),
		high(2)
	}
	ACCESS	read-write
	STATUS	mandatory
	DESCRIPTION
	"Transmit level."
	::= { ds3Entry 9 }


ds3Tr	OBJECT-TYPE
	SYNTAX	INTEGER
	{
		no(2),
		yes(1)
	}
	ACCESS	read-write
	STATUS	mandatory
	DESCRIPTION
	"Transmit loop-back."
	::= { ds3Entry 10 }

ds3Rt	OBJECT-TYPE
	SYNTAX	INTEGER
	{
		no(2),
		yes(1)
	}
	ACCESS	read-write
	STATUS	mandatory
	DESCRIPTION
	"Set to yes(1) to enable receive loop-back."
	::= { ds3Entry 11 }

ds3Equal	OBJECT-TYPE
	SYNTAX	INTEGER
	{
		short(1),
		long(2)
	}
	ACCESS	read-write
	STATUS	mandatory
	DESCRIPTION
	"Equalisation type."
	::= { ds3Entry 12 }

ds3LOSAlarm	OBJECT-TYPE
	SYNTAX	INTEGER
	{
		no(2),
		yes(1)
	}
	ACCESS	read-only
	STATUS	mandatory
	DESCRIPTION
	"Loss Of Signal Integrated Alarm"
	::= { ds3Entry 13 }

ds3Reconfig  OBJECT-TYPE
	SYNTAX	INTEGER
	{
		no(2),
		yes(1)
	}
	ACCESS	read-write
	STATUS	mandatory
	DESCRIPTION
	"Reconfigure Link"
	DEFVAL { no }
	::= { ds3Entry 14 }





-- E1-2C DLIM

e1Table	OBJECT-TYPE
	SYNTAX	SEQUENCE OF E1Entry
	ACCESS	not-accessible
	STATUS	mandatory
	DESCRIPTION
	"E1-2C Config/Status Table"
	::= { dv2DS 5 }

e1Entry	OBJECT-TYPE
	SYNTAX	E1Entry
	ACCESS	not-accessible
	STATUS	mandatory
	INDEX	{ e1LinkNo }
	::= { e1Table 1 }

E1Entry ::=
	SEQUENCE {
		e1LinkNo
			INTEGER,
		e1LimType
			INTEGER,
-- configurables
		e1Lb
			INTEGER,
		e1FRMRMode
			INTEGER,
		e1TxClkSel
			INTEGER,
		e1TS16PayLd
			INTEGER,
		e1TxAIS
			INTEGER,
		e1GappedClk
			INTEGER,
		e1IntrfType
			INTEGER,
		e1ClrStats
			INTEGER,
		e1Reconfig
			INTEGER,
		se1SA4
			INTEGER,
		se1SA5
			INTEGER,
		se1SA6
			INTEGER,
		se1SA7
			INTEGER,
		se1SA8
			INTEGER,
		se1SI0
			INTEGER,
		se1SI1
			INTEGER,
-- Defects
		e1LOSDefect
			INTEGER,
		e1OOFDefect
			INTEGER,
		e1AISDefect
			INTEGER,
		e1FerfDefect
			INTEGER,
		e1ExBERDefect
			INTEGER,
-- Alarms
		e1LOSAlarm
			INTEGER,
		e1LOFAlarm
			INTEGER,
		e1AISAlarm
			INTEGER,
		e1FerfAlarm
			INTEGER,
		e1ExBERAlarm
			INTEGER,
-- Error Counts
		e1SCRCErrs
			INTEGER,
		e1SFrameErrs
			INTEGER,
		e1SFEBEErrs
			INTEGER,
		e1SLcvs
			INTEGER,
-- Performance Parameters
		e1LineES
			Counter,
		e1LineSES
			Counter,
		e1ES
			Counter,
		e1SES
			Counter,
		e1AISS
			Counter,
		e1UAS
			Counter
}


e1LinkNo  OBJECT-TYPE
	SYNTAX	INTEGER (0..3)
	ACCESS	read-only
	STATUS	mandatory
	DESCRIPTION
	"Link number - this is the instance."
	::= { e1Entry 1 }


e1LimType OBJECT-TYPE
	SYNTAX	INTEGER
	{
		dual(1),
		quad(2),
		dual-sig(3),
		quad-sig(4)
	}
	ACCESS	read-only
	STATUS	mandatory
	DESCRIPTION
	"LIM I.D. type"
	::= { e1Entry 2 }

e1Lb	OBJECT-TYPE
	SYNTAX	INTEGER
	{
	  none(1),
	  line(2),
	  payload(3),
	  digital(4)
	}
	ACCESS	read-write
	STATUS	mandatory
	DESCRIPTION
	"Loopback Selection"
	::= { e1Entry 3 }

e1FRMRMode	OBJECT-TYPE
	SYNTAX	INTEGER
	{
		crc-mfrm(1),
		basic(2),
		unframed(3)
	}
	ACCESS	read-write
	STATUS	mandatory
	DESCRIPTION
	"e1 Framing options."
	::= { e1Entry 4 }


e1TxClkSel	OBJECT-TYPE
	SYNTAX	INTEGER
	{
		system(11),
		loc-oscil(12),
		loc-link0(13),
		loc-link1(14),
		loc-link2(15),
		loc-link3(16)
	}
	ACCESS	read-write
	STATUS	mandatory
	DESCRIPTION
	"Transmit clock select."
	::= { e1Entry 5 }

e1TS16PayLd	OBJECT-TYPE
	SYNTAX	INTEGER
	{
		no(2),
		yes(1)
	}
	ACCESS	read-write
	STATUS	mandatory
	DESCRIPTION
	"Employ TimeSlot 16 for customer data."
	::= { e1Entry 6 }

e1TxAIS		OBJECT-TYPE
	SYNTAX	INTEGER
	{
		no(2),
		yes(1)
	}
	ACCESS	read-write
	STATUS	mandatory
	DESCRIPTION
	"Transmit the AIS State."
	::= { e1Entry 7 }

e1GappedClk	OBJECT-TYPE
	SYNTAX	INTEGER
	{
		no(2),
		yes(1)
	}
	ACCESS	read-write
	STATUS	mandatory
	DESCRIPTION
	"Select 1,(yes) for Circuit-emulation."
	::= { e1Entry 8 }

e1IntrfType	OBJECT-TYPE
	SYNTAX	INTEGER
	{
		balanc-120(1),
		unbalan-75(2)
	}
	ACCESS	read-write
	STATUS	mandatory
	DESCRIPTION
	"E1 Framing options."
	::= { e1Entry 9 }

e1ClrStats	OBJECT-TYPE
	SYNTAX	INTEGER
	{
		yes(1),
		no(2)
	}
	ACCESS	read-write
	STATUS	mandatory
	DESCRIPTION
	"Clear Counters"
	::= { e1Entry 10 }

e1Reconfig OBJECT-TYPE
	SYNTAX	INTEGER
	{
		no(2),
		yes(1)
	}
	ACCESS	read-write
	STATUS	mandatory
	DESCRIPTION
	"Reconfigure Link"
	DEFVAL { no }
	::= { e1Entry 11 }

se1SA4 OBJECT-TYPE
	SYNTAX	INTEGER
	{
		off(2),
		on(1)
	}
	ACCESS	read-write
	STATUS	mandatory
	DESCRIPTION
	"Nat'l bit Sa4"
	DEFVAL { on }
	::= { e1Entry 12 }

se1SA5 OBJECT-TYPE
	SYNTAX	INTEGER
	{
		off(2),
		on(1)
	}
	ACCESS	read-write
	STATUS	mandatory
	DESCRIPTION
	"Nat'l bit Sa5"
	DEFVAL { on }
	::= { e1Entry 13 }

se1SA6 OBJECT-TYPE
	SYNTAX	INTEGER
	{
		off(2),
		on(1)
	}
	ACCESS	read-write
	STATUS	mandatory
	DESCRIPTION
	"Nat'l bit Sa6"
	DEFVAL { on }
	::= { e1Entry 14 }

se1SA7 OBJECT-TYPE
	SYNTAX	INTEGER
	{
		off(2),
		on(1)
	}
	ACCESS	read-write
	STATUS	mandatory
	DESCRIPTION
	"Nat'l bit Sa7"
	DEFVAL { on }
	::= { e1Entry 15 }

se1SA8 OBJECT-TYPE
	SYNTAX	INTEGER
	{
	        off(2),
		on(1)
	}
	ACCESS	read-write
	STATUS	mandatory
	DESCRIPTION
	"Nat'l bit Sa8"
	DEFVAL { on }
	::= { e1Entry 16 }

se1SI0 OBJECT-TYPE
	SYNTAX	INTEGER
	{
		off(2),
		on(1)
	}
	ACCESS	read-write
	STATUS	mandatory
	DESCRIPTION
	"Int'l bit Si0"
	DEFVAL { on }
	::= { e1Entry 17 }

se1SI1 OBJECT-TYPE
	SYNTAX	INTEGER
	{
		off(2),
		on(1)
	}
	ACCESS	read-write
	STATUS	mandatory
	DESCRIPTION
	"Nat'l bit Si1"
	DEFVAL { on }
	::= { e1Entry 18 }

e1LOSDefect	OBJECT-TYPE
	SYNTAX INTEGER {
		no(2),
		yes(1)
	}
	ACCESS read-only
	STATUS mandatory
	DESCRIPTION
	"Loss Of Signal Defect"
	::= { e1Entry 22 }


e1OOFDefect	OBJECT-TYPE
	SYNTAX INTEGER {
		no(2),
		yes(1)
	}
	ACCESS read-only
	STATUS mandatory
	DESCRIPTION
	"Receive Out Of Frame"
	::= { e1Entry 23 }

e1AISDefect	OBJECT-TYPE
	SYNTAX INTEGER {
		no(2),
		yes(1)
	}
	ACCESS read-only
	STATUS mandatory
	DESCRIPTION
	"Receive AIS Defect"
	::= { e1Entry 24 }

e1FerfDefect	OBJECT-TYPE
	SYNTAX INTEGER {
		no(2),
		yes(1)
	}
	ACCESS read-only
	STATUS mandatory
	DESCRIPTION
	"Receive Yellow Defect"
	::= { e1Entry 25 }

e1ExBERDefect	OBJECT-TYPE
	SYNTAX	INTEGER
	{
		yes(1),
		no(2)
	}
	ACCESS	read-only
	STATUS	mandatory
	DESCRIPTION
	"Excessive Bit Error Rate Defect"
	::= { e1Entry 26 }

e1LOSAlarm	OBJECT-TYPE
	SYNTAX INTEGER {
		no(2),
		yes(1)
	}
	ACCESS read-only
	STATUS mandatory
	DESCRIPTION
	"Loss Of Signal Integrated Alarm"
	::= { e1Entry 37 }

e1LOFAlarm	OBJECT-TYPE
	SYNTAX INTEGER {
		no(2),
		yes(1)
	}
	ACCESS read-only
	STATUS mandatory
	DESCRIPTION
	"Loss Of Frame Integrated Alarm"
	::= { e1Entry 38 }

e1AISAlarm	OBJECT-TYPE
	SYNTAX INTEGER {
		no(2),
		yes(1)
	}
	ACCESS read-only
	STATUS mandatory
	DESCRIPTION
	"AIS Integrated Alarm"
	::= { e1Entry 39 }

e1FerfAlarm	OBJECT-TYPE
	SYNTAX INTEGER {
		no(2),
		yes(1)
	}
	ACCESS read-only
	STATUS mandatory
	DESCRIPTION
	"Yellow Integrated Alarm"
	::= { e1Entry 40 }

e1ExBERAlarm	OBJECT-TYPE
	SYNTAX	INTEGER
	{
		yes(1),
		no(2)
	}
	ACCESS	read-only
	STATUS	mandatory
	DESCRIPTION
	"Excessive Bit Error Rate Alarm"
	::= { e1Entry 41 }

e1SCRCErrs	OBJECT-TYPE
	SYNTAX INTEGER
	ACCESS read-only
	STATUS mandatory
	DESCRIPTION
	"The CRC-4 error count for this link."
	::= { e1Entry 52 }

e1SFrameErrs OBJECT-TYPE
	SYNTAX INTEGER
	ACCESS read-only
	STATUS mandatory
	DESCRIPTION
	"The frame error count for this link."
	::= { e1Entry 53 }

e1SFEBEErrs	OBJECT-TYPE
	SYNTAX INTEGER
	ACCESS read-only
	STATUS mandatory
	DESCRIPTION
	"The FEBE error count for this link."
	::= { e1Entry 54 }

e1SLcvs	OBJECT-TYPE
	SYNTAX INTEGER
	ACCESS read-only
	STATUS mandatory
	DESCRIPTION
	"The E1 LCV count for this link."
	::= { e1Entry 55 }

e1LineES OBJECT-TYPE
	SYNTAX Counter
	ACCESS read-only
	STATUS mandatory
	DESCRIPTION
	"Line Errored Seconds"
	::= { e1Entry 66 }

e1LineSES OBJECT-TYPE
	SYNTAX Counter
	ACCESS read-only
	STATUS mandatory
	DESCRIPTION
	"Line Severely Errored Seconds"
	::= { e1Entry 67 }

e1ES OBJECT-TYPE
	SYNTAX Counter
	ACCESS read-only
	STATUS mandatory
	DESCRIPTION
	"Errored Seconds"
	::= { e1Entry 68 }

e1SES OBJECT-TYPE
	SYNTAX Counter
	ACCESS read-only
	STATUS mandatory
	DESCRIPTION
	"Severely Errored Seconds"
	::= { e1Entry 69 }

e1AISS OBJECT-TYPE
	SYNTAX Counter
	ACCESS read-only
	STATUS mandatory
	DESCRIPTION
	"AIS Seconds"
	::= { e1Entry 70 }

e1UAS OBJECT-TYPE
	SYNTAX Counter
	ACCESS read-only
	STATUS mandatory
	DESCRIPTION
	"Unavailable Seconds"
	::= { e1Entry 71 }







--  SONET DLIM

soTable	OBJECT-TYPE
	SYNTAX	SEQUENCE OF SoEntry
	ACCESS	not-accessible
	STATUS	mandatory
	DESCRIPTION
	"SOLIM/DELIM Status Table"
	::= { dv2DS 7 }

soEntry	OBJECT-TYPE
	SYNTAX	SoEntry
	ACCESS	not-accessible
	STATUS	mandatory
	INDEX	{ soLinkNo }
	::= { soTable 1 }

SoEntry ::=
	SEQUENCE
	{
		soLinkNo
			INTEGER,
		soLimType
			INTEGER,
		soTimingRef
			INTEGER,
		soTxEn0
			INTEGER,
		soTxEn1
			INTEGER,
		soLimDesc
			INTEGER,
		soReconfig
			INTEGER
	}


soLinkNo  OBJECT-TYPE
	SYNTAX	INTEGER (0..1)
	ACCESS	read-only
	STATUS	mandatory
	DESCRIPTION
	"Link number - this is the instance."
	::= { soEntry 1 }

soLimType   OBJECT-TYPE
	SYNTAX	INTEGER
	{
		solim-v0(1),
		solim-v1(2),
		solim-v2(3)
	}
	ACCESS	read-only
	STATUS	mandatory
	DESCRIPTION
	"Solim version"
	::= { soEntry 2 }

soTimingRef	OBJECT-TYPE
	SYNTAX INTEGER {
		system(11),
		local-oscillator(12),
		local-link0(13),
		local-link1(14)
	}
	ACCESS read-write
	STATUS mandatory
	DESCRIPTION
	"Local timing reference"
	::= { soEntry 3 }

soTxEn0	OBJECT-TYPE
	SYNTAX INTEGER {
		yes(1),
		no(2)
	}
	ACCESS read-write
	STATUS mandatory
	DESCRIPTION
	"Link 0 Tx Enable (v2 and above)"
	DEFVAL { yes }
	::= { soEntry 4 }

soTxEn1	OBJECT-TYPE
	SYNTAX INTEGER {
		yes(1),
		no(2)
	}
	ACCESS read-write
	STATUS mandatory
	DESCRIPTION
	"Link 1 Tx Enable (v2 and above)"
	DEFVAL { yes }
	::= { soEntry 5 }


soLimDesc OBJECT-TYPE
	SYNTAX INTEGER
	{
		pre-system-timing(1),
		dual-intermediate-reach(2),
		single-intermediate-reach(3),
		dual-short-reach(4),
		single-short-reach(5),
		dual-long-reach(6),
		single-long-reach(7),
		dual-hybrid-intermediate(8),
		dual-hybrid-long(9),
		dual-electrical(10)
	}
	ACCESS read-write
	STATUS mandatory
	DESCRIPTION
	"LIM Description"
	DEFVAL { dual-intermediate-reach }
	::= { soEntry 6 }

soReconfig OBJECT-TYPE
	SYNTAX	INTEGER
	{
		no(2),
		yes(1)
	}
	ACCESS	read-write
	STATUS	mandatory
	DESCRIPTION
	"Reconfigure Link"
	DEFVAL { no }
	::= { soEntry 7 }


-- DS1-xC DLIM

ds1V2Table      OBJECT-TYPE
        SYNTAX  SEQUENCE OF Ds1V2Entry
        ACCESS  not-accessible
        STATUS  mandatory
        DESCRIPTION
        "ds1 V2 Status Table"
        ::= { dv2DS 9 }

ds1V2Entry      OBJECT-TYPE
        SYNTAX  Ds1V2Entry
        ACCESS  not-accessible
        STATUS  mandatory
        INDEX   { ds1V2LinkNo }
        ::= { ds1V2Table 1 }

Ds1V2Entry ::=
        SEQUENCE {
                ds1V2LinkNo
                        INTEGER,
                ds1V2LimType
                        INTEGER,
-- configurables
                ds1V2TxLineLn
                        INTEGER,
                ds1V2FRMRMode
                        INTEGER,
                ds1V2Coding
                        INTEGER,
                ds1V2Lb
                        INTEGER,
                ds1V2TxAIS
                        INTEGER,
                ds1V2GappedClk
                        INTEGER,
                ds1V2TxClkSel
                        INTEGER,
		ds1V2ClrStats
			INTEGER,
		ds1V2Reconfig
			INTEGER,

-- Defects
		ds1V2LOSDefect
			INTEGER,
		ds1V2OOFDefect
			INTEGER,
		ds1V2AISDefect
			INTEGER,
		ds1V2FerfDefect
			INTEGER,
		ds1V2BERDefect
			INTEGER,
-- Alarms
		ds1V2LOSAlarm
			INTEGER,
		ds1V2LOFAlarm
			INTEGER,
		ds1V2AISAlarm
			INTEGER,
		ds1V2FerfAlarm
			INTEGER,
		ds1V2BERAlarm
			INTEGER,
-- Error Counts
		ds1V2FerCount
			INTEGER,
		ds1V2BeeCount
			INTEGER,
		ds1V2OCfCount
			INTEGER,
		ds1V2LcvCount
			INTEGER,

-- pkc added BER
-- Performance parameters
		ds1V2LineES
			Counter,
		ds1V2LineSES
			Counter,
		ds1V2ES
			Counter,
		ds1V2SES
			Counter,
		ds1V2AISS
			Counter,
		ds1V2UAS
			Counter,
		ds1V2ExBER
			Counter
}

ds1V2LinkNo  OBJECT-TYPE
        SYNTAX  INTEGER (0..3)
        ACCESS  read-only
        STATUS  mandatory
        DESCRIPTION
        "Link number - this is the instance."
        ::= { ds1V2Entry 1 }


ds1V2LimType OBJECT-TYPE
        SYNTAX  INTEGER
        {
		ds1-dual(1),
		ds1-quad(2),
 		ds1-dual-signaling(3),
		ds1-quad-signaling(4)
        }
        ACCESS  read-only
        STATUS  mandatory
        DESCRIPTION
        "LIM I.D. type"
        ::= { ds1V2Entry 2 }

ds1V2TxLineLn   OBJECT-TYPE
        SYNTAX  INTEGER
        {
                feet-0-110(1),
                feet-110-220(2),
                feet-220-330(3),
                feet-330-440(4),
                feet-440-550(5),
                feet-550-660(6),
                more-than-655-feet(7),
                square(8)
        }
        ACCESS  read-write
        STATUS  mandatory
        DESCRIPTION
        "Select txmt line length."
        ::= { ds1V2Entry 3 }


ds1V2FRMRMode   OBJECT-TYPE
        SYNTAX  INTEGER
        {
                none(1),
                sf(2),
                t1dm(3),
                slc96(4),
                esf4k(5),
                esf2K-3(6),
                esf2k-1(7)
        }
        ACCESS  read-write
        STATUS  mandatory
        DESCRIPTION
        "ds1V2 Framing options."
        ::= { ds1V2Entry 4 }

ds1V2Coding     OBJECT-TYPE
        SYNTAX  INTEGER
        {
               b8zs(2),
               ami(1)
        }
        ACCESS  read-write
        STATUS  mandatory
        DESCRIPTION
        "If Line Coding is yes(1), AMI is selected"
        ::= { ds1V2Entry 5 }

ds1V2Lb OBJECT-TYPE
        SYNTAX  INTEGER
        {
          none(1),
          line-lpbk(2),
          payload-lpbk(3),
          digital-lpbk(4)
        }
        ACCESS  read-write
        STATUS  mandatory
        DESCRIPTION
        "Loopback Selection"
        ::= { ds1V2Entry 6 }

ds1V2TxAIS              OBJECT-TYPE
        SYNTAX  INTEGER
        {
                no(2),
                yes(1)
        }
        ACCESS  read-write
        STATUS  mandatory
        DESCRIPTION
        "Transmit the AIS State."
        ::= { ds1V2Entry 7 }

ds1V2GappedClk  OBJECT-TYPE
        SYNTAX  INTEGER
        {
                yes(1),
                no(2)
        }
        ACCESS  read-write
        STATUS  mandatory
        DESCRIPTION
        "Select 1,(yes) for Circuit-emulation."
        ::= { ds1V2Entry 8 }


ds1V2TxClkSel	OBJECT-TYPE
	SYNTAX	INTEGER
	{
		system(11),
		local-oscillator(12),
		local-link0(13),
 		local-link1(14),
 		local-link2(15),
 		local-link3(16)
	}
	ACCESS	read-write
	STATUS	mandatory
	DESCRIPTION
	"Transmit clock select."
	::= { ds1V2Entry 9 }

ds1V2ClrStats        OBJECT-TYPE
        SYNTAX  INTEGER
        {
                yes(1),
                no(2)
        }
        ACCESS  read-write
        STATUS  mandatory
        DESCRIPTION
        "Clear Counters"
        ::= { ds1V2Entry 10 }

ds1V2Reconfig OBJECT-TYPE
	SYNTAX	INTEGER
	{
		no(2),
		yes(1)
	}
	ACCESS	read-write
	STATUS	mandatory
	DESCRIPTION
	"Reconfigure Link"
	DEFVAL { no }
        ::= { ds1V2Entry 11 }

ds1V2LOSDefect   OBJECT-TYPE
        SYNTAX INTEGER {
                no(2),
                yes(1)
        }
        ACCESS read-only
        STATUS mandatory
        DESCRIPTION
        "Loss Of Signal Defect"
        ::= { ds1V2Entry 22 }

ds1V2OOFDefect   OBJECT-TYPE
        SYNTAX INTEGER {
                no(2),
                yes(1)
        }
        ACCESS read-only
        STATUS mandatory
        DESCRIPTION
        "Receive Out Of Frame"
        ::= { ds1V2Entry 23 }

ds1V2AISDefect   OBJECT-TYPE
        SYNTAX INTEGER {
                no(2),
                yes(1)
        }
        ACCESS read-only
        STATUS mandatory
        DESCRIPTION
        "Receive AIS Defect"
        ::= { ds1V2Entry 24 }

ds1V2FerfDefect       OBJECT-TYPE
        SYNTAX INTEGER {
                no(2),
                yes(1)
        }
        ACCESS read-only
        STATUS mandatory
        DESCRIPTION
        "Receive FERF(Yellow) Defect"
        ::= { ds1V2Entry 25 }

ds1V2BERDefect       OBJECT-TYPE
        SYNTAX INTEGER {
                no(2),
                yes(1)
        }
        ACCESS read-only
        STATUS mandatory
        DESCRIPTION
        "Excessive Bit Error Rate Defect"
        ::= { ds1V2Entry 26 }

ds1V2LOSAlarm       OBJECT-TYPE
        SYNTAX INTEGER {
                no(2),
                yes(1)
        }
        ACCESS read-only
        STATUS mandatory
        DESCRIPTION
        "Loss Of Signal Integrated Alarm"
        ::= { ds1V2Entry 37 }

ds1V2LOFAlarm   OBJECT-TYPE
        SYNTAX INTEGER {
                no(2),
                yes(1)
        }
        ACCESS read-only
        STATUS mandatory
        DESCRIPTION
        "Loss Of Frame Integrated Alarm"
        ::= { ds1V2Entry 38 }

ds1V2AISAlarm   OBJECT-TYPE
        SYNTAX INTEGER {
                no(2),
                yes(1)
        }
        ACCESS read-only
        STATUS mandatory
        DESCRIPTION
        "AIS Integrated Alarm"
        ::= { ds1V2Entry 39 }

ds1V2FerfAlarm   OBJECT-TYPE
        SYNTAX INTEGER {
                no(2),
                yes(1)
        }
        ACCESS read-only
        STATUS mandatory
        DESCRIPTION
        "Yellow Integrated Alarm"
        ::= { ds1V2Entry 40 }

ds1V2BERAlarm       OBJECT-TYPE
        SYNTAX INTEGER {
                no(2),
                yes(1)
        }
        ACCESS read-only
        STATUS mandatory
        DESCRIPTION
        "Excessive Bit Error Rate Alarm"
        ::= { ds1V2Entry 41 }

ds1V2FerCount        OBJECT-TYPE
        SYNTAX INTEGER
        ACCESS read-only
        STATUS mandatory
        DESCRIPTION
        "The framing bit error count for this link."
        ::= { ds1V2Entry 52 }

ds1V2BeeCount OBJECT-TYPE
        SYNTAX INTEGER
        ACCESS read-only
        STATUS mandatory
        DESCRIPTION
        "The bit error count for this link."
        ::= { ds1V2Entry 53 }

ds1V2OCfCount        OBJECT-TYPE
        SYNTAX INTEGER
        ACCESS read-only
        STATUS mandatory
        DESCRIPTION
        "The Out-of-frame or Change of Frame alignment error count for this link."
        ::= { ds1V2Entry 54 }

ds1V2LcvCount        OBJECT-TYPE
        SYNTAX INTEGER
        ACCESS read-only
        STATUS mandatory
        DESCRIPTION
        "The DS1 Line code violations count for this link."
        ::= { ds1V2Entry 55 }


ds1V2LineES OBJECT-TYPE
        SYNTAX Counter
        ACCESS read-only
        STATUS mandatory
        DESCRIPTION
        "Line Errored Seconds"
        ::= { ds1V2Entry 66 }

ds1V2LineSES OBJECT-TYPE
        SYNTAX Counter
        ACCESS read-only
        STATUS mandatory
        DESCRIPTION
        "Line Severely Errored Seconds"
        ::= { ds1V2Entry 67 }

ds1V2ES OBJECT-TYPE
        SYNTAX Counter
        ACCESS read-only
        STATUS mandatory
        DESCRIPTION
        "Errored Seconds"
        ::= { ds1V2Entry 68 }

ds1V2SES OBJECT-TYPE
        SYNTAX Counter
        ACCESS read-only
        STATUS mandatory
        DESCRIPTION
        "Severely Errored Seconds"
        ::= { ds1V2Entry 69 }

ds1V2AISS OBJECT-TYPE
        SYNTAX Counter
        ACCESS read-only
        STATUS mandatory
        DESCRIPTION
        "AIS Seconds"
        ::= { ds1V2Entry 70 }

ds1V2UAS OBJECT-TYPE
        SYNTAX Counter
        ACCESS read-only
        STATUS mandatory
        DESCRIPTION
        "Unavailable Seconds"
        ::= { ds1V2Entry 71 }

-- pkc added for ds1_2c
ds1V2ExBER OBJECT-TYPE
        SYNTAX Counter
        ACCESS read-only
        STATUS mandatory
        DESCRIPTION
        "Excessive Bit Error Rate"
        ::= { ds1V2Entry 72 }

dlimLpbkTimeout OBJECT-TYPE
	SYNTAX	INTEGER (1..604800)
	ACCESS	read-write
	STATUS	mandatory
	DESCRIPTION
	"This parameter is used to set the dlim loopback timeout in minutes."
        ::= { dv2DS 10 }




-- DS3-2C DLIM
--ds3V2Table	OBJECT-TYPE
--	SYNTAX	SEQUENCE OF Ds3V2Entry
--	ACCESS	not-accessible
--	STATUS	mandatory
--	DESCRIPTION
--	"ds3-2C Config/Status Table"
--	::= { dv2DS 4 }

ds3V2Table	OBJECT-TYPE
	SYNTAX	SEQUENCE OF Ds3V2Entry
	ACCESS	not-accessible
	STATUS	mandatory
	DESCRIPTION
	"ds3-2C Config/Status Table"
	::= { dv2DS 11 }

ds3V2Entry	OBJECT-TYPE
	SYNTAX	Ds3V2Entry
	ACCESS	not-accessible
	STATUS	mandatory
	INDEX	{ ds3V2LinkNo }
	::= { ds3V2Table 1 }

Ds3V2Entry ::=
	SEQUENCE {
		ds3V2LinkNo
			INTEGER,
		ds3V2Lb
			INTEGER,
		ds3V2LimType
			INTEGER,
		ds3V2LimOK
			INTEGER,
		ds3V2TxLBO
			INTEGER,
		ds3V2TxClkSel
			INTEGER,
		ds3V2LOSDefect
			INTEGER,
		ds3V2LOSAlarm
			INTEGER,
		ds3V2Reconfig
			INTEGER
}


ds3V2LinkNo  OBJECT-TYPE
	SYNTAX	INTEGER (0..3)
	ACCESS	read-only
	STATUS	mandatory
	DESCRIPTION
	"Link number - this is the instance."
	::= { ds3V2Entry 1 }

ds3V2Lb		OBJECT-TYPE
	SYNTAX	INTEGER
	{
		none(2),
		line-lpbk(1),
		local-lpbk(3)
	}
	ACCESS	read-write
	STATUS	mandatory
	DESCRIPTION
	"Loopback Active"
	::= { ds3V2Entry 2 }


ds3V2LimType	OBJECT-TYPE
	SYNTAX	INTEGER
	{
		ds3-2c(1)
	}
	ACCESS	read-only
	STATUS	mandatory
	DESCRIPTION
	"LIM I.D. type"
	::= { ds3V2Entry 3 }

ds3V2LimOK	OBJECT-TYPE
	SYNTAX	INTEGER
	{
		yes(1),
		no(2)
	}
	ACCESS	read-only
	STATUS	mandatory
	DESCRIPTION
	"LIM OK."
	::= { ds3V2Entry 4 }

ds3V2TxLBO	OBJECT-TYPE
	SYNTAX	INTEGER
	{
		short(1),
		long(2)
	}
	ACCESS	read-write
	STATUS	mandatory
	DESCRIPTION
	"Transmit line build-out,(1)for short cables."
	::= { ds3V2Entry 5 }

ds3V2TxClkSel	OBJECT-TYPE
	SYNTAX	INTEGER
	{
		system(11),
		local-oscillator(12),
		link0-plcp(17),
		link1-plcp(18)
	}
	ACCESS	read-write
	STATUS	mandatory
	DESCRIPTION
	"Transmit clock select."
	::= { ds3V2Entry 6 }

ds3V2LOSDefect	OBJECT-TYPE
	SYNTAX	INTEGER
	{
		no(2),
		yes(1)
	}
	ACCESS	read-only
	STATUS	mandatory
	DESCRIPTION
	"Loss Of Signal Defect"
	::= { ds3V2Entry 8 }

ds3V2LOSAlarm	OBJECT-TYPE
	SYNTAX	INTEGER
	{
		no(2),
		yes(1)
	}
	ACCESS	read-only
	STATUS	mandatory
	DESCRIPTION
	"Loss Of Signal Alarm"
	::= { ds3V2Entry 9 }

ds3V2Reconfig OBJECT-TYPE
	SYNTAX	INTEGER
	{
		no(2),
		yes(1)
	}
	ACCESS	read-write
	STATUS	mandatory
	DESCRIPTION
	"Reconfigure Link"
	DEFVAL { no }
	::= { ds3V2Entry 10 }

--
-- E3-2C DLIM

--e3Table	OBJECT-TYPE
--	SYNTAX	SEQUENCE OF E3Entry
--	ACCESS	not-accessible
--	STATUS	mandatory
--	DESCRIPTION
--	"E3-2C Config/Status Table"
--	::= { dv2DS 6 }

e3Table	OBJECT-TYPE
	SYNTAX	SEQUENCE OF E3Entry
	ACCESS	not-accessible
	STATUS	mandatory
	DESCRIPTION
	"E3-2C Config/Status Table"
	::= { dv2DS 12 }

e3Entry	OBJECT-TYPE
	SYNTAX	E3Entry
	ACCESS	not-accessible
	STATUS	mandatory
	INDEX	{ e3LinkNo }
	::= { e3Table 1 }

E3Entry ::=
	SEQUENCE {
		e3LinkNo
			INTEGER,
		e3LimType
			INTEGER,
		e3LimOK
			INTEGER,
		e3EQSelect
			INTEGER,
		e3Loopback
			INTEGER,
		e3TxAIS
			INTEGER,
		e3TxClkSel
			INTEGER,
		e3LOSDefect
			INTEGER,
		e3LOSAlarm
			INTEGER,
		e3Reconfig
			INTEGER

}


e3LinkNo  OBJECT-TYPE
	SYNTAX	INTEGER (0..3)
	ACCESS	read-only
	STATUS	mandatory
	DESCRIPTION
	"Link number - this is the instance."
	::= { e3Entry 1 }

e3LimType	OBJECT-TYPE
	SYNTAX	INTEGER
	{
		e3-2c(1)
	}
	ACCESS	read-only
	STATUS	mandatory
	DESCRIPTION
	"LIM I.D. type"
	::= { e3Entry 2 }

e3LimOK	OBJECT-TYPE
	SYNTAX	INTEGER
	{
		no(2),
		yes(1)
	}
	ACCESS	read-only
	STATUS	mandatory
	DESCRIPTION
	"LIM OK."
	::= { e3Entry 3 }


e3EQSelect	OBJECT-TYPE
	SYNTAX	INTEGER
	{
		auto(1),
		set-0-to-3p5-dB(2),
		set-2p6-to-8-dB(3),
		set-6-to-9p9-dB(4),
		set-8p6-to-13p2-dB(5)
	}
	ACCESS	read-write
	STATUS	mandatory
	DESCRIPTION
	"Rx Line Equalization select."
	::= { e3Entry 4 }

e3Loopback	OBJECT-TYPE
	SYNTAX	INTEGER
	{
		none(3),
		line-lpbk(1),
		local-lpbk(2)
	}
	ACCESS	read-write
	STATUS	mandatory
	DESCRIPTION
	"Loopback LIU."
	::= { e3Entry 6 }

e3TxAIS	OBJECT-TYPE
	SYNTAX	INTEGER
	{
		no(2),
		yes(1)
	}	ACCESS	read-write
	STATUS	mandatory
	DESCRIPTION
	"Transmit AIS."
	::= { e3Entry 7 }

e3TxClkSel OBJECT-TYPE
	SYNTAX	INTEGER
	{
		system(11),
		local-oscillator(12),
		local-link0(13),
		local-link1(14)
	}
	ACCESS	read-write
	STATUS	mandatory
	DESCRIPTION
	"Transmit clock select."
	::= { e3Entry 8 }


e3LOSDefect	OBJECT-TYPE
	SYNTAX	INTEGER
	{
		no(2),
		yes(1)
	}
	ACCESS	read-only
	STATUS	mandatory
	DESCRIPTION
	"Loss Of Signal Defect"
	::= { e3Entry 9 }

e3LOSAlarm	OBJECT-TYPE
	SYNTAX	INTEGER
	{
		no(2),
		yes(1)
	}
	ACCESS	read-only
	STATUS	mandatory
	DESCRIPTION
	"Loss Of Signal Alarm"
	::= { e3Entry 10 }

e3Reconfig OBJECT-TYPE
	SYNTAX	INTEGER
	{
		no(2),
		yes(1)
	}
	ACCESS	read-write
	STATUS	mandatory
	DESCRIPTION
	"Reconfigure Link"
	DEFVAL { no }
	::= { e3Entry 11 }


-- HSSI DLIM
-- Depricate old HSSI table
--hssiTable	OBJECT-TYPE
--	SYNTAX	SEQUENCE OF HssiEntry
--	ACCESS	not-accessible
--	STATUS	mandatory
--	DESCRIPTION
--	"hssi Status Table"
--	::= { dv2DS 3 }
--
--hssiTable	OBJECT-TYPE
--	SYNTAX	SEQUENCE OF HssiEntry
--	ACCESS	not-accessible
--	STATUS	mandatory
--	DESCRIPTION
--	"hssi Status Table"
--	::= { dv2DS 8 }

hssiTable	OBJECT-TYPE
	SYNTAX	SEQUENCE OF HssiEntry
	ACCESS	not-accessible
	STATUS	mandatory
	DESCRIPTION
	"hssi Status Table"
	::= { dv2DS 13 }

hssiEntry	OBJECT-TYPE
	SYNTAX	HssiEntry
	ACCESS	not-accessible
	STATUS	mandatory
	INDEX	{ hssiLinkNo }
	::= { hssiTable 1 }

HssiEntry ::=
	SEQUENCE {
		hssiLinkNo
			INTEGER,
		hssiType
			INTEGER,
		hssiLimType
			INTEGER,
		hssiLinkReady
			INTEGER,
		hssiRemoteReady
			INTEGER,
		hssiClockSrc
			INTEGER,
		hssiLocalLoopback
			INTEGER,
		hssiRemoteLoopback
			INTEGER,
		hssiCtrTestMode
			INTEGER,
		hssiReconfig
			INTEGER,
		hssiLOSDefect
			INTEGER,
		hssiLOSAlarm
			INTEGER
}

hssiLinkNo  OBJECT-TYPE
	SYNTAX	INTEGER (0..3)
	ACCESS	read-only
	STATUS	mandatory
	DESCRIPTION
	"Link number - this is the instance."
	::= { hssiEntry 1 }


hssiLocalLoopback OBJECT-TYPE
	SYNTAX	INTEGER
	{
	        none(1),
		line(2),
		internal(3),
		bilateral(4)
	}
	ACCESS	read-write
	STATUS	mandatory
	DESCRIPTION
	"Local Loopback."
	DEFVAL { none }
	::= { hssiEntry 2 }

hssiRemoteLoopback OBJECT-TYPE
	SYNTAX	INTEGER
	{
	        none(1),
		line(2),
		digital(3),
		remote-line(4)
	}
	ACCESS	read-write
	STATUS	mandatory
	DESCRIPTION
	"Remote Loopback."
	DEFVAL { none }
	::= { hssiEntry 3 }

hssiReconfig OBJECT-TYPE
	SYNTAX	INTEGER
	{
		no(2),
		yes(1)
	}
	ACCESS	read-write
	STATUS	mandatory
	DESCRIPTION
	"Reconfigure Link"
	DEFVAL { no }
	::= { hssiEntry 4 }


hssiType	OBJECT-TYPE
	SYNTAX	INTEGER
	{
		dte(1),
		dce(2)
	}
	ACCESS	read-write
	STATUS	mandatory
	DESCRIPTION
	"Type of link."
	::= { hssiEntry 15 }

hssiLimType	OBJECT-TYPE
	SYNTAX	INTEGER
	{
		hssi-v1(1)
	}
	ACCESS	read-only
	STATUS	mandatory
	DESCRIPTION
	"LIM Version"
	::= { hssiEntry 16 }

hssiClockSrc	OBJECT-TYPE
	SYNTAX	INTEGER
	{
		local(1),
		from-dce(2),
		local-45Mbps(3),
		local-34Mbps(4)
	}
	ACCESS	read-write
	STATUS	mandatory
	DESCRIPTION
	"Source of clock. Note that for a DCE, from-DCE(4) should not be selected."
	::= { hssiEntry 17 }

hssiCtrTestMode OBJECT-TYPE
	SYNTAX	INTEGER
	{
		on(1),
		off(2)
	}
	ACCESS	read-only
	STATUS	mandatory
	DESCRIPTION
	"Test Mode."
	DEFVAL { off }
	::= { hssiEntry 18 }


hssiLinkReady	OBJECT-TYPE
	SYNTAX	INTEGER
	{
		yes(1),
		no(2)
	}
	ACCESS	read-only
	STATUS	mandatory
	DESCRIPTION
	"Set to yes(1) if link is ready."
	DEFVAL { no }
	::= { hssiEntry 19 }

hssiRemoteReady	OBJECT-TYPE
	SYNTAX	INTEGER
	{
		yes(1),
		no(2)
	}
	ACCESS	read-only
	STATUS	mandatory
	DESCRIPTION
	"Set to yes(1) if remote link is ready."
	DEFVAL { no }
	::= { hssiEntry 20 }

hssiLOSDefect	OBJECT-TYPE
	SYNTAX	INTEGER
	{
		no(2),
		yes(1)
	}
	ACCESS	read-only
	STATUS	mandatory
	DESCRIPTION
	"Loss Of Signal Defect"
	DEFVAL { no }
	::= { hssiEntry 25 }

hssiLOSAlarm	OBJECT-TYPE
	SYNTAX	INTEGER
	{
		no(2),
		yes(1)
	}
	ACCESS	read-only
	STATUS	mandatory
	DESCRIPTION
	"Loss Of Signal Alarm"
	DEFVAL { no }
	::= { hssiEntry 30 }

-- J2-xC DLIM

j2Table      OBJECT-TYPE
        SYNTAX  SEQUENCE OF J2Entry
        ACCESS  not-accessible
        STATUS  mandatory
        DESCRIPTION
        "J2 Config/Status Table"
        ::= { dv2DS 14 }

j2Entry      OBJECT-TYPE
        SYNTAX  J2Entry
        ACCESS  not-accessible
        STATUS  mandatory
        INDEX   { j2LinkNo }
        ::= { j2Table 1 }

J2Entry ::=
        SEQUENCE {
                j2LinkNo
                        INTEGER,
--              j2LimType
--                      INTEGER,
                j2FirmwareRev
                        INTEGER,
-- configurables
                j2TxEq
                        INTEGER,
                j2Lb
                        INTEGER,
                j2TxAIS
                        INTEGER,
--                j2GappedClk
--                      INTEGER,
                j2TxClkSel
                        INTEGER,
		j2ClrStats
			INTEGER,
		j2Reconfig
			INTEGER,
		j2TS97TS98
			Hex,
                j2QualClock
                        INTEGER,

-- Defects
		j2LOSDefect
			INTEGER,
		j2OOFDefect
                        INTEGER,
		j2AISDefect
			INTEGER,
		j2RAlmDefect
			INTEGER,
-- Alarms
		j2LOSAlarm
			INTEGER,
		j2LOFAlarm
			INTEGER,
		j2AISAlarm
			INTEGER,
		j2RAlmAlarm
			INTEGER,
-- Error Counts
		j2FerCount
			INTEGER,
		j2RAlmCount
			INTEGER,
--		j2OCfCount
--			INTEGER,
		j2LcvCount
			INTEGER,
		j2CrcCount
		        Counter,

-- Performance parameters
		j2LineES
			Counter,
		j2LineSES
			Counter,
		j2ES
			Counter,
		j2SES
			Counter,
		j2AISS
			Counter,
		j2UAS
			Counter
}

j2LinkNo  OBJECT-TYPE
        SYNTAX  INTEGER (0..3)
        ACCESS  read-only
        STATUS  mandatory
        DESCRIPTION
        "Link number - this is the instance."
        ::= { j2Entry 1 }

--
--j2LimType OBJECT-TYPE
--        SYNTAX  INTEGER
--        {
--		j2-dual(1),
--		j2-quad(2)
--        }
--        ACCESS  read-only
--        STATUS  obsoleted
--        DESCRIPTION
--        "LIM I.D. type"
--        ::= { j2Entry 2 }

j2FirmwareRev OBJECT-TYPE
        SYNTAX  INTEGER
        ACCESS  read-only
        STATUS  mandatory
        DESCRIPTION
        "Firmware Revision"
        ::= { j2Entry 3 }

j2TxEq OBJECT-TYPE
        SYNTAX  INTEGER
        {
		low-dB(1),
        	high-dB(2)
	}
        ACCESS  read-write
        STATUS  mandatory
        DESCRIPTION
        "Select equalizer setting"
        ::= { j2Entry 4 }

j2Lb OBJECT-TYPE
        SYNTAX  INTEGER
        {
          none(1),
          liu-line(2),
          j2-Framer-Payload(3),
          j2-Framer-Digital(4)
        }
        ACCESS  read-write
        STATUS  mandatory
        DESCRIPTION
        "Loopback Selection"
        ::= { j2Entry 6 }

j2TxAIS OBJECT-TYPE
        SYNTAX  INTEGER
        {
                no(2),
                yes(1)
        }
        ACCESS  read-write
        STATUS  mandatory
        DESCRIPTION
        "Transmit the AIS State."
        ::= { j2Entry 7 }

--j2GappedClk  OBJECT-TYPE
--        SYNTAX  INTEGER
--        {
--                non-gapped(1),
--                atm(2)
--        }
--        ACCESS  read-write
--        STATUS  obsoleted
--        DESCRIPTION
--        "ATM mode gaps channels 97-98 and framing bits."
--        DEFVAL { 2 }
--        ::= { j2Entry 8 }


j2TxClkSel	OBJECT-TYPE
	SYNTAX	INTEGER
	{
		system-bus(11),
		int-oscillator(12),
		link-0(13),
		link-1(14)
	}
	ACCESS	read-write
	STATUS	mandatory
	DESCRIPTION
	"Transmit clock select."
	::= { j2Entry 9 }

j2ClrStats        OBJECT-TYPE
        SYNTAX  INTEGER
        {
                yes(1),
                no(2)
        }
        ACCESS  read-write
        STATUS  mandatory
        DESCRIPTION
        "Clear Counters"
        ::= { j2Entry 10 }

j2Reconfig OBJECT-TYPE
	SYNTAX	INTEGER
	{
		no(2),
		yes(1)
	}
	ACCESS	read-write
	STATUS	mandatory
	DESCRIPTION
	"Reconfigure Link"
	DEFVAL { no }
        ::= { j2Entry 11 }

j2TS97TS98 OBJECT-TYPE
	SYNTAX	Hex
	ACCESS	read-write
	STATUS	mandatory
	DESCRIPTION
	"Set the value (in hex) of the bytes to be transmitted in time slots 97 and 98 of the J2 frame."
	DEFVAL { 65535 }
        ::= { j2Entry 12 }

j2QualClock OBJECT-TYPE
	SYNTAX	INTEGER
	{
		low-Primary(1),
		low-Secondary(2),
		high-Primary(3),
		high-Secondary(4),
                local-Oscillator(5)
	}
	ACCESS	read-only
	STATUS	mandatory
	DESCRIPTION
	"Quality of Clock Selection"
	DEFVAL { low-Primary }
        ::= { j2Entry 20 }

j2LOSDefect   OBJECT-TYPE
        SYNTAX INTEGER {
                no(2),
                yes(1)
        }
        ACCESS read-only
        STATUS mandatory
        DESCRIPTION
        "Loss Of Signal Defect"
        ::= { j2Entry 22 }

j2OOFDefect   OBJECT-TYPE
        SYNTAX INTEGER {
                no(2),
                yes(1)
        }
        ACCESS read-only
        STATUS mandatory
        DESCRIPTION
        "Receive Out Of Frame"
        ::= { j2Entry 23 }

j2AISDefect   OBJECT-TYPE
        SYNTAX INTEGER {
                no(2),
                yes(1)
        }
        ACCESS read-only
        STATUS mandatory
        DESCRIPTION
        "Receive AIS Defect"
        ::= { j2Entry 24 }


j2RAlmDefect       OBJECT-TYPE
        SYNTAX INTEGER {
                no(2),
                yes(1)
        }
        ACCESS read-only
        STATUS mandatory
        DESCRIPTION
        "Remote Alarm Defect"
        ::= { j2Entry 26 }

j2LOSAlarm       OBJECT-TYPE
        SYNTAX INTEGER {
                no(2),
                yes(1)
        }
        ACCESS read-only
        STATUS mandatory
        DESCRIPTION
        "Loss Of Signal Integrated Alarm"
        ::= { j2Entry 37 }

j2LOFAlarm   OBJECT-TYPE
        SYNTAX INTEGER {
                no(2),
                yes(1)
        }
        ACCESS read-only
        STATUS mandatory
        DESCRIPTION
        "Loss Of Frame Integrated Alarm"
        ::= { j2Entry 38 }

j2AISAlarm   OBJECT-TYPE
        SYNTAX INTEGER {
                no(2),
                yes(1)
        }
        ACCESS read-only
        STATUS mandatory
        DESCRIPTION
        "AIS Integrated Alarm"
        ::= { j2Entry 39 }

j2RAlmAlarm       OBJECT-TYPE
        SYNTAX INTEGER {
                no(2),
                yes(1)
        }
        ACCESS read-only
        STATUS mandatory
        DESCRIPTION
        "Remote Alarm Condition"
        ::= { j2Entry 41 }

j2FerCount        OBJECT-TYPE
        SYNTAX INTEGER
        ACCESS read-only
        STATUS mandatory
        DESCRIPTION
        "The framing bit error count for this link."
        ::= { j2Entry 52 }

j2RAlmCount OBJECT-TYPE
        SYNTAX INTEGER
        ACCESS read-only
        STATUS mandatory
        DESCRIPTION
        "The Remote Alarm error count for this link."
        ::= { j2Entry 53 }

--j2OCfCount        OBJECT-TYPE
--      SYNTAX INTEGER
--      ACCESS read-only
--      STATUS obsoleted
--      DESCRIPTION
--      "The Out-of-frame or Change of Frame alignment error count for
--	this link."
--      ::= { j2Entry 54 }

j2LcvCount        OBJECT-TYPE
        SYNTAX INTEGER
        ACCESS read-only
        STATUS mandatory
        DESCRIPTION
        "The J2 Line code violations count for this link."
        ::= { j2Entry 55 }

j2CrcCount OBJECT-TYPE
        SYNTAX Counter
        ACCESS read-only
        STATUS mandatory
        DESCRIPTION
        "Number of J2 muliframes received with CRC errors"
        ::= { j2Entry 56 }


j2LineES OBJECT-TYPE
        SYNTAX Counter
        ACCESS read-only
        STATUS mandatory
        DESCRIPTION
        "Line Errored Seconds"
        ::= { j2Entry 66 }

j2LineSES OBJECT-TYPE
        SYNTAX Counter
        ACCESS read-only
        STATUS mandatory
        DESCRIPTION
        "Line Severely Errored Seconds"
        ::= { j2Entry 67 }

j2ES OBJECT-TYPE
        SYNTAX Counter
        ACCESS read-only
        STATUS mandatory
        DESCRIPTION
        "Errored Seconds"
        ::= { j2Entry 68 }

j2SES OBJECT-TYPE
        SYNTAX Counter
        ACCESS read-only
        STATUS mandatory
        DESCRIPTION
        "Severely Errored Seconds"
        ::= { j2Entry 69 }

j2AISS OBJECT-TYPE
        SYNTAX Counter
        ACCESS read-only
        STATUS mandatory
        DESCRIPTION
        "AIS Seconds"
        ::= { j2Entry 70 }

j2UAS OBJECT-TYPE
        SYNTAX Counter
        ACCESS read-only
        STATUS mandatory
        DESCRIPTION
        "Unavailable Seconds"
        ::= { j2Entry 71 }


-- SCF-xC DLIM SI (SCF) start

scfTable      OBJECT-TYPE
        SYNTAX  SEQUENCE OF ScfEntry
        ACCESS  not-accessible
        STATUS  mandatory
        DESCRIPTION
        "SCF Config/Status Table"
        ::= { dv2DS 15 }

scfEntry      OBJECT-TYPE
        SYNTAX  ScfEntry
        ACCESS  not-accessible
        STATUS  mandatory
        INDEX   { scfLinkNo }
        ::= { scfTable 1 }

ScfEntry ::=
        SEQUENCE {
                scfLinkNo
                        INTEGER,
                scfLimType
                        INTEGER,
                scfFirmwareRev
                        INTEGER,
                scfQualClock
                        INTEGER,
-- configurables
		scfContr
			INTEGER,
		scfDCEDTE
			INTEGER,
                scfLb
                        INTEGER,
                scfLineTiming
                        INTEGER,
                scfDataRate
                        INTEGER,
		scfClkSel
			INTEGER,
		scfInterfaceType
			INTEGER,
		scfReconfig
			INTEGER,
-- Defects
		scfLOSDefect
			INTEGER,
-- Alarms
		scfLOSAlarm
			INTEGER

}

scfLinkNo  OBJECT-TYPE
        SYNTAX  INTEGER (0..3)
        ACCESS  read-only
        STATUS  mandatory
        DESCRIPTION
        "Link number - this is the instance."
        ::= { scfEntry 1 }

scfLimType OBJECT-TYPE
        SYNTAX  INTEGER
        {
		si-dual(1),
		si-quad(2)
        }
        ACCESS  read-only
        STATUS  mandatory
        DESCRIPTION
        "LIM I.D. type"
        ::= { scfEntry 2 }

scfFirmwareRev OBJECT-TYPE
        SYNTAX  INTEGER
        ACCESS  read-only
        STATUS  mandatory
        DESCRIPTION
        "Firmware Revision"
        ::= { scfEntry 3 }

scfQualClock OBJECT-TYPE
	SYNTAX	INTEGER
	{
		low-Primary(1),
		low-Secondary(2),
		high-Primary(3),
		high-Secondary(4),
                local-Oscillator(5)
	}
	ACCESS	read-only
	STATUS	mandatory
	DESCRIPTION
	"Quality of Clock Selection"
	DEFVAL { low-Primary }
        ::= { scfEntry 4 }

scfContr OBJECT-TYPE
        SYNTAX  INTEGER
        {
          ce-hpg-hc2(1),
          ms-ms2(2)
        }
        ACCESS  read-write
        STATUS  mandatory
        DESCRIPTION
        "Controller Selection"
	DEFVAL { ce-hpg-hc2 }
        ::= { scfEntry 5 }

scfDCEDTE OBJECT-TYPE
        SYNTAX  INTEGER
        {
          dce(1),
          dte(2)
        }
        ACCESS  read-write
        STATUS  mandatory
        DESCRIPTION
        "DCE or DTE Selection"
	DEFVAL { dce }
        ::= { scfEntry 6 }

scfLb OBJECT-TYPE
        SYNTAX  INTEGER
        {
          none(1),
          line(2),
          link(3),
          digital(4)
        }
        ACCESS  read-write
        STATUS  mandatory
        DESCRIPTION
        "Loopback Selection"
	DEFVAL { line }
        ::= { scfEntry 7 }

scfLineTiming OBJECT-TYPE
        SYNTAX  INTEGER
        {
          enabled(1),
          disabled(2)
        }
        ACCESS  read-write
        STATUS  mandatory
        DESCRIPTION
        "Receive Line Timing Selection"
	DEFVAL { enabled }
        ::= { scfEntry 8 }

scfDataRate OBJECT-TYPE
	SYNTAX	INTEGER
	{
		rate-2x4(1),
		rate-4x8(2),
		rate-7x2(3),
		rate-9x6(4),
		rate-14x4(5),
		rate-16x0(6),
		rate-16x6(7),
		rate-19x2(8),
		rate-28x8(9),
		rate-32x0(10),
		rate-38x4(11),
		rate-48x0(12),
		rate-50x0(13),
		rate-56x0(14),
		rate-57x6(15),
		rate-64x0(16),
		rate-76x8(17),
		rate-96x0(18),
		rate-112x0(19),
		rate-115x2(20),
		rate-128x0(21),
		rate-144x0(22),
		rate-153x6(23),
		rate-192x0(24),
		rate-224x0(25),
		rate-230x0(26),
		rate-256x0(27),
		rate-288x0(28),
		rate-307x2(29),
		rate-320x0(30),
		rate-384x0(31),
		rate-448x0(32),
		rate-512x0(33),
		rate-768x0(34),
		rate-1024x0(35),
		rate-1536x0(36),
		rate-1920x0(37),
		rate-2048x0(38),
		rate-3072x0(39),
		rate-4096x0(40),
		rate-6144x0(41),
		rate-8192x0(42)
	}
	ACCESS	read-write
	STATUS	mandatory
	DESCRIPTION
	"Data Rate Selection in K Bit/Sec"
	DEFVAL { rate-2x4 }
        ::= { scfEntry 9 }

scfClkSel   OBJECT-TYPE
        SYNTAX INTEGER {
                system(1),
                localOscillator(2)
        }
        ACCESS read-write
        STATUS mandatory
        DESCRIPTION
        "Clock select"
	DEFVAL { system }
        ::= { scfEntry 10 }

scfInterfaceType   OBJECT-TYPE
        SYNTAX INTEGER {
                x21(1),
                rs449(2),
		eia530-A(3),
		v35(4)
        }
        ACCESS read-write
        STATUS mandatory
        DESCRIPTION
        "Interface type selection"
	DEFVAL { x21 }
        ::= { scfEntry 11 }

scfReconfig OBJECT-TYPE
	SYNTAX	INTEGER
	{
		no(2),
		yes(1)
	}
	ACCESS	read-write
	STATUS	mandatory
	DESCRIPTION
	"Reconfigure Link"
	DEFVAL { no }
        ::= { scfEntry 12 }

scfLOSDefect   OBJECT-TYPE
        SYNTAX INTEGER {
                no(2),
                yes(1)
        }
        ACCESS read-only
        STATUS mandatory
        DESCRIPTION
        "Loss Of Signal Defect"
        ::= { scfEntry 13 }

scfLOSAlarm       OBJECT-TYPE
        SYNTAX INTEGER {
                no(2),
                yes(1)
        }
        ACCESS read-only
        STATUS mandatory
        DESCRIPTION
        "Loss Of Signal Integrated Alarm"
        ::= { scfEntry 14 }

-- SI (SCF) end


--___________________________________________________________________________
-- The Billing Group
-- 1/5/98   Pat Cassella   Added Deutsche TelKom SVC billing enhancements. Search for
--          Paul Burden    "DT change".
--          Mathi Packiam

-- Define the BillControl data type. DT change.
-- BillControl ::= INTEGER {disabled(1), enabled(2), deleteAll(3) }
	-- disabled: default/startup state.
	--         No new bills are created.
	--         Bills are not updated (any existing bills remain).
	-- enabled: Bills are updated at the specified interval.
	--        If an existing circuit has no bill, one is created.
	--        New bills are created as circuits are established.
	-- deleteAll: Existing bills are deleted.
	--           After the bills are deleted, reverts to disabled(1).

billAvailable 	OBJECT-TYPE
	SYNTAX	INTEGER
	ACCESS	read-only
	STATUS	mandatory
	DESCRIPTION
	"Number of billing records available."
	::= { dv2Billing 1 }

--billLogToDisk	OBJECT-TYPE
--	SYNTAX INTEGER {
--		no(2),
--		yes(1)
--	}
--	ACCESS  read-only
--	STATUS	obsolete
--	DESCRIPTION
--	"If set to yes(1) then records are written to the local file </billrec.dv2>. You should not normally leave this turned on."
--	::= { dv2Billing 2 }

billingTable OBJECT-TYPE
	SYNTAX SEQUENCE OF BillingEntry
	ACCESS not-accessible
	STATUS mandatory
	DESCRIPTION
	"This table is used to contain billing records."
	::= { dv2Billing 3 }

billingEntry OBJECT-TYPE
	SYNTAX	BillingEntry
	ACCESS	not-accessible
	STATUS	mandatory
        INDEX   { billSeq }
	::= { billingTable 1 }

BillingEntry ::=
	SEQUENCE {
		billSeq
			INTEGER,
		billSvpi
			VirtualPathIdentifier,
		billSvci
			VirtualCircuitIdentifier,
		billDvpi
			VirtualPathIdentifier,
		billDvci
			VirtualCircuitIdentifier,
		billSslot
			INTEGER,
		billSlink
			INTEGER,
		billDslot
			INTEGER,
		billDlink
			INTEGER,
		billCalled
			E164,
		billCalledSub
			E164SUB,
		billCalling
			E164,
		billCallingSub
			E164SUB,
		billCellInC
			Counter,
		billCellIn
			Counter,
		billFrameIn
			Counter,
		billByteInC
			Counter,
		billByteIn
			Counter,
		billCellOutC
			Counter,
		billCellOut
			Counter,
		billFrameOut
			Counter,
		billByteOutC
			Counter,
		billByteOut
			Counter,
-- billClass has been replaced with billFwdQOS and billBwdQOS. DT change.
--		billClass
--			INTEGER,
		billCause
			INTEGER,
--                              Y2K change
--		billStart
--			DateTimeString,
--                              Y2K change
--		billEnd
--			DateTimeString,
		billValid
			INTEGER,
                billCLP1OutC
                        Counter,
                billCLP1Out
                        Counter,
		billTag
			INTEGER,
--                              Y2K change : added,  use DateAndTime convention
		billStartM2
			DateAndTime,
--                              Y2K change : added,  use DateAndTime convention
		billEndM2
			DateAndTime,
-- The following changes for PCR,SCR,MBS,and QOS (entry 34 through 41) are per Deutsche
-- TeleKom upgrade request. DT change.
		billFwdPCR
                        INTEGER,
                billBwdPCR
                        INTEGER,
                billFwdSCR
                        INTEGER,
                billBwdSCR
                        INTEGER,
                billFwdMBS
                        INTEGER,
                billBwdMBS
                        INTEGER,
                billFwdQOS
                        INTEGER,
                billBwdQOS
                        INTEGER
}


billSeq	OBJECT-TYPE
	SYNTAX INTEGER (0..2147483647)
	ACCESS	read-only
	STATUS	mandatory
	DESCRIPTION
	"billing record sequence number."
	::= { billingEntry 1 }

billSvpi	OBJECT-TYPE
	SYNTAX VirtualPathIdentifier
	ACCESS	read-only
	STATUS	mandatory
	DESCRIPTION
	"Source Virtual Path Identifier for VC."
	::= { billingEntry 2 }

billSvci	OBJECT-TYPE
	SYNTAX VirtualCircuitIdentifier
	ACCESS	read-only
	STATUS	mandatory
	DESCRIPTION
	"Source Virtual Circuit Identifier for VC."
	::= { billingEntry 3 }

billDvpi	OBJECT-TYPE
	SYNTAX VirtualPathIdentifier
	ACCESS	read-only
	STATUS	mandatory
	DESCRIPTION
	"Destination Virtual Path Identifier for VC."
	::= { billingEntry 4 }

billDvci	OBJECT-TYPE
	SYNTAX VirtualCircuitIdentifier
	ACCESS	read-only
	STATUS	mandatory
	DESCRIPTION
	"Destination Virtual Circuit Identifier for VC."
	::= { billingEntry 5 }

billSslot	OBJECT-TYPE
	SYNTAX INTEGER
	ACCESS	read-only
	STATUS	mandatory
	DESCRIPTION
	"Source slot for VC."
	::= { billingEntry 6 }

billSlink	OBJECT-TYPE
	SYNTAX INTEGER
	ACCESS	read-only
	STATUS	mandatory
	DESCRIPTION
	"Source link for VC."
	::= { billingEntry 7 }

billDslot	OBJECT-TYPE
	SYNTAX INTEGER
	ACCESS	read-only
	STATUS	mandatory
	DESCRIPTION
	"Destination slot for VC."
	::= { billingEntry 8 }

billDlink	OBJECT-TYPE
	SYNTAX INTEGER
	ACCESS	read-only
	STATUS	mandatory
	DESCRIPTION
	"Destination link for VC."
	::= { billingEntry 9 }


billCalled	OBJECT-TYPE
	SYNTAX E164
	ACCESS	read-only
	STATUS	mandatory
	DESCRIPTION
	"Called or Destination E.164 address."
	::= { billingEntry 10 }

billCalledSub	OBJECT-TYPE
	SYNTAX E164SUB
	ACCESS	read-only
	STATUS	mandatory
	DESCRIPTION
	"Called or Destination E.164 sub-address."
	::= { billingEntry 11 }

billCalling	OBJECT-TYPE
	SYNTAX E164
	ACCESS	read-only
	STATUS	mandatory
	DESCRIPTION
	"Calling or Originating E.164 address."
	::= { billingEntry 12 }

billCallingSub	OBJECT-TYPE
	SYNTAX E164SUB
	ACCESS	read-only
	STATUS	mandatory
	DESCRIPTION
	"Calling or Originating E.164 sub-address."
	::= { billingEntry 13 }

billCellInC	OBJECT-TYPE
	SYNTAX Counter
	ACCESS	read-only
	STATUS	mandatory
	DESCRIPTION
	"Cell in overflows count."
	::= { billingEntry 14 }

billCellIn	OBJECT-TYPE
	SYNTAX Counter
	ACCESS	read-only
	STATUS	mandatory
	DESCRIPTION
	"Cell in count."
	::= { billingEntry 15 }

billFrameIn	OBJECT-TYPE
	SYNTAX Counter
	ACCESS	read-only
	STATUS	mandatory
	DESCRIPTION
	"Frame in count."
	::= { billingEntry 16 }

billByteInC	OBJECT-TYPE
	SYNTAX Counter
	ACCESS	read-only
	STATUS	mandatory
	DESCRIPTION
	"Byte in overflows count."
	::= { billingEntry 17 }

billByteIn	OBJECT-TYPE
	SYNTAX Counter
	ACCESS	read-only
	STATUS	mandatory
	DESCRIPTION
	"Byte in count."
	::= { billingEntry 18 }

billCellOutC	OBJECT-TYPE
	SYNTAX Counter
	ACCESS	read-only
	STATUS	mandatory
	DESCRIPTION
	"Cell out overflows count."
	::= { billingEntry 19 }

billCellOut	OBJECT-TYPE
	SYNTAX Counter
	ACCESS	read-only
	STATUS	mandatory
	DESCRIPTION
	"Cell out count."
	::= { billingEntry 20 }

billFrameOut	OBJECT-TYPE
	SYNTAX Counter
	ACCESS	read-only
	STATUS	mandatory
	DESCRIPTION
	"Frame out count."
	::= { billingEntry 21 }

billByteOutC	OBJECT-TYPE
	SYNTAX Counter
	ACCESS	read-only
	STATUS	mandatory
	DESCRIPTION
	"Byte out overflows count."
	::= { billingEntry 22 }

billByteOut	OBJECT-TYPE
	SYNTAX Counter
	ACCESS	read-only
	STATUS	mandatory
	DESCRIPTION
	"Byte out count."
	::= { billingEntry 23 }

-- billClass has been deprecated and replaced with billFwdQOS and billBwdQOS. DT change.
-- billClass	OBJECT-TYPE
-- 	SYNTAX INTEGER {
-- 		ubr(0),
-- 		cbr(1),
-- 		vbr-high(2),
-- 		vbr-med(3),
-- 		vbr-low(4)
-- 	}
-- 	ACCESS	read-only
-- 	STATUS	deprecated
-- 	DESCRIPTION
-- 	"Call class."
-- 	::= { billingEntry 24 }

billCause	OBJECT-TYPE
	SYNTAX INTEGER
	ACCESS	read-only
	STATUS	mandatory
	DESCRIPTION
	"Clear cause code."
	::= { billingEntry 25 }

--                              Y2K change : deprecated
--billStart	OBJECT-TYPE
--	SYNTAX	DateTimeString
--	ACCESS	read-only
--	STATUS	deprecated
--	DESCRIPTION
--	"Call start date-time."
--	::= { billingEntry 26 }
--
--                              Y2K change : deprecated
--billEnd	OBJECT-TYPE
--	SYNTAX	DateTimeString
--	ACCESS	read-only
--	STATUS	deprecated
--	DESCRIPTION
--	"Call end date-time."
--	::= { billingEntry 27 }

billValid	OBJECT-TYPE
	SYNTAX INTEGER
	{
		valid(1),
		invalid(2),
		block-invalid(3)
	}
	ACCESS	read-write
	STATUS	mandatory
	DESCRIPTION
	"Deletes billing record Entry by setting to invalid(2)."
	::= { billingEntry 28 }

billCLP1OutC    OBJECT-TYPE
	SYNTAX Counter
	ACCESS	read-only
	STATUS	mandatory
	DESCRIPTION
	"CLP1 out overflows count."
	::= { billingEntry 29 }

billCLP1Out     OBJECT-TYPE
	SYNTAX Counter
	ACCESS	read-only
	STATUS	mandatory
	DESCRIPTION
	"CLP1 out count."
	::= { billingEntry 30 }

billTag OBJECT-TYPE
	SYNTAX INTEGER
	ACCESS read-only
	STATUS mandatory
	DESCRIPTION
	"This identifies the billable SVC."
	::= { billingEntry 31 }

--                              Y2K change : use DateAndTime convention
billStartM2	OBJECT-TYPE
	SYNTAX	DateAndTime
	ACCESS	read-only
	STATUS	mandatory
	DESCRIPTION
	"Call start date-time."
	::= { billingEntry 32 }

--                              Y2K change : use DateAndTime convention
billEndM2	OBJECT-TYPE
	SYNTAX	DateAndTime
	ACCESS	read-only
	STATUS	mandatory
	DESCRIPTION
	"Call end date-time."
	::= { billingEntry 33 }

-- The following changes for PCR,SCR,MBS,and QOS (entry 34 through 41) are per Deutsche
-- TeleKom upgrade request. DT change.

--New. DT change.
billFwdPCR OBJECT-TYPE
	SYNTAX INTEGER
	ACCESS read-only
	STATUS mandatory
	DESCRIPTION
	"SVC Forward Peak Cell Rate."
	::= { billingEntry 34 }

--New. DT change.
billBwdPCR OBJECT-TYPE
	SYNTAX INTEGER
	ACCESS read-only
	STATUS mandatory
	DESCRIPTION
	"SVC Backward Peak Cell Rate."
	::= { billingEntry 35 }

billFwdSCR OBJECT-TYPE
	SYNTAX INTEGER
	ACCESS read-only
	STATUS mandatory
	DESCRIPTION
	"SVC Forward Sustained Cell Rate."
	::= { billingEntry 36 }

--New. DT change.
billBwdSCR OBJECT-TYPE
	SYNTAX INTEGER
	ACCESS read-only
	STATUS mandatory
	DESCRIPTION
	"SVC Backward Sustained Cell Rate."
	::= { billingEntry 37 }


--New. DT change.
billFwdMBS OBJECT-TYPE
	SYNTAX INTEGER
	ACCESS read-only
	STATUS mandatory
	DESCRIPTION
	"SVC Forward Maximum Burst Size."
	::= { billingEntry 38 }

--New. DT change.
billBwdMBS OBJECT-TYPE
	SYNTAX INTEGER
	ACCESS read-only
	STATUS mandatory
	DESCRIPTION
	"SVC Backward Maximum Burst Size."
	::= { billingEntry 39 }

--Modified. DT change.
-- modified for compiler: ubrBe(0) removed - nws
billFwdQOS	OBJECT-TYPE
	SYNTAX INTEGER {
	        qos1(1),
                qos2(2),
                qos3(3),
                qos4(4),
                abr(6),
                cbr(7),
                vbrRt(8),
                vbrNrt(9)
	}
	ACCESS	read-only
	STATUS	mandatory
	DESCRIPTION
	"Forward Quality of Service."
	::= { billingEntry 40 }

--Modified. DT change.
-- modified for compiler: ubrBe(0) removed - nws
billBwdQOS	OBJECT-TYPE
	SYNTAX INTEGER {
	        qos1(1),
                qos2(2),
                qos3(3),
                qos4(4),
                abr(6),
                cbr(7),
                vbrRt(8),
                vbrNrt(9)
	}
	ACCESS	read-only
	STATUS	mandatory
	DESCRIPTION
	"Backward Quality of Service."
	::= { billingEntry 41 }

-- Later: Obsolete and replace with BillControlEntry - seperate control for svc,spvc,pvc. DT change.
  billingControl	OBJECT-TYPE
  	SYNTAX	INTEGER {
  		stop-billing-process(1),
  		start-SPVC-billing-process(2),
                start-PVC-billing-process(3),
                start-SPVC-and-PVC-billing(4),
  		delete-all-billing-records(5),
  		start-SVC-billing-process(6),
  		start-SVC-and-PVC-billing(7)
  		}
  	ACCESS	read-write
  	STATUS	mandatory
  	DESCRIPTION
  	"This object is set to start SPVC/PVC process."
  	::= { dv2Billing 4 }

-- Obsolete old Billing period definition. DT change.
-- billingPeriod	OBJECT-TYPE
-- 	SYNTAX	INTEGER (10..604800)
-- 	ACCESS	read-write
-- 	STATUS	deprecated
-- 	DESCRIPTION
-- 	"This parameter is used to set the billing period in seconds."
-- 	::= { dv2Billing 5 }

--Obsolete the unused field.
--billRecordControl	OBJECT-TYPE
--	SYNTAX	INTEGER {
--		bill-update-record(1)
--		}
--	ACCESS	read-only
--	STATUS	mandatory
--	DESCRIPTION
--	"This object is set to update or add new billing record."
--	DEFVAL { bill-update-record }
--	::= { dv2Billing 6 }

billLost    OBJECT-TYPE
	SYNTAX Counter
	ACCESS	read-write
	STATUS	mandatory
	DESCRIPTION
	"Lost of billing record count."
	::= { dv2Billing 7 }

-- Later: Obsolete and replace with BillControlEntry - billLinkNo. DT change.
  billLinks	OBJECT-TYPE
  	SYNTAX INTEGER {
  	       link0(1),
  	       link1(2),
  	       all(255)
  	       }
  	ACCESS read-write
  	STATUS mandatory
  	DESCRIPTION
  	"This value is bitwise billing link control."
  	::= { dv2Billing 8 }

billTrapControl	OBJECT-TYPE
	SYNTAX	INTEGER {
		enable(1),
		disable(2)
		}
	ACCESS	read-write
	STATUS	mandatory
	DESCRIPTION
	"This object is set to enable or disable billing traps"
	::= { dv2Billing 9 }

billDirControl OBJECT-TYPE
	SYNTAX	INTEGER {
		uni-direction(1),
		bi-direction(2)
		}
	ACCESS	read-write
	STATUS	mandatory
	DESCRIPTION
	"This object is selected for uni-direction billing or bi-direction billing."
	::= { dv2Billing 10 }

--billRecLostReset OBJECT-TYPE
--	SYNTAX INTEGER {
--		yes(1),
--		no(2)
--	}
--	ACCESS	read-write
--	STATUS	mandatory
--	DESCRIPTION
--	"reset for billing records lost field"
--	DEFVAL { no }
--	::= { dv2Billing 11 }

-- New Billing period definition via Kiran Mistry. DT change.
billingInterval	OBJECT-TYPE
	SYNTAX	INTEGER {
        	period15min(1),
	        period30min(2),
	        period60min(3),
	        period120min(4)
                }
	ACCESS	read-write
	STATUS	mandatory
	DESCRIPTION
	"This parameter is used to set the billing period in 15/30/60/120 minute intervals"
	::= { dv2Billing 12 }

--New. DT change.
-- billControlTable OBJECT-TYPE
-- 	SYNTAX SEQUENCE OF BillControlEntry
-- 	ACCESS not-accessible
-- 	STATUS mandatory
-- 	DESCRIPTION
--         "This table contains flags to control the billing on each link"
-- 	::= { dv2Billing 13 }

--New. DT change.
-- billControlEntry OBJECT-TYPE
-- 	SYNTAX	BillControlEntry
-- 	ACCESS	not-accessible
-- 	STATUS	mandatory
--         INDEX   { billLinkNo }
-- 	::= { billControlTable 1 }

--New. DT change.
-- BillControlEntry ::=
-- 	SEQUENCE {
-- 		billLinkNo
-- 			INTEGER,
-- 		billPvcControl
-- 			INTEGER, -BillControl
-- 		billSvcControl
-- 			INTEGER, -BillControl
-- 		billSPvcControl
-- 			INTEGER -BillControl
-- 	}

--New. DT change.
-- billLinkNo    OBJECT-TYPE
-- 	SYNTAX INTEGER (0..3)
-- 	ACCESS	read-only
-- 	STATUS	mandatory
-- 	DESCRIPTION
-- 	"Link number, starting at 0."
-- 	::= { BillControlEntry 1 }

--New. DT change.
-- billPvcControl    OBJECT-TYPE
-- 	SYNTAX INTEGER {
-- 		disabled(1),
-- 		enabled(2),
-- 		deleteAll(3)
-- 	} - BillControl type
-- 	ACCESS	read-write
-- 	STATUS	mandatory
-- 	DESCRIPTION
-- 	"Flag to control PVC billing."
-- 	::= { BillControlEntry 2 }

--New. DT change.
-- billSvcControl    OBJECT-TYPE
-- 	SYNTAX INTEGER {
-- 		disabled(1),
-- 		enabled(2),
-- 		deleteAll(3)
-- 	} - BillControl type
-- 	ACCESS	read-write
-- 	STATUS	mandatory
-- 	DESCRIPTION
-- 	"Flag to control SVC billing."
-- 	::= { BillControlEntry 3 }

--New. DT change.
-- billSPvcControl    OBJECT-TYPE
-- 	SYNTAX INTEGER { disabled(1), enabled(2), deleteAll(3) } - BillControl type
-- 	ACCESS	read-write
-- 	STATUS	mandatory
-- 	DESCRIPTION
-- 	"Flag to control SPVC billing."
-- 	::= { BillControlEntry 4 }

--___________________________________________________________________________
--The QEDOC Group

qeDocMacAddress 	OBJECT-TYPE
	SYNTAX	PhysAddress
	ACCESS	read-only
	STATUS	mandatory
	DESCRIPTION
	"MAC address of Ethernet ports."
	::= { dv2QeDoc 1 }

qeDocTunRetryPeriod	OBJECT-TYPE
	SYNTAX INTEGER	(5..60)
	ACCESS read-write
	STATUS mandatory
	DESCRIPTION
	"Number of seconds between retries of tunnel establishment."
	::= { dv2QeDoc 2 }

qeDocTunIdlePeriod	OBJECT-TYPE
	SYNTAX INTEGER (5..3600)
	ACCESS read-write
	STATUS mandatory
	DESCRIPTION
	"Number of seconds to wait without activity before clearing tunnel call."
	::= { dv2QeDoc 3 }

qeDocBridgeTable OBJECT-TYPE
	SYNTAX SEQUENCE OF QeDocBridgeEntry
	ACCESS not-accessible
	STATUS mandatory
	DESCRIPTION
	"This table is used to statistics and control for the bridges."
	::= { dv2QeDoc 4 }

qeDocBridgeEntry OBJECT-TYPE
	SYNTAX	QeDocBridgeEntry
	ACCESS	not-accessible
	STATUS	mandatory
        INDEX   { qeDocBridgeLinkNo }
	::= { qeDocBridgeTable 1 }

QeDocBridgeEntry ::=
	SEQUENCE {
		qeDocBridgeLinkNo
			INTEGER,
		qeDocBridgeEnable
			INTEGER,
		qeDocBridgeLink0Eligible
			INTEGER,
		qeDocBridgeLink1Eligible
			INTEGER,
		qeDocBridgeLink2Eligible
			INTEGER,
		qeDocBridgeLink3Eligible
			INTEGER
}

qeDocBridgeLinkNo	OBJECT-TYPE
	SYNTAX INTEGER (0..3)
	ACCESS	read-only
	STATUS	mandatory
	DESCRIPTION
	"Link number."
	::= { qeDocBridgeEntry 1 }

qeDocBridgeEnable	OBJECT-TYPE
	SYNTAX INTEGER {
		yes(1),
		no(2)
	}
	ACCESS	read-write
	STATUS	mandatory
	DESCRIPTION
	"Set to yes(1) to enable MAC bridging."
	::= { qeDocBridgeEntry 2 }

qeDocBridgeLink0Eligible	OBJECT-TYPE
	SYNTAX INTEGER {
		yes(1),
		no(2)
	}
	ACCESS	read-write
	STATUS	mandatory
	DESCRIPTION
	"Link 0 eligible for frames"
	::= { qeDocBridgeEntry 3 }

qeDocBridgeLink1Eligible	OBJECT-TYPE
	SYNTAX INTEGER {
		yes(1),
		no(2)
	}
	ACCESS	read-write
	STATUS	mandatory
	DESCRIPTION
	"Link 1 eligible for frames"
	::= { qeDocBridgeEntry 4 }

qeDocBridgeLink2Eligible	OBJECT-TYPE
	SYNTAX INTEGER {
		yes(1),
		no(2)
	}
	ACCESS	read-write
	STATUS	mandatory
	DESCRIPTION
	"Link 2 eligible for frames"
	::= { qeDocBridgeEntry 5 }

qeDocBridgeLink3Eligible	OBJECT-TYPE
	SYNTAX INTEGER {
		yes(1),
		no(2)
	}
	ACCESS	read-write
	STATUS	mandatory
	DESCRIPTION
	"Link 3 eligible for frames"
	::= { qeDocBridgeEntry 6 }

--___________________________________________________________________________
-- The Tunnel Management Table

qeDocTunTable OBJECT-TYPE
	SYNTAX SEQUENCE OF QeDocTunEntry
	ACCESS not-accessible
	STATUS mandatory
	DESCRIPTION
	"This table is used to establish and control tunnels set-up using SVCs."
	::= { dv2QeDoc 6  }

qeDocTunEntry	OBJECT-TYPE
	SYNTAX QeDocTunEntry
	ACCESS not-accessible
	STATUS mandatory
        INDEX   { qeDocTunIndex }
	::= { qeDocTunTable 1 }

QeDocTunEntry	::=
	SEQUENCE {
		qeDocTunIndex
			INTEGER,
		qeDocTunName
			DisplayString,
		qeDocTunType
			INTEGER,
		qeDocTunState
			INTEGER,
		qeDocTunCallState
			INTEGER,
		qeDocTunVPI
			VirtualPathIdentifier,
		qeDocTunVCI
			VirtualCircuitIdentifier,
		qeDocTunPriority
			INTEGER,
		qeDocTunSlot
			INTEGER,
		qeDocTunLink
			INTEGER,
		qeDocTunInFrames
			Counter,
		qeDocTunOutFrames
			Counter,
		qeDocTunRemNet
			IpAddress,
		qeDocTunRemMask
			IpAddress,
		qeDocTunLocNet
			IpAddress,
		qeDocTunLocMask
			IpAddress,
		qeDocTunRemStartSkt
			INTEGER,
		qeDocTunRemEndSkt
			INTEGER,
		qeDocTunLocStartSkt
			INTEGER,
		qeDocTunLocEndSkt
			INTEGER,
		qeDocTunSktType
			INTEGER,
		qeDocTunDestAddress
			E164,
		qeDocTunDestSubAddress
			E164SUB,
		qeDocTunValidity
			INTEGER,
		qeDocTunLink0Eligible
			INTEGER,
		qeDocTunLink1Eligible
			INTEGER,
		qeDocTunLink2Eligible
			INTEGER,
		qeDocTunLink3Eligible
			INTEGER,
                qeDocTunRfc1483Encap
			INTEGER,
		qeDocTunClp
			INTEGER
}

qeDocTunIndex OBJECT-TYPE
	SYNTAX INTEGER (1..127)
	ACCESS read-write
	STATUS mandatory
	DESCRIPTION
	"The tunnel index number."
	::= { qeDocTunEntry 1 }

qeDocTunName	OBJECT-TYPE
	SYNTAX DisplayString
	ACCESS read-write
	STATUS mandatory
	DESCRIPTION
	"Mnemonic name for tunnel."
	::= { qeDocTunEntry 2 }

qeDocTunType	OBJECT-TYPE
	SYNTAX INTEGER {
		unused(1),
		ip(2),
		mac-bridge(3)
	}
	ACCESS read-write
	STATUS mandatory
	DESCRIPTION
	"Specifies the type of tunnel."
	::= { qeDocTunEntry 3 }

qeDocTunState	OBJECT-TYPE
	SYNTAX INTEGER {
		idle(1),
		use-pvc(2),
		use-svc(3),
                failed(4)
	}
	ACCESS read-write
	STATUS mandatory
	DESCRIPTION
	"Set to Use pvc(2) if using with a PVC. Set to Use svc(3) if using with a SVC. Set to idle(1) to prevent tunnel being established."
	::= { qeDocTunEntry 4 }

qeDocTunCallState	OBJECT-TYPE
	SYNTAX INTEGER {
		idle(1),
		allocated(2),
		waccept(3),
		active(4)
	}
	ACCESS read-only
	STATUS mandatory
	DESCRIPTION
	"State of tunnel call."
	::= { qeDocTunEntry 5 }

qeDocTunInFrames	OBJECT-TYPE
	SYNTAX Counter
	ACCESS read-only
	STATUS mandatory
	DESCRIPTION
	"Received frames count."
	::= { qeDocTunEntry 6 }

qeDocTunOutFrames	OBJECT-TYPE
	SYNTAX Counter
	ACCESS read-only
	STATUS mandatory
	DESCRIPTION
	"Transmitted frames count."
	::= { qeDocTunEntry 7 }

qeDocTunVPI	OBJECT-TYPE
	SYNTAX VirtualPathIdentifier
	ACCESS read-only
	STATUS mandatory
	DESCRIPTION
	"VPI being used for the tunnel."
	::= { qeDocTunEntry 8 }

qeDocTunVCI	OBJECT-TYPE
	SYNTAX VirtualCircuitIdentifier
	ACCESS read-only
	STATUS mandatory
	DESCRIPTION
	"VCI being used for the tunnel."
	::= { qeDocTunEntry 9 }

qeDocTunPriority	OBJECT-TYPE
	SYNTAX INTEGER (0..1)
	ACCESS read-only
	STATUS mandatory
	DESCRIPTION
	"Cell priority bit value."
	::= { qeDocTunEntry 10 }

qeDocTunSlot	OBJECT-TYPE
	SYNTAX INTEGER (0..15)
	ACCESS read-only
	STATUS mandatory
	DESCRIPTION
	"Target slot for tunnel."
	::= { qeDocTunEntry 11 }

qeDocTunLink	OBJECT-TYPE
	SYNTAX INTEGER (0..3)
	ACCESS read-only
	STATUS mandatory
	DESCRIPTION
	"Target link for tunnel."
	::= { qeDocTunEntry 12 }

qeDocTunRemNet	OBJECT-TYPE
	SYNTAX IpAddress
	ACCESS read-write
	STATUS mandatory
	DESCRIPTION
	"Remote network address for tunnel."
	::= { qeDocTunEntry 13 }

qeDocTunRemMask	OBJECT-TYPE
	SYNTAX IpAddress
	ACCESS read-write
	STATUS mandatory
	DESCRIPTION
	"Mask for remote network."
	::= { qeDocTunEntry 14 }

qeDocTunLocNet	OBJECT-TYPE
	SYNTAX IpAddress
	ACCESS read-write
	STATUS mandatory
	DESCRIPTION
	"Local network address for tunnel."
	::= { qeDocTunEntry 15 }

qeDocTunLocMask	OBJECT-TYPE
	SYNTAX IpAddress
	ACCESS read-write
	STATUS mandatory
	DESCRIPTION
	"Mask for local network."
	::= { qeDocTunEntry 16 }

qeDocTunRemStartSkt	OBJECT-TYPE
	SYNTAX INTEGER (1..65535)
	ACCESS read-write
	STATUS mandatory
	DESCRIPTION
	"Specifies start of socket range from remote that is allowed/barred from access to tunnel."
	::= { qeDocTunEntry 17 }

qeDocTunRemEndSkt	OBJECT-TYPE
	SYNTAX INTEGER (1..65535)
	ACCESS read-write
	STATUS mandatory
	DESCRIPTION
	"Specifies end of socket range from remote that is allowed/barred from access to tunnel."
	::= { qeDocTunEntry 18 }

qeDocTunLocStartSkt	OBJECT-TYPE
	SYNTAX INTEGER (1..65535)
	ACCESS read-write
	STATUS mandatory
	DESCRIPTION
	"Specifies start of socket range from local that is allowed/barred from access to tunnel."
	::= { qeDocTunEntry 19 }

qeDocTunLocEndSkt	OBJECT-TYPE
	SYNTAX INTEGER (1..65535)
	ACCESS read-write
	STATUS mandatory
	DESCRIPTION
	"Specifies end of socket range from local that is allowed/barred from access to tunnel."
	::= { qeDocTunEntry 20 }

qeDocTunSktType	OBJECT-TYPE
	SYNTAX INTEGER {
		tcpInc-udpInc(4),
		tcpInc-udpExc(3),
		tcpExc-udpInc(2),
		tcpExc-udpExc(1)
	}
	ACCESS read-write
	STATUS mandatory
	DESCRIPTION
	"Specifies the protocol type and whether to include or exclude frames with socket number in the specified range."
	::= { qeDocTunEntry 21 }

qeDocTunDestAddress	OBJECT-TYPE
	SYNTAX E164
	ACCESS read-write
	STATUS mandatory
	DESCRIPTION
	"Destination address for tunnel. This is only required for SVC tunnels."
	::= { qeDocTunEntry 22 }

qeDocTunDestSubAddress	OBJECT-TYPE
	SYNTAX E164SUB
	ACCESS read-write
	STATUS mandatory
	DESCRIPTION
	"Destination sub-address for tunnel. This is only required for SVC tunnels."
	::= { qeDocTunEntry 23 }

qeDocTunLink0Eligible	OBJECT-TYPE
	SYNTAX INTEGER {
		yes(1),
		no(2)
	}
	ACCESS	read-write
	STATUS	mandatory
	DESCRIPTION
	"Link 0 eligible for frames"
	::= { qeDocTunEntry 24 }

qeDocTunLink1Eligible	OBJECT-TYPE
	SYNTAX INTEGER {
		yes(1),
		no(2)
	}
	ACCESS	read-write
	STATUS	mandatory
	DESCRIPTION
	"Link 1 eligible for frames"
	::= { qeDocTunEntry 25 }

qeDocTunLink2Eligible	OBJECT-TYPE
	SYNTAX INTEGER {
		yes(1),
		no(2)
	}
	ACCESS	read-write
	STATUS	mandatory
	DESCRIPTION
	"Link 2 eligible for frames"
	::= { qeDocTunEntry 26 }

qeDocTunLink3Eligible	OBJECT-TYPE
	SYNTAX INTEGER {
		yes(1),
		no(2)
	}
	ACCESS	read-write
	STATUS	mandatory
	DESCRIPTION
	"Link 3 eligible for frames"
	::= { qeDocTunEntry 27 }

qeDocTunValidity OBJECT-TYPE
	SYNTAX INTEGER {
		valid(1),
		invalid(2)
	}
	ACCESS read-write
	STATUS mandatory
	DESCRIPTION
	"Setting to invalid(2) removes the row from the table."
	::= { qeDocTunEntry 28 }

qeDocTunRfc1483Encap OBJECT-TYPE
	SYNTAX INTEGER {
                yes(1),
                no(2)
	}
	ACCESS read-write
	STATUS mandatory
	DESCRIPTION
        "Setting to yes(1) enable RFC 1483 LLC encapsulation."
        ::= { qeDocTunEntry 29 }

-- Make entry# = 31 to match the slave mib definition.
qeDocTunClp	OBJECT-TYPE
 	SYNTAX INTEGER (0..1)
 	ACCESS read-only
 	STATUS mandatory
 	DESCRIPTION
 	"Cell loss priority bit value."
 	::= { qeDocTunEntry 31 }

qeDocIpAddress OBJECT-TYPE
	SYNTAX IpAddress
	ACCESS read-write
	STATUS mandatory
	DESCRIPTION
	"The IP address of the QEDOC for management use."
	::= { dv2QeDoc 7 }

qeDocIpMask OBJECT-TYPE
	SYNTAX IpAddress
	ACCESS read-write
	STATUS mandatory
	DESCRIPTION
	"The mask for management use."
	::= { dv2QeDoc 8 }

qeDocIpBCast OBJECT-TYPE
	SYNTAX IpAddress
	ACCESS read-write
	STATUS mandatory
	DESCRIPTION
	"The management broadcast address."
	::= { dv2QeDoc 9 }


--___________________________________________________________________________
-- The SDHSonet config table

sdhCTable OBJECT-TYPE
	SYNTAX SEQUENCE OF SdhCEntry
	ACCESS not-accessible
	STATUS mandatory
	DESCRIPTION
	"This table is used to control sdh/Sonet configuration."
	::= { dv2SDH 1 }

sdhCEntry OBJECT-TYPE
	SYNTAX	SdhCEntry
	ACCESS	not-accessible
	STATUS	mandatory
        INDEX   { sdhCLinkNo }
	::= { sdhCTable 1 }

SdhCEntry ::=
	SEQUENCE {
		sdhCLinkNo
			INTEGER,
		sdhCLinkEnab
			INTEGER,
		sdhCLoopTimer
			INTEGER,
		sdhCLoopDiag
			INTEGER,
		sdhCLoopLine
			INTEGER,
		sdhCScrambler
			INTEGER,
		sdhC0x55
			INTEGER,
		sdhSonetSdh
			INTEGER,
		sdhClearCounts
			INTEGER,
		sdhReconfig
			INTEGER,
		sdhCLpbkTimeout
			INTEGER,
		sdhStmSts    
			INTEGER,
		sdhAPSOnOff
			INTEGER,
		sdhCIdleCell
			INTEGER
}


sdhCLinkNo	OBJECT-TYPE
	SYNTAX INTEGER (0..1)
	ACCESS read-only
	STATUS mandatory
	DESCRIPTION
	"The link number for this configuration."
	::= { sdhCEntry 1 }

sdhCLinkEnab	OBJECT-TYPE
	SYNTAX INTEGER {
		yes(1),
		no(2)
	}
	ACCESS read-write
	STATUS mandatory
	DESCRIPTION
	"Set to yes(1) to enable the link."
	::= { sdhCEntry 2 }

sdhCLoopTimer	OBJECT-TYPE
	SYNTAX INTEGER {
		no(2),
		yes(1)
	}
	ACCESS read-write
	STATUS mandatory
	DESCRIPTION
	"Set to yes(1) to enable loop timing for this link."
	::= { sdhCEntry 3 }

sdhCLoopDiag OBJECT-TYPE
	SYNTAX INTEGER {
		no(2),
		yes(1)
	}
	ACCESS read-write
	STATUS mandatory
	DESCRIPTION
	"Set to yes(1) to enable diagnostic loopback."
	::= { sdhCEntry 4 }

sdhCLoopLine OBJECT-TYPE
	SYNTAX INTEGER {
		no(2),
		yes(1)
	}
	ACCESS read-write
	STATUS mandatory
	DESCRIPTION
	"Set to yes(1) to enable line loopback."
	::= { sdhCEntry 5 }

sdhCScrambler	OBJECT-TYPE
	SYNTAX INTEGER {
		yes(1),
		no(2)
	}
	ACCESS read-write
	STATUS mandatory
	DESCRIPTION
	"Set to no(2) to disable scramble mode for this link."
	::= { sdhCEntry 6 }

sdhC0x55	OBJECT-TYPE
	SYNTAX INTEGER {
		yes(1),
		no(2)
	}
	ACCESS read-write
	STATUS mandatory
	DESCRIPTION
	"If set to no(2) then HCS is XORed with 0x55"
	::= { sdhCEntry 7 }

sdhSonetSdh	OBJECT-TYPE
	SYNTAX INTEGER {
		sonet(1),
		sdh(2)
	}
	ACCESS read-write
	STATUS mandatory
	DESCRIPTION
	"If set to sdh(2) then sdh header is used"
	::= { sdhCEntry 8 }

sdhClearCounts	OBJECT-TYPE
	SYNTAX INTEGER {
		no(2),
		yes(1)
	}
	ACCESS read-write
	STATUS mandatory
	DESCRIPTION
	"Clear Error Counts and Performance Parameters"
	::= { sdhCEntry 9 }

sdhReconfig 	OBJECT-TYPE
	SYNTAX INTEGER {
		no(2),
		yes(1)
	}
	ACCESS read-write
	STATUS mandatory
	DESCRIPTION
	"Perform Reconfiguration for Link"
	::= { sdhCEntry 10 }

sdhCLpbkTimeout	OBJECT-TYPE
	SYNTAX	INTEGER (1..604800)
	ACCESS	read-write
	STATUS	mandatory
	DESCRIPTION
	"This parameter is used to set the loopback timeout in minutes."
	::= { sdhCEntry 11 }

sdhStmSts       OBJECT-TYPE
        SYNTAX INTEGER {
                oc-3(1),
                oc-1(2)
        }
        ACCESS read-write
        STATUS mandatory
        DESCRIPTION
        "Set to 155.52(1) for STS-3c/STM-1 format"
        DEFVAL { oc-3 }
        ::= { sdhCEntry 12 }

sdhAPSOnOff	OBJECT-TYPE
	SYNTAX INTEGER {
		off(1),
		on(2)
	}
	ACCESS read-write
	STATUS mandatory
	DESCRIPTION
	"If set to on(2) then sdh APS is used"
	DEFVAL { off }
	::= { sdhCEntry 13 }

sdhCIdleCell OBJECT-TYPE
	SYNTAX INTEGER {
	        unassigned(1),
	        idle(2)
	}
	ACCESS read-write
	STATUS mandatory
	DESCRIPTION
	"Idle Cell Header Contents"
	::= { sdhCEntry 14 }

--___________________________________________________________________________
-- The sdh status table

-- Depricate old sdh status table
--sdhSTable OBJECT-TYPE
--	SYNTAX SEQUENCE OF SdhSEntry
--	ACCESS not-accessible
--	STATUS mandatory
--	DESCRIPTION
--	"The status table for sdh/SONET."
--	::= { dv2SDH 2 }

sdhSTable OBJECT-TYPE
	SYNTAX SEQUENCE OF SdhSEntry
	ACCESS not-accessible
	STATUS mandatory
	DESCRIPTION
	"The status table for sdh/SONET."
	::= { dv2SDH 3 }

sdhSEntry OBJECT-TYPE
	SYNTAX	SdhSEntry
	ACCESS	not-accessible
	STATUS	mandatory
        INDEX   { sdhSLinkNo }
	::= { sdhSTable 1 }

SdhSEntry ::=
	SEQUENCE {
		sdhSLinkNo
			INTEGER,
		sdhSTXclock
			INTEGER,
		sdhSRXclock
			INTEGER,
-- Defects(section, line, path)
		sdhSSectLOS
			INTEGER,
		sdhSSectOOF
			INTEGER,
		sdhSSectLOF
			INTEGER,
		sdhSLineAIS
			INTEGER,
		sdhSLineFERF
			INTEGER,
		sdhSPathAIS
			INTEGER,
		sdhSPathYellow
			INTEGER,
		sdhSPathFERF
			INTEGER,
		sdhSPathLOP
			INTEGER,
		sdhSPathLabelMM
			INTEGER,
		sdhSExBERDefect
			INTEGER,
-- misc status'
		sdhSPathLabel
			INTEGER,
		sdhSCellDelState
			INTEGER,
-- Alarms(section, line, path)
		sdhSAlarmLOS
			INTEGER,
		sdhSAlarmLOF
			INTEGER,
		sdhSAlarmLineAIS
			INTEGER,
 		sdhSAlarmLineRFI
 			INTEGER,
		sdhSAlarmPathAIS
			INTEGER,
 		sdhSAlarmPathRFI
			INTEGER,
		sdhSAlarmLOP
			INTEGER,
		sdhSAlarmPLM
 			INTEGER,
		sdhSExBERAlarm
			INTEGER,
-- cell counts
		sdhSCorrHCS
			Counter,
		sdhSUnCorrHCS
			Counter
}


sdhSLinkNo	OBJECT-TYPE
	SYNTAX INTEGER (0..1)
	ACCESS read-only
	STATUS mandatory
	DESCRIPTION
	"The link number for this status."
	::= { sdhSEntry 1 }

sdhSTXclock	OBJECT-TYPE
	SYNTAX INTEGER {
		up(1),
		down(2)
	}
	ACCESS read-only
	STATUS mandatory
	DESCRIPTION
	"The state of TX clock for this link."
	::= { sdhSEntry 2 }

sdhSRXclock	OBJECT-TYPE
	SYNTAX INTEGER {
		up(1),
		down(2)
	}
	ACCESS read-only
	STATUS mandatory
	DESCRIPTION
	"The state of RX clock for this link."
	::= { sdhSEntry 3 }

sdhSSectLOS	OBJECT-TYPE
	SYNTAX INTEGER {
		yes(1),
		no(2)
	}
	ACCESS read-only
	STATUS mandatory
	DESCRIPTION
	"The loss of signal indicator."
	::= { sdhSEntry 4 }

sdhSSectOOF	OBJECT-TYPE
	SYNTAX INTEGER {
		yes(1),
		no(2)
	}
	ACCESS read-only
	STATUS mandatory
	DESCRIPTION
	"The out of frame indicator."
	::= { sdhSEntry 5 }

sdhSSectLOF	OBJECT-TYPE
	SYNTAX INTEGER {
		yes(1),
		no(2)
	}
	ACCESS read-only
	STATUS mandatory
	DESCRIPTION
	"The loss of frame indicator."
	::= { sdhSEntry 6 }

sdhSLineAIS	OBJECT-TYPE
	SYNTAX INTEGER {
		yes(1),
		no(2)
	}
	ACCESS read-only
	STATUS mandatory
	DESCRIPTION
	"Set to yes(1) if Line AIS detected."
	::= { sdhSEntry 7 }

sdhSLineFERF	OBJECT-TYPE
	SYNTAX INTEGER {
		yes(1),
		no(2)
	}
	ACCESS read-only
	STATUS mandatory
	DESCRIPTION
	"Set to yes(1) if Line FERF detected."
	::= { sdhSEntry 8 }


sdhSPathAIS	OBJECT-TYPE
	SYNTAX INTEGER{
		yes(1),
		no(2)
	}
	ACCESS read-only
	STATUS mandatory
	DESCRIPTION
	"Set to yes(1) if Alarm Indication Signal detected."
	::= { sdhSEntry 9 }

sdhSPathYellow	OBJECT-TYPE
	SYNTAX INTEGER{
		yes(1),
		no(2)
	}
	ACCESS read-only
	STATUS mandatory
	DESCRIPTION
	"Set to yes(1) if yellow alarm active."
	::= { sdhSEntry 10 }

sdhSPathFERF	OBJECT-TYPE
	SYNTAX INTEGER {
		yes(1),
		no(2)
	}
	ACCESS read-only
	STATUS mandatory
	DESCRIPTION
	"Set to yes(1) if Far End Receive Failure detected."
	::= { sdhSEntry 11 }

sdhSPathLOP	OBJECT-TYPE
	SYNTAX INTEGER {
		yes(1),
		no(2)
	}
	ACCESS read-only
	STATUS mandatory
	DESCRIPTION
	"Set to yes(1) if Loss Of Pointer detected."
	::= { sdhSEntry 12 }

sdhSPathLabelMM	OBJECT-TYPE
	SYNTAX INTEGER {
		yes(1),
		no(2)
	}
	ACCESS read-only
	STATUS mandatory
	DESCRIPTION
	"Set to yes(1) if a Path Label Mismatch is detected"
	::= { sdhSEntry 13 }

sdhSExBERDefect	OBJECT-TYPE
	SYNTAX INTEGER {
		yes(1),
		no(2)
	}
	ACCESS read-only
	STATUS mandatory
	DESCRIPTION
	"Excessive Bit Error Rate Defect"
	::= { sdhSEntry 14 }

sdhSPathLabel	OBJECT-TYPE
	SYNTAX INTEGER {
		atm(1),
		non-atm(2)
	}
	ACCESS read-only
	STATUS mandatory
	DESCRIPTION
	"The Path Label."
	::= { sdhSEntry 15 }

sdhSCellDelState OBJECT-TYPE
	SYNTAX INTEGER {
		hunt-or-presync(1),
		sync(2)
	}
	ACCESS read-only
	STATUS mandatory
	DESCRIPTION
	"The Cell Delineation State"
	::= { sdhSEntry 16 }

sdhSAlarmLOS	OBJECT-TYPE
	SYNTAX INTEGER {
		yes(1),
		no(2)
	}
	ACCESS read-only
	STATUS mandatory
	DESCRIPTION
	"Set to yes(1) if a LOS failure is declared"
	::= { sdhSEntry 17 }

sdhSAlarmLOF	OBJECT-TYPE
	SYNTAX INTEGER {
		yes(1),
		no(2)
	}
	ACCESS read-only
	STATUS mandatory
	DESCRIPTION
	"Set to yes(1) if a LOF failure is declared"
	::= { sdhSEntry 18 }

sdhSAlarmLineAIS	OBJECT-TYPE
	SYNTAX INTEGER {
		yes(1),
		no(2)
	}
	ACCESS read-only
	STATUS mandatory
	DESCRIPTION
	"Set to yes(1) if a Line AIS failure is declared"
	::= { sdhSEntry 19 }

sdhSAlarmLineRFI	OBJECT-TYPE
	SYNTAX INTEGER {
		yes(1),
		no(2)
	}
	ACCESS read-only
	STATUS mandatory
	DESCRIPTION
	"Set to yes(1) if a Line Remote Failure Indication (Yellow Alarm) failure is declared"
	::= { sdhSEntry 20 }

sdhSAlarmPathAIS	OBJECT-TYPE
	SYNTAX INTEGER {
		yes(1),
		no(2)
	}
	ACCESS read-only
	STATUS mandatory
	DESCRIPTION
	"Set to yes(1) if a Path AIS failure is declared"
	::= { sdhSEntry 21 }

sdhSAlarmPathRFI	OBJECT-TYPE
	SYNTAX INTEGER {
		yes(1),
		no(2)
	}
	ACCESS read-only
	STATUS mandatory
	DESCRIPTION
	"Set to yes(1) if a Path Remote Failure Indication (Yellow Alarm) failure is declared"
	::= { sdhSEntry 22 }

sdhSAlarmLOP	OBJECT-TYPE
	SYNTAX INTEGER {
		yes(1),
		no(2)
	}
	ACCESS read-only
	STATUS mandatory
	DESCRIPTION
	"Set to yes(1) if a LOP failure is declared"
	::= { sdhSEntry 23 }

sdhSAlarmPLM	OBJECT-TYPE
	SYNTAX INTEGER {
		yes(1),
		no(2)
	}
	ACCESS read-only
	STATUS mandatory
	DESCRIPTION
	"Set to yes(1) if a Payload Mismatch failure is declared"
	::= { sdhSEntry 24 }

sdhSExBERAlarm	OBJECT-TYPE
	SYNTAX INTEGER {
		yes(1),
		no(2)
	}
	ACCESS read-only
	STATUS mandatory
	DESCRIPTION
	"Excessive Bit Error Rate Alarm"
	::= { sdhSEntry 25 }

sdhSCorrHCS	OBJECT-TYPE
	SYNTAX Counter
	ACCESS read-only
	STATUS mandatory
	DESCRIPTION
	"The correctable HCS errors count."
	::= { sdhSEntry 26 }

sdhSUnCorrHCS	OBJECT-TYPE
	SYNTAX Counter
	ACCESS read-only
	STATUS mandatory
	DESCRIPTION
	"The uncorrectable HCS errors count."
	::= { sdhSEntry 27 }



--___________________________________________________________________________
-- The sdh performance monitoring table

sdhS2Table OBJECT-TYPE
	SYNTAX SEQUENCE OF SdhS2Entry
	ACCESS not-accessible
	STATUS mandatory
	DESCRIPTION
	"The second status table for sdh/SONET."
	::= { dv2SDH 4 }

sdhS2Entry OBJECT-TYPE
	SYNTAX	SdhS2Entry
	ACCESS	not-accessible
	STATUS	mandatory
        INDEX   { sdhS2LinkNo }
	::= { sdhS2Table 1 }

SdhS2Entry ::=
	SEQUENCE
	{
		sdhS2LinkNo
			INTEGER,
-- Section near-end performance parameters
		sdhSSectBIP8
			Counter,
 		sdhSSectES
			Counter,
 		sdhSSectSES
			Counter,
-- Line near-end performance parameters
		sdhSLineBIP24
			Counter,
 		sdhSLineES
			Counter,
 		sdhSLineSES
			Counter,
 		sdhSLineUAS
			Counter,
 		sdhSLineFC
			Counter,
-- Path near-end performance parameters
		sdhSPathBIP8
			Counter,
 		sdhSPathES
			Counter,
 		sdhSPathSES
			Counter,
 		sdhSPathUAS
			Counter,
 		sdhSPathFC
			Counter,
-- Line far-end performance parameters
		sdhSLineFEBE
			Counter,
 		sdhSLineFarEndES
			Counter,
 		sdhSLineFarEndSES
			Counter,
 		sdhSLineFarEndUAS
			Counter,
 		sdhSLineFarEndFC
			Counter,
-- Path	far-end performance parameters
		sdhSPathFEBE
			Counter,
 		sdhSPathFarEndES
			Counter,
 		sdhSPathFarEndSES
			Counter,
 		sdhSPathFarEndUAS
			Counter,
 		sdhSPathFarEndFC
			Counter
	}

sdhS2LinkNo	OBJECT-TYPE
	SYNTAX INTEGER (0..1)
	ACCESS read-only
	STATUS mandatory
	DESCRIPTION
	"The link number for this status."
	::= { sdhS2Entry 1 }

sdhSSectBIP8	OBJECT-TYPE
	SYNTAX Counter
	ACCESS read-only
	STATUS mandatory
	DESCRIPTION
	"Section BIP-8 error count."
	::= { sdhS2Entry 2 }

sdhSSectES	OBJECT-TYPE
	SYNTAX Counter
	ACCESS read-only
	STATUS mandatory
	DESCRIPTION
	"Section Errored Seconds"
	::= { sdhS2Entry 3 }

sdhSSectSES	OBJECT-TYPE
	SYNTAX Counter
	ACCESS read-only
	STATUS mandatory
	DESCRIPTION
	"Section Severely Errored Seconds"
	::= { sdhS2Entry 4 }

sdhSLineBIP24	OBJECT-TYPE
	SYNTAX Counter
	ACCESS read-only
	STATUS mandatory
	DESCRIPTION
	"Line BIP-24 error count."
	::= { sdhS2Entry 5 }

sdhSLineES	OBJECT-TYPE
	SYNTAX Counter
	ACCESS read-only
	STATUS mandatory
	DESCRIPTION
	"Line Errored Seconds"
	::= { sdhS2Entry 6 }

sdhSLineSES	OBJECT-TYPE
	SYNTAX Counter
	ACCESS read-only
	STATUS mandatory
	DESCRIPTION
	"Line Severely Errored Seconds"
	::= { sdhS2Entry 7 }

sdhSLineUAS	OBJECT-TYPE
	SYNTAX Counter
	ACCESS read-only
	STATUS mandatory
	DESCRIPTION
	"Line Unavailable Seconds"
	::= { sdhS2Entry 8 }

sdhSLineFC	OBJECT-TYPE
	SYNTAX Counter
	ACCESS read-only
	STATUS mandatory
	DESCRIPTION
	"Line Failure Count"
	::= { sdhS2Entry 9 }

sdhSPathBIP8	OBJECT-TYPE
	SYNTAX Counter
	ACCESS read-only
	STATUS mandatory
	DESCRIPTION
	"The path BIP-8 count."
	::= { sdhS2Entry 10 }

sdhSPathES	OBJECT-TYPE
	SYNTAX Counter
	ACCESS read-only
	STATUS mandatory
	DESCRIPTION
	"Path Errored Seconds"
	::= { sdhS2Entry 11 }

sdhSPathSES	OBJECT-TYPE
	SYNTAX Counter
	ACCESS read-only
	STATUS mandatory
	DESCRIPTION
	"Path Severely Errored Seconds"
	::= { sdhS2Entry 12 }

sdhSPathUAS	OBJECT-TYPE
	SYNTAX Counter
	ACCESS read-only
	STATUS mandatory
	DESCRIPTION
	"Path Unavailable Seconds"
	::= { sdhS2Entry 13 }

sdhSPathFC	OBJECT-TYPE
	SYNTAX Counter
	ACCESS read-only
	STATUS mandatory
	DESCRIPTION
	"Path Failure Count"
	::= { sdhS2Entry 14 }

sdhSLineFEBE	OBJECT-TYPE
	SYNTAX Counter
	ACCESS read-only
	STATUS mandatory
	DESCRIPTION
	"Far end block errors."
	::= { sdhS2Entry 15 }

sdhSLineFarEndES	OBJECT-TYPE
	SYNTAX Counter
	ACCESS read-only
	STATUS mandatory
	DESCRIPTION
	"Far End Line Errored Seconds"
	::= { sdhS2Entry 16 }

sdhSLineFarEndSES	OBJECT-TYPE
	SYNTAX Counter
	ACCESS read-only
	STATUS mandatory
	DESCRIPTION
	"Far End Line Severely Errored Seconds"
	::= { sdhS2Entry 17 }

sdhSLineFarEndUAS	OBJECT-TYPE
	SYNTAX Counter
	ACCESS read-only
	STATUS mandatory
	DESCRIPTION
	"Far End Line Unavailable Seconds"
	::= { sdhS2Entry 18 }

sdhSLineFarEndFC	OBJECT-TYPE
	SYNTAX Counter
	ACCESS read-only
	STATUS mandatory
	DESCRIPTION
	"Far End Line Failure Count"
	::= { sdhS2Entry 19 }

sdhSPathFEBE	OBJECT-TYPE
	SYNTAX Counter
	ACCESS read-only
	STATUS mandatory
	DESCRIPTION
	"The Path Far End Block Error count."
	::= { sdhS2Entry 20 }

sdhSPathFarEndES	OBJECT-TYPE
	SYNTAX Counter
	ACCESS read-only
	STATUS mandatory
	DESCRIPTION
	"Far End Path Errored Second"
	::= { sdhS2Entry 21 }

sdhSPathFarEndSES	OBJECT-TYPE
	SYNTAX Counter
	ACCESS read-only
	STATUS mandatory
	DESCRIPTION
	"Far End Path Severely Errored Seconds"
	::= { sdhS2Entry 22 }

sdhSPathFarEndUAS	OBJECT-TYPE
	SYNTAX Counter
	ACCESS read-only
	STATUS mandatory
	DESCRIPTION
	"Far End Path Unavailable Seconds"
	::= { sdhS2Entry 23 }

sdhSPathFarEndFC	OBJECT-TYPE
	SYNTAX Counter
	ACCESS read-only
	STATUS mandatory
	DESCRIPTION
	"Far End Path Failure Count"
	::= { sdhS2Entry 24 }


--___________________________________________________________________________
-- The Pvc group

pvcResourceTable OBJECT-TYPE
	SYNTAX SEQUENCE OF PvcResourceEntry
	ACCESS not-accessible
	STATUS mandatory
	DESCRIPTION
	"This table contains information about the resource available for pvcs on each link."
	::= { dv2Pvc 1 }

pvcResourceEntry OBJECT-TYPE
	SYNTAX PvcResourceEntry
	ACCESS not-accessible
	STATUS mandatory
	INDEX { pvcSlot,
		pvcLink }
	::= { pvcResourceTable 1 }

PvcResourceEntry ::= SEQUENCE {
		pvcSlot
			INTEGER (0..15),
		pvcLink
			INTEGER,
		pvcVciStart
			VirtualCircuitIdentifier,
		pvcVciEnd
			VirtualCircuitIdentifier,
		pvcVpiStart
			VirtualPathIdentifier,
		pvcVpiEnd
			VirtualPathIdentifier,
		pvcVpStart
			VirtualPathIdentifier,
		pvcVpEnd
			VirtualPathIdentifier,
--		pvcForwardCellRateTotal
--			INTEGER (0..16777215),
--		pvcForwardCellRateAvailable
--			INTEGER (0..16777215),
		pvcBackwardCellRateTotal
			INTEGER (0..16777215),
--		pvcBackwardCellRateAvailable
--			INTEGER (0..16777215),
		pvcLinkQoS
			INTEGER,
		pvcMolnVci
			INTEGER,
		pvcMolnVpi
			INTEGER,
		pvcLowPriOverbookFactor
			INTEGER

	}

pvcSlot OBJECT-TYPE
	SYNTAX INTEGER (0..15)
	ACCESS read-only
	STATUS mandatory
	DESCRIPTION
	"The slot number."
	::= { pvcResourceEntry 1 }

pvcLink OBJECT-TYPE
	SYNTAX INTEGER (0..3)
	ACCESS read-only
	STATUS mandatory
	DESCRIPTION
	"The link number being used for the call."
	::= { pvcResourceEntry 2 }

pvcVciStart OBJECT-TYPE
	SYNTAX VirtualCircuitIdentifier
	ACCESS read-write
	STATUS mandatory
	DESCRIPTION
	"Identifies the start of the range of PVC VCI values supported on this link."
	::= { pvcResourceEntry 3 }

pvcVciEnd OBJECT-TYPE
	SYNTAX VirtualCircuitIdentifier
	ACCESS read-write
	STATUS mandatory
	DESCRIPTION
	"Identifies the end of the range of PVC VCI values supported on this link."
	::= { pvcResourceEntry 4 }

pvcVpiStart OBJECT-TYPE
	SYNTAX VirtualPathIdentifier
	ACCESS read-write
	STATUS mandatory
	DESCRIPTION
	"Identifies the start of the range of PVC VPI values supported on this link."
	::= { pvcResourceEntry 5 }

pvcVpiEnd OBJECT-TYPE
	SYNTAX VirtualPathIdentifier
	ACCESS read-write
	STATUS mandatory
	DESCRIPTION
	"Identifies the end of the range of PVC VPI values supported on this link."
	::= { pvcResourceEntry 6 }

pvcVpStart OBJECT-TYPE
	SYNTAX VirtualPathIdentifier
	ACCESS read-write
	STATUS mandatory
	DESCRIPTION
	"Identifies the start of the range of VPs supported on this link."
	::= { pvcResourceEntry 7 }

pvcVpEnd OBJECT-TYPE
	SYNTAX VirtualPathIdentifier
	ACCESS read-write
	STATUS mandatory
	DESCRIPTION
	"Identifies the end of the range of VPs supported on this link."
	::= { pvcResourceEntry 8 }

--pvcForwardCellRateTotal OBJECT-TYPE
--	SYNTAX INTEGER (0..16777215)
--	ACCESS read-write
--	STATUS mandatory
--	DESCRIPTION
--	"The forward total cell rate configured for PVCs on this link. Note that this object is in cells per second (CPS)."
--	::= { pvcResourceEntry 9 }

--pvcForwardCellRateAvailable OBJECT-TYPE
--	SYNTAX INTEGER (0..16777215)
--	ACCESS read-only
--	STATUS mandatory
--	DESCRIPTION
--	"The forward cell rate available for PVCs on this link. Note that this object is in cells per second (CPS)."
--	::= { pvcResourceEntry 10 }

pvcBackwardCellRateTotal OBJECT-TYPE
	SYNTAX INTEGER (0..16777215)
	ACCESS read-write
	STATUS mandatory
	DESCRIPTION
	"The backward total cell rate configured for PVCs on this link. Note that this object is in cells per second (CPS)."
	::= { pvcResourceEntry 11 }

--pvcBackwardCellRateAvailable OBJECT-TYPE
--	SYNTAX INTEGER (0..16777215)
--	ACCESS read-only
--	STATUS mandatory
--	DESCRIPTION
--	"The backward cell rate available for PVCs on this link. Note that this object is in cells per second (CPS)."
--	::= { pvcResourceEntry 12 }

pvcLinkQoS OBJECT-TYPE
	SYNTAX INTEGER
	{
		uni(1),
		nni(2),
		b-ici(3),
		non-atm-link(4)
	}
	ACCESS read-write
	STATUS mandatory
	DESCRIPTION
	"This specifies the type of ATM link."
	::= { pvcResourceEntry 13 }

pvcMolnVpi OBJECT-TYPE
	SYNTAX INTEGER (0..255)
	ACCESS read-write
	STATUS mandatory
	DESCRIPTION
	"This is the VPI for the management overlay network."
	::= {pvcResourceEntry 14 }

pvcMolnVci OBJECT-TYPE
	SYNTAX INTEGER (0..255)
	ACCESS read-write
	STATUS mandatory
	DESCRIPTION
	"This is the VCI for the management overlay network."
	DEFVAL { 16 }
	::= {pvcResourceEntry 15 }

pvcLowPriOverbookFactor OBJECT-TYPE
	SYNTAX INTEGER (0..10000)
	ACCESS read-write
	STATUS mandatory
	DESCRIPTION
	"This is the percentage of low priority traffic overbook factor."
	DEFVAL { 0 }
	::= {pvcResourceEntry 16 }


pvcTable OBJECT-TYPE
	SYNTAX SEQUENCE OF PvcEntry
	ACCESS not-accessible
	STATUS mandatory
	DESCRIPTION
	"This table contains information on each PVC."
	::= { dv2Pvc 2 }

pvcEntry OBJECT-TYPE
	SYNTAX PvcEntry
	ACCESS not-accessible
	STATUS mandatory
	INDEX { pvcDSlot,
		pvcDLink,
		pvcDvci,
		pvcDvpi,
		pvcSSlot,
		pvcSLink,
		pvcSvci,
		pvcSvpi }
	::= { pvcTable 1 }

PvcEntry ::= SEQUENCE {
		pvcDSlot
			INTEGER (0..15),
		pvcDLink
			INTEGER (0..3),
		pvcDvci
			VirtualCircuitIdentifier,
		pvcDvpi
			VirtualPathIdentifier,
		pvcSSlot
			INTEGER (0..15),
		pvcSLink
			INTEGER (0..3),
		pvcSvci
			VirtualCircuitIdentifier,
		pvcSvpi
			VirtualPathIdentifier,
		pvcForwardPeakCellRate
			INTEGER (0..16777215),
		pvcForwardPeakSize
			INTEGER (0..16777215),
		pvcForwardPeakMode
			INTEGER,
		pvcBackwardPeakCellRate
			INTEGER (0..16777215),
		pvcBackwardPeakSize
			INTEGER (0..16777215),
		pvcBackwardPeakMode
			INTEGER,
		pvcForwardSustainedCellRate
			INTEGER (0..16777215),
		pvcForwardSustainedSize
			INTEGER (0..16777215),
		pvcForwardSustainedMode
			INTEGER,
		pvcBackwardSustainedCellRate
			INTEGER (0..16777215),
		pvcBackwardSustainedSize
			INTEGER (0..16777215),
		pvcBackwardSustainedMode
			INTEGER,
		pvcAuxForwardPeakCellRate
			INTEGER (0..16777215),
		pvcAuxForwardPeakSize
			INTEGER (0..16777215),
		pvcAuxForwardPeakMode
			INTEGER,
		pvcAuxBackwardPeakCellRate
			INTEGER (0..16777215),
		pvcAuxBackwardPeakSize
			INTEGER (0..16777215),
		pvcAuxBackwardPeakMode
			INTEGER,
		pvcAuxForwardSustainedCellRate
			INTEGER (0..16777215),
		pvcAuxForwardSustainedSize
			INTEGER (0..16777215),
		pvcAuxForwardSustainedMode
			INTEGER,
		pvcAuxBackwardSustainedCellRate
			INTEGER (0..16777215),
		pvcAuxBackwardSustainedSize
			INTEGER (0..16777215),
		pvcAuxBackwardSustainedMode
			INTEGER,
		pvcQoSClass
			INTEGER,
		pvcStatus
			INTEGER,
		pvcMulticast
			INTEGER,
		pvcInternalVpi
			INTEGER,
		pvcInternalVci
			INTEGER,
		pvcNumLeaves
			INTEGER,
		pvcDirection
			INTEGER
	}


pvcDSlot OBJECT-TYPE
	SYNTAX INTEGER (0..15)
	ACCESS read-write
	STATUS mandatory
	DESCRIPTION
	"The destination slot for the PVC."
	::= { pvcEntry 1 }

pvcDLink OBJECT-TYPE
	SYNTAX INTEGER (0..3)
	ACCESS read-write
	STATUS mandatory
	DESCRIPTION
	"The destination link for the PVC."
	::= { pvcEntry 2 }

pvcDvci OBJECT-TYPE
	SYNTAX VirtualCircuitIdentifier
	ACCESS read-write
	STATUS mandatory
	DESCRIPTION
	"The destination virtual circuit identifier for the PVC."
	::= { pvcEntry 3 }

pvcDvpi OBJECT-TYPE
	SYNTAX VirtualPathIdentifier
	ACCESS read-write
	STATUS mandatory
	DESCRIPTION
	"The destination virtual path identifier for the PVC."
	::= { pvcEntry 4 }

pvcSSlot OBJECT-TYPE
	SYNTAX INTEGER (0..15)
	ACCESS read-write
	STATUS mandatory
	DESCRIPTION
	"The source slot for the PVC."
 	::= { pvcEntry 5 }

pvcSLink OBJECT-TYPE
	SYNTAX INTEGER (0..3)
	ACCESS read-write
	STATUS mandatory
	DESCRIPTION
	"The source link for the PVC."
	::= { pvcEntry 6 }

pvcSvci OBJECT-TYPE
	SYNTAX VirtualCircuitIdentifier
	ACCESS read-write
	STATUS mandatory
	DESCRIPTION
	"The source virtual circuit identifier for the PVC."
	::= { pvcEntry 7 }

pvcSvpi OBJECT-TYPE
	SYNTAX VirtualPathIdentifier
	ACCESS read-write
	STATUS mandatory
	DESCRIPTION
	"The source virtual path identifier for the PVC."
	::= { pvcEntry 8 }

pvcForwardPeakCellRate OBJECT-TYPE
	SYNTAX INTEGER (0..16777215)
	ACCESS read-write
	STATUS mandatory
	DESCRIPTION
	"Forward Peak Cell Rate (CPS)"
	::= { pvcEntry 9 }

pvcForwardPeakSize OBJECT-TYPE
	SYNTAX INTEGER (0..16777215)
	ACCESS read-write
	STATUS mandatory
	DESCRIPTION
	"Forward Peak Bucket Size (Cells)"
	::= { pvcEntry 10 }

pvcForwardPeakMode OBJECT-TYPE
	SYNTAX INTEGER {
		off(1),
		clp0-disc(2),
		clp1-disc(3),
		clp01-disc(4)
	}
	ACCESS read-write
	STATUS mandatory
	DESCRIPTION
	"Forward Peak Mode"
	::= { pvcEntry 11 }

pvcBackwardPeakCellRate OBJECT-TYPE
	SYNTAX INTEGER (0..16777215)
	ACCESS read-write
	STATUS mandatory
	DESCRIPTION
	"Backward Peak Cell Rate (CPS)"
	::= { pvcEntry 12 }

pvcBackwardPeakSize OBJECT-TYPE
	SYNTAX INTEGER (0..16777215)
	ACCESS read-write
	STATUS mandatory
	DESCRIPTION
	"Backward Peak Bucket Size (Cells)"
	::= { pvcEntry 13 }

pvcBackwardPeakMode OBJECT-TYPE
	SYNTAX INTEGER {
		off(1),
		clp0-disc(2),
		clp1-disc(3),
		clp01-disc(4)
	}
	ACCESS read-write
	STATUS mandatory
	DESCRIPTION
	"Backward Peak Mode"
	::= { pvcEntry 14 }

pvcForwardSustainedCellRate OBJECT-TYPE
	SYNTAX INTEGER (0..16777215)
	ACCESS read-write
	STATUS mandatory
	DESCRIPTION
	"Forward Sustained Cell Rate (CPS)"
	::= { pvcEntry 15 }

pvcForwardSustainedSize OBJECT-TYPE
	SYNTAX INTEGER (0..16777215)
	ACCESS read-write
	STATUS mandatory
	DESCRIPTION
	"Forward Sustained Bucket Size (Cells)"
	::= { pvcEntry 16 }

pvcForwardSustainedMode OBJECT-TYPE
	SYNTAX INTEGER {
		off(1),
		clp0-disc(2),
		clp1-disc(3),
		clp01-disc(4),
		clp0-tag(6),
		clp01-tag(8)
	}
	ACCESS read-write
	STATUS mandatory
	DESCRIPTION
	"Forward Sustained Mode"
	::= { pvcEntry 17 }

pvcBackwardSustainedCellRate OBJECT-TYPE
	SYNTAX INTEGER (0..16777215)
	ACCESS read-write
	STATUS mandatory
	DESCRIPTION
	"Backward Sustained Cell Rate (CPS)"
	::= { pvcEntry 18 }

pvcBackwardSustainedSize OBJECT-TYPE
	SYNTAX INTEGER (0..16777215)
	ACCESS read-write
	STATUS mandatory
	DESCRIPTION
	"Backward Sustained Bucket Size (Cells)"
	::= { pvcEntry 19 }

pvcBackwardSustainedMode OBJECT-TYPE
	SYNTAX INTEGER {
		off(1),
		clp0-disc(2),
		clp1-disc(3),
		clp01-disc(4),
		clp0-tag(6),
		clp01-tag(8)
	}
	ACCESS read-write
	STATUS mandatory
	DESCRIPTION
	"Backward Sustained Mode"
	::= { pvcEntry 20 }

pvcAuxForwardPeakCellRate OBJECT-TYPE
	SYNTAX INTEGER (0..16777215)
	ACCESS read-write
	STATUS mandatory
	DESCRIPTION
	"Auxiliary Forward Peak Cell Rate (CPS)"
	::= { pvcEntry 21 }

pvcAuxForwardPeakSize OBJECT-TYPE
	SYNTAX INTEGER (0..16777215)
	ACCESS read-write
	STATUS mandatory
	DESCRIPTION
	"Auxiliary Forward Peak Bucket Size (Cells)"
	::= { pvcEntry 22 }

pvcAuxForwardPeakMode OBJECT-TYPE
	SYNTAX INTEGER {
		off(1),
		clp0-disc(2),
		clp1-disc(3),
		clp01-disc(4)
	}
	ACCESS read-write
	STATUS mandatory
	DESCRIPTION
	"Auxiliary Forward Peak Mode"
	::= { pvcEntry 23 }

pvcAuxBackwardPeakCellRate OBJECT-TYPE
	SYNTAX INTEGER (0..16777215)
	ACCESS read-write
	STATUS mandatory
	DESCRIPTION
	"Auxiliary Backward Peak Cell Rate (CPS)"
	::= { pvcEntry 24 }

pvcAuxBackwardPeakSize OBJECT-TYPE
	SYNTAX INTEGER (0..16777215)
	ACCESS read-write
	STATUS mandatory
	DESCRIPTION
	"Auxiliary Backward Peak Bucket Size (Cells)"
	::= { pvcEntry 25 }

pvcAuxBackwardPeakMode OBJECT-TYPE
	SYNTAX INTEGER {
		off(1),
		clp0-disc(2),
		clp1-disc(3),
		clp01-disc(4)
	}
	ACCESS read-write
	STATUS mandatory
	DESCRIPTION
	"Auxiliary Backward Peak Mode"
	::= { pvcEntry 26 }

pvcAuxForwardSustainedCellRate OBJECT-TYPE
	SYNTAX INTEGER (0..16777215)
	ACCESS read-write
	STATUS mandatory
	DESCRIPTION
	"Auxiliary Forward Sustained Cell Rate (CPS)"
	::= { pvcEntry 27 }

pvcAuxForwardSustainedSize OBJECT-TYPE
	SYNTAX INTEGER (0..16777215)
	ACCESS read-write
	STATUS mandatory
	DESCRIPTION
	"Auxiliary Forward Sustained Bucket Size (Cells)"
	::= { pvcEntry 28 }

pvcAuxForwardSustainedMode OBJECT-TYPE
	SYNTAX INTEGER {
		off(1),
		clp0-disc(2),
		clp1-disc(3),
		clp01-disc(4),
		clp0-tag(6),
		clp01-tag(8)
	}
	ACCESS read-write
	STATUS mandatory
	DESCRIPTION
	"Auxiliary Forward Sustained Mode"
	::= { pvcEntry 29 }

pvcAuxBackwardSustainedCellRate OBJECT-TYPE
	SYNTAX INTEGER (0..16777215)
	ACCESS read-write
	STATUS mandatory
	DESCRIPTION
	"Auxiliary Backward Sustained Cell Rate (CPS)"
	::= { pvcEntry 30 }

pvcAuxBackwardSustainedSize OBJECT-TYPE
	SYNTAX INTEGER (0..16777215)
	ACCESS read-write
	STATUS mandatory
	DESCRIPTION
	"Auxiliary Backward Sustained Bucket Size"
	::= { pvcEntry 31 }

pvcAuxBackwardSustainedMode OBJECT-TYPE
	SYNTAX INTEGER {
		off(1),
		clp0-disc(2),
		clp1-disc(3),
		clp01-disc(4),
		clp0-tag(6),
		clp01-tag(8)
	}
	ACCESS read-write
	STATUS mandatory
	DESCRIPTION
	"Auxiliary Backward Sustained Mode"
	::= { pvcEntry 32 }


pvcQoSClass OBJECT-TYPE
	SYNTAX INTEGER {
		cbr(1),
		vbr-high(2),
		vbr-med(3),
		vbr-low(4)
	}
	ACCESS read-write
	STATUS mandatory
	DESCRIPTION
	"CBR(1) is a constant bit rate service, vbr-high(2) is variable bit rate with high priority, vbr-med(3) has low priority, vbr-low(4) is a `best effort' service - low priority and the cells may be discard."
	::= { pvcEntry 33 }

pvcStatus OBJECT-TYPE
	SYNTAX INTEGER {
		valid(1),
		invalid(2),
		start-PVC(3),
		notified(4),
		running(5),
		waiting(6)
		}
	ACCESS read-write
	STATUS mandatory
	DESCRIPTION
	"If this object is set to invalid(2), the PVC entry is removed. Set to start-PVC(3) to activate the PVC. When the state changes to running(5) then the PVC is successfully running. (6) pvc restarted"
	::= { pvcEntry 34 }

pvcMulticast OBJECT-TYPE
	SYNTAX INTEGER {
		no(1),
		yes(2)
		}
	ACCESS read-write
	STATUS mandatory
	DESCRIPTION
	"If this object is set to no, multicast is not allowed; otherwise, multicast is allowed."
	::= { pvcEntry 35 }

pvcInternalVpi OBJECT-TYPE
	SYNTAX INTEGER
	ACCESS read-only
	STATUS mandatory
	DESCRIPTION
	"This object indicates the internal VPI value that the source side of multicast tree ranslates its orignal VPI to."
	::= { pvcEntry 36 }

pvcInternalVci OBJECT-TYPE
	SYNTAX INTEGER
	ACCESS read-only
	STATUS mandatory
	DESCRIPTION
	"This object indicates the internal VCI value that the source side of multicast tree ranslates its orignal VCI to."
	::= { pvcEntry 37 }

pvcNumLeaves OBJECT-TYPE
	SYNTAX INTEGER
	ACCESS read-only
	STATUS mandatory
	DESCRIPTION
	"This object indicates the number of leaves this multicast tree currently contains."
	::= { pvcEntry 38 }

pvcDirection OBJECT-TYPE
	SYNTAX INTEGER {
		bidirect(1),
		unidirect(2)
		}
	ACCESS read-write
	STATUS mandatory
	DESCRIPTION
	"This object determines if a multicast PVC is to be unidirectional or bidirectional"
	::= { pvcEntry 39 }

--___________________________________________________________________________
-- The Svc group

svcMaxPtPtConnections OBJECT-TYPE
	SYNTAX INTEGER (0..750)
	ACCESS read-write
	STATUS mandatory
	DESCRIPTION
	"The maximum number of point-to-point connections."
	DEFVAL { 25 }
	::= { dv2Svc 1 }

svcMaxPtMptConnections OBJECT-TYPE
	SYNTAX INTEGER (0..25)
	ACCESS read-write
	STATUS mandatory
	DESCRIPTION
	"The maximum number of point-to-multipoint connections."
	DEFVAL { 3 }
	::= { dv2Svc 2 }

svcMaxPtMptParties OBJECT-TYPE
	SYNTAX INTEGER (0..500)
	ACCESS read-write
	STATUS mandatory
	DESCRIPTION
	"The maximum number of parties in a point-to-multipoint connection."
	DEFVAL { 10 }
	::= { dv2Svc 3 }

--svcIlmiSigVci OBJECT-TYPE
--	SYNTAX VirtualCircuitIdentifier
--	ACCESS read-write
--	STATUS mandatory
--	DESCRIPTION
--	"The VCI used for ILMI address registration."
--	DEFVAL { 16 }
--	::= { dv2Svc 4 }

--svcIlmiSigVpi OBJECT-TYPE
--	SYNTAX VirtualPathIdentifier
--	ACCESS read-write
--	STATUS mandatory
--	DESCRIPTION
--	"The VPI used for ILMI address registration."
--	DEFVAL { 0 }
--	::= { dv2Svc 5 }

svcResourceTable OBJECT-TYPE
	SYNTAX SEQUENCE OF SvcResourceEntry
	ACCESS not-accessible
	STATUS mandatory
	DESCRIPTION
	"This table contains information about the resource available for svcs on each link."
	::= { dv2Svc 6 }

svcResourceEntry OBJECT-TYPE
	SYNTAX SvcResourceEntry
	ACCESS not-accessible
	STATUS mandatory
	INDEX { svcSAP }
	::= { svcResourceTable 1 }

SvcResourceEntry ::= SEQUENCE {
		svcSAP
			INTEGER (0..31),
		svcHiLo
			INTEGER,
		svcVciStart
			INTEGER (32..4095),
		svcVciEnd
			INTEGER (32..4095),
		svcVpiStart
			INTEGER (0..255),
		svcVpiEnd
			INTEGER (0..255),
		svcVpStart
			INTEGER (0..255),
		svcVpEnd
			INTEGER (0..255),
--		svcForwardCellRateTotal
--			INTEGER (0..16777215),
--		svcForwardCellRateAvailable
--			INTEGER (0..16777215),
		svcBackwardCellRateTotal
			INTEGER (0..16777215),
		svcBackwardCellRateAvailable
			INTEGER (0..16777215),
		svcSigVci
			INTEGER (0..511),
		svcSigVpi
			INTEGER (0..255),
		svcSAPStatus
			INTEGER,
		svcCDVTSize
			INTEGER,
		svcIntType
			INTEGER,
		svcPolicing
			INTEGER,
		svcLowPriOverbookFactor
			INTEGER,
		svcMaxSapConn
			INTEGER,
		svcCurSapConn
			INTEGER,
		svcLinkNo
			INTEGER (0..3),
		svcVpiMapping
			INTEGER,
		svcQosRoute
			INTEGER,
		svcSwtch
			INTEGER,
		svcRestart
			INTEGER,
		svcE164Addr
			E164,
                svcAutoSapOff
                        INTEGER


	}

svcSAP OBJECT-TYPE
	SYNTAX INTEGER (0..31)
	ACCESS read-only
	STATUS mandatory
	DESCRIPTION
	"Identifies the SAP."
	::= { svcResourceEntry 1 }

svcHiLo OBJECT-TYPE
	SYNTAX INTEGER {
		low(2),
		high(1)
	}
	ACCESS read-write
	STATUS mandatory
	DESCRIPTION
	"Select VPI/VCI values from low to high or high to low"
	DEFVAL { low }
	::= { svcResourceEntry 2 }

svcVciStart OBJECT-TYPE
	SYNTAX INTEGER (32..4095)
	ACCESS read-only
	STATUS mandatory
	DESCRIPTION
	"Identifies the start of the range of SVC VCI values supported on this link."
	::= { svcResourceEntry 3 }

svcVciEnd OBJECT-TYPE
	SYNTAX INTEGER (32..4095)
	ACCESS read-only
	STATUS mandatory
	DESCRIPTION
	"Identifies the end of the range of SVC VCI values supported on this link."
	::= { svcResourceEntry 4 }

svcVpiStart OBJECT-TYPE
	SYNTAX INTEGER (0..255)
	ACCESS read-write
	STATUS mandatory
	DESCRIPTION
	"Identifies the start of the range of SVC VPI values supported on this link."
	::= { svcResourceEntry 5 }

svcVpiEnd OBJECT-TYPE
	SYNTAX INTEGER (0..255)
	ACCESS read-write
	STATUS mandatory
	DESCRIPTION
	"Identifies the end of the range of SVC VPI values supported on this link."
	::= { svcResourceEntry 6 }

svcVpStart OBJECT-TYPE
	SYNTAX INTEGER (0..255)
	ACCESS read-write
	STATUS mandatory
	DESCRIPTION
	"Identifies the start of the range of SVPs supported on this link."
	::= { svcResourceEntry 7 }

svcVpEnd OBJECT-TYPE
	SYNTAX INTEGER (0..255)
	ACCESS read-write
	STATUS mandatory
	DESCRIPTION
	"Identifies the end of the range of SVPs supported on this link."
	::= { svcResourceEntry 8 }

--svcForwardCellRateTotal OBJECT-TYPE
--	SYNTAX INTEGER (0..16777215)
--	ACCESS read-write
--	STATUS mandatory
--	DESCRIPTION
--	"The forward total cell rate configured for SVCs on this link. Note that this object is in cells per second (CPS)."
--	::= { svcResourceEntry 9 }

--svcForwardCellRateAvailable OBJECT-TYPE
--	SYNTAX INTEGER (0..16777215)
--	ACCESS read-only
--	STATUS mandatory
--	DESCRIPTION
--	"The forward cell rate available for SVCs on this link. Note that this object is in cells per second (CPS)."
--	::= { svcResourceEntry 10 }

svcBackwardCellRateTotal OBJECT-TYPE
	SYNTAX INTEGER (0..16777215)
	ACCESS read-write
	STATUS mandatory
	DESCRIPTION
	"The backward total cell rate configured for SVCs on this link. Note that this object is in cells per second (CPS)."
	::= { svcResourceEntry 11 }

svcBackwardCellRateAvailable OBJECT-TYPE
	SYNTAX INTEGER (0..16777215)
	ACCESS read-only
	STATUS mandatory
	DESCRIPTION
	"The backward cell rate available for SVCs on this link. Note that this object is in cells per second (CPS)."
	::= { svcResourceEntry 12 }

svcSigVci OBJECT-TYPE
	SYNTAX INTEGER (0..511)
	ACCESS read-write
	STATUS mandatory
	DESCRIPTION
	"The VCI used for signalling."
	DEFVAL { 5 }
	::= { svcResourceEntry 13 }

svcSigVpi OBJECT-TYPE
	SYNTAX INTEGER (0..255)
	ACCESS read-write
	STATUS mandatory
	DESCRIPTION
	"The VPI used for signalling."
	::= { svcResourceEntry  14 }


svcSAPStatus OBJECT-TYPE
	SYNTAX INTEGER {
		off(1),
		reconfigure(2),
		reset(3),
		on(4),
		idle(5)
	}
	ACCESS read-write
	STATUS mandatory
	DESCRIPTION
	"Select on(4) to activate the SAP, off(1) to deactivate, reconfigure(2) to hot reconfigure the vci/vpi ranges and reset(3) to clear all calls on the SAP."
	::= { svcResourceEntry 15 }

svcCDVTSize OBJECT-TYPE
	SYNTAX INTEGER
	ACCESS read-write
	STATUS mandatory
	DESCRIPTION
	"Cell Delay Variation Tolerance size."
	DEFVAL { 4 }
	::= { svcResourceEntry 16 }

svcIntType OBJECT-TYPE
	SYNTAX INTEGER {
		network(1),
		user(2)
	}
	ACCESS read-write
	STATUS mandatory
	DESCRIPTION
	"Interface type - NETWORK or USER."
	::= { svcResourceEntry 17 }

svcPolicing OBJECT-TYPE
	SYNTAX INTEGER {
		on(1),
		off(2)
	}
	ACCESS read-write
	STATUS mandatory
	DESCRIPTION
	"Policing - ON or OFF"
	::= { svcResourceEntry 18 }

svcLowPriOverbookFactor OBJECT-TYPE
	SYNTAX INTEGER (0..10000)
	ACCESS read-write
	STATUS mandatory
	DESCRIPTION
	"This is the percentage of low priority traffic overbook factor."
	DEFVAL { 0 }
	::= {svcResourceEntry 19 }

svcMaxSapConn OBJECT-TYPE
	SYNTAX INTEGER (0..750)
	ACCESS read-write
	STATUS mandatory
	DESCRIPTION
	"Maximum SVCs this SAP"
	DEFVAL { 500 }
	::= {svcResourceEntry 20 }

svcCurSapConn OBJECT-TYPE
	SYNTAX INTEGER
	ACCESS read-only
	STATUS mandatory
	DESCRIPTION
	"Current SVC count this SAP"
	DEFVAL { 0 }
	::= {svcResourceEntry 21 }

svcLinkNo OBJECT-TYPE
	SYNTAX INTEGER (0..3)
	ACCESS read-write
	STATUS mandatory
	DESCRIPTION
	"This is the physical link number associated with this SAP"
	DEFVAL { 0 }
	::= {svcResourceEntry 22 }

svcVpiMapping OBJECT-TYPE
	SYNTAX INTEGER {
		off(1),
		on(2)
		}
	ACCESS read-write
	STATUS mandatory
	DESCRIPTION
	"VPI and VPCI mapping status"
	::= { svcResourceEntry 23 }

svcQosRoute OBJECT-TYPE
	SYNTAX INTEGER {
		off(1),
		on(2)
	}
	ACCESS read-write
	STATUS mandatory
	DESCRIPTION
	"QoS based route"
	::= { svcResourceEntry 24 }

svcSwtch OBJECT-TYPE
	SYNTAX INTEGER {
		uni30(1),
		uni31(2),
		iisp30(3),
		iisp31(4)
	}
	ACCESS read-write
	STATUS mandatory
	DESCRIPTION
	"UNI Interface Type"
	::= {svcResourceEntry 25 }

svcRestart OBJECT-TYPE
	SYNTAX INTEGER {
		off(1),
		on(2)
	}
	ACCESS read-write
	STATUS mandatory
	DESCRIPTION
	"Send Restart when link is up"
	DEFVAL { off }
	::= {svcResourceEntry 26 }

svcE164Addr OBJECT-TYPE
	SYNTAX E164
	ACCESS read-write
	STATUS mandatory
	DESCRIPTION
	"The E.164 address for this SAP"
	::= {svcResourceEntry 27 }

svcAutoSapOff OBJECT-TYPE
        SYNTAX INTEGER {
               yes(1),
               no(2)
        }
        ACCESS read-write
        STATUS mandatory
        DESCRIPTION
        "This option allows a Sap Status to be automatically turned OFF after T309 expiry. Select Yes(1) if a sap (which was ON before) is to be turned OFF after T309 expiry, else select No(2). By default, No(2) is selected."
        DEFVAL { no }
        ::= {svcResourceEntry 28 }

svcTable OBJECT-TYPE
	SYNTAX SEQUENCE OF SvcEntry
	ACCESS not-accessible
	STATUS mandatory
	DESCRIPTION
	"This table contains information on each on SVC."
	::= { dv2Svc 7 }

svcEntry OBJECT-TYPE
	SYNTAX SvcEntry
	ACCESS not-accessible
	STATUS mandatory
	INDEX {	svcId }
	::= { svcTable 1 }

SvcEntry ::= SEQUENCE {
		svcId
			INTEGER,
		svcDSlot
			INTEGER (0..15),
		svcDLink
			INTEGER (0..3),
		svcDvci
			VirtualCircuitIdentifier,
		svcDvpi
			VirtualPathIdentifier,
		svcDE164
			E164,
		svcDE164Sub
			E164SUB,
		svcSSlot
			INTEGER (0..15),
		svcSLink
			INTEGER (0..3),
		svcSvci
			VirtualCircuitIdentifier,
		svcSvpi
			VirtualPathIdentifier,
		svcSE164
			E164,
		svcSE164Sub
			E164SUB,
		svcForwardPeakCellRate
			INTEGER (0..16777215),
		svcForwardPeakMode
			INTEGER,
		svcBackwardPeakCellRate
			INTEGER (0..16777215),
		svcBackwardPeakMode
			INTEGER,
		svcForwardSustainableCellRate
			INTEGER (0..16777215),
		svcForwardMaxBurstSize
			INTEGER (0..16777215),
		svcForwardSustainableMode
			INTEGER,
		svcBackwardSustainableCellRate
			INTEGER (0..16777215),
		svcBackwardMaxBurstSize
			INTEGER (0..16777215),
		svcBackwardSustainableMode
			INTEGER,
		svcQoSClass
			INTEGER,
		svcBillTag
			INTEGER,
		svcDuration
			Counter,
		svcType
			INTEGER,
		svcStatus
			INTEGER,
		svcNumLeaves
			INTEGER,
		svcInternalVpi
			INTEGER,
		svcInternalVci
			INTEGER
	}

svcId OBJECT-TYPE
	SYNTAX INTEGER (0..2147483647)
	ACCESS read-only
	STATUS mandatory
	DESCRIPTION
	"The svc ID number"
	::= { svcEntry 1 }

svcDSlot OBJECT-TYPE
	SYNTAX INTEGER (0..15)
	ACCESS read-only
	STATUS mandatory
	DESCRIPTION
	"The destination slot of the SVC."
	::= { svcEntry 2 }

svcDLink OBJECT-TYPE
	SYNTAX INTEGER (0..3)
	ACCESS read-only
	STATUS mandatory
	DESCRIPTION
	"The destination link of the SVC."
	::= { svcEntry 3 }

svcDvci OBJECT-TYPE
	SYNTAX VirtualCircuitIdentifier
	ACCESS read-only
	STATUS mandatory
	DESCRIPTION
	"The destination virtual circuit identifier for the SVC."
	::= { svcEntry 4 }

svcDvpi OBJECT-TYPE
	SYNTAX VirtualPathIdentifier
	ACCESS read-only
	STATUS mandatory
	DESCRIPTION
	"The destination virtual path identifier for the SVC."
	::= { svcEntry 5 }

svcDE164 OBJECT-TYPE
	SYNTAX E164
	ACCESS read-only
	STATUS mandatory
	DESCRIPTION
	"The destination E.164 address for the SVC."
	::= { svcEntry 6 }

svcDE164Sub OBJECT-TYPE
	SYNTAX E164SUB
	ACCESS read-only
	STATUS mandatory
	DESCRIPTION
	"The destination sub-address for the SVC."
	::= { svcEntry 7 }

svcSSlot OBJECT-TYPE
	SYNTAX INTEGER (0..15)
	ACCESS read-only
	STATUS mandatory
	DESCRIPTION
	"The source slot of the SVC."
	::= { svcEntry 8 }

svcSLink OBJECT-TYPE
	SYNTAX INTEGER (0..3)
	ACCESS read-only
	STATUS mandatory
	DESCRIPTION
	"The source link of the SVC."
	::= { svcEntry 9 }

svcSvci OBJECT-TYPE
	SYNTAX VirtualCircuitIdentifier
	ACCESS read-only
	STATUS mandatory
	DESCRIPTION
	"The source virtual circuit identifier for a SVC."
	::= { svcEntry 10 }

svcSvpi OBJECT-TYPE
	SYNTAX VirtualPathIdentifier
	ACCESS read-only
	STATUS mandatory
	DESCRIPTION
	"The source virtual path identifier for a SVC."
	::= { svcEntry 11 }

svcSE164 OBJECT-TYPE
	SYNTAX E164
	ACCESS read-only
	STATUS mandatory
	DESCRIPTION
	"The source E.164 address for the SVC."
	::= { svcEntry 12 }

svcSE164Sub OBJECT-TYPE
	SYNTAX E164SUB
	ACCESS read-only
	STATUS mandatory
	DESCRIPTION
	"The source sub-address for the SVC."
	::= { svcEntry 13 }

svcForwardPeakCellRate OBJECT-TYPE
	SYNTAX INTEGER (0..16777215)
	ACCESS read-only
	STATUS mandatory
	DESCRIPTION
	"The forward user cell rate for a SVC. The forward user cell rate is a measurement of bandwidth available to the initiating user to transfer information to the responding user."
	::= { svcEntry 14 }

svcForwardPeakMode OBJECT-TYPE
	SYNTAX INTEGER {
		off(1),
		clp0-discard(2),
		clp01-discard(4),
		clp0-tag(6),
		clp01-tag(8)
	}
	ACCESS read-only
	STATUS mandatory
	DESCRIPTION
	"SVC/SVP Forward Peak Mode"
	::= { svcEntry 15 }

svcBackwardPeakCellRate OBJECT-TYPE
	SYNTAX INTEGER (0..16777215)
	ACCESS read-only
	STATUS mandatory
	DESCRIPTION
	"The backward user cell rate for a SVC. The backward user cell rate is a measurement of bandwidth available to the responding user to transfer information to the initiating user."
	::= { svcEntry 16 }

svcBackwardPeakMode OBJECT-TYPE
	SYNTAX INTEGER {
		off(1),
		clp0-discard(2),
		clp01-discard(4),
		clp0-tag(6),
		clp01-tag(8)
	}
	ACCESS read-only
	STATUS mandatory
	DESCRIPTION
	"SVC/SVP Backward Peak Mode"
	::= { svcEntry 17 }

svcForwardSustainableCellRate OBJECT-TYPE
	SYNTAX INTEGER (0..16777215)
	ACCESS read-only
	STATUS mandatory
	DESCRIPTION
	"The sustainable forward cell rate for the SVC."
	::= { svcEntry 18 }

svcForwardMaxBurstSize OBJECT-TYPE
	SYNTAX INTEGER (0..16777215)
	ACCESS read-only
	STATUS mandatory
	DESCRIPTION
	"The forward maximum burst size for the SVC."
	::= { svcEntry 19 }

svcForwardSustainableMode OBJECT-TYPE
	SYNTAX INTEGER {
		off(1),
		clp0-discard(2),
		clp01-discard(4),
		clp0-tag(6),
		clp01-tag(8)
	}
	ACCESS read-only
	STATUS mandatory
	DESCRIPTION
	"SVC/SVP Forward Sustained Mode"
	::= { svcEntry 20 }

svcBackwardSustainableCellRate OBJECT-TYPE
	SYNTAX INTEGER (0..16777215)
	ACCESS read-only
	STATUS mandatory
	DESCRIPTION
	"The sustainable backward cell rate for the SVC."
	::= { svcEntry 21 }

svcBackwardMaxBurstSize OBJECT-TYPE
	SYNTAX INTEGER (0..16777215)
	ACCESS read-only
	STATUS mandatory
	DESCRIPTION
	"The backward maximum burst size for the SVC."
	::= { svcEntry 22 }

svcBackwardSustainableMode OBJECT-TYPE
	SYNTAX INTEGER {
		off(1),
		clp0-discard(2),
		clp01-discard(4),
		clp0-tag(6),
		clp01-tag(8)
	}
	ACCESS read-only
	STATUS mandatory
	DESCRIPTION
	"SVC/SVP Backward Sustained Mode"
	::= { svcEntry 23 }

svcQoSClass OBJECT-TYPE
	SYNTAX INTEGER {
		qos1(1),
		qos2(2),
		qos3(3),
		qos4(4),
		ubrBe(5),
		abr(6),
		cbr(7),
		vbrRt(8),
		vbrNrt(9)
	}
	ACCESS read-only
	STATUS mandatory
	DESCRIPTION
	"CBR(1) is a constant bit rate service, vbr-high(2) is variable bit rate with high priority, vbr-med(3) has low priority, vbr-low(4) is a `best effort' service - low priority and the cells may be discarded."
	::= { svcEntry 24 }

svcBillTag OBJECT-TYPE
	SYNTAX INTEGER
	ACCESS read-only
	STATUS mandatory
	DESCRIPTION
	"This identifies the billable SVC."
	::= { svcEntry 25 }

svcDuration OBJECT-TYPE
	SYNTAX Counter
	ACCESS read-only
	STATUS mandatory
	DESCRIPTION
	"Duration of the SVC in milliseconds."
	::= { svcEntry 26 }

svcType OBJECT-TYPE
	SYNTAX INTEGER {
		point-to-point(1),
		point-to-multipoint(2)
		}
	ACCESS read-only
	STATUS mandatory
	DESCRIPTION
	"The type of SVC."
	::= { svcEntry 27 }

svcStatus OBJECT-TYPE
	SYNTAX INTEGER {
		idle(1),
		invalid(2),
		reset(3),
		active(5)
		}
	ACCESS read-write
	STATUS mandatory
	DESCRIPTION
	"If this object is set to invalid (2), the SVC is cleared and the entry is removed. If set to active(4) then the SVC is active."
	::= { svcEntry 28 }

svcNumLeaves OBJECT-TYPE
	SYNTAX INTEGER
	ACCESS read-only
	STATUS mandatory
	DESCRIPTION
	"Number of multicast leaves"
	::= { svcEntry 29 }

svcInternalVpi OBJECT-TYPE
	SYNTAX INTEGER
	ACCESS read-only
	STATUS mandatory
	DESCRIPTION
	"internal VPI used for multicast operation"
	::= { svcEntry 30 }

svcInternalVci OBJECT-TYPE
	SYNTAX INTEGER
	ACCESS read-only
	STATUS mandatory
	DESCRIPTION
	"internal VCI used for multicast operation"
	::= { svcEntry 31 }

sPvcTable OBJECT-TYPE
	SYNTAX SEQUENCE OF SPvcEntry
	ACCESS not-accessible
	STATUS mandatory
	DESCRIPTION
	"This table contains information on Semi-Permanent Virtual Circuits (SPVCs)."
	::= { dv2Svc 8 }

sPvcEntry OBJECT-TYPE
	SYNTAX SPvcEntry
	ACCESS not-accessible
	STATUS mandatory
	INDEX { sPvcId }
	::= { sPvcTable 1 }

SPvcEntry ::= SEQUENCE {

		sPvcId
			INTEGER,
		sPvcCallId
			INTEGER,
		sPvcLink
			INTEGER,
		sPvcAddress
			E164,
		sPvcForwardPeakCellRate
			INTEGER (0..16777215),
		sPvcForwardPeakMode
			INTEGER,
		sPvcBackwardPeakCellRate
			INTEGER (0..16777215),
		sPvcBackwardPeakMode
			INTEGER,
		sPvcForwardSustainableCellRate
			INTEGER (0..16777215),
		sPvcForwardMaxBurstSize
			INTEGER (0..16777215),
		sPvcForwardSustainableMode
			INTEGER,
		sPvcBackwardSustainableCellRate
			INTEGER (0..16777215),
		sPvcBackwardMaxBurstSize
			INTEGER (0..16777215),
		sPvcBackwardSustainableMode
			INTEGER,
		sPvcQoSClass
			INTEGER,
		sPvcSourceVci
			VirtualCircuitIdentifier,
		sPvcSourceVpi
			VirtualPathIdentifier,
		sPvcTargetVci
			VirtualCircuitIdentifier,
		sPvcTargetVpi
			VirtualPathIdentifier,
		sPvcRetry
			INTEGER (0..1000),
		sPvcConnectTime
			INTEGER,
		sPvcNumberRetries
			INTEGER (0..1000),
		sPvcFailures
			INTEGER,
		sPvcAlertFailures
			INTEGER,
		sPvcCauseDiag
			Q93bCauseDiag,
		sPvcType
			INTEGER,
		sPvcCallState
			INTEGER,
		sPvcStatus
			INTEGER,
		sPvcCauseDiagCode
			INTEGER,
		sPvcMulticast
			INTEGER
	}

sPvcId OBJECT-TYPE
	SYNTAX INTEGER (1..750)
	ACCESS read-write
	STATUS mandatory
	DESCRIPTION
	"Slot-unique SPVC identifier."
	::= { sPvcEntry 1 }

sPvcCallId OBJECT-TYPE
	SYNTAX INTEGER
	ACCESS read-only
	STATUS mandatory
	DESCRIPTION
	"Call identifier."
	DEFVAL { -1 }
	::= { sPvcEntry 2 }

sPvcLink OBJECT-TYPE
	SYNTAX INTEGER (0..15)
	ACCESS read-write
	STATUS mandatory
	DESCRIPTION
	"The physical link for the SPVC."
	::= { sPvcEntry 3 }

sPvcAddress OBJECT-TYPE
	SYNTAX E164
	ACCESS read-write
	STATUS mandatory
	DESCRIPTION
	"The E.164 address for the SPVC."
	::= { sPvcEntry 4 }

sPvcForwardPeakCellRate OBJECT-TYPE
	SYNTAX INTEGER (0..16777215)
	ACCESS read-write
	STATUS mandatory
	DESCRIPTION
	"The forward user cell rate for an SPVC. The forward user cell rate is a measurement of bandwidth available to the initiating user to transfer information to the responding user."
	::= { sPvcEntry 5 }

sPvcForwardPeakMode OBJECT-TYPE
	SYNTAX INTEGER {
		off(1),
		clp01-discard(4)
	}
	ACCESS read-write
	STATUS mandatory
	DESCRIPTION
	"SPVC/SPVP Forward Peak Mode"
	DEFVAL { clp01-discard }
	::= { sPvcEntry 6 }

sPvcBackwardPeakCellRate OBJECT-TYPE
	SYNTAX INTEGER (0..16777215)
	ACCESS read-write
	STATUS mandatory
	DESCRIPTION
	"The backward user cell rate for an SPVC. The backward user cell rate is a measurement of bandwidth available to the responding user to transfer information to the initiating user."
	::= { sPvcEntry 7 }

sPvcBackwardPeakMode OBJECT-TYPE
	SYNTAX INTEGER {
		off(1),
		clp01-discard(4)
	}
	ACCESS read-write
	STATUS mandatory
	DESCRIPTION
	"SPVC/SPVP Backward Peak Mode"
	DEFVAL { clp01-discard }
	::= { sPvcEntry 8 }

sPvcForwardSustainableCellRate OBJECT-TYPE
	SYNTAX INTEGER (0..16777215)
	ACCESS read-write
	STATUS mandatory
	DESCRIPTION
	"The sustainable forward cell rate for the SPVC."
	::= { sPvcEntry 9 }

sPvcForwardMaxBurstSize OBJECT-TYPE
	SYNTAX INTEGER (0..16777215)
	ACCESS read-write
	STATUS mandatory
	DESCRIPTION
	"The forward maximum burst size for the SPVC."
	::= { sPvcEntry 10 }

sPvcForwardSustainableMode OBJECT-TYPE
	SYNTAX INTEGER {
		off(1),
		clp0-discard(2),
		clp01-discard(4),
		clp0-tag(6)
	}
	ACCESS read-write
	STATUS mandatory
	DESCRIPTION
	"SPVC/SPVP Forward Sustained Mode"
	DEFVAL { clp0-discard }
	::= { sPvcEntry 11 }

sPvcBackwardSustainableCellRate OBJECT-TYPE
	SYNTAX INTEGER (0..16777215)
	ACCESS read-write
	STATUS mandatory
	DESCRIPTION
	"The sustainable backward cell rate for the SPVC."
	::= { sPvcEntry 12 }

sPvcBackwardMaxBurstSize OBJECT-TYPE
	SYNTAX INTEGER (0..16777215)
	ACCESS read-write
	STATUS mandatory
	DESCRIPTION
	"The backward maximum burst size for the SPVC."
	::= { sPvcEntry 13 }

sPvcBackwardSustainableMode OBJECT-TYPE
	SYNTAX INTEGER {
		off(1),
		clp0-discard(2),
		clp01-discard(4),
		clp0-tag(6)
	}
	ACCESS read-write
	STATUS mandatory
	DESCRIPTION
	"SPVC/SPVP Backward Sustained Mode"
	DEFVAL { clp0-discard }
	::= { sPvcEntry 14 }

sPvcQoSClass OBJECT-TYPE
	SYNTAX INTEGER {
		cbr(1),
		vbr-high(2),
		vbr-med(3),
		vbr-low(4),
		best-effort(5)
	}
	ACCESS read-write
	STATUS mandatory
	DESCRIPTION
	"CBR(1) is a constant bit rate service, vbr-high(2) is variable bit rate with high priority, vbr-med(3) has low priority, vbr-low(4) has low priority and the cells may be discarded, best-effort is the same as vbr-low except no bandwidth is reserved."
	DEFVAL { cbr }
	::= { sPvcEntry 15 }

sPvcSourceVci OBJECT-TYPE
	SYNTAX VirtualCircuitIdentifier
	ACCESS read-write
	STATUS mandatory
	DESCRIPTION
	"The source virtual circuit identifier for the SPVC."
	::= { sPvcEntry 16 }

sPvcSourceVpi OBJECT-TYPE
	SYNTAX VirtualPathIdentifier
	ACCESS read-write
	STATUS mandatory
	DESCRIPTION
	"The source virtual path identifier for the SPVC."
	::= { sPvcEntry 17 }

sPvcTargetVci OBJECT-TYPE
	SYNTAX VirtualCircuitIdentifier
	ACCESS read-write
	STATUS mandatory
	DESCRIPTION
	"The target virtual circuit identifier for the SPVC."
	::= { sPvcEntry 18 }

sPvcTargetVpi OBJECT-TYPE
	SYNTAX VirtualPathIdentifier
	ACCESS read-write
	STATUS mandatory
	DESCRIPTION
	"The target virtual path identifier for the SPVC."
	::= { sPvcEntry 19 }

sPvcRetry OBJECT-TYPE
	SYNTAX INTEGER (0..1000)
	ACCESS read-write
	STATUS mandatory
	DESCRIPTION
	"Retry timeout. Zero represents an infinite timeout."
	DEFVAL { 5 }
	::= { sPvcEntry 20 }

sPvcConnectTime OBJECT-TYPE
	SYNTAX INTEGER
	ACCESS read-only
	STATUS mandatory
	DESCRIPTION
	"Connect time in ms."
	::= { sPvcEntry 21 }

sPvcNumberRetries OBJECT-TYPE
	SYNTAX INTEGER (0..1000)
	ACCESS read-write
	STATUS mandatory
	DESCRIPTION
	"Number of retries to attempt. Zero represents no limit."
	::= { sPvcEntry 22 }

sPvcFailures OBJECT-TYPE
	SYNTAX INTEGER
	ACCESS read-only
	STATUS mandatory
	DESCRIPTION
	"A count of the SPVC setup failures."
	::= { sPvcEntry 23 }

sPvcAlertFailures OBJECT-TYPE
	SYNTAX INTEGER {
		no-trap(1),
		fail(2),
		fail-or-clear(3),
		fail-all-attempts(4),
		call-success(5),
		trap-all(6),
		trap-state-change(7)
		}
	ACCESS read-write
	STATUS mandatory
	DESCRIPTION
	"Describes the circumstances under which to issue an Alert message to the NMS."
	DEFVAL { no-trap }
	::= { sPvcEntry 24 }

sPvcCauseDiag OBJECT-TYPE
	SYNTAX Q93bCauseDiag
	ACCESS read-only
	STATUS mandatory
	DESCRIPTION
	"Cause and diagnostic codes."
	::= { sPvcEntry 25 }

sPvcType OBJECT-TYPE
	SYNTAX INTEGER {
		passive(1),
		active(2)
		}
	ACCESS read-only
	STATUS mandatory
	DESCRIPTION
	"If the SPVC entry is passive, it will not try to initiate a call. An active
will attempt to build an SPVC at intervals set by the retry field."
	DEFVAL { active }
	::= { sPvcEntry 26 }

sPvcCallState OBJECT-TYPE
	SYNTAX INTEGER {
		idle(1),
		call-setup(2),
		reset(3),
		invalid(4)
		}
	ACCESS read-write
	STATUS mandatory
	DESCRIPTION
	"Sets the state of the SPVC. Set the value to invalid(3) to tear down the SPVC."
	DEFVAL { idle }
	::= { sPvcEntry 27 }

sPvcStatus OBJECT-TYPE
	SYNTAX INTEGER {
		idle(1),
		sPVC-wait(2),
		l4-wait(3),
		active(4)
		}
	ACCESS read-only
	STATUS mandatory
	DESCRIPTION
	"Describes the state of the SPVC."
	DEFVAL { idle }
	::= { sPvcEntry 28 }

sPvcCauseDiagCode OBJECT-TYPE
	SYNTAX INTEGER
	ACCESS read-only
	STATUS mandatory
	DESCRIPTION
	"Cause and diagnostic codes as defined in UNI-3.0 Annex E ."
	::= { sPvcEntry 29 }

sPvcMulticast OBJECT-TYPE
	SYNTAX INTEGER {
		pt-pt(1),
		pt-mpt-root(2),
		pt-mpt-leaf(3),
                bidirect-root(4)
		}
	ACCESS read-write
	STATUS mandatory
	DESCRIPTION
	"pt-pt - point-to-point SPVC; pt-mpt - point-to-multipoint SPVC; bidirect-root: pt-mpt birection root."
	DEFVAL { pt-pt }
	::= { sPvcEntry 30 }

svcQ93bStatTable OBJECT-TYPE
	SYNTAX SEQUENCE OF SvcQ93bStatEntry
	ACCESS not-accessible
	STATUS mandatory
	DESCRIPTION
	"This table contains statistical protocol information for each link."
	::= { dv2Svc 9 }

svcQ93bStatEntry OBJECT-TYPE
	SYNTAX SvcQ93bStatEntry
	ACCESS not-accessible
	STATUS mandatory
	INDEX { svcQ93bStatSAP }
	::= { svcQ93bStatTable 1 }

SvcQ93bStatEntry ::= SEQUENCE {
		svcQ93bStatSAP
			INTEGER (0..31),
		svcQ93bStatActive
			INTEGER (0..16777215),
		svcQ93bStatAccumalative
			INTEGER (0..16777215),
		svcQ93bStatCallProcTx
			INTEGER (0..16777215),
		svcQ93bStatConnTx
			INTEGER (0..16777215),
		svcQ93bStatConnAckTx
			INTEGER (0..16777215),
		svcQ93bStatSetupTx
			INTEGER (0..16777215),
		svcQ93bStatRelTx
			INTEGER (0..16777215),
		svcQ93bStatRelCmpltTx
			INTEGER (0..16777215),
		svcQ93bStatRstTx
			INTEGER (0..16777215),
		svcQ93bStatRstAckTx
			INTEGER (0..16777215),
		svcQ93bStatStatTx
			INTEGER (0..16777215),
		svcQ93bStatStatEnqTx
			INTEGER (0..16777215),
		svcQ93bStatAddPtyTx
			INTEGER (0..16777215),
		svcQ93bStatAddPtyAckTx
			INTEGER (0..16777215),
		svcQ93bStatAddPtyRejTx
			INTEGER (0..16777215),
		svcQ93bStatDropPtyTx
			INTEGER (0..16777215),
		svcQ93bStatDropPtyAckTx
			INTEGER (0..16777215),
		svcQ93bStatLstCauseTx
			INTEGER (0..16777215),
		svcQ93bStatLstDiagTx
			INTEGER (0..16777215),
		svcQ93bStatCallProcRx
			INTEGER (0..16777215),
		svcQ93bStatConnRx
			INTEGER (0..16777215),
		svcQ93bStatConnAckRx
			INTEGER (0..16777215),
		svcQ93bStatSetupRx
			INTEGER (0..16777215),
		svcQ93bStatRelRx
			INTEGER (0..16777215),
		svcQ93bStatRelCmpltRx
			INTEGER (0..16777215),
		svcQ93bStatRstRx
			INTEGER (0..16777215),
		svcQ93bStatRstAckRx
			INTEGER (0..16777215),
		svcQ93bStatStatRx
			INTEGER (0..16777215),
		svcQ93bStatStatEnqRx
			INTEGER (0..16777215),
		svcQ93bStatAddPtyRx
			INTEGER (0..16777215),
		svcQ93bStatAddPtyAckRx
			INTEGER (0..16777215),
		svcQ93bStatAddPtyRejRx
			INTEGER (0..16777215),
		svcQ93bStatDropPtyRx
			INTEGER (0..16777215),
		svcQ93bStatDropPtyAckRx
			INTEGER (0..16777215),
		svcQ93bStatLstCauseRx
			INTEGER (0..16777215),
		svcQ93bStatLstDiagRx
			INTEGER (0..16777215),
		svcQ93bStatClr
			INTEGER,
		svcQ93bStatDiagTx
			Q93bCauseDiag,
		svcQ93bStatDiagRx
			Q93bCauseDiag
	}

svcQ93bStatSAP OBJECT-TYPE
	SYNTAX INTEGER (0..31)
	ACCESS read-only
	STATUS mandatory
	DESCRIPTION
	"This is the layer 3 Service Access Point for the link."
	::= { svcQ93bStatEntry 1 }

svcQ93bStatActive OBJECT-TYPE
	SYNTAX INTEGER (0..16777215)
	ACCESS read-only
	STATUS mandatory
	DESCRIPTION
	"Number of calls currently active on this SAP."
	::= { svcQ93bStatEntry 2 }

svcQ93bStatAccumalative OBJECT-TYPE
	SYNTAX INTEGER (0..16777215)
	ACCESS read-only
	STATUS mandatory
	DESCRIPTION
	"Total number of calls established on this SAP."
	::= { svcQ93bStatEntry 3 }

svcQ93bStatCallProcTx OBJECT-TYPE
	SYNTAX INTEGER (0..16777215)
	ACCESS read-only
	STATUS mandatory
	DESCRIPTION
	"Call Proceeding pdus transmitted on this SAP."
	::= { svcQ93bStatEntry 4 }

svcQ93bStatConnTx OBJECT-TYPE
	SYNTAX INTEGER (0..16777215)
	ACCESS read-only
	STATUS mandatory
	DESCRIPTION
	"Connect pdus transmitted on this SAP."
	::= { svcQ93bStatEntry 5 }

svcQ93bStatConnAckTx OBJECT-TYPE
	SYNTAX INTEGER (0..16777215)
	ACCESS read-only
	STATUS mandatory
	DESCRIPTION
	"Connect Acknowledge pdus transmitted on this SAP."
	::= { svcQ93bStatEntry 6 }

svcQ93bStatSetupTx OBJECT-TYPE
	SYNTAX INTEGER (0..16777215)
	ACCESS read-only
	STATUS mandatory
	DESCRIPTION
	"Setup pdus transmitted on this SAP."
	::= { svcQ93bStatEntry 7 }

svcQ93bStatRelTx OBJECT-TYPE
	SYNTAX INTEGER (0..16777215)
	ACCESS read-only
	STATUS mandatory
	DESCRIPTION
	"Release pdus transmitted on this SAP."
	::= { svcQ93bStatEntry 8 }

svcQ93bStatRelCmpltTx OBJECT-TYPE
	SYNTAX INTEGER (0..16777215)
	ACCESS read-only
	STATUS mandatory
	DESCRIPTION
	"Release Complete pdus transmitted on this SAP."
	::= { svcQ93bStatEntry 9 }

svcQ93bStatRstTx OBJECT-TYPE
	SYNTAX INTEGER (0..16777215)
	ACCESS read-only
	STATUS mandatory
	DESCRIPTION
	"Restart pdus transmitted on this SAP."
	::= { svcQ93bStatEntry 10 }

svcQ93bStatRstAckTx OBJECT-TYPE
	SYNTAX INTEGER (0..16777215)
	ACCESS read-only
	STATUS mandatory
	DESCRIPTION
	"Restart Acknowledge pdus transmitted on this SAP."
	::= { svcQ93bStatEntry 11 }

svcQ93bStatStatTx OBJECT-TYPE
	SYNTAX INTEGER (0..16777215)
	ACCESS read-only
	STATUS mandatory
	DESCRIPTION
	"Status pdus transmitted on this SAP."
	::= { svcQ93bStatEntry 12 }

svcQ93bStatStatEnqTx OBJECT-TYPE
	SYNTAX INTEGER (0..16777215)
	ACCESS read-only
	STATUS mandatory
	DESCRIPTION
	"Status Enquiry pdus transmitted on this SAP."
	::= { svcQ93bStatEntry 13 }

svcQ93bStatAddPtyTx OBJECT-TYPE
	SYNTAX INTEGER (0..16777215)
	ACCESS read-only
	STATUS mandatory
	DESCRIPTION
	"Add Party pdus transmitted on this SAP."
	::= { svcQ93bStatEntry 14 }

svcQ93bStatAddPtyAckTx OBJECT-TYPE
	SYNTAX INTEGER (0..16777215)
	ACCESS read-only
	STATUS mandatory
	DESCRIPTION
	"Add Party Acknowledge pdus transmitted on this SAP."
	::= { svcQ93bStatEntry 15 }

svcQ93bStatAddPtyRejTx OBJECT-TYPE
	SYNTAX INTEGER (0..16777215)
	ACCESS read-only
	STATUS mandatory
	DESCRIPTION
	"Add Party Reject pdus transmitted on this SAP."
	::= { svcQ93bStatEntry 16 }

svcQ93bStatDropPtyTx OBJECT-TYPE
	SYNTAX INTEGER (0..16777215)
	ACCESS read-only
	STATUS mandatory
	DESCRIPTION
	"Drop Party pdus transmitted on this SAP."
	::= { svcQ93bStatEntry 17 }

svcQ93bStatDropPtyAckTx OBJECT-TYPE
	SYNTAX INTEGER (0..16777215)
	ACCESS read-only
	STATUS mandatory
	DESCRIPTION
	"Drop Party Acknowledge pdus transmitted on this SAP."
	::= { svcQ93bStatEntry 18 }

svcQ93bStatLstCauseTx OBJECT-TYPE
	SYNTAX INTEGER (0..16777215)
	ACCESS read-only
	STATUS mandatory
	DESCRIPTION
	"Last cause code transmitted."
	::= { svcQ93bStatEntry 19 }

svcQ93bStatLstDiagTx OBJECT-TYPE
	SYNTAX INTEGER (0..16777215)
	ACCESS read-only
	STATUS mandatory
	DESCRIPTION
	"Last diagnostic code transmitted."
	::= { svcQ93bStatEntry 20 }

svcQ93bStatCallProcRx OBJECT-TYPE
	SYNTAX INTEGER (0..16777215)
	ACCESS read-only
	STATUS mandatory
	DESCRIPTION
	"Call Proceeding pdus received on this SAP."
	::= { svcQ93bStatEntry 21 }

svcQ93bStatConnRx OBJECT-TYPE
	SYNTAX INTEGER (0..16777215)
	ACCESS read-only
	STATUS mandatory
	DESCRIPTION
	"Connect pdus received on this SAP."
	::= { svcQ93bStatEntry 22 }

svcQ93bStatConnAckRx OBJECT-TYPE
	SYNTAX INTEGER (0..16777215)
	ACCESS read-only
	STATUS mandatory
	DESCRIPTION
	"Connect Acknowledge pdus received on this SAP."
	::= { svcQ93bStatEntry 23 }

svcQ93bStatSetupRx OBJECT-TYPE
	SYNTAX INTEGER (0..16777215)
	ACCESS read-only
	STATUS mandatory
	DESCRIPTION
	"Setup pdus received on this SAP."
	::= { svcQ93bStatEntry 24 }

svcQ93bStatRelRx OBJECT-TYPE
	SYNTAX INTEGER (0..16777215)
	ACCESS read-only
	STATUS mandatory
	DESCRIPTION
	"Release pdus received on this SAP."
	::= { svcQ93bStatEntry 25 }

svcQ93bStatRelCmpltRx OBJECT-TYPE
	SYNTAX INTEGER (0..16777215)
	ACCESS read-only
	STATUS mandatory
	DESCRIPTION
	"Release Complete pdus received on this SAP."
	::= { svcQ93bStatEntry 26 }

svcQ93bStatRstRx OBJECT-TYPE
	SYNTAX INTEGER (0..16777215)
	ACCESS read-only
	STATUS mandatory
	DESCRIPTION
	"Restart pdus received on this SAP."
	::= { svcQ93bStatEntry 27 }

svcQ93bStatRstAckRx OBJECT-TYPE
	SYNTAX INTEGER (0..16777215)
	ACCESS read-only
	STATUS mandatory
	DESCRIPTION
	"Restart Acknowledge pdus received on this SAP."
	::= { svcQ93bStatEntry 28 }

svcQ93bStatStatRx OBJECT-TYPE
	SYNTAX INTEGER (0..16777215)
	ACCESS read-only
	STATUS mandatory
	DESCRIPTION
	"Status pdus received on this SAP."
	::= { svcQ93bStatEntry 29 }

svcQ93bStatStatEnqRx OBJECT-TYPE
	SYNTAX INTEGER (0..16777215)
	ACCESS read-only
	STATUS mandatory
	DESCRIPTION
	"Status Enquiry pdus received on this SAP."
	::= { svcQ93bStatEntry 30 }

svcQ93bStatAddPtyRx OBJECT-TYPE
	SYNTAX INTEGER (0..16777215)
	ACCESS read-only
	STATUS mandatory
	DESCRIPTION
	"Add Party pdus received on this SAP."
	::= { svcQ93bStatEntry 31 }

svcQ93bStatAddPtyAckRx OBJECT-TYPE
	SYNTAX INTEGER (0..16777215)
	ACCESS read-only
	STATUS mandatory
	DESCRIPTION
	"Add Party Acknowledge pdus received on this SAP."
	::= { svcQ93bStatEntry 32 }

svcQ93bStatAddPtyRejRx OBJECT-TYPE
	SYNTAX INTEGER (0..16777215)
	ACCESS read-only
	STATUS mandatory
	DESCRIPTION
	"Add Party Reject pdus received on this SAP."
	::= { svcQ93bStatEntry 33 }

svcQ93bStatDropPtyRx OBJECT-TYPE
	SYNTAX INTEGER (0..16777215)
	ACCESS read-only
	STATUS mandatory
	DESCRIPTION
	"Drop Party pdus received on this SAP."
	::= { svcQ93bStatEntry 34 }

svcQ93bStatDropPtyAckRx OBJECT-TYPE
	SYNTAX INTEGER (0..16777215)
	ACCESS read-only
	STATUS mandatory
	DESCRIPTION
	"Drop Party Acknowledge pdus received on this SAP."
	::= { svcQ93bStatEntry 35 }

svcQ93bStatLstCauseRx OBJECT-TYPE
	SYNTAX INTEGER (0..16777215)
	ACCESS read-only
	STATUS mandatory
	DESCRIPTION
	"Last cause code received."
	::= { svcQ93bStatEntry 36 }

svcQ93bStatLstDiagRx OBJECT-TYPE
	SYNTAX INTEGER (0..16777215)
	ACCESS read-only
	STATUS mandatory
	DESCRIPTION
	"Last diagnostic code received."
	::= { svcQ93bStatEntry 37 }

svcQ93bStatClr OBJECT-TYPE
	SYNTAX INTEGER {
			no(1),
			yes(2)
		}
	ACCESS read-write
	STATUS mandatory
	DESCRIPTION
	"Clear Q.93B statistics for this SAP."
	::= { svcQ93bStatEntry 38 }

svcQ93bStatDiagTx OBJECT-TYPE
	SYNTAX Q93bCauseDiag
	ACCESS read-only
	STATUS mandatory
	DESCRIPTION
	"Tx SAP diagnostic codes"
	::= { svcQ93bStatEntry 39 }

svcQ93bStatDiagRx OBJECT-TYPE
	SYNTAX Q93bCauseDiag
	ACCESS read-only
	STATUS mandatory
	DESCRIPTION
	"Rx SAP diagnostic codes"
	::= { svcQ93bStatEntry 40 }

svcQsaalStatTable OBJECT-TYPE
	SYNTAX SEQUENCE OF SvcQsaalStatEntry
	ACCESS not-accessible
	STATUS mandatory
	DESCRIPTION
	"This table contains protocol information for the Q.SAAL layer for each link."
	::= { dv2Svc 10 }

svcQsaalStatEntry OBJECT-TYPE
	SYNTAX SvcQsaalStatEntry
	ACCESS not-accessible
	STATUS mandatory
	INDEX { svcQsaalStatSAP }
	::= { svcQsaalStatTable 1 }

SvcQsaalStatEntry ::= SEQUENCE {
		svcQsaalStatSAP
			INTEGER (0..31),
		svcQsaalStatOutSduDisc
			INTEGER (0..16777215),
		svcQsaalStatInPduErr
			INTEGER (0..16777215),
		svcQsaalStatInPduDisc
			INTEGER (0..16777215),
		svcQsaalStatOutPduErr
			INTEGER (0..16777215),
		svcQsaalStatOutPduDisc
			INTEGER (0..16777215),
		svcQsaalStatBgnTx
			INTEGER (0..16777215),
		svcQsaalStatBgakTx
			INTEGER (0..16777215),
		svcQsaalStatBgrejTx
			INTEGER (0..16777215),
		svcQsaalStatEndTx
			INTEGER (0..16777215),
		svcQsaalStatRsTx
			INTEGER (0..16777215),
		svcQsaalStatRsakTx
			INTEGER (0..16777215),
		svcQsaalStatSdTx
			INTEGER (0..16777215),
		svcQsaalStatSdpTx
			INTEGER (0..16777215),
		svcQsaalStatPollTx
			INTEGER (0..16777215),
		svcQsaalStatStatTx
			INTEGER (0..16777215),
		svcQsaalStatUstatTx
			INTEGER (0..16777215),
		svcQsaalStatUdTx
			INTEGER (0..16777215),
		svcQsaalStatMdTx
			INTEGER (0..16777215),
		svcQsaalStatBgnRx
			INTEGER (0..16777215),
		svcQsaalStatBgakRx
			INTEGER (0..16777215),
		svcQsaalStatBgrejRx
			INTEGER (0..16777215),
		svcQsaalStatEndRx
			INTEGER (0..16777215),
		svcQsaalStatRsRx
			INTEGER (0..16777215),
		svcQsaalStatRsakRx
			INTEGER (0..16777215),
		svcQsaalStatSdRx
			INTEGER (0..16777215),
		svcQsaalStatSdpRx
			INTEGER (0..16777215),
		svcQsaalStatPollRx
			INTEGER (0..16777215),
		svcQsaalStatStatRx
			INTEGER (0..16777215),
		svcQsaalStatUstatRx
			INTEGER (0..16777215),
		svcQsaalStatUdRx
			INTEGER (0..16777215),
		svcQsaalStatMdRx
			INTEGER (0..16777215),
		svcQsaalStatClr
			INTEGER
	}

svcQsaalStatSAP OBJECT-TYPE
	SYNTAX INTEGER (0..31)
	ACCESS read-only
	STATUS mandatory
	DESCRIPTION
	"This is the layer 3 Service Access Point for the link."
	::= { svcQsaalStatEntry 1 }

svcQsaalStatOutSduDisc OBJECT-TYPE
	SYNTAX INTEGER (0..16777215)
	ACCESS read-only
	STATUS mandatory
	DESCRIPTION
	"Outgoing SDUs discarded."
	::= { svcQsaalStatEntry 2 }

svcQsaalStatInPduErr OBJECT-TYPE
	SYNTAX INTEGER (0..16777215)
	ACCESS read-only
	STATUS mandatory
	DESCRIPTION
	"Number of incoming PDUs with a reception error."
	::= { svcQsaalStatEntry 3 }

svcQsaalStatInPduDisc OBJECT-TYPE
	SYNTAX INTEGER (0..16777215)
	ACCESS read-only
	STATUS mandatory
	DESCRIPTION
	"Number of incoming PDUs discarded."
	::= { svcQsaalStatEntry 4 }

svcQsaalStatOutPduErr OBJECT-TYPE
	SYNTAX INTEGER (0..16777215)
	ACCESS read-only
	STATUS mandatory
	DESCRIPTION
	"Number of outgoing PDUs with a transmission error."
	::= { svcQsaalStatEntry 5 }

svcQsaalStatOutPduDisc OBJECT-TYPE
	SYNTAX INTEGER (0..16777215)
	ACCESS read-only
	STATUS mandatory
	DESCRIPTION
	"Number of outgoing PDUs discarded."
	::= { svcQsaalStatEntry 6 }

svcQsaalStatBgnTx OBJECT-TYPE
	SYNTAX INTEGER (0..16777215)
	ACCESS read-only
	STATUS mandatory
	DESCRIPTION
	"BGN pdus transmitted on this SAP."
	::= { svcQsaalStatEntry 7 }

svcQsaalStatBgakTx OBJECT-TYPE
	SYNTAX INTEGER (0..16777215)
	ACCESS read-only
	STATUS mandatory
	DESCRIPTION
	"BGAK pdus transmitted on this SAP."
	::= { svcQsaalStatEntry 8 }

svcQsaalStatBgrejTx OBJECT-TYPE
	SYNTAX INTEGER (0..16777215)
	ACCESS read-only
	STATUS mandatory
	DESCRIPTION
	"BGREJ pdus transmitted on this SAP."
	::= { svcQsaalStatEntry 9 }

svcQsaalStatEndTx OBJECT-TYPE
	SYNTAX INTEGER (0..16777215)
	ACCESS read-only
	STATUS mandatory
	DESCRIPTION
	"END pdus transmitted on this SAP."
	::= { svcQsaalStatEntry 10 }

svcQsaalStatRsTx OBJECT-TYPE
	SYNTAX INTEGER (0..16777215)
	ACCESS read-only
	STATUS mandatory
	DESCRIPTION
	"RS pdus transmitted on this SAP."
	::= { svcQsaalStatEntry 11 }

svcQsaalStatRsakTx OBJECT-TYPE
	SYNTAX INTEGER (0..16777215)
	ACCESS read-only
	STATUS mandatory
	DESCRIPTION
	"RSAK pdus transmitted on this SAP."
	::= { svcQsaalStatEntry 12 }

svcQsaalStatSdTx OBJECT-TYPE
	SYNTAX INTEGER (0..16777215)
	ACCESS read-only
	STATUS mandatory
	DESCRIPTION
	"SD pdus transmitted on this SAP."
	::= { svcQsaalStatEntry 13 }

svcQsaalStatSdpTx OBJECT-TYPE
	SYNTAX INTEGER (0..16777215)
	ACCESS read-only
	STATUS mandatory
	DESCRIPTION
	"SDP pdus transmitted on this SAP."
	::= { svcQsaalStatEntry 14 }

svcQsaalStatPollTx OBJECT-TYPE
	SYNTAX INTEGER (0..16777215)
	ACCESS read-only
	STATUS mandatory
	DESCRIPTION
	"POLL pdus transmitted on this SAP."
	::= { svcQsaalStatEntry 15 }

svcQsaalStatStatTx OBJECT-TYPE
	SYNTAX INTEGER (0..16777215)
	ACCESS read-only
	STATUS mandatory
	DESCRIPTION
	"STAT pdus transmitted on this SAP."
	::= { svcQsaalStatEntry 16 }

svcQsaalStatUstatTx OBJECT-TYPE
	SYNTAX INTEGER (0..16777215)
	ACCESS read-only
	STATUS mandatory
	DESCRIPTION
	"USTAT pdus transmitted on this SAP."
	::= { svcQsaalStatEntry 17 }

svcQsaalStatUdTx OBJECT-TYPE
	SYNTAX INTEGER (0..16777215)
	ACCESS read-only
	STATUS mandatory
	DESCRIPTION
	"UD pdus transmitted on this SAP."
	::= { svcQsaalStatEntry 18 }

svcQsaalStatMdTx OBJECT-TYPE
	SYNTAX INTEGER (0..16777215)
	ACCESS read-only
	STATUS mandatory
	DESCRIPTION
	"MD pdus transmitted on this SAP."
	::= { svcQsaalStatEntry 19 }

svcQsaalStatBgnRx OBJECT-TYPE
	SYNTAX INTEGER (0..16777215)
	ACCESS read-only
	STATUS mandatory
	DESCRIPTION
	"BGN pdus received on this SAP."
	::= { svcQsaalStatEntry 20 }

svcQsaalStatBgakRx OBJECT-TYPE
	SYNTAX INTEGER (0..16777215)
	ACCESS read-only
	STATUS mandatory
	DESCRIPTION
	"BGAK pdus received on this SAP."
	::= { svcQsaalStatEntry 21 }

svcQsaalStatBgrejRx OBJECT-TYPE
	SYNTAX INTEGER (0..16777215)
	ACCESS read-only
	STATUS mandatory
	DESCRIPTION
	"BGREJ pdus received on this SAP."
	::= { svcQsaalStatEntry 22 }

svcQsaalStatEndRx OBJECT-TYPE
	SYNTAX INTEGER (0..16777215)
	ACCESS read-only
	STATUS mandatory
	DESCRIPTION
	"END pdus received on this SAP."
	::= { svcQsaalStatEntry 23 }

svcQsaalStatRsRx OBJECT-TYPE
	SYNTAX INTEGER (0..16777215)
	ACCESS read-only
	STATUS mandatory
	DESCRIPTION
	"RS pdus received on this SAP."
	::= { svcQsaalStatEntry 24 }

svcQsaalStatRsakRx OBJECT-TYPE
	SYNTAX INTEGER (0..16777215)
	ACCESS read-only
	STATUS mandatory
	DESCRIPTION
	"RSAK pdus received on this SAP."
	::= { svcQsaalStatEntry 25 }

svcQsaalStatSdRx OBJECT-TYPE
	SYNTAX INTEGER (0..16777215)
	ACCESS read-only
	STATUS mandatory
	DESCRIPTION
	"SD pdus received on this SAP."
	::= { svcQsaalStatEntry 26 }

svcQsaalStatSdpRx OBJECT-TYPE
	SYNTAX INTEGER (0..16777215)
	ACCESS read-only
	STATUS mandatory
	DESCRIPTION
	"SDP pdus received on this SAP."
	::= { svcQsaalStatEntry 27 }

svcQsaalStatPollRx OBJECT-TYPE
	SYNTAX INTEGER (0..16777215)
	ACCESS read-only
	STATUS mandatory
	DESCRIPTION
	"POLL pdus received on this SAP."
	::= { svcQsaalStatEntry 28 }

svcQsaalStatStatRx OBJECT-TYPE
	SYNTAX INTEGER (0..16777215)
	ACCESS read-only
	STATUS mandatory
	DESCRIPTION
	"STAT pdus received on this SAP."
	::= { svcQsaalStatEntry 29 }

svcQsaalStatUstatRx OBJECT-TYPE
	SYNTAX INTEGER (0..16777215)
	ACCESS read-only
	STATUS mandatory
	DESCRIPTION
	"USTAT pdus received on this SAP."
	::= { svcQsaalStatEntry 30 }

svcQsaalStatUdRx OBJECT-TYPE
	SYNTAX INTEGER (0..16777215)
	ACCESS read-only
	STATUS mandatory
	DESCRIPTION
	"UD pdus received on this SAP."
	::= { svcQsaalStatEntry 31 }

svcQsaalStatMdRx OBJECT-TYPE
	SYNTAX INTEGER (0..16777215)
	ACCESS read-only
	STATUS mandatory
	DESCRIPTION
	"MD pdus received on this SAP."
	::= { svcQsaalStatEntry 32 }

svcQsaalStatClr OBJECT-TYPE
	SYNTAX INTEGER {
			no(1),
			yes(2)
		}
	ACCESS read-write
	STATUS mandatory
	DESCRIPTION
	"Clear statistics for this SAP."
	::= { svcQsaalStatEntry 33 }

svcQsaalTmrPoll OBJECT-TYPE
	SYNTAX INTEGER
	ACCESS read-write
	STATUS mandatory
	DESCRIPTION
	"SSCOP Timer_POLL (8=800ms)."
	DEFVAL { 8 }
	::= { dv2Svc 11 }

svcQsaalTmrKeepAlive OBJECT-TYPE
	SYNTAX INTEGER
	ACCESS read-write
	STATUS mandatory
	DESCRIPTION
	"SSCOP Timer_KEEPALIVE (20=2seconds)."
	DEFVAL { 20 }
	::= { dv2Svc 12 }

svcQsaalTmrNoResponse OBJECT-TYPE
	SYNTAX INTEGER
	ACCESS read-write
	STATUS mandatory
	DESCRIPTION
	"SSCOP Timer_NORESPONSE (100=10seconds)."
	DEFVAL { 100 }
	::= { dv2Svc 13 }

svcQsaalTmrCC OBJECT-TYPE
	SYNTAX INTEGER
	ACCESS read-write
	STATUS mandatory
	DESCRIPTION
	"SSCOP Timer_CC (20=2seconds)."
	DEFVAL { 20 }
	::= { dv2Svc 14 }

svcQsaalMaxPD OBJECT-TYPE
	SYNTAX INTEGER
	ACCESS read-write
	STATUS mandatory
	DESCRIPTION
	"SSCOP Maximum PD."
	DEFVAL { 15 }
	::= { dv2Svc 15 }

svcQ93bTmrT303 OBJECT-TYPE
	SYNTAX INTEGER
	ACCESS read-write
	STATUS mandatory
	DESCRIPTION
	"Q.93B T303 (40=4seconds)."
	DEFVAL { 40 }
	::= { dv2Svc 16 }

svcQ93bTmrT310 OBJECT-TYPE
	SYNTAX INTEGER
	ACCESS read-write
	STATUS mandatory
	DESCRIPTION
	"Q.93B T310 (200=20seconds)."
	DEFVAL { 200 }
	::= { dv2Svc 17 }

svcQ93bTmrT308 OBJECT-TYPE
	SYNTAX INTEGER
	ACCESS read-write
	STATUS mandatory
	DESCRIPTION
	"Q.93B T308 (300=30seconds)."
	DEFVAL { 300 }
	::= { dv2Svc 18 }

svcQ93bTmrT309 OBJECT-TYPE
	SYNTAX INTEGER
	ACCESS read-write
	STATUS mandatory
	DESCRIPTION
	"Q.93B T309 (150=15seconds)."
	DEFVAL { 150 }
	::= { dv2Svc 19 }

maxOutstanding OBJECT-TYPE
	SYNTAX INTEGER (1..20)
	ACCESS read-write
	STATUS mandatory
	DESCRIPTION
	"Max Outgoing Outstanding Calls."
	DEFVAL { 3 }
	::= { dv2Svc 20 }

svcLoadRoute OBJECT-TYPE
	SYNTAX INTEGER {
		both(1),
		none(2),
		rte-table(3),
		dtl-bin(4)
		}
	ACCESS read-write
	STATUS mandatory
	DESCRIPTION
	"Poke point for loading routing tables"
	DEFVAL { both }
	::= { dv2Svc 21 }

svcHalfConTimer OBJECT-TYPE
	SYNTAX INTEGER (0..3000)
	ACCESS read-write
	STATUS mandatory
	DESCRIPTION
	"SVC half connect recovery poll timer"
	DEFVAL { 10 }
	::= { dv2Svc 22 }

svcHalfConCnt OBJECT-TYPE
	SYNTAX INTEGER
	ACCESS read-only
	STATUS mandatory
	DESCRIPTION
	"SVC half connect counter"
	DEFVAL { 0 }
	::= { dv2Svc 23 }

svcQ93bTmrT398 OBJECT-TYPE
	SYNTAX INTEGER
	ACCESS read-write
	STATUS mandatory
	DESCRIPTION
	"Q.93B T398 (40= 4 seconds)."
	DEFVAL { 40 }
	::= { dv2Svc 24 }

svcQ93bTmrT399 OBJECT-TYPE
	SYNTAX INTEGER
	ACCESS read-write
	STATUS mandatory
	DESCRIPTION
	"Q.93B T399 (140= 14 seconds)."
	DEFVAL { 140 }
	::= { dv2Svc 25 }

svcRetryPeriod OBJECT-TYPE
	SYNTAX INTEGER (15..180)
	ACCESS read-write
	STATUS mandatory
	DESCRIPTION
	"Retry Period"
	DEFVAL { 180 }
	::= { dv2Svc 26 }

svcCellRateTable OBJECT-TYPE
	SYNTAX SEQUENCE OF SvcCellRateEntry
	ACCESS not-accessible
	STATUS mandatory
	DESCRIPTION
	"This table contains information about the limitations on Cell Rates on link"
	::= { dv2Svc 27 }

svcCellRateEntry OBJECT-TYPE
	SYNTAX SvcCellRateEntry
	ACCESS not-accessible
	STATUS mandatory
	INDEX { svcCRLinkNo }
	::= { svcCellRateTable 1 }

SvcCellRateEntry ::= SEQUENCE {
		svcCRLinkNo
			INTEGER,
		svcPCRCLP01Max
			INTEGER,
		svcSCRMax
			INTEGER,
		svcMBSMax
			INTEGER
}

svcCRLinkNo OBJECT-TYPE
	SYNTAX INTEGER (0..3)
	ACCESS read-only
	STATUS mandatory
	DESCRIPTION
	"This is the physical link number associated with this SAP"
	::= {svcCellRateEntry 1 }



svcPCRCLP01Max  OBJECT-TYPE
	SYNTAX INTEGER (0..16777216)
	ACCESS read-write
	STATUS mandatory
	DESCRIPTION
	"PCRCLP01 Max(0 disables checking)"
	DEFVAL { 0 }
	::= { svcCellRateEntry 2 }

svcSCRMax   OBJECT-TYPE
	SYNTAX INTEGER (0..16777216)
	ACCESS read-write
	STATUS mandatory
	DESCRIPTION
	"SCR Max(0 disables checking)"
	DEFVAL { 0 }
	::= {  svcCellRateEntry 3 }

svcMBSMax   OBJECT-TYPE
	SYNTAX INTEGER (0..16777216)
	ACCESS read-write
	STATUS mandatory
	DESCRIPTION
	"MBS Max(0 disables checking)"
	DEFVAL { 0 }
	::= {  svcCellRateEntry 4 }


svcTrafficTable OBJECT-TYPE
	SYNTAX SEQUENCE OF SvcTrafficEntry
	ACCESS not-accessible
	STATUS mandatory
	DESCRIPTION
	"This table contains information about the limitations on Cell Rates on link"
	::= { dv2Svc 28 }

svcTrafficEntry OBJECT-TYPE
	SYNTAX SvcTrafficEntry
	ACCESS not-accessible
	STATUS mandatory
	INDEX { svcTLinkNo }
	::= { svcTrafficTable 1 }

SvcTrafficEntry ::= SEQUENCE {
		svcTLinkNo
			INTEGER,
		svcCBRallowed
			INTEGER,
		svcVBRHallowed
			INTEGER,
		svcVBRMallowed
			INTEGER,
		svcVBRLUBRallowed
			INTEGER,
		svcVBRLUBRsubtractpercent
	 		INTEGER
}

svcTLinkNo OBJECT-TYPE
	SYNTAX INTEGER (0..3)
	ACCESS read-only
	STATUS mandatory
	DESCRIPTION
	"Lnk Number"
	::= {svcTrafficEntry 1 }

svcCBRallowed   OBJECT-TYPE
	SYNTAX INTEGER {
		yes(1),
		no(2)
		}
	ACCESS read-write
	STATUS mandatory
	DESCRIPTION
	"Allows or disallows CBR traffic"
	DEFVAL { yes }
	::= {svcTrafficEntry 2 }

svcVBRHallowed  OBJECT-TYPE
	SYNTAX INTEGER {
		yes(1),
		no(2)
		}
	ACCESS read-write
	STATUS mandatory
	DESCRIPTION
	"Allows or disallows VBR High traffic"
	DEFVAL { yes }
	::= { svcTrafficEntry 3 }

svcVBRMallowed OBJECT-TYPE
	SYNTAX INTEGER {
		yes(1),
		no(2)
		}
	ACCESS read-write
	STATUS mandatory
	DESCRIPTION
	"Allows or disallows VBR Med traffic"
	DEFVAL { yes }
	::= { svcTrafficEntry 4 }

svcVBRLUBRallowed OBJECT-TYPE
	SYNTAX INTEGER {
		yes(1),
		no(2)
		}
	ACCESS read-write
	STATUS mandatory
	DESCRIPTION
	"Allows or disallows VBR Low/UBR traffic"
	DEFVAL { yes }
	::= { svcTrafficEntry 5 }

svcVBRLUBRsubtractpercent  OBJECT-TYPE
	SYNTAX INTEGER (0..100)
	ACCESS read-write
	STATUS mandatory
	DESCRIPTION
	"Specifies a percentage of BW to be subtracted for VBR Low/UBR traffic"
	DEFVAL { 0 }
	::= { svcTrafficEntry 6 }

--___________________________________________________________________________
-- The dv2CE channel table configuration

ceTable OBJECT-TYPE
	SYNTAX SEQUENCE OF CeEntry
 	ACCESS not-accessible
 	STATUS mandatory
 	DESCRIPTION
 	"Configuration Table for dv2CE Links"
 	::= { dv2CE 1 }

ceEntry OBJECT-TYPE
 	SYNTAX	CeEntry
 	ACCESS	not-accessible
 	STATUS	mandatory
	INDEX   { ceLinkNo }
	::= { ceTable 1 }

CeEntry ::=
 	SEQUENCE {
 		ceLinkNo
 			INTEGER,
 		ceEnable
			INTEGER,
		ceMode
			INTEGER,
		cePriority
			INTEGER,
		cePvcValid
			INTEGER,
		ceDstSlot
			INTEGER,
		ceDstLink
			INTEGER,
		ceDstVpi
			VirtualPathIdentifier,
		ceDstVci
			VirtualCircuitIdentifier,
		ceCDV
			INTEGER,
		ceCDVMax
			INTEGER,
		ceMulticast
			INTEGER,
		ceXhInt
			INTEGER
}


ceLinkNo OBJECT-TYPE
	SYNTAX INTEGER (0..127)
	ACCESS read-only
	STATUS mandatory
	DESCRIPTION
	"Link Number for Table Entry"
	::= { ceEntry 1 }

ceEnable OBJECT-TYPE
	SYNTAX INTEGER {
			yes(1),
			no(2),
			restart(3)
		}
	ACCESS read-write
	STATUS mandatory
	DESCRIPTION
	"Setting to yes(1) enables the Link"
	::= { ceEntry 2 }

ceMode OBJECT-TYPE
	SYNTAX INTEGER {
			none(1),
			adaptive(2),
			srts(3)
		}
	ACCESS read-write
	STATUS mandatory
	DESCRIPTION
	"Service Clock Recovery Mode"
	::= { ceEntry 3 }

cePriority OBJECT-TYPE
	SYNTAX INTEGER {
			high(1),
			low(2)
		}
	ACCESS read-only
	STATUS mandatory
	DESCRIPTION
	"Set to high for normal CBR operation"
	::= { ceEntry 4 }

cePvcValid OBJECT-TYPE
	SYNTAX INTEGER {
			no(1),
			yes(2)
		}
	ACCESS read-only
	STATUS mandatory
	DESCRIPTION
	"Indicates if valid PVC exists for Link"
	::= { ceEntry 5 }

ceDstSlot OBJECT-TYPE
	SYNTAX INTEGER (0..15)
	ACCESS read-only
	STATUS mandatory
	DESCRIPTION
	"Destination Slot for PVC"
        DEFVAL { 0 }
	::= { ceEntry 6 }

ceDstLink OBJECT-TYPE
	SYNTAX INTEGER {
			link0(1),
			link1(2),
			link2(3),
			link3(4),
			multicast(7)
		}
	ACCESS read-only
	STATUS mandatory
	DESCRIPTION
	"Destination Link for PVC"
	::= { ceEntry 7 }

ceDstVpi OBJECT-TYPE
	SYNTAX VirtualPathIdentifier
	ACCESS read-only
	STATUS mandatory
 	DESCRIPTION
	"Destination VPI for PVC"
	::= { ceEntry 8 }

ceDstVci OBJECT-TYPE
	SYNTAX VirtualCircuitIdentifier
	ACCESS read-only
	STATUS mandatory
	DESCRIPTION
	"Destination VCI for PVC"
	::= { ceEntry 9 }

ceCDV OBJECT-TYPE
	SYNTAX INTEGER (1..31)
	ACCESS read-write
	STATUS mandatory
	DESCRIPTION
	"Cell Delay Variation Tolerance"
	DEFVAL { 4 }
	::= { ceEntry 10 }

ceCDVMax OBJECT-TYPE
	SYNTAX INTEGER (1..62)
	ACCESS read-write
	STATUS mandatory
	DESCRIPTION
	"Cell Delay Variation Tolerance"
	DEFVAL { 8 }
	::= { ceEntry 11 }

ceMulticast OBJECT-TYPE
	SYNTAX INTEGER {
			no(1),
			yes(2)
		}	ACCESS read-only
	STATUS mandatory
	DESCRIPTION
	"Is link part of multicast tree"
	::= { ceEntry 24 }

ceXhInt OBJECT-TYPE
	SYNTAX INTEGER {
			inactive(1),
			point-to-point(2),
			uni-root(3),
			bi-root(4),
			uni-rt-and-leaf(5),
			uni-leaf(6),
			bi-leaf(7),
			unknown(8)
		}
	ACCESS read-only
	STATUS mandatory
	DESCRIPTION
	"XH Interface for Link"
	::= { ceEntry 25 }
		


--___________________________________________________________________________
-- The dv2CE channel table status

ceStatTable OBJECT-TYPE
	SYNTAX SEQUENCE OF CeStatEntry
	ACCESS not-accessible
	STATUS mandatory
	DESCRIPTION
	"status information about the dv2CE."
	::= { dv2CE 2 }

ceStatEntry OBJECT-TYPE
	SYNTAX	CeStatEntry
	ACCESS	not-accessible
	STATUS	mandatory
        INDEX   { ceStatPortNo }
	::= { ceStatTable 1 }

CeStatEntry ::=
	SEQUENCE {
		ceStatPortNo
			INTEGER,
		ceStatReset
			INTEGER,
		ceStatTxState
			INTEGER,
		ceStatRxState
			INTEGER,
		ceTxCnt
			Counter,
		ceRxCnt
			Counter,
		ceOflCnt
			Counter,
		ceUflCnt
			Counter,
		ceDisCnt
			Counter,
		ceInvCnt
			Counter,
		ceResCnt
			Counter,
		ceFifoLvlCnt
			Counter

}

ceStatPortNo OBJECT-TYPE
	SYNTAX INTEGER (0..3)
	ACCESS read-only
	STATUS mandatory
	DESCRIPTION
	"Link Number for Table Entry"
	::= { ceStatEntry 1 }

ceStatReset OBJECT-TYPE
	SYNTAX INTEGER {
			no(1),
			yes(2)
		}
	ACCESS read-write
	STATUS mandatory
	DESCRIPTION
	"Clear Statistics for Link"
	::= { ceStatEntry 2 }


ceStatTxState OBJECT-TYPE
	SYNTAX INTEGER {
			idle(1),
			start(2),
			fifostart(3),
			wideband(4),
			fifokick(5),
			narrowband(6),
			operating(7)
		}
	ACCESS read-only
	STATUS mandatory
	DESCRIPTION
	"Indicates if data is being received and segmented"
	::= { ceStatEntry 3 }

ceStatRxState OBJECT-TYPE
	SYNTAX INTEGER {
			idle(1),
			ais(2),
			operating(3)
		}
	ACCESS read-only
	STATUS mandatory
	DESCRIPTION
	"Indicates if data being reassembled and transmitted"
	::= { ceStatEntry 4 }

ceTxCnt OBJECT-TYPE
	SYNTAX Counter
	ACCESS read-only
	STATUS mandatory
	DESCRIPTION
	"Count of Cells transmitted from switch fabric"
	::= { ceStatEntry 5 }

ceRxCnt OBJECT-TYPE
	SYNTAX Counter
	ACCESS read-only
	STATUS mandatory
	DESCRIPTION
	"Count of Cells received into switch fabric"
	::= { ceStatEntry 6 }

ceOflCnt OBJECT-TYPE
	SYNTAX Counter
	ACCESS read-only
	STATUS mandatory
	DESCRIPTION
	"Count of 1S intervals during which RX FIFO overflowed"
	::= { ceStatEntry 7 }

ceUflCnt OBJECT-TYPE
	SYNTAX Counter
	ACCESS read-only
	STATUS mandatory
	DESCRIPTION
	"Count of 1S intervals during which RX FIFO underflowed"
	::= { ceStatEntry 8 }

ceDisCnt OBJECT-TYPE
	SYNTAX Counter
	ACCESS read-only
	STATUS mandatory
	DESCRIPTION
	"Count of 1S intervals during which cells were discarded"
	::= { ceStatEntry 9 }

ceInvCnt OBJECT-TYPE
	SYNTAX Counter
	ACCESS read-only
	STATUS mandatory
	DESCRIPTION
	"Count of 1S intervals during which cells were invented"
	::= { ceStatEntry 10 }

ceResCnt OBJECT-TYPE
	SYNTAX Counter
	ACCESS read-only
	STATUS mandatory
	DESCRIPTION
	"Count of 1S intervals during which AAL1 resync occurred"
	::= { ceStatEntry 11 }

ceFifoLvlCnt OBJECT-TYPE
	SYNTAX Counter
	ACCESS read-only
	STATUS mandatory
	DESCRIPTION
	"Number of Cells currently in FIFO"
	::= { ceStatEntry 12 }

--___________________________________________________________________________
-- The dv2CE timing status

cePriVal OBJECT-TYPE
	SYNTAX INTEGER {
		no(1),
		yes(2)
	}
	ACCESS read-only
	STATUS mandatory
	DESCRIPTION
	"Primary Clock Valid"
	::= { dv2CE 21 }

ceSecVal OBJECT-TYPE
	SYNTAX INTEGER {
		no(1),
		yes(2)
	}
	ACCESS read-only
	STATUS mandatory
	DESCRIPTION
	"Secondary Clock Valid"
	::= { dv2CE 22 }

ceClkSel OBJECT-TYPE
	SYNTAX INTEGER {
		primary(1),
		secondary(2)
	}
	ACCESS read-only
	STATUS mandatory
	DESCRIPTION
	"Clock Select"
	::= { dv2CE 23 }

ceClkInp OBJECT-TYPE
	SYNTAX INTEGER {
		no(1),
		yes(2)
	}
	ACCESS read-only
	STATUS mandatory
	DESCRIPTION
	"Is there clock input"
	::= { dv2CE 24 }

ceStr3 OBJECT-TYPE
      SYNTAX INTEGER {
              no(1),
              yes(2)
      }
      ACCESS read-only
      STATUS mandatory
      DESCRIPTION
      "Is there STR3"
      ::= { dv2CE 25 }


--___________________________________________________________________________
-- The dv2VE channel table configuration

veTable OBJECT-TYPE
	SYNTAX SEQUENCE OF VeEntry
 	ACCESS not-accessible
 	STATUS mandatory
 	DESCRIPTION
 	"Configuration Table for dv2VE Links"
 	::= { dv2VE 1 }

veEntry OBJECT-TYPE
 	SYNTAX	VeEntry
 	ACCESS	not-accessible
 	STATUS	mandatory
	INDEX   { veLinkNo }
	::= { veTable 1 }

VeEntry ::=
 	SEQUENCE {
 		veLinkNo
 			INTEGER,
 		veEnable
			INTEGER,
		veMode
			INTEGER,
		vePriority
			INTEGER,
		vePvcValid
			INTEGER,
		veDstSlot
			INTEGER,
		veDstLink
			INTEGER,
		veDstVpi
			VirtualPathIdentifier,
		veDstVci
			VirtualCircuitIdentifier,
		veCDV
			INTEGER,
		veCDVMax
			INTEGER,
		veMulticast
			INTEGER,
		veXhInt
			INTEGER
}

veLinkNo OBJECT-TYPE
	SYNTAX INTEGER (0..127)
	ACCESS read-only
	STATUS mandatory
	DESCRIPTION
	"Link Number for Table Entry"
	::= { veEntry 1 }

veEnable OBJECT-TYPE
	SYNTAX INTEGER {
			yes(1),
			no(2),
			restart(3)
		}
	ACCESS read-write
	STATUS mandatory
	DESCRIPTION
	"Setting to yes(1) enables the Link"
	::= { veEntry 2 }

veMode OBJECT-TYPE
	SYNTAX INTEGER {
			video(4)
		}
	ACCESS read-only
	STATUS mandatory
	DESCRIPTION
	"Service Clock Recovery Mode"
	::= { veEntry 3 }

vePriority OBJECT-TYPE
	SYNTAX INTEGER {
			high(1),
			low(2)
		}
	ACCESS read-only
	STATUS mandatory
	DESCRIPTION
	"Set to high for normal CBR operation"
	::= { veEntry 4 }

vePvcValid OBJECT-TYPE
	SYNTAX INTEGER {
			no(1),
			yes(2)
		}
	ACCESS read-only
	STATUS mandatory
	DESCRIPTION
	"Indicates if valid PVC exists for Link"
	::= { veEntry 5 }

veDstSlot OBJECT-TYPE
	SYNTAX INTEGER (0..15)
	ACCESS read-only
	STATUS mandatory
	DESCRIPTION
	"Destination Slot for PVC"
        DEFVAL { 0 }
	::= { veEntry 6 }

veDstLink OBJECT-TYPE
	SYNTAX INTEGER {
			link0(1),
			link1(2),
			link2(3),
			link3(4),
			multicast(7)
		}	ACCESS read-only
	STATUS mandatory
	DESCRIPTION
	"Destination Link for PVC"
	::= { veEntry 7 }

veDstVpi OBJECT-TYPE
	SYNTAX VirtualPathIdentifier
	ACCESS read-only
	STATUS mandatory
	DESCRIPTION
	"Destination VPI for PVC"
	::= { veEntry 8 }

veDstVci OBJECT-TYPE
	SYNTAX VirtualCircuitIdentifier
	ACCESS read-only
	STATUS mandatory
	DESCRIPTION
	"Destination VCI for PVC"
	::= { veEntry 9 }

veCDV OBJECT-TYPE
	SYNTAX INTEGER (1..31)
	ACCESS read-write
	STATUS mandatory
	DESCRIPTION
	"Cell Delay Variation Tolerance"
	DEFVAL { 31 }
	::= { veEntry 10 }

veCDVMax OBJECT-TYPE
	SYNTAX INTEGER (1..62)
	ACCESS read-write
	STATUS mandatory
	DESCRIPTION
	"Cell Delay Variation Tolerance"
	DEFVAL { 62 }
	::= { veEntry 11 }

veMulticast OBJECT-TYPE
	SYNTAX INTEGER {
			no(1),
			yes(2)
		}	ACCESS read-only
	STATUS mandatory
	DESCRIPTION
	"Is link part of multicast tree"
	::= { veEntry 24 }

veXhInt OBJECT-TYPE
	SYNTAX INTEGER {
			inactive(1),
			point-to-point(2),
			uni-root(3),
			bi-root(4),
			uni-rt-and-leaf(5),
			uni-leaf(6),
			bi-leaf(7),
			unknown(8)
		}
	ACCESS read-only
	STATUS mandatory
	DESCRIPTION
	"XH Interface for Link"
	::= { veEntry 25 }



--___________________________________________________________________________
-- The dv2VE channel table status

veStatTable OBJECT-TYPE
	SYNTAX SEQUENCE OF VeStatEntry
	ACCESS not-accessible
	STATUS mandatory
	DESCRIPTION
	"status information about the dv2VE."
	::= { dv2VE 2 }

veStatEntry OBJECT-TYPE
	SYNTAX	VeStatEntry
	ACCESS	not-accessible
	STATUS	mandatory
        INDEX   { veStatPortNo }
	::= { veStatTable 1 }

VeStatEntry ::=
	SEQUENCE {
		veStatPortNo
			INTEGER,
		veStatReset
			INTEGER,
		veStatTxState
			INTEGER,
		veStatRxState
			INTEGER,
		veTxCnt
			Counter,
		veRxCnt
			Counter,
		veOflCnt
			Counter,
		veUflCnt
			Counter,
		veDisCnt
			Counter,
		veInvCnt
			Counter,
		veResCnt
			Counter,
		veFifoLvlCnt
			Counter

}

veStatPortNo OBJECT-TYPE
	SYNTAX INTEGER (0..3)
	ACCESS read-only
	STATUS mandatory
	DESCRIPTION
	"Link Number for Table Entry"
	::= { veStatEntry 1 }

veStatReset OBJECT-TYPE
	SYNTAX INTEGER {
			no(1),
			yes(2)
		}
	ACCESS read-write
	STATUS mandatory
	DESCRIPTION
	"Clear Statistics for Link"
	::= { veStatEntry 2 }

veStatTxState OBJECT-TYPE
	SYNTAX INTEGER {
			idle(1),
			start(2),
			fifostart(3),
			wideband(4),
			fifokick(5),
			narrowband(6),
			operating(7)
		}
	ACCESS read-only
	STATUS mandatory
	DESCRIPTION
	"Indicates if data is being received and segmented"
	::= { veStatEntry 3 }


veStatRxState OBJECT-TYPE
	SYNTAX INTEGER {
			idle(1),
			ais(2),
			operating(3)
		}
	ACCESS read-only
	STATUS mandatory
	DESCRIPTION
	"Indicates if data being reassembled and transmitted"
	::= { veStatEntry 4 }

veTxCnt OBJECT-TYPE
	SYNTAX Counter
	ACCESS read-only
	STATUS mandatory
	DESCRIPTION
	"Count of Cells transmitted from switch fabric"
	::= { veStatEntry 5 }

veRxCnt OBJECT-TYPE
	SYNTAX Counter
	ACCESS read-only
	STATUS mandatory
	DESCRIPTION
	"Count of Cells received into switch fabric"
	::= { veStatEntry 6 }

veOflCnt OBJECT-TYPE
	SYNTAX Counter
	ACCESS read-only
	STATUS mandatory
	DESCRIPTION
	"Count of 1S intervals during which RX FIFO overflowed or underflowed"
	::= { veStatEntry 7 }

veUflCnt OBJECT-TYPE
	SYNTAX Counter
	ACCESS read-only
	STATUS mandatory
	DESCRIPTION
	"Count of 1S intervals during which RX FIFO underflowed"
	::= { veStatEntry 8 }

veDisCnt OBJECT-TYPE
	SYNTAX Counter
	ACCESS read-only
	STATUS mandatory
	DESCRIPTION
	"Count of 1S intervals during which cells were discarded"
	::= { veStatEntry 9 }

veInvCnt OBJECT-TYPE
	SYNTAX Counter
	ACCESS read-only
	STATUS mandatory
	DESCRIPTION
	"Count of 1S intervals during which cells were invented"
	::= { veStatEntry 10 }

veResCnt OBJECT-TYPE
	SYNTAX Counter
	ACCESS read-only
	STATUS mandatory
	DESCRIPTION
	"Count of 1S intervals during which AAL1 resync occurred"
	::= { veStatEntry 11 }

veFifoLvlCnt OBJECT-TYPE
	SYNTAX Counter
	ACCESS read-only
	STATUS mandatory
	DESCRIPTION
	"Number of Cells currently in FIFO"
	::= { veStatEntry 12 }

--
-- Groups suported by the M-JPEG LIM card, for now tie this to the DV2 MIB definition

-- The Slip Group

jpegSlipIp OBJECT-TYPE
	SYNTAX  IpAddress
	ACCESS  read-write
	STATUS  mandatory
	DESCRIPTION
	"IP address of SLIP line."
	::= { mjlimSlipLine 1 }

jpegSlipMask OBJECT-TYPE
	SYNTAX  IpAddress
	ACCESS  read-write
	STATUS  mandatory
	DESCRIPTION
	"Mask for SLIP line."
	::= { mjlimSlipLine 2 }

jpegSlipRemoteIp OBJECT-TYPE
	SYNTAX  IpAddress
	ACCESS  read-write
	STATUS  mandatory
	DESCRIPTION
	"IP address of remote end of SLIP line."
	::= { mjlimSlipLine 3 }

jpegSlipSpeed OBJECT-TYPE
	SYNTAX  INTEGER {
		baud2400(1),
		baud4800(2),
		baud9600(3),
		baud19200(4),
		baud38400(5)
	}
	ACCESS  read-write
	STATUS  mandatory
	DESCRIPTION
	"Baud rate of SLIP serial line."
	DEFVAL { baud38400 }
	::= { mjlimSlipLine 4 }

-- The LIM System Group


--limSysCurrTime OBJECT-TYPE
--	SYNTAX	DisplayString (SIZE (0..255))
--	ACCESS	read-only
--	STATUS	mandatory
--	DESCRIPTION
--	"M-JPEG LIM System Time"
--	::= { mjlimSystem 1 }

limSysState OBJECT-TYPE
	SYNTAX	INTEGER { init(1), idle(2), start(3), working(4), terminate(5), fault(6) }
	ACCESS	read-only
	STATUS	mandatory
	DESCRIPTION
	"M-JPEG LIM System State"
	DEFVAL { init }
	::= { mjlimSystem 1 }

limSysFault OBJECT-TYPE
	SYNTAX	INTEGER { on(1), off(2) }
	ACCESS	read-only
	STATUS	mandatory
	DESCRIPTION
	"M-JPEG LIM Hardware Fault - front panel lamp"
	DEFVAL { off }
	::= { mjlimSystem 2 }

limSysCompErr OBJECT-TYPE
	SYNTAX	INTEGER { on(1), off(2) }
	ACCESS	read-only
	STATUS	mandatory
	DESCRIPTION
	"M-JPEG LIM Compression Error - front panel lamp"
	DEFVAL { off }
	::= { mjlimSystem 3 }

limSysDecompErr OBJECT-TYPE
	SYNTAX	INTEGER { on(1), off(2) }
	ACCESS	read-only
	STATUS	mandatory
	DESCRIPTION
	"M-JPEG LIM Decompression Error - front panel lamp"
	DEFVAL { off }
	::= { mjlimSystem 4 }

limSysVideoIn OBJECT-TYPE
	SYNTAX	INTEGER { on(1), off(2) }
	ACCESS	read-only
	STATUS	mandatory
	DESCRIPTION
	"M-JPEG LIM Video Input Present - front panel lamp"
	DEFVAL { off }
	::= { mjlimSystem 5 }

limSysVideoOut OBJECT-TYPE
	SYNTAX	INTEGER { on(1), off(2) }
	ACCESS	read-only
	STATUS	mandatory
	DESCRIPTION
	"M-JPEG LIM Video Output Active - front panel lamp"
	DEFVAL { off }
	::= { mjlimSystem 6 }

limSysStartMode OBJECT-TYPE
	SYNTAX	INTEGER { auto(1), force-init(2) }
	ACCESS	read-write
	STATUS	mandatory
	DESCRIPTION
	"M-JPEG LIM Default Startup mode"
	DEFVAL { auto }
	::= { mjlimSystem 30 }

-- The DSP Transfer Control Group

sendFileSel OBJECT-TYPE
	SYNTAX	INTEGER  { none(1), vjlim-cod(2), vjlca-cod(3) }
	ACCESS	read-write
	STATUS	mandatory
	DESCRIPTION
	"File to send"
	::= { mjlimControl 1 }

jpegCurrentFile OBJECT-TYPE
        SYNTAX  INTEGER  { none(1), vjlim-cod(2), vjlca-cod(3) }
	ACCESS  read-only
	STATUS  mandatory
	DESCRIPTION
	"File being sent"
	::= { mjlimControl 2 }

sendFileStat OBJECT-TYPE
	SYNTAX	INTEGER  { idle(1), start(2), continue(3), end(4), ack(5), aborted(6), error(7) }
	ACCESS	read-only
	STATUS	mandatory
	DESCRIPTION
	"Status of file send"
	::= { mjlimControl 3 }

sendFileBytes OBJECT-TYPE
	SYNTAX	INTEGER
	ACCESS	read-only
	STATUS	mandatory
	DESCRIPTION
	"Bytes sent"
	::= { mjlimControl 4 }

jpegReset OBJECT-TYPE
	SYNTAX  INTEGER  {
		no(1),
		reset(2)
	}
	ACCESS  read-write
	STATUS  mandatory
	DESCRIPTION
	"Hard/Soft Reset"
	::= { mjlimControl 20 }

jpegSaveCfg OBJECT-TYPE
        SYNTAX  INTEGER  {
                no(1),
                yes(2)
        }
        ACCESS  read-write
        STATUS  mandatory
        DESCRIPTION
        "Save Configuration"
        ::= { mjlimControl 21 }

jpegLoadCfg OBJECT-TYPE
        SYNTAX  INTEGER  {
                no(1),
                yes(2)
        }
        ACCESS  read-write
        STATUS  mandatory
        DESCRIPTION
        "Load Configuration"
        ::= { mjlimControl 22 }

jpegSWRev OBJECT-TYPE
	SYNTAX DisplayString (SIZE (0..10))
	ACCESS read-only
	STATUS mandatory
	DESCRIPTION
	"JPEG Code Revision"
	::= { mjlimControl 40 }

-- The Video Input Group

vidInJpeg OBJECT-TYPE
	SYNTAX	INTEGER { start(1), stop(2) }
	ACCESS	read-write
	STATUS	mandatory
	DESCRIPTION
	"M-JPEG LIM Video Input JPEG mode"
	DEFVAL { start }
	::= { vidInCfg 1 }

vidInRate OBJECT-TYPE
	SYNTAX	INTEGER { mbps25(1), mbps20(2), mbps15(3), mbps10(4), mbps5(5) }
	ACCESS	read-write
	STATUS	mandatory
	DESCRIPTION
	"M-JPEG LIM Video Input Channel Bit Rate"
	DEFVAL { mbps20 }
	::= { vidInCfg 2 }

vidInProvMode OBJECT-TYPE
	SYNTAX	INTEGER { auto(1), manual(2) }
	ACCESS	read-write
	STATUS	mandatory
	DESCRIPTION
	"M-JPEG LIM Video Input Provisioning Mode"
	DEFVAL { auto }
	::= { vidInCfg 3 }

vidInFrameRate OBJECT-TYPE
	SYNTAX	INTEGER { full(1) }
	ACCESS	read-write
	STATUS	mandatory
	DESCRIPTION
	"M-JPEG LIM Video Input Frame Rate"
	DEFVAL { full }
	::= { vidInCfg 4 }

vidInWindowSize OBJECT-TYPE
	SYNTAX	INTEGER { full-screen(1), constrained(2) }
	ACCESS	read-write
	STATUS	mandatory
	DESCRIPTION
	"M-JPEG LIM Video Input Window size"
	DEFVAL { full-screen }
	::= { vidInCfg 5 }

vidInQuanFactor OBJECT-TYPE
	SYNTAX	INTEGER (10..100)
	ACCESS	read-write
	STATUS	mandatory
	DESCRIPTION
	"M-JPEG LIM Video Input Quantization factor"
	DEFVAL { 30 }
	::= { vidInCfg 6 }


vidInTransMode OBJECT-TYPE
        SYNTAX  INTEGER { cbr(1), capped-vbr(2) }
        ACCESS  read-write
        STATUS  mandatory
        DESCRIPTION
        "M-JPEG LIM Video Input Transmit Mode"
        DEFVAL { cbr }
        ::= { vidInCfg 7 }



vidInStand OBJECT-TYPE
	SYNTAX	INTEGER { ntsc(1), pal(2) }
	ACCESS	read-write
	STATUS	mandatory
	DESCRIPTION
	"M-JPEG LIM Video Input Standard"
	DEFVAL { ntsc }
	::= { vidInCfg 8 }

vidInVcrMode OBJECT-TYPE
	SYNTAX	INTEGER { on(1), off(2) }
	ACCESS	read-write
	STATUS	mandatory
	DESCRIPTION
	"M-JPEG LIM Video Input VCR mode"
	DEFVAL { off }
	::= { vidInCfg 9 }

vidInAnLpbk OBJECT-TYPE
	SYNTAX	INTEGER { on(1), off(2) }
	ACCESS	read-write
	STATUS	mandatory
	DESCRIPTION
	"M-JPEG LIM Video Input Analog Loopback"
	DEFVAL { off }
	::= { vidInCfg 10 }

vidInTest OBJECT-TYPE
	SYNTAX	INTEGER { on(1), off(2) }
	ACCESS	read-write
	STATUS	mandatory
	DESCRIPTION
	"M-JPEG LIM Video Input Test Pattern"
	DEFVAL { off }
	::= { vidInCfg 11 }


-- The Video Input Status Group


vidInState OBJECT-TYPE
	SYNTAX	INTEGER { init(1), idle(2), start(3), working(4), terminate(5), fault(6) }
	ACCESS	read-only
	STATUS	mandatory
	DESCRIPTION
	"M-JPEG LIM Video Input State"
	DEFVAL { init }
	::= { vidInSta 1 }

vidInPres OBJECT-TYPE
	SYNTAX	INTEGER { on(1), off(2) }
	ACCESS	read-only
	STATUS	mandatory
	DESCRIPTION
	"M-JPEG LIM Video Input Present Indicator"
	DEFVAL { off }
	::= { vidInSta 2 }

vidInCurQFactor OBJECT-TYPE
	SYNTAX	INTEGER
	ACCESS	read-only
	STATUS	mandatory
	DESCRIPTION
	"M-JPEG LIM Video Input Current Quality Factor"
	::= { vidInSta 3 }

vidInCurFrameRate OBJECT-TYPE
	SYNTAX	INTEGER
	ACCESS	read-only
	STATUS	mandatory
	DESCRIPTION
	"M-JPEG LIM Video Input Current Frame Rate"
	::= { vidInSta 4 }

vidInAvgBitRate OBJECT-TYPE
	SYNTAX	INTEGER
	ACCESS	read-only
	STATUS	mandatory
	DESCRIPTION
	"M-JPEG LIM Video Input Average Bitrate (Mpbs)"
	::= { vidInSta 5 }

vidInPeakBitRate OBJECT-TYPE
	SYNTAX	INTEGER
	ACCESS	read-only
	STATUS	mandatory
	DESCRIPTION
	"M-JPEG LIM Video Input Peak Bitrate (Mbps)"
	::= { vidInSta 6 }

vidInSubSample OBJECT-TYPE
	SYNTAX	INTEGER	 { on(1), off(2) }
	ACCESS	read-only
	STATUS	mandatory
	DESCRIPTION
	"M-JPEG LIM Video Input Field Subsample Status"
	::= { vidInSta 7 }

vidInCompCnt OBJECT-TYPE
	SYNTAX	Counter
	ACCESS	read-only
	STATUS	mandatory
	DESCRIPTION
	"M-JPEG LIM Video Input Compressed Packet Count"
	::= { vidInSta 8 }

vidInSkipCnt OBJECT-TYPE
	SYNTAX	Counter
	ACCESS	read-only
	STATUS	mandatory
	DESCRIPTION
	"M-JPEG LIM Video Input Skipped Packet Count"
	::= { vidInSta 9 }

vidInBuffOvf OBJECT-TYPE
	SYNTAX	Counter
	ACCESS	read-only
	STATUS	mandatory
	DESCRIPTION
	"M-JPEG LIM Video Input Buffer Controller Overflow Count"
	::= { vidInSta 10 }

vidInImageErr OBJECT-TYPE
	SYNTAX	Counter
	ACCESS	read-only
	STATUS	mandatory
	DESCRIPTION
	"M-JPEG LIM Video Input JPEG Chip FIFO Overflow"
	::= { vidInSta 11 }

vidInFldSynErr OBJECT-TYPE
	SYNTAX	Counter
	ACCESS	read-only
	STATUS	mandatory
	DESCRIPTION
	"M-JPEG LIM Video Input Field Synchronization Errors"
	::= { vidInSta 12 }

vidInCompErr OBJECT-TYPE
	SYNTAX	Counter
	ACCESS	read-only
	STATUS	mandatory
	DESCRIPTION
	"M-JPEG LIM Video Input Compression Errors"
	::= { vidInSta 13 }

vidInBufLevel OBJECT-TYPE
	SYNTAX	INTEGER
	ACCESS	read-only
	STATUS	mandatory
	DESCRIPTION
	"M-JPEG LIM Video Input Buffer Fill Level (%)"
	::= { vidInSta 14 }

vidInFailReason OBJECT-TYPE
	SYNTAX	INTEGER { none(1), ccube(2), timeout(3), channel(4), xilinx(5), badparms(6), algorithm(7) }
	ACCESS	read-only
	STATUS	mandatory
	DESCRIPTION
	"M-JPEG LIM Video Input Fail Reason"
	DEFVAL { none }
	::= { vidInSta 15 }


--- The Video Out Configuration Group

vidOutJpeg OBJECT-TYPE
	SYNTAX	INTEGER { start(1), stop(2) }
	ACCESS	read-write
	STATUS	mandatory
	DESCRIPTION
	"M-JPEG LIM Video Output JPEG Mode"
	DEFVAL { start }
	::= { vidOutCfg 1 }

vidOutStand OBJECT-TYPE
	SYNTAX	INTEGER { ntsc(1), pal(2), auto-sel(3) }
	ACCESS	read-write
	STATUS	mandatory
	DESCRIPTION
	"M-JPEG LIM Video Output Standard"
	DEFVAL { ntsc }
	::= { vidOutCfg 2 }

vidOutSource OBJECT-TYPE
	SYNTAX	INTEGER { genlock(1), through(2), free(3) }
	ACCESS	read-write
	STATUS	mandatory
	DESCRIPTION
	"M-JPEG LIM Video Output Timing Source"
	DEFVAL { through }
	::= { vidOutCfg 3 }

vidOutUnLpb OBJECT-TYPE
	SYNTAX	INTEGER { on(1), off(2) }
	ACCESS	read-write
	STATUS	mandatory
	DESCRIPTION
	"M-JPEG LIM Video Output Uncompressed Loopback"
	DEFVAL { off }
	::= { vidOutCfg 4 }

vidOutIdleSrc OBJECT-TYPE
	SYNTAX	INTEGER { black(1), color(2) }
	ACCESS	read-write
	STATUS	mandatory
	DESCRIPTION
	"M-JPEG LIM Video Output Idle Source"
	DEFVAL { black }
	::= { vidOutCfg 5 }

vidOutChnlLpbk OBJECT-TYPE
	SYNTAX	INTEGER { on(1), off(2) }
	ACCESS	read-write
	STATUS	mandatory
	DESCRIPTION
	"M-JPEG LIM Video Output Channel Loopback"
	DEFVAL { off }
	::= { vidOutCfg 6 }

--- The Video Out Status Group

vidOutState OBJECT-TYPE
	SYNTAX	INTEGER { init(1), idle(2), start(3), working(4), terminate(5), fault(6) }
	ACCESS	read-only
	STATUS	mandatory
	DESCRIPTION
	"M-JPEG LIM Video Output state"
	DEFVAL { init }
	::= { vidOutSta 1 }

vidOutRate OBJECT-TYPE
	SYNTAX	INTEGER
	ACCESS	read-only
	STATUS	mandatory
	DESCRIPTION
	"M-JPEG LIM Video Output Bitrate (Mbps)"
	::= { vidOutSta 2 }

vidOutFrameRate OBJECT-TYPE
	SYNTAX	INTEGER
	ACCESS	read-only
	STATUS	mandatory
	DESCRIPTION
	"M-JPEG LIM Video Output Frame Rate"
	::= { vidOutSta 3 }

vidOutWindowWidth OBJECT-TYPE
	SYNTAX	INTEGER
	ACCESS	read-only
	STATUS	mandatory
	DESCRIPTION
	"M-JPEG LIM Video Output Window Width"
	::= { vidOutSta 4 }

vidOutWindowHeight OBJECT-TYPE
	SYNTAX	INTEGER
	ACCESS	read-only
	STATUS	mandatory
	DESCRIPTION
	"M-JPEG LIM Video Output Window Height"
	::= { vidOutSta 5 }

vidOutChnlLock OBJECT-TYPE
	SYNTAX	INTEGER { on(1), off(2) }
	ACCESS	read-only
	STATUS	mandatory
	DESCRIPTION
	"M-JPEG LIM Video Output Channel Lock Indicator"
	::= { vidOutSta 6 }

vidOutPackets OBJECT-TYPE
	SYNTAX	Counter
	ACCESS	read-only
	STATUS	mandatory
	DESCRIPTION
	"M-JPEG LIM Video Output Packets Received Count"
	::= { vidOutSta 7 }

vidOutPlayed OBJECT-TYPE
	SYNTAX	Counter
	ACCESS	read-only
	STATUS	mandatory
	DESCRIPTION
	"M-JPEG LIM Video Output Packets Played Count"
	::= { vidOutSta 8 }

vidOutSkipped OBJECT-TYPE
	SYNTAX	Counter
	ACCESS	read-only
	STATUS	mandatory
	DESCRIPTION
	"M-JPEG LIM Video Output Skipped Packet Count"
	::= { vidOutSta 9 }

vidOutChnlErr OBJECT-TYPE
	SYNTAX	Counter
	ACCESS	read-only
	STATUS	mandatory
	DESCRIPTION
	"M-JPEG LIM Video Output Channel Error Count"
	::= { vidOutSta 10 }

vidOutBuffOvf OBJECT-TYPE
	SYNTAX	Counter
	ACCESS	read-only
	STATUS	mandatory
	DESCRIPTION
	"M-JPEG LIM Video Output Buffer Controller Overflow Count"
	::= { vidOutSta 11 }

vidOutImageErr OBJECT-TYPE
	SYNTAX	Counter
	ACCESS	read-only
	STATUS	mandatory
	DESCRIPTION
	"M-JPEG LIM Video Output JPEG Chip Error Count"
	::= { vidOutSta 12 }

vidOutSeqnoErr OBJECT-TYPE
	SYNTAX	Counter
	ACCESS	read-only
	STATUS	mandatory
	DESCRIPTION
	"M-JPEG LIM Video Output Packet Sequence Number Error Count"
	::= { vidOutSta 13 }

vidOutCurrQFactor OBJECT-TYPE
	SYNTAX	INTEGER
	ACCESS	read-only
	STATUS	mandatory
	DESCRIPTION
	"M-JPEG LIM Video Output Current JPEG Quantization Factor"
	::= { vidOutSta 14 }

vidOutStdStat OBJECT-TYPE
	SYNTAX	INTEGER { ntsc(1), pal(2) }
	ACCESS	read-only
	STATUS	mandatory
	DESCRIPTION
	"M-JPEG LIM Video Output Standard Status"
	::= { vidOutSta 15 }

vidOutBuffLevel OBJECT-TYPE
	SYNTAX	INTEGER
	ACCESS	read-only
	STATUS	mandatory
	DESCRIPTION
	"M-JPEG LIM Video Output Buffer Fill Level (%)"
	::= { vidOutSta 16 }

vidOutPktsInBuff OBJECT-TYPE
	SYNTAX	INTEGER
	ACCESS	read-only
	STATUS	mandatory
	DESCRIPTION
	"M-JPEG LIM Video Output Packets in Buffer"
	::= { vidOutSta 17 }

vidOutFailReason OBJECT-TYPE
	SYNTAX	INTEGER { none(1), ccube(2), timeout(3), channel(4), xilinx(5), badparms(6), algorithm(7) }
	ACCESS	read-only
	STATUS	mandatory
	DESCRIPTION
	"M-JPEG LIM Video Output Fail Reason"
	DEFVAL { none }
	::= { vidOutSta 18 }

vidOutSrcSts OBJECT-TYPE
	SYNTAX	INTEGER { genlock(1), through(2), free(3) }
	ACCESS	read-only
	STATUS	mandatory
	DESCRIPTION
	"M-JPEG LIM Video Output Timing Source Status"
	DEFVAL { genlock }
	::= { vidOutSta 19 }

-- The Audio Input Group

audInLoopBack OBJECT-TYPE
	SYNTAX	INTEGER { on(1), off(2) }
	ACCESS	read-write
	STATUS	mandatory
	DESCRIPTION
	"M-JPEG LIM Audio Input LoopBack Mode"
	DEFVAL { off }
	::= { audInCfg 1 }

-- The Audio Output Group


audOutMute OBJECT-TYPE
	SYNTAX	INTEGER { on(1), off(2) }
	ACCESS	read-write
	STATUS	mandatory
	DESCRIPTION
	"M-JPEG LIM Audio Output Mute Control"
	DEFVAL { off }
	::= { audOutCfg 1 }

audOutDigLpbk OBJECT-TYPE
	SYNTAX	INTEGER { on(1), off(2) }
	ACCESS	read-write
	STATUS	mandatory
	DESCRIPTION
	"M-JPEG LIM Audio Digital Loopback"
	DEFVAL { off }
	::= { audOutCfg 2 }

audOutLock OBJECT-TYPE
	SYNTAX	INTEGER { on(1), off(2) }
	ACCESS	read-only
	STATUS	mandatory
	DESCRIPTION
	"M-JPEG LIM Audio Output Channel Lock Indicator"
	DEFVAL { off }
	::= { audOutSta 1 }

audOutMuteStat OBJECT-TYPE
	SYNTAX	INTEGER { on(1), off(2) }
	ACCESS	read-only
	STATUS	mandatory
	DESCRIPTION
	"M-JPEG LIM Audio Output Mute Status"
	::= { audOutSta 2 }

-- The Data Configuration Group

dataIp OBJECT-TYPE
	SYNTAX  IpAddress
	ACCESS  read-write
	STATUS  mandatory
	DESCRIPTION
	"IP address of Data Channel."
	::= { dataCfg 1 }

dataMask OBJECT-TYPE
	SYNTAX  IpAddress
	ACCESS  read-write
	STATUS  mandatory
	DESCRIPTION
	" Network Mask for Data Channel."
	::= { dataCfg 2 }

dataRemoteIp OBJECT-TYPE
	SYNTAX  IpAddress
	ACCESS  read-write
	STATUS  mandatory
	DESCRIPTION
	"IP address of remote end of Data Channel."
	::= { dataCfg 3 }


-- ***************************************************************************

-- VH320 LIM Objects

-- The VH320 System Group

limHostRev OBJECT-TYPE
	SYNTAX DisplayString (SIZE (0..10))
	ACCESS read-only
	STATUS mandatory
	DESCRIPTION
	"Host S/W Revision"
	::= { vhsystem 1 }

limBootRev OBJECT-TYPE
	SYNTAX DisplayString (SIZE (0..10))
	ACCESS read-only
	STATUS mandatory
	DESCRIPTION
	"Boot S/W Revision"
	::= { vhsystem 2 }

limHwRev OBJECT-TYPE
	SYNTAX DisplayString (SIZE (0..10))
	ACCESS read-only
	STATUS mandatory
	DESCRIPTION
	"Hardware Architecture"
	::= { vhsystem 3 }

limAction OBJECT-TYPE
	SYNTAX INTEGER { none(1),
			 reset(2),
			 test(3),
			 mtce(4) }
	ACCESS read-write
	STATUS mandatory
	DESCRIPTION
	"LIM action"
	DEFVAL { none }
	::= { vhsystem 4 }

limState OBJECT-TYPE
	SYNTAX INTEGER { init(1),
			 testing(2),
			 idle(3),
			 start(4),
			 working(5),
			 terminate(6),
			 fault(7),
			 mtce(8),
			 loading(9),
			 await-framing(10) }
	ACCESS read-only
	STATUS mandatory
	DESCRIPTION
	"LIM state"
	DEFVAL { init }
	::= { vhsystem 5 }

limFault OBJECT-TYPE
	SYNTAX INTEGER  { off(1),
			  on(2) }
	ACCESS read-only
	STATUS mandatory
	DESCRIPTION
	"LIM Fault LED"
	DEFVAL { off }
	::= { vhsystem 6 }

limFaultReason OBJECT-TYPE
	SYNTAX INTEGER { none(1),
			 bad-rev(2),
			 hw-fault(3),
			 memory(4),
			 fileio(5),
			 codec-section(6),
			 sw-error(7) }
	ACCESS read-only
	STATUS mandatory
	DESCRIPTION
	"LIM Fault Reason"
	::= { vhsystem 7 }

limCodec0 OBJECT-TYPE
	SYNTAX INTEGER  { off(1),
			  on(2) }
	ACCESS read-only
	STATUS mandatory
	DESCRIPTION
	"H.320 Codec 0 Active LED"
	DEFVAL { off }
	::= { vhsystem 8 }

limCodec1 OBJECT-TYPE
	SYNTAX INTEGER { off(1),
			 on(2) }
	ACCESS read-only
	STATUS mandatory
	DESCRIPTION
	"H.320 Codec 1 Active LED"
	DEFVAL { on }
	::= { vhsystem 9 }

limSCmgmt OBJECT-TYPE
	SYNTAX INTEGER { up(1),
			 down(2) }
	ACCESS read-only
	STATUS mandatory
	DESCRIPTION
	"Slot Controller Mgmt Link Status"
	DEFVAL { down }
	::= { vhsystem 10 }

limSCmgmtData OBJECT-TYPE
	SYNTAX INTEGER { idle(1),
			 start(2),
			 continue(3),
			 end(4),
			 ack(5),
			 aborted(6),
			 error(7) }
	ACCESS read-only
	STATUS mandatory
	DESCRIPTION
	"Slot Controller Mgmt Information Data State"
	DEFVAL { idle }
	::= { vhsystem 11 }

limSCfileXferReq OBJECT-TYPE
	SYNTAX INTEGER { none(1),
			 vh320-cod(2),
			 vhdev-cod(3) }
	ACCESS read-write
	STATUS mandatory
	DESCRIPTION
	"Slot Controller Mgmt File Transfer Request"
	DEFVAL { none }
	::= { vhsystem 12 }

limSCfileXferStat OBJECT-TYPE
	SYNTAX INTEGER { idle(1),
			 start(2),
			 continue(3),
			 end(4),
			 ack(5),
			 aborted(6),
			 error(7) }
	ACCESS read-only
	STATUS mandatory
	DESCRIPTION
	"Slot Controller Mgmt File Transfer State"
	DEFVAL { idle }
	::= { vhsystem 13 }

limSCbytes OBJECT-TYPE
	SYNTAX INTEGER
	ACCESS read-only
	STATUS mandatory
	DESCRIPTION
	"Slot Controller Mgmt File Transfer Byte Count"
	::= { vhsystem 14 }




-- The VH320 Codec Control Group

-- Call Control Table

ctrlTable OBJECT-TYPE
	SYNTAX SEQUENCE OF CtrlEntry
	ACCESS not-accessible
	STATUS mandatory
	::= { vhcontrol 1 }

ctrlEntry OBJECT-TYPE
	SYNTAX CtrlEntry
	ACCESS not-accessible
	STATUS mandatory
	INDEX { ctrlIndex }
	::= { ctrlTable 1 }

CtrlEntry ::=
	SEQUENCE{
		ctrlIndex
			INTEGER,
		ctrlCodecType
			INTEGER,
		ctrlCodecAction
			INTEGER,
		ctrlCodecReq
			INTEGER,
		ctrlCallType
			INTEGER,
		ctrlCodecSta
			INTEGER,
		ctrlChnlLpbk
			INTEGER,
		ctrlFraming
			INTEGER,
		ctrlChnlStat
			INTEGER,
		ctrlFaultReason
			INTEGER
	}

ctrlIndex OBJECT-TYPE
	SYNTAX INTEGER  (0..1)
	ACCESS read-only
	STATUS mandatory
	DESCRIPTION
	"Codec Index"
	::= { ctrlEntry 1 }

ctrlCodecType OBJECT-TYPE
	SYNTAX INTEGER { h320(1) }
	ACCESS read-only
	STATUS mandatory
	DESCRIPTION
	"Codec Type"
	DEFVAL { h320 }
	::= { ctrlEntry 2 }

ctrlCodecAction OBJECT-TYPE
	SYNTAX INTEGER { none(1),
			 reset(2),
			 test(3),
			 mtce(4) }
	ACCESS read-write
	STATUS mandatory
	DESCRIPTION
	"Codec Action"
	DEFVAL { none }
	::= { ctrlEntry 3 }

ctrlCodecReq OBJECT-TYPE
	SYNTAX INTEGER { connect(1),
			 disconnect(2) }
	ACCESS read-write
	STATUS mandatory
	DESCRIPTION
	"Codec Request"
	DEFVAL { connect }
	::= { ctrlEntry 4 }

ctrlCallType OBJECT-TYPE
	SYNTAX INTEGER { h0(1) }
	ACCESS read-only
	STATUS mandatory
	DESCRIPTION
	"Codec Call Type"
	DEFVAL { h0 }
	::= { ctrlEntry 5 }

ctrlCodecSta OBJECT-TYPE
	SYNTAX INTEGER { init(1),
			 testing(2),
			 idle(3),
			 start(4),
			 working(5),
			 terminate(6),
			 fault(7),
			 mtce(8),
			 loading(9),
			 await-framing(10) }
	ACCESS read-only
	STATUS mandatory
	DESCRIPTION
	"Codec Status"
	::= { ctrlEntry 6 }

ctrlChnlLpbk OBJECT-TYPE
	SYNTAX INTEGER { none(1),
			 to-other(2),
			 to-self(3) }
	ACCESS read-write
	STATUS mandatory
	DESCRIPTION
	"Codec Channel Loopback"
	DEFVAL { none }
	::= { ctrlEntry 7 }

ctrlFraming OBJECT-TYPE
	SYNTAX INTEGER { no(1),
			 yes(2) }
	ACCESS read-only
	STATUS mandatory
	DESCRIPTION
	"Codec H.221 Framing Detected"
	::= { ctrlEntry 8 }

ctrlChnlStat OBJECT-TYPE
	SYNTAX INTEGER { down(1),
			 idle(2),
			 up(3),
			 loopback(4) }
	ACCESS read-only
	STATUS mandatory
	DESCRIPTION
	"Codec Channel Link Status"
	::= { ctrlEntry 9 }

ctrlFaultReason OBJECT-TYPE
	SYNTAX INTEGER { none(1),
			 host(2),
			 video(3),
			 audio(4),
			 data(5),
			 fileio(6),
			 mem(7),
			 h221(8),
			 h242(9),
			 tdm(10) }
	ACCESS read-only
	STATUS mandatory
	DESCRIPTION
	"Codec Fault Reason"
	::= { ctrlEntry 10 }




-- The Video Table

vidTable OBJECT-TYPE
	SYNTAX SEQUENCE OF VidEntry
	ACCESS not-accessible
	STATUS mandatory
	::= { vhcontrol 2 }

vidEntry OBJECT-TYPE
	SYNTAX VidEntry
	ACCESS not-accessible
	STATUS mandatory
	INDEX { vidIndex }
	::= { vidTable 1 }

VidEntry ::=
	SEQUENCE{
		vidIndex
			INTEGER,
		vidStandard
			INTEGER,
		vidTxVidReq
			INTEGER,
		vidRxVidReq
			INTEGER,
		vidViewPip
			INTEGER,
		vidCompQual
			INTEGER,
		vidEncFrameCount
			Counter,
		vidDecFrameCount
			Counter,
		vidState
			INTEGER,
		vidInPresent
			INTEGER,
		vidEncBitRate
			INTEGER,
		vidDigLpbk
			INTEGER
	}

vidIndex OBJECT-TYPE
	SYNTAX	INTEGER (0..1)
	ACCESS	read-only
	STATUS	mandatory
	DESCRIPTION
	"VH320 Codec Index"
	::= { vidEntry 1 }

vidStandard OBJECT-TYPE
	SYNTAX	INTEGER { ntsc(1),
			  pal(2) }
	ACCESS	read-write
	STATUS	mandatory
	DESCRIPTION
	"VH320 Analog Video I/O Standard"
	DEFVAL { ntsc }
	::= { vidEntry 2 }

vidTxVidReq OBJECT-TYPE
	SYNTAX	INTEGER { normal(1),
			  freeze(2),
			  mute(3) }
	ACCESS	read-write
	STATUS	mandatory
	DESCRIPTION
	"VH320 Transmit Video Request"
	DEFVAL { normal }
	::= { vidEntry 3 }

vidRxVidReq OBJECT-TYPE
	SYNTAX	INTEGER { normal(1),
			  freeze(2),
			  mute(3) }
	ACCESS	read-write
	STATUS	mandatory
	DESCRIPTION
	"VH320 Display Video Request"
	DEFVAL { normal }
	::= { vidEntry 4 }

vidViewPip OBJECT-TYPE
	SYNTAX	INTEGER { no(1),
			  yes(2) }
	ACCESS	read-write
	STATUS	mandatory
	DESCRIPTION
	"VH320 View Self Picture in Picture"
	DEFVAL { no }
	::= { vidEntry 5 }

vidCompQual OBJECT-TYPE
	SYNTAX	INTEGER { best-picture(1),
			  best-motion(2) }
	ACCESS	read-write
	STATUS	mandatory
	DESCRIPTION
	"VH320 Compression Quality"
	DEFVAL { best-picture }
	::= { vidEntry 6 }

vidDigLpbk OBJECT-TYPE
	SYNTAX	INTEGER { no(1),
			  yes(2) }
	ACCESS	read-write
	STATUS	mandatory
	DESCRIPTION
	"VH320 Digital Loopback"
	::= { vidEntry 7 }

vidEncFrameCount OBJECT-TYPE
	SYNTAX  Counter
	ACCESS	read-only
	STATUS	mandatory
	DESCRIPTION
	"VH320 Video Encoded Frame Count"
	::= { vidEntry 8 }

vidDecFrameCount OBJECT-TYPE
	SYNTAX	Counter
	ACCESS	read-only
	STATUS	mandatory
	DESCRIPTION
	"VH320 Video Decoded Frame Count"
	::= { vidEntry 9 }

vidState OBJECT-TYPE
	SYNTAX	INTEGER { init(1),
			  diag(2),
			  idle(3),
			  start(4),
			  working(5),
			  terminate(6),
			  fault(7) }
	ACCESS	read-only
	STATUS	mandatory
	DESCRIPTION
	"VH320 Video State"
	DEFVAL { idle }
	::= { vidEntry 10 }

vidInPresent OBJECT-TYPE
	SYNTAX	INTEGER { no(1),
			  yes(2) }
	ACCESS	read-only
	STATUS	mandatory
	DESCRIPTION
	"VH320 Video Input Present"
	DEFVAL { no }
	::= { vidEntry 11 }

vidEncBitRate OBJECT-TYPE
        SYNTAX  INTEGER
        ACCESS  read-only
        STATUS  mandatory
        DESCRIPTION
        "VH320 Encoded Bitrate (bps)"
        ::= { vidEntry 12 }


-- The Audio Table

audTable OBJECT-TYPE
	SYNTAX SEQUENCE OF AudEntry
	ACCESS not-accessible
	STATUS mandatory
	::= { vhcontrol 3 }

audEntry OBJECT-TYPE
	SYNTAX AudEntry
	ACCESS not-accessible
	STATUS mandatory
	INDEX { audIndex }
	::= { audTable 1 }

AudEntry ::=
	SEQUENCE{
		audIndex
			INTEGER,
		audState
			INTEGER,
		audPrefMode
			INTEGER,
		audCommMode
			INTEGER,
		audBitRate
			INTEGER,
		audMuteInReq
			INTEGER,
		audMuteOutReq
			INTEGER,
		audMuteOutStat
			INTEGER,
		audLpbk
			INTEGER,
		audInVol
			INTEGER,
		audOutVol
			INTEGER,
		audInDelay
			INTEGER,
		audOutDelay
			INTEGER,
		audFaultReason
			INTEGER
	}

audIndex OBJECT-TYPE
	SYNTAX	INTEGER (0..1)
	ACCESS	read-only
	STATUS	mandatory
	DESCRIPTION
	"VH320 Codec Index"
	::= { audEntry 1 }

audState OBJECT-TYPE
	SYNTAX	INTEGER { init(1),
			  testing(2),
			  idle(3),
			  start(4),
			  working(5),
			  terminate(6),
			  fault(7),
			  mtce(8),
			  loading(9),
			  await-framing(10) }
	ACCESS	read-only
	STATUS	mandatory
	DESCRIPTION
	"VH320 Audio State"
	::= { audEntry 2 }

audPrefMode OBJECT-TYPE
	SYNTAX	INTEGER { u-law(1),
			  a-law(2),
			  g722(3),
			  g728(4) }
	ACCESS	read-write
	STATUS	mandatory
	DESCRIPTION
	"VH320 Audio Preferred Coding Mode"
	DEFVAL { g722 }
	::= { audEntry 3 }

audCommMode OBJECT-TYPE
	SYNTAX	INTEGER { u-law(1),
			  a-law(2),
			  g722(3),
			  g728(4) }
	ACCESS	read-only
	STATUS	mandatory
	DESCRIPTION
	"VH320 Audio Common Coding Mode"
	DEFVAL { g722 }
	::= { audEntry 4 }

audBitRate OBJECT-TYPE
	SYNTAX	INTEGER
	ACCESS	read-only
	STATUS	mandatory
	DESCRIPTION
	"VH320 Audio Bit Rate (bps)"
	::= { audEntry 5 }

audMuteInReq OBJECT-TYPE
	SYNTAX	INTEGER { off(1),
			  on(2) }
	ACCESS	read-write
	STATUS	mandatory
	DESCRIPTION
	"VH320 Audio Mute Input Request"
	DEFVAL { off }
	::= { audEntry 6 }

audMuteOutReq OBJECT-TYPE
	SYNTAX	INTEGER { off(1),
			  on(2) }
	ACCESS	read-write
	STATUS	mandatory
	DESCRIPTION
	"VH320 Audio Mute Output Request"
	::= { audEntry 7 }

audMuteOutStat OBJECT-TYPE
	SYNTAX	INTEGER { off(1),
			  on(2),
			  auto(3) }
	ACCESS	read-only
	STATUS	mandatory
	DESCRIPTION
	"VH320 Audio Mute Output Status"
	::= { audEntry 8 }

audLpbk OBJECT-TYPE
	SYNTAX	INTEGER { none(1),
			  analog-in(2),
			  digital-in(3),
			  compress-in(4),
			  analog-out(5),
			  digital-out(6),
			  compress-out(7) }
	ACCESS	read-write
	STATUS	mandatory
	DESCRIPTION
	"VH320 Audio Loopback Request"
	DEFVAL { none }
	::= { audEntry 9 }

audInVol OBJECT-TYPE
	SYNTAX	INTEGER (0..255)
	ACCESS	read-write
	STATUS	mandatory
	DESCRIPTION
	"VH320 Audio Input Volume"
	DEFVAL { 64 }
	::= { audEntry 10 }

audOutVol OBJECT-TYPE
	SYNTAX	INTEGER (0..255)
	ACCESS	read-write
	STATUS	mandatory
	DESCRIPTION
	"VH320 Audio Output Volume"
	DEFVAL { 255 }
	::= { audEntry 11 }

audInDelay OBJECT-TYPE
	SYNTAX	INTEGER (0..200)
	ACCESS	read-write
	STATUS	mandatory
	DESCRIPTION
	"VH320 Audio Input Delay Request (ms)"
	DEFVAL { 150 }
	::= { audEntry 12 }

audOutDelay OBJECT-TYPE
	SYNTAX	INTEGER (0..200)
	ACCESS	read-write
	STATUS	mandatory
	DESCRIPTION
	"VH320 Audio Output Delay Status (ms)"
	DEFVAL { 150 }
	::= { audEntry 13 }

audFaultReason OBJECT-TYPE
	SYNTAX	INTEGER { none(1),
			  mem(2),
			  self-test(3),
			  download(4),
			  loopback(5),
			  dsp(6) }
	ACCESS	read-only
	STATUS	mandatory
	DESCRIPTION
	"VH320 Audio Fault Reason"
	DEFVAL { none }
	::= { audEntry 14 }


-- The Data Port Group

dataTable OBJECT-TYPE
	SYNTAX SEQUENCE OF DataEntry
	ACCESS not-accessible
	STATUS mandatory
	::= { vhcontrol 4 }

dataEntry OBJECT-TYPE
	SYNTAX DataEntry
	ACCESS not-accessible
	STATUS mandatory
	INDEX { dataIndex }
	::= {  dataTable 1 }

DataEntry ::=
	SEQUENCE{
		dataIndex
			INTEGER,
		dataChnlType
			INTEGER,
		dataPortSpeed
			INTEGER,
		dataPortProt
			INTEGER,
		dataHDLCcheck
			INTEGER,
		dataChnlStat
			INTEGER,
		dataBytesRcvd
			Counter,
		dataBytesSent
			Counter,
		dataResetStat
			INTEGER
	}

dataIndex OBJECT-TYPE
	SYNTAX	INTEGER  (0..1)
	ACCESS	read-only
	STATUS	mandatory
	DESCRIPTION
	"VH320 Codec Index"
	::= { dataEntry 1 }

dataChnlType OBJECT-TYPE
        SYNTAX INTEGER { lsd(1),
			 hsd(2),
			 mlp(3),
			 hmlp(4),
			 none(5) }
        ACCESS  read-write
        STATUS  mandatory
        DESCRIPTION
        "Data Channel Type"
        ::= { dataEntry 2 }

dataPortSpeed OBJECT-TYPE
        SYNTAX INTEGER { baud-2400(1),
			 baud-9600(2),
			 baud-19200(3),
			 baud-38400(4) }
        ACCESS  read-write
        STATUS  mandatory
        DESCRIPTION
        "Data Port Speed (bps)"
	DEFVAL { baud-38400 }
        ::= { dataEntry 3 }

dataPortProt OBJECT-TYPE
        SYNTAX INTEGER { async(1),
			 hdlc(2) }
        ACCESS  read-write
        STATUS  mandatory
        DESCRIPTION
        "Data Port Protocol"
	DEFVAL { async }
        ::= { dataEntry 4 }

dataHDLCcheck OBJECT-TYPE
        SYNTAX INTEGER { no(1),
			 yes(2) }
        ACCESS  read-write
        STATUS  mandatory
        DESCRIPTION
        "HDLC Check CRC"
	DEFVAL { no }
        ::= { dataEntry 5 }

dataChnlStat OBJECT-TYPE
	SYNTAX	INTEGER { up(1),
			  down(2) }
        ACCESS  read-only
        STATUS  mandatory
        DESCRIPTION
        "Data Channel Status"
	DEFVAL { down }
        ::= { dataEntry 6 }

dataBytesRcvd OBJECT-TYPE
	SYNTAX	Counter
        ACCESS  read-only
        STATUS  mandatory
        DESCRIPTION
        "Data Channel Bytes Received"
        ::= { dataEntry 7 }

dataBytesSent OBJECT-TYPE
	SYNTAX	Counter
        ACCESS  read-only
        STATUS  mandatory
        DESCRIPTION
        "Data Channel Bytes Sent"
        ::= { dataEntry 8 }

dataResetStat OBJECT-TYPE
	SYNTAX	INTEGER { no(1),
			  yes(2) }
        ACCESS  read-write
        STATUS  mandatory
        DESCRIPTION
        "Data Channel Reset Statistics"
        ::= { dataEntry 9 }


-- The Management Port Group

mgmtTable OBJECT-TYPE
	SYNTAX SEQUENCE OF MgmtEntry
	ACCESS not-accessible
	STATUS mandatory
	::= { vhmgmt 1 }

mgmtEntry OBJECT-TYPE
	SYNTAX MgmtEntry
	ACCESS not-accessible
	STATUS mandatory
	INDEX { mgmtIndex }
	::= {  mgmtTable 1 }

MgmtEntry ::=
	SEQUENCE{
		mgmtIndex
			INTEGER,
		mgmtDescr
			DisplayString,
		mgmtPortProt
			INTEGER,
		mgmtPortSpeed
			INTEGER,
		mgmtPortAddress
			IpAddress,
		mgmtAddressMask
			IpAddress,
		mgmtRemoteAddress
			IpAddress,
		mgmtPortStat
			INTEGER,
		mgmtBytesRcvd
			Counter,
		mgmtBytesSent
			Counter,
		mgmtResetStat
			INTEGER
	}

mgmtIndex OBJECT-TYPE
	SYNTAX	INTEGER (0..1)
	ACCESS	read-only
	STATUS	mandatory
	DESCRIPTION
	"VH320 Management Port Index"
	::= { mgmtEntry 1 }

mgmtDescr OBJECT-TYPE
	SYNTAX	DisplayString
	ACCESS	read-only
	STATUS	mandatory
	DESCRIPTION
	" VH320 Management Port Descriptor"
	::= { mgmtEntry 2 }

mgmtPortProt OBJECT-TYPE
        SYNTAX INTEGER { async(1),
			 slip(2) }
        ACCESS  read-write
        STATUS  mandatory
        DESCRIPTION
        "Management Port Protocol"
	DEFVAL { async }
        ::= { mgmtEntry 3 }

mgmtPortSpeed OBJECT-TYPE
        SYNTAX	INTEGER { serial-200(1),
			  baud-2400(2),
			  baud-9600(3),
			  baud-19200(4),
			  baud-38400(5) }
        ACCESS  read-write
        STATUS  mandatory
        DESCRIPTION
        "Management Port Speed (bps)"
	DEFVAL { baud-38400 }
        ::= { mgmtEntry 4 }

mgmtPortAddress OBJECT-TYPE
        SYNTAX	IpAddress
        ACCESS  read-write
        STATUS  mandatory
        DESCRIPTION
        "Management Port Address"
        ::= { mgmtEntry 5 }

mgmtAddressMask OBJECT-TYPE
        SYNTAX	IpAddress
        ACCESS  read-write
        STATUS  mandatory
        DESCRIPTION
        "Management Port Address Mask"
        ::= { mgmtEntry 6 }

mgmtRemoteAddress OBJECT-TYPE
        SYNTAX	IpAddress
        ACCESS  read-write
        STATUS  mandatory
        DESCRIPTION
        "Management Remote Address"
        ::= { mgmtEntry 7 }

mgmtPortStat OBJECT-TYPE
	SYNTAX	INTEGER { up(1),
			  down(2) }
        ACCESS  read-only
        STATUS  mandatory
        DESCRIPTION
        "Management Port Status"
	DEFVAL { down }
        ::= { mgmtEntry 8 }

mgmtBytesRcvd OBJECT-TYPE
	SYNTAX	Counter
        ACCESS  read-only
        STATUS  mandatory
        DESCRIPTION
        "Management Bytes Received"
        ::= { mgmtEntry 9 }

mgmtBytesSent OBJECT-TYPE
	SYNTAX	Counter
        ACCESS  read-only
        STATUS  mandatory
        DESCRIPTION
        "Management Bytes Sent"
        ::= { mgmtEntry 10 }

mgmtResetStat OBJECT-TYPE
	SYNTAX	INTEGER { no(1),
			  yes(2) }
        ACCESS  read-write
        STATUS  mandatory
        DESCRIPTION
        "Management Reset Statistics"
        ::= { mgmtEntry 11 }


-- *************************************************************************
-- The OAM config table

oamTable OBJECT-TYPE
        SYNTAX SEQUENCE OF OamEntry
        ACCESS not-accessible
        STATUS mandatory
        DESCRIPTION
        "This table is used for per-port OAM configuration."
        ::= { dv2Oam 1 }

oamEntry OBJECT-TYPE
        SYNTAX  OamEntry
        ACCESS  not-accessible
        STATUS  mandatory
        INDEX   { oamLinkNo }
        ::= { oamTable 1 }

OamEntry ::=
	SEQUENCE {
		oamLinkNo
                        INTEGER,
		oamSegEndPoint
			INTEGER,
		oamVcEndPoint
			INTEGER,
		oamAisRdiGeneration
			INTEGER,
		oamLastRxType
			INTEGER,
		oamLastRxVpi
			VirtualPathIdentifier,
		oamLastRxVci
			VirtualCircuitIdentifier,
		oamRxCount
			Counter,
		oamLastTxType
			INTEGER,
		oamLastTxVpi
			VirtualPathIdentifier,
		oamLastTxVci
			VirtualCircuitIdentifier,
		oamTxCount
			Counter,
		oamClearStats
			INTEGER
		}

oamLinkNo       OBJECT-TYPE
        SYNTAX INTEGER (0..3)
        ACCESS read-only
        STATUS mandatory
        DESCRIPTION
        "The link number for this configuration."
        ::= { oamEntry 1 }

oamSegEndPoint  OBJECT-TYPE
        SYNTAX INTEGER {
                yes(1),
                no(2)
        }
        ACCESS read-write
        STATUS mandatory
        DESCRIPTION
        "Set to yes(1) to configure the link as segment end point."
        DEFVAL { yes }
        ::= { oamEntry 2 }

oamVcEndPoint  OBJECT-TYPE
        SYNTAX INTEGER {
                no(2),
                yes(1)
        }
        ACCESS read-write
        STATUS mandatory
        DESCRIPTION
        "Set to yes(1) to configure the link as connection end point."
        DEFVAL { no }
        ::= { oamEntry 3 }

oamAisRdiGeneration        OBJECT-TYPE
        SYNTAX INTEGER {
                no(2),
                yes(1)
        }
        ACCESS read-write
        STATUS mandatory
        DESCRIPTION
        "Set to yes(1) to generate AIS/RDI up on physical failure."
        DEFVAL { no }
        ::= { oamEntry 4 }

oamLastRxType	OBJECT-TYPE
	SYNTAX INTEGER {
		ais(1),
		rdi(2),
		loopback(3),
		continuity-check(4),
		performance-monitoring(5),
		unsupported(6),
		none(10)
		}
	ACCESS read-only
	STATUS mandatory
	DESCRIPTION
	"Type of the last received OAM cell."
	DEFVAL {none }
	::= { oamEntry 5 }

oamLastRxVpi	OBJECT-TYPE
	SYNTAX VirtualPathIdentifier
	ACCESS read-only
	STATUS mandatory
	DESCRIPTION
	"VPI value of the last received OAM cell."
	::= { oamEntry 6 }

oamLastRxVci	OBJECT-TYPE
	SYNTAX VirtualCircuitIdentifier
	ACCESS read-only
	STATUS mandatory
	DESCRIPTION
	"VCI value of the last received OAM cell."
	::= { oamEntry 7 }

oamRxCount	OBJECT-TYPE
	SYNTAX Counter
	ACCESS read-only
	STATUS mandatory
	DESCRIPTION
	"Sum of received OAM cells."
	::= { oamEntry 8 }

oamLastTxType	OBJECT-TYPE
	SYNTAX INTEGER {
		ais(1),
		rdi(2),
		loopback(3),
		continuity-check(4),
		performance-monitoring(5),
		unsupported(6),
		none(10)
		}
	ACCESS read-only
	STATUS mandatory
	DESCRIPTION
	"Type of the last transmitted OAM cell."
	DEFVAL {none }
	::= { oamEntry 9 }

oamLastTxVpi	OBJECT-TYPE
	SYNTAX VirtualPathIdentifier
	ACCESS read-only
	STATUS mandatory
	DESCRIPTION
	"VPI value of the last transmitted OAM cell."
	::= { oamEntry 10 }

oamLastTxVci	OBJECT-TYPE
	SYNTAX VirtualCircuitIdentifier
	ACCESS read-only
	STATUS mandatory
	DESCRIPTION
	"VCI value of the last transmitted OAM cell."
	::= { oamEntry 11 }

oamTxCount	OBJECT-TYPE
	SYNTAX Counter
	ACCESS read-only
	STATUS mandatory
	DESCRIPTION
	"Sum of transmitted OAM cells."
	::= { oamEntry 12 }

oamClearStats	OBJECT-TYPE
	SYNTAX INTEGER {
		no(1),
		yes(2)
		}
	ACCESS read-write
	STATUS mandatory
	DESCRIPTION
	"Set to yes(2) to clear OAM Tx and Rx Statistics."
	::= { oamEntry 13 }

oamLoopbackTable OBJECT-TYPE
        SYNTAX SEQUENCE OF OamLoopbackEntry
        ACCESS not-accessible
        STATUS mandatory
        DESCRIPTION
        "This table is used to configure and control loopback test.
         Change Test Status to Start Test(1) to initiate loopback test."
        ::= { dv2Oam 2 }

oamLoopbackEntry OBJECT-TYPE
        SYNTAX  OamLoopbackEntry
        ACCESS  not-accessible
        STATUS  mandatory
        INDEX   { oamLoopbackLinkNo }
        ::= { oamLoopbackTable 1 }

OamLoopbackEntry ::=
        SEQUENCE {
                oamLoopbackLinkNo
                        INTEGER,
                oamLoopbackVpi
                        VirtualPathIdentifier,
                oamLoopbackVci
                        VirtualCircuitIdentifier,
                oamLoopbackSpan
                        INTEGER,
                oamLoopbackMaxNumCells
                        INTEGER,
                oamLoopbackNumCellsSent
                        INTEGER,
                oamLoopbackTimeOut
                        INTEGER,
                oamLoopbackActive
                        INTEGER,
                oamLoopbackResult
                        INTEGER,
                oamLoopbackLocId
                        INTEGER
}


oamLoopbackLinkNo       OBJECT-TYPE
        SYNTAX INTEGER (0..1)
        ACCESS read-only
        STATUS mandatory
        DESCRIPTION
        "The link number for this configuration."
        ::= { oamLoopbackEntry 1 }

oamLoopbackVpi  OBJECT-TYPE
        SYNTAX VirtualPathIdentifier
        ACCESS read-write
        STATUS mandatory
        DESCRIPTION
        "VPI value for the loopback cells to send."
        DEFVAL { 0 }
        ::= { oamLoopbackEntry 2 }

oamLoopbackVci  OBJECT-TYPE
        SYNTAX VirtualCircuitIdentifier
        ACCESS read-write
        STATUS mandatory
        DESCRIPTION
        "VCI value for the loopback cells to send."
        DEFVAL { 5 }
        ::= { oamLoopbackEntry 3 }

oamLoopbackSpan OBJECT-TYPE
        SYNTAX INTEGER {
                segment(4),
                end-to-end(5),
                location-id(6)
        }
        ACCESS read-write
        STATUS mandatory
        DESCRIPTION
        "Flow span for the loopback cells to send."
        DEFVAL { segment }
        ::= { oamLoopbackEntry 4 }

oamLoopbackMaxNumCells     OBJECT-TYPE
        SYNTAX INTEGER (1..20)
        ACCESS read-write
        STATUS mandatory
        DESCRIPTION
        "Maximum number of loopback cells to send."
        DEFVAL { 2 }
        ::= { oamLoopbackEntry 5 }

oamLoopbackNumCellsSent     OBJECT-TYPE
        SYNTAX INTEGER (0..20)
        ACCESS read-only
        STATUS mandatory
        DESCRIPTION
        "Number of loopback cells sent."
        DEFVAL { 0 }
        ::= { oamLoopbackEntry 6 }

oamLoopbackTimeOut      OBJECT-TYPE
        SYNTAX INTEGER (1..10)
        ACCESS read-write
        STATUS mandatory
        DESCRIPTION
        "Number of seconds to wait for loopback cells to return."
        DEFVAL { 5 }
        ::= { oamLoopbackEntry 7 }

oamLoopbackActive       OBJECT-TYPE
        SYNTAX INTEGER {
                start-test(1),
                complete(2),
                idle(3),
                under-test(4)
        }
        ACCESS read-write
        STATUS mandatory
        DESCRIPTION
        "Change to Start Test to run loopback test."
        DEFVAL { idle }
        ::= { oamLoopbackEntry 8 }

oamLoopbackResult       OBJECT-TYPE
        SYNTAX INTEGER {
                pass(1),
                fail(2),
                physical-loopback-detected(3),
                unknown(4),
                vpi-range-error(5),
                vp-is-invalid(6),
                vci-range-error(7),
                vci-and-span-mismatch(8),
                vpc-not-established(9),
                vcc-not-established(10)
        }
        ACCESS read-only
        STATUS mandatory
        DESCRIPTION
        "Loopback test result."
        DEFVAL { unknown }
        ::= { oamLoopbackEntry 9 }

oamLoopbackLocId     OBJECT-TYPE
        SYNTAX INTEGER (0..255)
        ACCESS read-write
        STATUS mandatory
        DESCRIPTION
        "Location Node ID for loopback point."
        DEFVAL { 0 }
        ::= { oamLoopbackEntry 10 }

oamDisable	OBJECT-TYPE
	SYNTAX INTEGER {
		no(1),
		yes(2)
		}
	ACCESS read-write
	STATUS mandatory
	DESCRIPTION
	"yes(2) will disable the oam for entire slot."
        DEFVAL { no }
	::= { dv2Oam 3 }

--***** New OAM table ******
-- ***  VCa port  ***
oamVcaTable OBJECT-TYPE
        SYNTAX SEQUENCE OF OamVcaEntry
        ACCESS not-accessible
        STATUS mandatory
        DESCRIPTION
        "This table is used for per-port OAM configuration."
        ::= { dv2Oam 4 }

oamVcaEntry OBJECT-TYPE
        SYNTAX  OamVcaEntry
        ACCESS  not-accessible
        STATUS  mandatory
        INDEX   { oamVcaVpi, oamVcaVci }
        ::= { oamVcaTable 1 }

OamVcaEntry ::=
	SEQUENCE {
		oamVcaVpi
                        VirtualPathIdentifier,
		oamVcaVci
                        VirtualCircuitIdentifier,
		oamVcaConnectionType
			INTEGER,
		oamVcaVpcEndPoint
			INTEGER,
		oamVcaAisRdiGeneration
			INTEGER,
		oamVcaAisRdiState
			INTEGER,
		oamVcaDefectType
			INTEGER,
		oamVcaDefectNode
			INTEGER,
		oamVcaDefectSlot
			INTEGER,
		oamVcaDefectLink
			INTEGER,
		oamVcaTrapEnable
			INTEGER,
		oamVcaCC
			INTEGER,
		oamVcaCCState
			INTEGER,
		oamVcaPM
			INTEGER,
		oamVcaPMBlockSize
			INTEGER,
		oamVcaPMState
			INTEGER,
		oamVcaBkwRptLosCells
			INTEGER,
		oamVcaBkwRptMisCells
			INTEGER,
		oamVcaBkwRptBip16
			INTEGER,
		oamVcaBkwRptSevErr
			INTEGER
		}

oamVcaVpi       OBJECT-TYPE
        SYNTAX VirtualPathIdentifier
        ACCESS read-only
        STATUS mandatory
        DESCRIPTION
        "The VPI for this configuration."
        ::= { oamVcaEntry 1 }

oamVcaVci       OBJECT-TYPE
        SYNTAX VirtualCircuitIdentifier
        ACCESS read-only
        STATUS mandatory
        DESCRIPTION
        "The VCI for this configuration."
        ::= { oamVcaEntry 2 }

oamVcaConnectionType  OBJECT-TYPE
        SYNTAX INTEGER {
                connection-point(1),
                segment-endpoint(2),
                end-to-end-endpoint(3),
		pass-thru(4)
        }
        ACCESS read-write
        STATUS mandatory
        DESCRIPTION
        "Set End point configuration on hardware per VPC/VCC"
        DEFVAL { connection-point }
        ::= { oamVcaEntry 3 }

oamVcaVpcEndPoint  OBJECT-TYPE
        SYNTAX INTEGER {
                no(1),
                yes(2)
        }
        ACCESS read-write
        STATUS mandatory
        DESCRIPTION
        "Set yes(1) to configure the VC to VPC end point."
        DEFVAL { no }
        ::= { oamVcaEntry 4 }

oamVcaAisRdiGeneration  OBJECT-TYPE
        SYNTAX INTEGER {
                disable(1),
                enable(2)
        }
        ACCESS read-write
        STATUS mandatory
        DESCRIPTION
        "AIS/RDI disable or enable with or without traps."
        DEFVAL { disable }
        ::= { oamVcaEntry 5 }

oamVcaAisRdiState       OBJECT-TYPE
        SYNTAX INTEGER {
		none(1),
		ais(2),
		rdi(3)
	}
        ACCESS read-only
        STATUS mandatory
        DESCRIPTION
        "AIS/RDI state for this VP/VC."
        ::= { oamVcaEntry 6 }

oamVcaDefectType       OBJECT-TYPE
        SYNTAX INTEGER {
		none(1),
		link-down(2),
		loss-of-continuity(3),
		unknown(4)
	}
        ACCESS read-only
        STATUS mandatory
        DESCRIPTION
        "AIS/RDI defect type."
        ::= { oamVcaEntry 7 }

oamVcaDefectNode       OBJECT-TYPE
        SYNTAX INTEGER (0..255)
        ACCESS read-only
        STATUS mandatory
        DESCRIPTION
        "AIS/RDI location."
        ::= { oamVcaEntry 8 }

oamVcaDefectSlot       OBJECT-TYPE
        SYNTAX INTEGER (0..15)
        ACCESS read-only
        STATUS mandatory
        DESCRIPTION
        "AIS/RDI location."
        ::= { oamVcaEntry 9 }

oamVcaDefectLink       OBJECT-TYPE
        SYNTAX INTEGER (0..31)
        ACCESS read-only
        STATUS mandatory
        DESCRIPTION
        "AIS/RDI location."
        ::= { oamVcaEntry 10 }

oamVcaTrapEnable  OBJECT-TYPE
        SYNTAX INTEGER {
                disable(1),
                enable(2)
        }
        ACCESS read-write
        STATUS mandatory
        DESCRIPTION
        "Set enable to generate trap when AIS/RDI received."
        DEFVAL { disable }
        ::= { oamVcaEntry 11 }

oamVcaCC  OBJECT-TYPE
        SYNTAX INTEGER {
		none(1),
                act-source-seg-cell(2),
                act-source-ee-cell(3),
                act-sink-seg-cell(4),
                act-sink-ee-cell(5),
                act-bidir-seg-cell(6),
                act-bidir-ee-cell(7),
                act-source-seg-manual(8),
                act-source-ee-manual(9),
                act-sink-seg-manual(10),
                act-sink-ee-manual(11),
                act-bidir-seg-manual(12),
                act-bidir-ee-manual(13)
        }
        ACCESS read-write
        STATUS mandatory
        DESCRIPTION
        "Activate segment or end to end Continuity Checks."
        DEFVAL { none }
        ::= { oamVcaEntry 12 }

oamVcaCCState       OBJECT-TYPE
        SYNTAX INTEGER {
		not-supported(1),
		ready(2),
		wait-act-con(3),
		wait-act-res(4),
		wait-deact-con(5),
		active-cell(6),
		active-manual(7)
	}
        ACCESS read-only
        STATUS mandatory
        DESCRIPTION
        "Continuity Check state."
        ::= { oamVcaEntry 13 }

oamVcaPM  OBJECT-TYPE
        SYNTAX INTEGER {
		none(1),
                act-source-seg-cell(2),
                act-source-ee-cell(3),
                act-sink-seg-cell(4),
                act-sink-ee-cell(5),
                act-source-seg-manual(6),
                act-source-ee-manual(7),
                act-sink-seg-manual(8),
                act-sink-ee-manual(9)
        }
        ACCESS read-write
        STATUS mandatory
        DESCRIPTION
        "Activate segment or end to end Performance Monitoring."
        DEFVAL { none }
        ::= { oamVcaEntry 14 }

oamVcaPMBlockSize  OBJECT-TYPE
        SYNTAX INTEGER {
                size128(1),
                size256(2),
                size512(3),
                size1024(4)
        }
        ACCESS read-write
        STATUS mandatory
        DESCRIPTION
        "Performance Monitoring block size."
        DEFVAL { size128 }
        ::= { oamVcaEntry 15 }

oamVcaPMState       OBJECT-TYPE
        SYNTAX INTEGER {
		not-supported(1),
		ready(2),
		wait-act-con(3),
		wait-act-res(4),
		wait-deact-con(5),
		active-cell(6),
		active-manual(7)
	}
        ACCESS read-only
        STATUS mandatory
        DESCRIPTION
        "Continuity Check state."
        ::= { oamVcaEntry 16 }

oamVcaBkwRptLosCells       OBJECT-TYPE
        SYNTAX INTEGER
        ACCESS read-only
        STATUS mandatory
        DESCRIPTION
        "Backward Reporting loss of cell."
        ::= { oamVcaEntry 17 }

oamVcaBkwRptMisCells       OBJECT-TYPE
        SYNTAX INTEGER
        ACCESS read-only
        STATUS mandatory
        DESCRIPTION
        "Backward Reporting misinserted cell."
        ::= { oamVcaEntry 18 }

oamVcaBkwRptBip16       OBJECT-TYPE
        SYNTAX INTEGER
        ACCESS read-only
        STATUS mandatory
        DESCRIPTION
        "Backward Reporting BIP-16 violations."
        ::= { oamVcaEntry 19 }

oamVcaBkwRptSevErr       OBJECT-TYPE
        SYNTAX INTEGER
        ACCESS read-only
        STATUS mandatory
        DESCRIPTION
        "Backward Reporting Severly Errored Cells."
        ::= { oamVcaEntry 20 }

-- ***  VCb port  ***
oamVcbTable OBJECT-TYPE
        SYNTAX SEQUENCE OF OamVcbEntry
        ACCESS not-accessible
        STATUS mandatory
        DESCRIPTION
        "This table is used for per-port OAM configuration."
        ::= { dv2Oam 5 }

oamVcbEntry OBJECT-TYPE
        SYNTAX  OamVcbEntry
        ACCESS  not-accessible
        STATUS  mandatory
        INDEX   { oamVcbVpi, oamVcbVci }
        ::= { oamVcbTable 1 }

OamVcbEntry ::=
	SEQUENCE {
		oamVcbVpi
                        VirtualPathIdentifier,
		oamVcbVci
                        VirtualCircuitIdentifier,
		oamVcbConnectionType
			INTEGER,
		oamVcbVpcEndPoint
			INTEGER,
		oamVcbAisRdiGeneration
			INTEGER,
		oamVcbAisRdiState
			INTEGER,
		oamVcbDefectType
			INTEGER,
		oamVcbDefectNode
			INTEGER,
		oamVcbDefectSlot
			INTEGER,
		oamVcbDefectLink
			INTEGER,
		oamVcbTrapEnable
			INTEGER,
		oamVcbCC
			INTEGER,
		oamVcbCCState
			INTEGER,
		oamVcbPM
			INTEGER,
		oamVcbPMBlockSize
			INTEGER,
		oamVcbPMState
			INTEGER,
		oamVcbBkwRptLosCells
			INTEGER,
		oamVcbBkwRptMisCells
			INTEGER,
		oamVcbBkwRptBip16
			INTEGER,
		oamVcbBkwRptSevErr
			INTEGER
		}

oamVcbVpi       OBJECT-TYPE
        SYNTAX VirtualPathIdentifier
        ACCESS read-only
        STATUS mandatory
        DESCRIPTION
        "The VPI for this configuration."
        ::= { oamVcbEntry 1 }

oamVcbVci       OBJECT-TYPE
        SYNTAX VirtualCircuitIdentifier
        ACCESS read-only
        STATUS mandatory
        DESCRIPTION
        "The VCI for this configuration."
        ::= { oamVcbEntry 2 }

oamVcbConnectionType  OBJECT-TYPE
        SYNTAX INTEGER {
                connection-point(1),
                segment-endpoint(2),
                end-to-end-endpoint(3),
		pass-thru(4)
        }
        ACCESS read-write
        STATUS mandatory
        DESCRIPTION
        "Set End point configuration on hardware per VPC/VCC"
        DEFVAL { connection-point }
        ::= { oamVcbEntry 3 }

oamVcbVpcEndPoint  OBJECT-TYPE
        SYNTAX INTEGER {
                no(1),
                yes(2)
        }
        ACCESS read-write
        STATUS mandatory
        DESCRIPTION
        "Set yes(1) to configure the VC to VPC end point."
        DEFVAL { no }
        ::= { oamVcbEntry 4 }

oamVcbAisRdiGeneration  OBJECT-TYPE
        SYNTAX INTEGER {
                disable(1),
                enable(2)
        }
        ACCESS read-write
        STATUS mandatory
        DESCRIPTION
        "AIS/RDI disable or enable with or without traps."
        DEFVAL { disable }
        ::= { oamVcbEntry 5 }

oamVcbAisRdiState       OBJECT-TYPE
        SYNTAX INTEGER {
		none(1),
		ais(2),
		rdi(3)
	}
        ACCESS read-only
        STATUS mandatory
        DESCRIPTION
        "AIS/RDI state for this VP/VC."
        ::= { oamVcbEntry 6 }

oamVcbDefectType       OBJECT-TYPE
        SYNTAX INTEGER {
		none(1),
		link-down(2),
		loss-of-continuity(3),
		unknown(4)
	}
        ACCESS read-only
        STATUS mandatory
        DESCRIPTION
        "AIS/RDI defect type."
        ::= { oamVcbEntry 7 }

oamVcbDefectNode      OBJECT-TYPE
        SYNTAX INTEGER (0..255)
        ACCESS read-only
        STATUS mandatory
        DESCRIPTION
        "AIS/RDI location."
        ::= { oamVcbEntry 8 }

oamVcbDefectSlot      OBJECT-TYPE
        SYNTAX INTEGER (0..15)
        ACCESS read-only
        STATUS mandatory
        DESCRIPTION
        "AIS/RDI location."
        ::= { oamVcbEntry 9 }

oamVcbDefectLink      OBJECT-TYPE
        SYNTAX INTEGER (0..31)
        ACCESS read-only
        STATUS mandatory
        DESCRIPTION
        "AIS/RDI location."
        ::= { oamVcbEntry 10 }

oamVcbTrapEnable  OBJECT-TYPE
        SYNTAX INTEGER {
                disable(1),
                enable(2)
        }
        ACCESS read-write
        STATUS mandatory
        DESCRIPTION
        "Set enable to generate trap when AIS/RDI received."
        DEFVAL { disable }
        ::= { oamVcbEntry 11 }

oamVcbCC  OBJECT-TYPE
        SYNTAX INTEGER {
		none(1),
                act-source-seg-cell(2),
                act-source-ee-cell(3),
                act-sink-seg-cell(4),
                act-sink-ee-cell(5),
                act-bidir-seg-cell(6),
                act-bidir-ee-cell(7),
                act-source-seg-manual(8),
                act-source-ee-manual(9),
                act-sink-seg-manual(10),
                act-sink-ee-manual(11),
                act-bidir-seg-manual(12),
                act-bidir-ee-manual(13)
        }
        ACCESS read-write
        STATUS mandatory
        DESCRIPTION
        "Activate segment or end to end Continuity Checks."
        DEFVAL { none }
        ::= { oamVcbEntry 12 }

oamVcbCCState       OBJECT-TYPE
        SYNTAX INTEGER {
		not-supported(1),
		ready(2),
		wait-act-con(3),
		wait-act-res(4),
		wait-deact-con(5),
		active-cell(6),
		active-manual(7)
	}
        ACCESS read-only
        STATUS mandatory
        DESCRIPTION
        "Continuity Check state."
        ::= { oamVcbEntry 13 }

oamVcbPM  OBJECT-TYPE
        SYNTAX INTEGER {
		none(1),
                act-source-seg-cell(2),
                act-source-ee-cell(3),
                act-sink-seg-cell(4),
                act-sink-ee-cell(5),
                act-source-seg-manual(6),
                act-source-ee-manual(7),
                act-sink-seg-manual(8),
                act-sink-ee-manual(9)
        }
        ACCESS read-write
        STATUS mandatory
        DESCRIPTION
        "Activate segment or end to end Performance Monitoring."
        DEFVAL { none }
        ::= { oamVcbEntry 14 }

oamVcbPMBlockSize  OBJECT-TYPE
        SYNTAX INTEGER {
                size128(1),
                size256(2),
                size512(3),
                size1024(4)
        }
        ACCESS read-write
        STATUS mandatory
        DESCRIPTION
        "Performance Monitoring block size."
        DEFVAL { size128 }
        ::= { oamVcbEntry 15 }

oamVcbPMState       OBJECT-TYPE
        SYNTAX INTEGER {
		not-supported(1),
		ready(2),
		wait-act-con(3),
		wait-act-res(4),
		wait-deact-con(5),
		active-cell(6),
		active-manual(7)
	}
        ACCESS read-only
        STATUS mandatory
        DESCRIPTION
        "Continuity Check state."
        ::= { oamVcbEntry 16 }

oamVcbBkwRptLosCells       OBJECT-TYPE
        SYNTAX INTEGER
        ACCESS read-only
        STATUS mandatory
        DESCRIPTION
        "Backward Reporting loss of cell."
        ::= { oamVcbEntry 17 }

oamVcbBkwRptMisCells       OBJECT-TYPE
        SYNTAX INTEGER
        ACCESS read-only
        STATUS mandatory
        DESCRIPTION
        "Backward Reporting misinserted cell."
        ::= { oamVcbEntry 18 }

oamVcbBkwRptBip16       OBJECT-TYPE
        SYNTAX INTEGER
        ACCESS read-only
        STATUS mandatory
        DESCRIPTION
        "Backward Reporting BIP-16 violations."
        ::= { oamVcbEntry 19 }

oamVcbBkwRptSevErr       OBJECT-TYPE
        SYNTAX INTEGER
        ACCESS read-only
        STATUS mandatory
        DESCRIPTION
        "Backward Reporting Severly Errored Cells."
        ::= { oamVcbEntry 20 }

-- ************************************************************************************************************************
-- The LMI config and status table

lmiTable OBJECT-TYPE
        SYNTAX SEQUENCE OF LmiEntry
        ACCESS not-accessible
        STATUS mandatory
        DESCRIPTION
        "This table is used to control ILMI configuration."
        ::= { dv2Lmi 1 }

lmiEntry OBJECT-TYPE
        SYNTAX  LmiEntry
        ACCESS  not-accessible
        STATUS  mandatory
        INDEX   { lmiLinkNo }
        ::= { lmiTable 1 }

LmiEntry ::=
        SEQUENCE {
		lmiLinkNo
			INTEGER,
		lmiVpi
			VirtualPathIdentifier,
		lmiVci
			VirtualCircuitIdentifier,
		lmiType
			INTEGER,
		lmiState
			INTEGER,
		lmiFormat
			INTEGER,
		lmiPrefix
			E164SUB,
		lmiOnOff
			INTEGER,
		lmiPollPeriod
			INTEGER,
		lmiNoRspDown
			INTEGER,
		lmiLinkMgmt
			INTEGER,
		lmiConnectivity
			INTEGER,
		lmiPrefixMod
			E164,
		lmiEsi
		        E164
		}

lmiLinkNo       OBJECT-TYPE
        SYNTAX INTEGER (0..1)
        ACCESS read-only
        STATUS mandatory
        DESCRIPTION
        "The link number for this configuration."
        ::= { lmiEntry 1 }

lmiVpi OBJECT-TYPE
	SYNTAX VirtualPathIdentifier
	ACCESS read-write
	STATUS mandatory
	DESCRIPTION
	"The VPI used for ILMI."
	DEFVAL { 0 }
	::= { lmiEntry 2 }

lmiVci OBJECT-TYPE
	SYNTAX VirtualCircuitIdentifier
	ACCESS read-write
	STATUS mandatory
	DESCRIPTION
	"The VCI used for ILMI."
	DEFVAL { 16 }
	::= { lmiEntry 3 }

lmiType  OBJECT-TYPE
        SYNTAX INTEGER {
                network-side(1),
                user-side(2)
        }
        ACCESS read-write
        STATUS mandatory
        DESCRIPTION
        "Set to network side (1) to configure the link as network side ILMI."
        DEFVAL { network-side }
        ::= { lmiEntry 4 }

lmiState  OBJECT-TYPE
        SYNTAX INTEGER {
                initialized(1),
                connecting(2),
		registered(3),
                registering(4),
		deregistering(5),
		polling(6),
		disconnecting(7)
        }
        ACCESS read-only
        STATUS mandatory
        DESCRIPTION
        "The state of ILMI for this link."
        DEFVAL { initialized }
        ::= { lmiEntry 5 }

lmiFormat  OBJECT-TYPE
	SYNTAX INTEGER {
		nsap-e-164(1),
		nsap-dcc(2),
		nsap-icd(3),
		non-nsap-e-164(4)
	}
	ACCESS read-write
	STATUS mandatory
	DESCRIPTION
	"ILMI address format."
	DEFVAL { nsap-icd }
	::= { lmiEntry 6 }

lmiPrefix  OBJECT-TYPE
	SYNTAX E164SUB
	ACCESS read-only
	STATUS mandatory
	DESCRIPTION
	"Default Network prefix to use."
	::= { lmiEntry 7 }

lmiOnOff OBJECT-TYPE
	SYNTAX INTEGER {
		off(1),
		on(2),
		re-register(3)
	       }
	ACCESS read-write
	STATUS mandatory
	DESCRIPTION
	"Turn on/off ILMI."
	DEFVAL { on }
	::= { lmiEntry 8 }

lmiPollPeriod OBJECT-TYPE
	SYNTAX INTEGER (3..10)
	ACCESS read-write
	STATUS mandatory
	DESCRIPTION
	"Period in seconds to send polling request for link management."
	DEFVAL { 5 }
	::= { lmiEntry 9 }

lmiNoRspDown OBJECT-TYPE
	SYNTAX INTEGER (2..10)
	ACCESS read-write
	STATUS mandatory
	DESCRIPTION
	"Number of failed polls (no response) before declaration of link down."
	DEFVAL { 4 }
	::= { lmiEntry 10 }

lmiLinkMgmt OBJECT-TYPE
	SYNTAX INTEGER {
		on(2),
		off(1)
		}
	ACCESS read-write
	STATUS mandatory
	DESCRIPTION
	"Turn on/off link management."
	DEFVAL { on }
	::= { lmiEntry 11 }

lmiConnectivity OBJECT-TYPE
	SYNTAX INTEGER {
		up(1),
		down(2),
		unknown(3)
		}
	ACCESS read-only
	STATUS mandatory
	DESCRIPTION
	"ATM interface status."
	DEFVAL { down }
	::= { lmiEntry 12 }

lmiPrefixMod  OBJECT-TYPE
	SYNTAX E164
	ACCESS read-write
	STATUS mandatory
	DESCRIPTION
	"Modifiable Network prefix to use. MUST BE 26 DIGITS"
	::= { lmiEntry 13 }

lmiEsi  OBJECT-TYPE
	SYNTAX E164
	ACCESS read-write
	STATUS mandatory
	DESCRIPTION
	"ESI field to use on User side. MUST BE 12 DIGITS"
	::= { lmiEntry 14 }

lmiNetSideTable OBJECT-TYPE
	SYNTAX SEQUENCE OF LmiNetSideEntry
	ACCESS not-accessible
	STATUS mandatory
	DESCRIPTION
	"This table is used to configure and control network side ILMI."

	::= { dv2Lmi 2 }

lmiNetSideEntry OBJECT-TYPE
	SYNTAX  LmiNetSideEntry
	ACCESS  not-accessible
	STATUS  mandatory
	INDEX   { lmiNetSideLinkNo, lmiNetSidePrefixId }
	::= { lmiNetSideTable 1 }

LmiNetSideEntry ::=
	SEQUENCE {
		lmiNetSideLinkNo
			INTEGER,
		lmiNetSidePrefixId
			INTEGER,
		lmiNetSidePrefix
			E164SUB,
		lmiNetSidePrefixStatus
			INTEGER
}


lmiNetSideLinkNo       OBJECT-TYPE
	SYNTAX INTEGER (0..1)
	ACCESS read-only
	STATUS mandatory
	DESCRIPTION
	"The link number for this configuration."
	::= { lmiNetSideEntry 1 }

lmiNetSidePrefixId       OBJECT-TYPE
	SYNTAX INTEGER (1..5)
	ACCESS read-only
	STATUS mandatory
	DESCRIPTION
	"Network prefix identification number."
	::= { lmiNetSideEntry 2 }

lmiNetSidePrefix       OBJECT-TYPE
	SYNTAX E164SUB
	ACCESS read-only
	STATUS mandatory
	DESCRIPTION
	"Network prefix to register or de-register."
	::= { lmiNetSideEntry 3 }

lmiNetSidePrefixStatus       OBJECT-TYPE
	SYNTAX INTEGER {
		start-registration(1),
		start-deregistration(2),
		valid(3),
		invalid(4),
		registered(5),
		deregistered(6),
		time-out-failure(7),
		unknown(8),
		not-allowed(9),
		rejected(10)
		}
	ACCESS read-only
	STATUS mandatory
	DESCRIPTION
	"Set to register to send the prefix to the user side;
	 set to de-register to remove the prefix from the user side."
	DEFVAL { unknown }
	::= { lmiNetSideEntry 4 }

lmiUserSideTable OBJECT-TYPE
	SYNTAX SEQUENCE OF LmiUserSideEntry
	ACCESS not-accessible
	STATUS mandatory
	DESCRIPTION
	"This table is used to configure and control user side ILMI."
	::= { dv2Lmi 3 }

lmiUserSideEntry OBJECT-TYPE
	SYNTAX  LmiUserSideEntry
	ACCESS  not-accessible
	STATUS  mandatory
	INDEX   { lmiUserSideLinkNo, lmiUserSideAddressId }
	::= { lmiUserSideTable 1 }

LmiUserSideEntry ::=
        SEQUENCE {
                lmiUserSideLinkNo
                        INTEGER,
                lmiUserSideAddressId
                        INTEGER,
                lmiUserSideAddress
                        E164SUB,
                lmiUserSideAddressStatus
                        INTEGER
}

lmiUserSideLinkNo       OBJECT-TYPE
        SYNTAX INTEGER (0..1)
        ACCESS read-only
        STATUS mandatory
        DESCRIPTION
        "The link number for this configuration."
        ::= { lmiUserSideEntry 1 }

lmiUserSideAddressId       OBJECT-TYPE
        SYNTAX INTEGER (1..16)
        ACCESS read-only
        STATUS mandatory
        DESCRIPTION
        "The link number for this configuration."
        ::= { lmiUserSideEntry 2 }

lmiUserSideAddress       OBJECT-TYPE
        SYNTAX E164SUB
        ACCESS read-only
        STATUS mandatory
        DESCRIPTION
        "ATM address to register or de-register."
        ::= { lmiUserSideEntry 3 }

lmiUserSideAddressStatus       OBJECT-TYPE
        SYNTAX INTEGER {
              start-registration(1),
              start-deregistration(2),
              valid(3),
              invalid(4),
              registered(5),
              deregistered(6),
              time-out-failure(7),
              unknown(8),
              not-allowed(9),
              rejected(10)
              }
        ACCESS read-only
        STATUS mandatory
        DESCRIPTION
        "Set to valid to register the address to the network side;
         set to invalid to de-register the address from the network side."
        DEFVAL { unknown }
        ::= { lmiUserSideEntry 4 }


--___________________________________________________________________________
--
--                   The Alarm Handler Node Alarm Status'
--___________________________________________________________________________

alarmNodeCrit OBJECT-TYPE
	SYNTAX INTEGER
	{
		clr(1),
		crit(2),
		crit-aco(3)
	}
	ACCESS read-only
	STATUS mandatory
	DESCRIPTION
	"Node Critical Alarm Status"
	::= { dv2AlarmHandler 1 }

alarmNodeMajor OBJECT-TYPE
	SYNTAX INTEGER
	{
		clr(1),
		maj(2),
		maj-aco(3)
	}
	ACCESS read-only
	STATUS mandatory
	DESCRIPTION
	"Node Major Alarm Status"
	::= { dv2AlarmHandler 2 }

alarmNodeMinor OBJECT-TYPE
	SYNTAX INTEGER
	{
		clr(1),
		min(2),
		min-aco(3)
	}
	ACCESS read-only
	STATUS mandatory
	DESCRIPTION
	"Node Minor Alarm Status"
	::= { dv2AlarmHandler 3 }

--___________________________________________________________________________
--
--                   The Alarm Handler Slot Status Table
--___________________________________________________________________________

alarmStatTable OBJECT-TYPE
	SYNTAX SEQUENCE OF AlarmStatEntry
	ACCESS not-accessible
	STATUS mandatory
	DESCRIPTION
	"This table is used for Alarm Handler status"
	::= { dv2AlarmHandler 4 }

alarmStatEntry OBJECT-TYPE
	SYNTAX	AlarmStatEntry
	ACCESS	not-accessible
	STATUS	mandatory
        INDEX   { alrStatSlotNo }
	::= { alarmStatTable 1 }

AlarmStatEntry ::=
	SEQUENCE {
		alrStatSlotNo
			INTEGER,
		slotCritStatus
			INTEGER,
		slotMajorStatus
			INTEGER,
		slotMinorStatus
			INTEGER,
		link0CritStatus
			INTEGER,
		link0MajorStatus
			INTEGER,
		link0MinorStatus
			INTEGER,
		link1CritStatus
			INTEGER,
		link1MajorStatus
			INTEGER,
		link1MinorStatus
			INTEGER,
		link2CritStatus
			INTEGER,
		link2MajorStatus
			INTEGER,
		link2MinorStatus
			INTEGER,
		link3CritStatus
			INTEGER,
		link3MajorStatus
			INTEGER,
		link3MinorStatus
			INTEGER
		 }

alrStatSlotNo	OBJECT-TYPE
	SYNTAX INTEGER (0..15)
	ACCESS read-only
	STATUS mandatory
	DESCRIPTION
	"Slot Number"
	::= { alarmStatEntry 1 }

slotCritStatus	OBJECT-TYPE
	SYNTAX INTEGER
	{
		clr(1),
		crit(2),
		crit-aco(3)
	}
	ACCESS read-only
	STATUS mandatory
	DESCRIPTION
	"Slot Critical Alarm Status"
	::= { alarmStatEntry 2 }

slotMajorStatus	OBJECT-TYPE
	SYNTAX INTEGER
	{
		clr(1),
		maj(2),
		maj-aco(3)
	}
	ACCESS read-only
	STATUS mandatory
	DESCRIPTION
	"Slot Major Alarm Status"
	::= { alarmStatEntry 3 }

slotMinorStatus	OBJECT-TYPE
	SYNTAX INTEGER
	{
		clr(1),
		min(2),
		min-aco(3)
	}
	ACCESS read-only
	STATUS mandatory
	DESCRIPTION
	"Slot Minor Alarm Status"
	::= { alarmStatEntry 4 }

link0CritStatus	OBJECT-TYPE
	SYNTAX INTEGER
	{
		clr(1),
		crit(2),
		crit-aco(3)
	}
	ACCESS read-only
	STATUS mandatory
	DESCRIPTION
	"Link 0 Critical Alarm Status"
	::= { alarmStatEntry 5 }

link0MajorStatus OBJECT-TYPE
	SYNTAX INTEGER
	{
		clr(1),
		maj(2),
		maj-aco(3)
	}
	ACCESS read-only
	STATUS mandatory
	DESCRIPTION
	"Link 0 Major Alarm Status"
	::= { alarmStatEntry 6 }

link0MinorStatus OBJECT-TYPE
	SYNTAX INTEGER
	{
		clr(1),
		min(2),
		min-aco(3)
	}
	ACCESS read-only
	STATUS mandatory
	DESCRIPTION
	"Link 0 Minor Alarm Status"
	::= { alarmStatEntry 7 }

link1CritStatus	OBJECT-TYPE
	SYNTAX INTEGER
	{
		clr(1),
		crit(2),
		crit-aco(3)
	}
	ACCESS read-only
	STATUS mandatory
	DESCRIPTION
	"Link 1 Critical Alarm Status"
	::= { alarmStatEntry 8 }

link1MajorStatus OBJECT-TYPE
	SYNTAX INTEGER
	{
		clr(1),
		maj(2),
		maj-aco(3)
	}
	ACCESS read-only
	STATUS mandatory
	DESCRIPTION
	"Link 1 Major Alarm Status"
	::= { alarmStatEntry 9 }

link1MinorStatus OBJECT-TYPE
	SYNTAX INTEGER
	{
		clr(1),
		min(2),
		min-aco(3)
	}
	ACCESS read-only
	STATUS mandatory
	DESCRIPTION
	"Link 1 Minor Alarm Status"
	::= { alarmStatEntry 10 }

link2CritStatus	OBJECT-TYPE
	SYNTAX INTEGER
	{
		clr(1),
		crit(2),
		crit-aco(3)
	}
	ACCESS read-only
	STATUS mandatory
	DESCRIPTION
	"Link 2 Critical Alarm Status"
	::= { alarmStatEntry 11 }

link2MajorStatus OBJECT-TYPE
	SYNTAX INTEGER
	{
		clr(1),
		maj(2),
		maj-aco(3)
	}
	ACCESS read-only
	STATUS mandatory
	DESCRIPTION
	"Link 2 Major Alarm Status"
	::= { alarmStatEntry 12 }

link2MinorStatus OBJECT-TYPE
	SYNTAX INTEGER
	{
		clr(1),
		min(2),
		min-aco(3)
	}
	ACCESS read-only
	STATUS mandatory
	DESCRIPTION
	"Link 2 Minor Alarm Status"
	::= { alarmStatEntry 13 }

link3CritStatus	OBJECT-TYPE
	SYNTAX INTEGER
	{
		clr(1),
		crit(2),
		crit-aco(3)
	}
	ACCESS read-only
	STATUS mandatory
	DESCRIPTION
	"Link 3 Critical Alarm Status"
	::= { alarmStatEntry 14 }

link3MajorStatus OBJECT-TYPE
	SYNTAX INTEGER
	{
		clr(1),
		maj(2),
		maj-aco(3)
	}
	ACCESS read-only
	STATUS mandatory
	DESCRIPTION
	"Link 3 Major Alarm Status"
	::= { alarmStatEntry 15 }

link3MinorStatus OBJECT-TYPE
	SYNTAX INTEGER
	{
		clr(1),
		min(2),
		min-aco(3)
	}
	ACCESS read-only
	STATUS mandatory
	DESCRIPTION
	"Link 3 Minor Alarm Status"
	::= { alarmStatEntry 16 }


--___________________________________________________________________________
--
--                   The Alarm Handler Node ACO Status
--___________________________________________________________________________

alarmNodeACO OBJECT-TYPE
	SYNTAX INTEGER
	{
		off(1),
		on(2)
	}
	ACCESS read-write
	STATUS mandatory
	DESCRIPTION
	"Node ACO Status"
	::= { dv2AlarmHandler 5 }

--___________________________________________________________________________
--
--                   The Alarm Handler ACO Table
--___________________________________________________________________________

alarmACOTable OBJECT-TYPE
	SYNTAX SEQUENCE OF AlarmACOEntry
	ACCESS not-accessible
	STATUS mandatory
	DESCRIPTION
	"This table is used for the Alarm Handler ACO"
	::= { dv2AlarmHandler 6 }

alarmACOEntry OBJECT-TYPE
	SYNTAX	AlarmACOEntry
	ACCESS	not-accessible
	STATUS	mandatory
        INDEX   { alrACOslotNo }
	::= { alarmACOTable 1 }

AlarmACOEntry ::=
	SEQUENCE {
		alrACOslotNo
			INTEGER,
		alrACOslotACO
			INTEGER,
		alrACOlink0ACO
			INTEGER,
		alrACOlink1ACO
			INTEGER,
		alrACOlink2ACO
			INTEGER,
		alrACOlink3ACO
			INTEGER
		 }

alrACOslotNo	OBJECT-TYPE
	SYNTAX INTEGER (0..15)
	ACCESS read-only
	STATUS mandatory
	DESCRIPTION
	"Slot Number"
	::= { alarmACOEntry 1 }

alrACOslotACO	OBJECT-TYPE
	SYNTAX INTEGER
	{
		off(1),
		on(2)
	}
	ACCESS read-write
	STATUS mandatory
	DESCRIPTION
	"Slot ACO Status"
	::= { alarmACOEntry 2 }

alrACOlink0ACO	OBJECT-TYPE
	SYNTAX INTEGER
	{
		off(1),
		on(2)
	}
	ACCESS read-write
	STATUS mandatory
	DESCRIPTION
	"Link 0 ACO Status"
	::= { alarmACOEntry 3 }

alrACOlink1ACO	OBJECT-TYPE
	SYNTAX INTEGER
	{
		off(1),
		on(2)
	}
	ACCESS read-write
	STATUS mandatory
	DESCRIPTION
	"Link 1 ACO Status"
	::= { alarmACOEntry 4 }

alrACOlink2ACO	OBJECT-TYPE
	SYNTAX INTEGER
	{
		off(1),
		on(2)
	}
	ACCESS read-write
	STATUS mandatory
	DESCRIPTION
	"Link 2 ACO Status"
	::= { alarmACOEntry 5 }

alrACOlink3ACO	OBJECT-TYPE
	SYNTAX INTEGER
	{
		off(1),
		on(2)
	}
	ACCESS read-write
	STATUS mandatory
	DESCRIPTION
	"Link 3 ACO Status"
	::= { alarmACOEntry 6 }

--___________________________________________________________________________
--
--                   The User Status/Alarm Input Table
--___________________________________________________________________________

userStatusTable OBJECT-TYPE
	SYNTAX SEQUENCE OF UserStatusEntry
	ACCESS not-accessible
	STATUS mandatory
	DESCRIPTION
	"This table is used for the User Status Inputs"
	::= { dv2AlarmHandler 7 }

userStatusEntry OBJECT-TYPE
	SYNTAX	UserStatusEntry
	ACCESS	not-accessible
	STATUS	mandatory
        INDEX   { userInputNo }
	::= { userStatusTable 1 }

UserStatusEntry ::=
	SEQUENCE {
		userInputNo
			INTEGER,
		userInputEnable
			INTEGER,
		userInputTrapEnable
			INTEGER,
		userInputTrapDesc
			DisplayString,
		userInputActiveState
			INTEGER,
		userInputAlrClass
 			INTEGER,
		userInputStatus
			INTEGER
		 }

userInputNo	OBJECT-TYPE
	SYNTAX INTEGER (0..1)
	ACCESS read-only
	STATUS mandatory
	DESCRIPTION
	"User Status Input Number"
	::= { userStatusEntry 1 }

userInputEnable	OBJECT-TYPE
	SYNTAX INTEGER
	{
		enabled(1),
		disabled(2),
		not-applicable(3)
	}
	ACCESS read-write
	STATUS mandatory
	DESCRIPTION
	"Enable User Status Input"
	DEFVAL { not-applicable }
	::= { userStatusEntry 2 }

userInputTrapEnable OBJECT-TYPE
	SYNTAX INTEGER
	{
		enabled(1),
		disabled(2)
	}
	ACCESS read-write
	STATUS mandatory
	DESCRIPTION
	"Enable User Defined Trap/Event"
	DEFVAL { disabled }
	::= { userStatusEntry 3 }

userInputTrapDesc	OBJECT-TYPE
	SYNTAX DisplayString
	ACCESS read-write
	STATUS mandatory
	DESCRIPTION
	"Description string for trap/event"
	::= { userStatusEntry 4 }

userInputActiveState OBJECT-TYPE
	SYNTAX INTEGER
	{
		active-closed(1),
		active-open(2)
	}
	ACCESS read-write
	STATUS mandatory
	DESCRIPTION
	"Alarm active state of user input relay switch"
	::= { userStatusEntry 5 }

userInputAlrClass	OBJECT-TYPE
	SYNTAX INTEGER
	{
		critical(1),
		major(2),
		minor(3),
		informational(4)
	}
	ACCESS read-only
	STATUS mandatory
	DESCRIPTION
	"Classification of Status/Alarm Input"
	DEFVAL { informational }
	::= { userStatusEntry 10 }

userInputStatus	OBJECT-TYPE
	SYNTAX INTEGER
	{
		clear(1),
		active(2)
	}
	ACCESS read-only
	STATUS mandatory
	DESCRIPTION
	"Current Status of Status/Alarm Input"
	::= { userStatusEntry 11 }

--___________________________________________________________________________
--
--                   Scan Alarm Classification File
--___________________________________________________________________________

alarmScanFile OBJECT-TYPE
	SYNTAX INTEGER
	{
		no(2),
		yes(1)
	}
	ACCESS read-write
	STATUS mandatory
	DESCRIPTION
	"Rescan the alr_class.txt file"
	::= { dv2AlarmHandler 8 }


--__________________________________________________________________________
--
--		     CAC support group
--
--__________________________________________________________________________



cacCurrentEbtId		OBJECT-TYPE
			SYNTAX INTEGER (0..65535)
			ACCESS read-only
			STATUS mandatory
			DESCRIPTION
			"Current EBT file ID code.
			<DETAIL_DESCRIPTION>
			cacCurrentEbtId holds the EBT file ID code of the EBT file
			currently in memory in a verified state.  The CAC application
			is responsible for maintaining the state of this variable.
			If there is a verified EBT in memory cacCurrentEbtId will
			still hold the EBT file's ID code even if the CAC is disabled
			or the CAC version is scr-pcr. If there is no EBT in memory
			or the verification was unsuccessful then the value of
			cacCurrentEbtId is zero (0)."
			::= { dv2Cac 1 }

cacEbtCommand		OBJECT-TYPE
			SYNTAX INTEGER
			{
				none(1),
				load-EBT(2),
				dump-EBT(3),
				delete-EBT(4)
			}
			ACCESS read-write
			STATUS mandatory
			DESCRIPTION
			"EBT file command.
			<DETAIL_DESCRIPTION>
			This field, normally with the value none, may be set by the
			manager to: * load-ebt to initiate the loading of a new EBT
			                       file into memory.
			            * dump-ebt to initiate the dump of the EBT memory
					       content into flash.
			            * delete-ebt to cause an EBT file to be deleted
			                       in the flash.
			The value of cacEbtCommand will return to none when the EBT
			file command has been completed."
			::= { dv2Cac 2 }

cacCommandEbtId		OBJECT-TYPE
			SYNTAX INTEGER (0..65535)
			ACCESS read-write
			STATUS mandatory
			DESCRIPTION
			"Command EBT file ID code.
			<DETAIL_DESCRIPTION>
			cacCommandEbtId is written to by the manager to identify the
			EBT file in the flash that should be loaded or deleted. When
			the cacEbtCommand MIB item is set to either load-ebt or
			delete-ebt, the CAC software attempts to load or delete the
			EBT file named ebXXXXX.bin from flash, where XXXXX is the
			value cacCommandEbtId padded to five digits with leading zeros.
			The value zero (0) is not a valid EBT file ID code and is
			reserved to indicate that EBT file ID code has not been specified."
			::= { dv2Cac 3 }

cacEbtState		OBJECT-TYPE
			SYNTAX INTEGER
			{
				uninitialized(1),
				initializing(2),
				loading(3),
				ready(4),
				unusable(5)
			}
			ACCESS read-only
			STATUS mandatory
			DESCRIPTION
			"State of the CAC.
			<DETAIL_DESCRIPTION>
			The state: * uninitialized is an initial MIB value which is never
			             returned to without starting from a new MIB.
			           * initializing indicates the initial part of the CAC boot.
			           * loading indicates that an EBT file is being loaded.
			           * ready indicates that a valid EBT is in memory. In
			             this state the current EBT file ID code shows the ID
			             code of the EBT in memory.
			           * unusable is reached after an unsuccessful load and
			             indicates that the data in the EBT memory block is
			             unusable (in this state current EBT file ID code shows 0)."
			DEFVAL { uninitialized }
			::= { dv2Cac 4 }

cacErrorCode		OBJECT-TYPE
			SYNTAX INTEGER
			{
				no-error(1),
				nonexistent-file(2),
				bad-file-length(3),
				copy-corrupted(4),
				nunused-cbtdwoebtid(5),
				nunused-cinvalid(6),
				nebtid-uninit-cstays(7),
				ninvalid-cstays(8),
				ninvalid-cebtid-uninit(9),
				ninvalid-cinvalid(10),
				ninvalid-cnoerror(11),
				link-not-ready(12),
				link-not-configuring(13),
				ebt-not-loaded(14),
				class-not-found(15),
				dump-fs-error(16),
				bad-ebt-command(17),
				delete-fs-error(18),
				ebt-id-invalid(19)
			}
			ACCESS read-only
			STATUS mandatory
			DESCRIPTION
			"Error code.
			<DETAIL_DESCRIPTION>
			Error codes are produced at certain stages in the CAC application.
			The interpretation of the error codes is:
			Terms: 'ebXXXXX.bin' : binary file in flash
			data structure: EBT_file_template based structure
			* no-error: no error encountered.
			* nonexistent-file: the 'ebXXXXX.bin' file not found in the flash,
			  during APEX boot or MIB EBT load request.
			* bad-file-length: mismatch in file length specified within
			  'ebXXXXX.bin' and the pre-specified file length. Occurs while
			  loading file into data structures.
			* copy-corrupted: copying of data from 'ebXXXXX.bin' into the data
			  structure, EBT_file_template did not proceed smoothly and the data
			  structure is now corrupted.
			* nunused-cbtdwoEBTid: command EBT id not used and current EBT id
			  is 0. The CAC booted without valid EBT values in the data structure.
			  Occurs during boot while loading file into data structures.
			* nunused-cinvalid: command EBT id not used. The file eb'current EBT
			  id'.bin contains invalid data. Occurs just after the EBT file got
			  loaded into the data structure, when the verification of values
			  in the data structure takes place.
			* nEBTid-uninit-cstays: command EBT id is 0 and the data structures
			  remain unchanged. Occurs when mib item cacTableload is switched to yes.
			* ninvalid-cstays: eb'command EBT id'.bin contains invalid data and
			  the data structures remain unchanged. Occurs when mib item cacTableload
			  is switched to yes.
			* ninvalid-cEBTid-uninit: eb'command EBT id'.bin contains invalid data
			  and the current EBT id is zero. This means that data structure is
			  corrupted. Occurs when mib item cacTableload is switched to yes.
			* ninvalid-cinvalid: both eb'command EBT id'.bin and eb'current EBT
			  id'.bin contains invalid data. The data structure is corrupted.
			  Occurs when mib item cacTableload is switched to yes.
			* ninvalid-cnoerror: eb'command EBT id'.bin contains invalid data
			  and the eb'current EBT id'.bin is loaded successfully. Occurs
			  when mib item cacTableload is switched to yes.
			* link-not-ready: it is a runtime error which states that link is
			  not ready for configuration.
			* link-not-configuring: it is a runtime error which states that link
			  is not in configuring mode and therefore the recalculation of EBT
			  or scr-pcr sums is not possible.
			* EBT-not-loaded: it is a runtime error which states that the data
			  structure does not contain valid data. This occurs when the EBT
			  enable mib switch is turned to 'yes' or the cac version mib item
			  is switched to EBT.
			* class-not-found: this runtime error indicates that during the
			  processing of allocate, deallocate or change functions, a class
			  corresponding to SCR, PCR or MBS was not found. The effective
			  bandwidth used in this situation is the same as a CBR allocation
			  using the attempted connection's PCR.
			* dump-fs-error: this error indicates that a file system error
			  (e.g. the file system became full) during the EBT file dump function.
			  The dump file was deleted after the file system error was detected."
			DEFVAL { no-error }
			::= { dv2Cac 5 }


cacPerLinkTable		OBJECT-TYPE
		        SYNTAX SEQUENCE OF CacPerLinkEntry
			ACCESS not-accessible
			STATUS mandatory
			DESCRIPTION
			"This table containing per link data.
			<DETAIL_DESCRIPTION>
			Contains per link specific data"
			::= { dv2Cac 6 }

cacPerLinkEntry		OBJECT-TYPE
			SYNTAX  CacPerLinkEntry
			ACCESS  not-accessible
			STATUS  mandatory
			INDEX   {cacLinkNo}
			::= { cacPerLinkTable 1 }

CacPerLinkEntry ::=	SEQUENCE {
		 		cacLinkNo
					INTEGER,
				cacLinkSumE10
                                        Gauge,
                                cacLinkSumE1T
                                        Gauge,
				cacLinkObfPvc1
					INTEGER,
				cacLinkObfSvc1
					INTEGER,
				cacLinkSumE20
                                        Gauge,
                                cacLinkSumE2T
                                        Gauge,
				cacLinkObfPvc2
					INTEGER,
				cacLinkObfSvc2
					INTEGER,
                                cacLinkTotalBwScrPcr
                                        INTEGER,
                                cacCurrentLinkUsage
                                        INTEGER,
                                cacMaxLinkUsage
                                        INTEGER,
                                cacLinkReset
                                        INTEGER,
                                cacLinkVersion
                                        INTEGER,
                                cacLinkEnable
                                        INTEGER,
                                cacLinkSignalMode
                                        INTEGER,
                                cacLinkState
					INTEGER
				}


cacLinkNo	        OBJECT-TYPE
		        SYNTAX INTEGER (0..3)
		        ACCESS read-only
		        STATUS mandatory
		        DESCRIPTION
		        "Link number.
			<DETAIL_DESCRIPTION>
			cacLinkNo is the index (0..3) to the array of link data."
		        ::= { cacPerLinkEntry 1 }

cacLinkSumE10		OBJECT-TYPE
		        SYNTAX Gauge
		        ACCESS read-only
		        STATUS mandatory
		        DESCRIPTION
		        "Running sum of e10.
			<DETAIL_DESCRIPTION>
			cacSumE10 zero loss effective bandwidth for high priority queue.
			This value is maintained only when the CAC is enabled on the link
			(cacEnable) and when the EBT CAC version is being used
			(cacVersion==EBT) otherwise the values here are zero."
		        ::= { cacPerLinkEntry 2 }

cacLinkSumE1T		OBJECT-TYPE
		        SYNTAX Gauge
		        ACCESS read-only
		        STATUS mandatory
		        DESCRIPTION
		        "Running sum of e1T.
			<DETAIL_DESCRIPTION>
			cacSumE1T tangent effective bandwidth for high priority queue.
			This value is maintained only when the CAC is enabled on the link
			(cacEnable) and when the EBT CAC version is being used
			(cacVersion==EBT) otherwise the values here are zero."
		        ::= { cacPerLinkEntry 3 }


cacLinkObfPvc1		OBJECT-TYPE
		        SYNTAX INTEGER
		        ACCESS read-write
		        STATUS mandatory
		        DESCRIPTION
		        "Utilization factor for  high priority pvc.
			<DETAIL_DESCRIPTION>
			Utilization factor for PVCs and SPVCs for the high priority queue."
			DEFVAL { 100 }
		        ::= { cacPerLinkEntry 4 }

cacLinkObfSvc1		OBJECT-TYPE
		        SYNTAX INTEGER
		        ACCESS read-write
		        STATUS mandatory
		        DESCRIPTION
		        "Utilization factor for high priority svc.
			<DETAIL_DESCRIPTION>
			Utilization factor for SVCs for the high priority queue."
			DEFVAL { 100 }
		        ::= { cacPerLinkEntry 5 }

cacLinkSumE20		OBJECT-TYPE
		        SYNTAX Gauge
		        ACCESS read-only
		        STATUS mandatory
		        DESCRIPTION
		        "Running sum of e20.
			<DETAIL_DESCRIPTION>
			cacSumE20 zero loss effective bandwidth for low priority queue.
			This value is maintained only when the CAC is enabled on the link
			(cacEnable) and when the EBT CAC version is being used
			(cacVersion==EBT) otherwise the values here are zero."
		        ::= { cacPerLinkEntry 6 }

cacLinkSumE2T		OBJECT-TYPE
		        SYNTAX Gauge
		        ACCESS read-only
		        STATUS mandatory
		        DESCRIPTION
		        "Running sum of e2T.
			<DETAIL_DESCRIPTION>
			cacSumE1T zero tangent effective bandwidth for low priority queue.
			This value is maintained only when the CAC is enabled on the link
			(cacEnable) and when the EBT CAC version is being used
			(cacVersion==EBT) otherwise the values here are zero."
		        ::= { cacPerLinkEntry 7 }

cacLinkObfPvc2		OBJECT-TYPE
		        SYNTAX INTEGER
		        ACCESS read-write
		        STATUS mandatory
		        DESCRIPTION
		        "Utilization factor for low priority pvc.
			<DETAIL_DESCRIPTION>
			Utilization factor for PVCs and SPVCs for the low priority queue."
			DEFVAL { 100 }
		        ::= { cacPerLinkEntry 8 }

cacLinkObfSvc2		OBJECT-TYPE
		        SYNTAX INTEGER
		        ACCESS read-write
		        STATUS mandatory
		        DESCRIPTION
		        "Utilization factor for low priority svc.
			<DETAIL_DESCRIPTION>
			Utilization factor for SVCs for the low priority queue."
			DEFVAL { 100 }
		        ::= { cacPerLinkEntry 9 }

cacLinkTotalBwScrPcr	OBJECT-TYPE
			SYNTAX INTEGER
			ACCESS read-only
			STATUS mandatory
			DESCRIPTION
			"total bw allocation on the link by scr-pcr CAC.
			<DETAIL_DESCRIPTION>
			cacTotalBwScrPcr is the total bandwidth allocated to extant connections
			when the CAC is enabled and when the SCR-PCR CAC is being used.
			Its value is zero if CAC is disabled or the EBT CAC mode is used."
		        ::= { cacPerLinkEntry 10 }

cacCurrentLinkUsage	OBJECT-TYPE
			SYNTAX INTEGER
			ACCESS read-only
			STATUS mandatory
			DESCRIPTION
			"Current link bandwidth allocation.
			<DETAIL_DESCRIPTION>
			It is the current indication of bandwidth allocation on a link based
			on the formula using effective bandwidths"
		        ::= { cacPerLinkEntry 11 }

cacMaxLinkUsage		OBJECT-TYPE
			SYNTAX INTEGER
			ACCESS read-only
			STATUS mandatory
			DESCRIPTION
			"Max link bw allocation since last reset or card boot.
			<DETAIL_DESCRIPTION>
			cacMaxLinkUsage shows the maximum value that cacCurrentLinkUsage
			has reached since cacMaxLinkUsage was last reset."
		        ::= { cacPerLinkEntry 12 }

cacLinkReset		OBJECT-TYPE
			SYNTAX INTEGER
			{
				no(1),
				yes(2)
			}
			ACCESS read-write
			STATUS mandatory
			DESCRIPTION
			"Reload maximum link usage from current allocation.
			<DETAIL_DESCRIPTION>
			cacReset resets cacMaxLinkUsage, after the reset cacMaxLinkUsage
			shows the same value as cacCurrentLinkUsage."
			DEFVAL { no }
			::= {cacPerLinkEntry 13 }

cacLinkVersion		OBJECT-TYPE
			SYNTAX INTEGER
			{
				ebt(1),
				scr-pcr(2)
			}
			ACCESS read-write
			STATUS mandatory
			DESCRIPTION
			"Use EB CAC or scr-pcr CAC?
			<DETAIL_DESCRIPTION>
			The per-link variable cacVersion may take on the values
			* SCR-PCR indicating that the old, pre Rel 4.2 CAC based on SCR
			  and PCR values, is in operation or
			* EBT indicating that the new CAC based on effective bandwidths is used.
			cacVersion may be set by the manager.
			If cacVersion is set to EBT by the manager it will revert to SCR-PCR
			unless a valid EBT is currently available in memory
			(in which case cacEbtState==ready and cacCurrentEbtId holds a non-zero value).
			The cacVersion may also revert to SCR-PCR if, during boot or an EBT load,
			a valid EBT cannot be established in memory.
			A change of state in cacVersion will result in recalculatation of EB Sums."
			DEFVAL { ebt }
			::= { cacPerLinkEntry 14 }

cacLinkEnable		OBJECT-TYPE
			SYNTAX INTEGER
			{
				no(1),
				yes(2)
			}
			ACCESS read-write
			STATUS mandatory
			DESCRIPTION
			"Enable cac?
			<DETAIL_DESCRIPTION>
			When cacEnable has the value
			* yes, then the three CAC service routines are operational as defined,
			* no, then all connections are accepted regardless of required bandwidths
			CAC may be enabled or disabled by the manager at any time that the
			cacLinkState is ready.  Enabling CAC will cause recalculatation of
			EB sums for that link.  Disabling CAC will cause the EB sums for
			the link (also for associated V-SAPs) to be set to zero."
			DEFVAL { yes }
			::= { cacPerLinkEntry 15 }

cacLinkSignalMode	OBJECT-TYPE
			SYNTAX INTEGER
			{
				single-channel(1),
				multi-channel(2)
			}
			ACCESS read-only
			STATUS mandatory
			DESCRIPTION
			"Link signalling mode
			<DETAIL_DESCRIPTION>
			cacSignallingMode is a read-only variable indicating whether the link
			is currently in the signalling mode:
			* single-channel or
			* multi-channel
			The value of cacSignallingMode is updated any time a virtual SAP is
			either associated or disassociated with a physical SAP. Multi-channel
			mode indicates that at least one virtual SAP is associated with the
			link's physical SAP. In multi-channel mode the zero-loss effective
			bandwidths are not used for connection admission control."
			DEFVAL { single-channel }
			::= { cacPerLinkEntry 16 }

cacLinkState		OBJECT-TYPE
			SYNTAX INTEGER
			{
				uninitialized(1),
				configuring(2),
				recalculating(3),
				ready(4)
			}
			ACCESS read-only
			STATUS mandatory
			DESCRIPTION
			"State of the Link
			<DETAIL_DESCRIPTION>
			The cacLinkState variable can take the values:
			* uninitialised is an initial MIB value which is never returned to
			  without staring from a new MIB.
			* configuring indicates that the CAC on that link cannot be used at
			  the current time. This indicates that CAC is booting, an EBT is
			  being loaded. This is a transient state that will go to ready or
			  recalculating.
			* recalculating indicates that the sums for both eb and scr-pcr
			  are cleared and are recalculated for the existing connections.
			* ready indicates that CAC may be used on that link.
			  The state machine is given in Figure 3. Transitions out of the
			  ready state can be caused by a boot, an EBT load or the call back
			  functions on (per link) Enable and Version. Whether the transition
			  from configuring back to ready is direct or via recalculating depends
			  on whether or not there is a need to recalculate the effective bandwidth
			  sums; this depends on several factors that can be derived from the
			  detailed design in Section 6.2.4.7.
			  The value of the cacLinkState variable is valid and indicates the
			  current link state of the CAC indepenently of the value of cacEnable,
			  cacVersion and cacEbtState.
			  When cacLinkState is configuring, certain CAC functions are disabled:
			  * Requests to the allocate, deallocate and allocation_change service
			    routines will be rejected without processing.
			  * Requests to the allocation summary routine may produce inconsistent results.
			    When cacLinkState is recalculating, certain CAC functions are disabled:
			  * Requests to allocation_change and deallocate service routines will
			    be rejected without processing.
			  * Requests to the allocation summary routine may produce inconsistent results."
			DEFVAL { uninitialized }
			::= { cacPerLinkEntry 17 }

cacPerSapTable		OBJECT-TYPE
		        SYNTAX SEQUENCE OF CacPerSapEntry
			ACCESS not-accessible
			STATUS mandatory
			DESCRIPTION
			"This table containing per Sap data.
			<DETAIL_DESCRIPTION>
			The virtual SAP table in the MIB has 12 entries indexed by cacSapNo
			in the range (20..31). For each SAP there the table entries are detailed below.
			These entries are only used when at least one of the link's cacSignallingMode
			is multi-channel. The association of a virtual SAP to a link is given in
			the resource table MIB group."
			::= { dv2Cac 7 }


cacPerSapEntry		OBJECT-TYPE
			SYNTAX  CacPerSapEntry
			ACCESS  not-accessible
			STATUS  mandatory
			INDEX   {cacSapNo}
			::= { cacPerSapTable 1 }



CacPerSapEntry ::=	SEQUENCE {
		 		cacSapNo
					INTEGER,
		                cacSapSumE1T
				        Gauge,
				cacSapSumE2T
				        Gauge,
				cacSapTotalBwScrPcr
				        INTEGER,
				cacCurrentSapUsage
					INTEGER,
				cacMaxSapUsage
					INTEGER,
				cacSapReset
					INTEGER
}

cacSapNo	        OBJECT-TYPE
		        SYNTAX INTEGER (20..31)
		        ACCESS read-only
		        STATUS mandatory
		        DESCRIPTION
		        "SAP number.
			<DETAIL_DESCRIPTION>
			cacSapNo is the index (0..11) to the array of sap data."
		        ::= { cacPerSapEntry 1 }

cacSapSumE1T		OBJECT-TYPE
		        SYNTAX Gauge
		        ACCESS read-only
		        STATUS mandatory
		        DESCRIPTION
		        "Running sum of e1T.
			<DETAIL_DESCRIPTION>
			cacSumE1T tangent effective bandwidth for high priority queue
			These values are maintained only when the CAC is enabled on the link
			(cacEnable), when the SAP is assigned to a link and when the EBT CAC
			version is being used (cacVersion==EBT) otherwise the values here are zero."
		        ::= { cacPerSapEntry 2 }

cacSapSumE2T		OBJECT-TYPE
		        SYNTAX Gauge
		        ACCESS read-only
		        STATUS mandatory
		        DESCRIPTION
		        "Running sum of e2T.
			<DETAIL_DESCRIPTION>
			cacSumE1T tangent effective bandwidth for low priority queue
			These values are maintained only when the CAC is enabled on the link
			(cacEnable), when the SAP is assigned to a link and when the EBT CAC version
			is being used (cacVersion==EBT) otherwise the values here are zero."
		        ::= { cacPerSapEntry 3 }

cacSapTotalBwScrPcr	OBJECT-TYPE
			SYNTAX INTEGER
			ACCESS read-only
			STATUS mandatory
			DESCRIPTION
			"total bw allocation on the link by scr-pcr CAC.
			<DETAIL_DESCRIPTION>
			cacTotalBwScrPcr is the total bandwidth allocated to extant connections
			when the CAC is enabled and when the SCR-PCR CAC is being used. Its value
			is zero if CAC is disabled or the EBT CAC mode is used."
		        ::= { cacPerSapEntry 4 }

cacCurrentSapUsage	OBJECT-TYPE
			SYNTAX INTEGER
			ACCESS read-only
			STATUS mandatory
			DESCRIPTION
			"Current SAP bandwidth allocation
			<DETAIL_DESCRIPTION>
			It is the current indication of bandwidth allocation on a sap based on
			the formula using effective bandwidths."
		        ::= { cacPerSapEntry 5 }

cacMaxSapUsage		OBJECT-TYPE
			SYNTAX INTEGER
			ACCESS read-only
			STATUS mandatory
			DESCRIPTION
			"Max SAP b/w allocation since last reset or card boot.
			<DETAIL_DESCRIPTION>
			cacMaxSapUsage shows the maximum value that cacCurrentSapUsage has
			reached since cacMaxSapUsage was last reset."
		        ::= { cacPerSapEntry 6 }

cacSapReset		OBJECT-TYPE
			SYNTAX INTEGER
			{
				no(1),
				yes(2)
			}
			ACCESS read-write
			STATUS mandatory
			DESCRIPTION
			"Reload maximum SAP usage from current allocation
			<DETAIL_DESCRIPTION>
			cacReset resets cacMaxSapUsage, after the reset cacMaxSapUsage
			shows the same value as cacCurrentSapUsage."
			DEFVAL { no }
			::= {cacPerSapEntry 7
 }

--___________________________________________________________________________

-- Traps


	dv2Message	TRAP-TYPE
		ENTERPRISE	dv2
		VARIABLES	{ sysLastTrapMessage }
		DESCRIPTION
		"This is used to send an arbitary text string to the NMS."
		::= 1

	slotChanged	TRAP-TYPE
		ENTERPRISE	dv2
		VARIABLES	{ slot0PhySlotNo, slot0PhyState }
		DESCRIPTION
		"This is sent when a slot changes state."
		::= 2

	linkChanged	TRAP-TYPE
		ENTERPRISE	dv2
		VARIABLES	{ slot0PhySlotNo, slot0PhyLink0State, slot0PhyLink1State,
                                  slot0PhyLink2State, slot0PhyLink3State, slot0PhyLstChngLnkNum,
                                  slot0PhyLstChngPrevLnkStat }
		DESCRIPTION
		"This is sent when a link changes state."
		::= 3

	psuChanged	TRAP-TYPE
		ENTERPRISE	dv2
		VARIABLES	{ slot0PsuIndex, slot0PsuFault }
		DESCRIPTION
		"This is sent when a power supply changes state."
		::= 4

	configChanged	TRAP-TYPE
		ENTERPRISE	dv2
		VARIABLES	{ sysConfigChanged, slotNumber }
		DESCRIPTION
		"This is sent when <config.cfg> has changed."
		::= 5

--	ds1RecYelAlarm	TRAP-TYPE
--		ENTERPRISE	dv2
--		VARIABLES	{ sysLastTrapMessage, slotNumber, sysLkLinkNo }
--		DESCRIPTION
--		"This is sent when a DS1 yellow alarm is received"
--		::= 6

--	ds1ClrYelAlarm	TRAP-TYPE
--		ENTERPRISE	dv2
--		VARIABLES	{ sysLastTrapMessage, slotNumber, sysLkLinkNo }
--		DESCRIPTION
--		"This is sent when a DS1 yellow alarm is cleared"
--		::= 7

--	ds1RecBlueAlarm	TRAP-TYPE
--		ENTERPRISE	dv2
--		VARIABLES	{ sysLastTrapMessage, slotNumber, sysLkLinkNo }
--		DESCRIPTION
--		"This is sent when a DS1 AIS (BLUE) alarm is received"
--		::= 8

--	ds1ClrBlueAlarm	TRAP-TYPE
--		ENTERPRISE	dv2
--		VARIABLES	{ sysLastTrapMessage, slotNumber, sysLkLinkNo }
--		DESCRIPTION
--		"This is sent when a DS1 AIS (BLUE) alarm is cleared"
--		::= 9

--	ds1RecLOF	TRAP-TYPE
--		ENTERPRISE	dv2
--		VARIABLES	{ sysLastTrapMessage, slotNumber, sysLkLinkNo }
--		DESCRIPTION
--		"This is sent when a DS1 Loss of Frame alarm is received"
--		::= 10

--	ds1ClrLOF	TRAP-TYPE
--		ENTERPRISE	dv2
--		VARIABLES	{ sysLastTrapMessage, slotNumber, sysLkLinkNo }
--		DESCRIPTION
--		"This is sent when a DS1 Loss of Frame alarm is cleared"
--		::= 11

--	plcpRecYelAlarm	TRAP-TYPE
--		ENTERPRISE	dv2
--		VARIABLES	{ sysLastTrapMessage, slotNumber, sysLkLinkNo }
--		DESCRIPTION
--		"This is sent when a PLCP yellow alarm is received"
--		::= 12

--	plcpClrYelAlarm	TRAP-TYPE
--		ENTERPRISE	dv2
--		VARIABLES	{ sysLastTrapMessage, slotNumber, sysLkLinkNo }
--		DESCRIPTION
--		"This is sent when a PLCP yellow alarm is cleared"
--		::= 13

--	plcpRecLOF	TRAP-TYPE
--		ENTERPRISE	dv2
--		VARIABLES	{ sysLastTrapMessage, slotNumber, sysLkLinkNo }
--		DESCRIPTION
--		"This is sent when a PLCP Loss of frame alarm is received"
--		::= 14

--	plcpClrLOF	TRAP-TYPE
--		ENTERPRISE	dv2
--		VARIABLES	{ sysLastTrapMessage, slotNumber, sysLkLinkNo }
--		DESCRIPTION
--		"This is sent when a PLCP Loss of frame alarm is cleared"
--		::= 15

--	ds3RecYelAlarm	TRAP-TYPE
--		ENTERPRISE	dv2
--		VARIABLES	{ sysLastTrapMessage, slotNumber, sysLkLinkNo }
--		DESCRIPTION
--		"This is sent when a DS3 yellow alarm is received"
--		::= 16

--	ds3ClrYelAlarm	TRAP-TYPE
--		ENTERPRISE	dv2
--		VARIABLES	{ sysLastTrapMessage, slotNumber, sysLkLinkNo }
--		DESCRIPTION
--		"This is sent when a DS3 yellow alarm is cleared"
--		::= 17

--	ds3RecBlueAlarm	TRAP-TYPE
--		ENTERPRISE	dv2
--		VARIABLES	{ sysLastTrapMessage, slotNumber, sysLkLinkNo }
--		DESCRIPTION
--		"This is sent when a DS3 AIS (BLUE) alarm is received"
--		::= 18

--	ds3ClrBlueAlarm	TRAP-TYPE
--		ENTERPRISE	dv2
--		VARIABLES	{ sysLastTrapMessage, slotNumber, sysLkLinkNo }
--		DESCRIPTION
--		"This is sent when a DS3 AIS (BLUE) alarm is cleared"
--		::= 19

--	ds3RecLOF	TRAP-TYPE
--		ENTERPRISE	dv2
--		VARIABLES	{ sysLastTrapMessage , slotNumber, sysLkLinkNo}
--		DESCRIPTION
--		"This is sent when a DS3 Loss of Frame alarm is received"
--		::= 20

--	ds3ClrLOF	TRAP-TYPE
--		ENTERPRISE	dv2
--		VARIABLES	{ sysLastTrapMessage, slotNumber, sysLkLinkNo }
--		DESCRIPTION
--		"This is sent when a DS3 Loss of Frame alarm is cleared"
--		::= 21

	reset040	TRAP-TYPE
		ENTERPRISE	dv2
		VARIABLES	{ sysLastTrapMessage, slotNumber}
		DESCRIPTION
		"This is sent when a the master processor is reset by operator"
		::= 22

	badPassword	TRAP-TYPE
		ENTERPRISE	dv2
		VARIABLES	{ sysLastTrapMessage, slotNumber }
		DESCRIPTION
		"This is sent when a user enters a bad password"
		::= 23

--	forcedReload	TRAP-TYPE
--		ENTERPRISE	dv2
--		VARIABLES	{ sysLastTrapMessage, slotNumber}
--		DESCRIPTION
--		"This is sent when the software on flash memory is decompressed and started"
--		::= 24

--	noUserFile	TRAP-TYPE
--		ENTERPRISE	dv2
--		VARIABLES	{ sysLastTrapMessage, slotNumber }
--		DESCRIPTION
--		"This is sent when a user doesn't exist in the users.cfg file"
--		::= 25

	billingRecFail	TRAP-TYPE
		ENTERPRISE	dv2
		VARIABLES	{ sysLastTrapMessage, slotNumber}
		DESCRIPTION
		"Could not create billing record"
		::= 26
--                                                    add variable #10, #11
	clockAlarm	TRAP-TYPE
		ENTERPRISE	dv2
		VARIABLES	{ alarmStatus, sysLastTrapMessage, sysClkAlarmErr, pSlotNumber,
                                  pSysRefSelect, sSlotNumber, sSysRefSelect, inService }
		DESCRIPTION
		"Change in system clock alarm state: declare or clear minor/major alarms,
                describe error and location, includes primary/secondary clock locations and
		the active clock reference"
		::= 27

	spvcInit	TRAP-TYPE
		ENTERPRISE	dv2
		VARIABLES	{ sysLastTrapMessage, sPvcId, slotNumber }
		DESCRIPTION
		"Call successfully established"
		::= 28

	spvcFail	TRAP-TYPE
		ENTERPRISE	dv2
		VARIABLES	{ sysLastTrapMessage, sPvcId, slotNumber, sPvcCauseDiagCode} 
		DESCRIPTION
		"Call attempt failed"
		::= 29

	spvcCallClr	TRAP-TYPE
		ENTERPRISE	dv2
		VARIABLES	{ sysLastTrapMessage, sPvcId, slotNumber }
		DESCRIPTION
		"Call cleared after established"
		::= 30

	spvcCallReset	TRAP-TYPE
		ENTERPRISE	dv2
		VARIABLES	{ sysLastTrapMessage, sPvcId, slotNumber  }
		DESCRIPTION
		"Call reset after established"
		::= 31

--	spvcDeleted	TRAP-TYPE
--		ENTERPRISE	dv2
--		VARIABLES	{ sysLastTrapMessage, sPvcId, slotNumber }
--		DESCRIPTION
--		"SPVC deleted from configuration"
--		::= 32

	spvcRetryExceeded	TRAP-TYPE
		ENTERPRISE	dv2
		VARIABLES	{ sysLastTrapMessage, sPvcId, slotNumber }
		DESCRIPTION
		"Call attempts exceeded retry limit"
		::= 33

--	spvcCallAttempt		TRAP-TYPE
--		ENTERPRISE	dv2
--		VARIABLES	{ sysLastTrapMessage, sPvcId, slotNumber }
--		DESCRIPTION
--		" SPVC TBD"
--		::= 34

--	e1-2C-AIS-SET	TRAP-TYPE
--		ENTERPRISE	dv2
--		VARIABLES	{ sysLastTrapMessage, slotNumber, sysLkLinkNo }
--		DESCRIPTION
--		"This is sent for an AIS alarm declared"
--		::= 35

--	e1-2C-AIS-CLR	TRAP-TYPE
--		ENTERPRISE	dv2
--		VARIABLES	{ sysLastTrapMessage, slotNumber, sysLkLinkNo }
--		DESCRIPTION
--		"This is sent for an AIS alarm cleared"
--		::= 36

--	e1-2C-LOF-SET	TRAP-TYPE
--		ENTERPRISE	dv2
--		VARIABLES	{ sysLastTrapMessage, slotNumber, sysLkLinkNo }
--		DESCRIPTION
--		"This is sent for a Loss of Frame alarm declared"
--		::= 37

--	e1-2C-LOF-CLR	TRAP-TYPE
--		ENTERPRISE	dv2
--		VARIABLES	{ sysLastTrapMessage, slotNumber, sysLkLinkNo }
--		DESCRIPTION
--		"This is sent for a Loss of Frame alarm cleared"
--		::= 38

--	e3RecFERF	TRAP-TYPE
--		ENTERPRISE	dv2
--		VARIABLES	{ sysLastTrapMessage, slotNumber, sysLkLinkNo }
--		DESCRIPTION
--		"This is sent when a E3 FERF is received"
--		::= 39

--	e3ClrFERF	TRAP-TYPE
--		ENTERPRISE	dv2
--		VARIABLES	{ sysLastTrapMessage, slotNumber, sysLkLinkNo }
--		DESCRIPTION
--		"This is sent when a E3 FERF is cleared"
--		::= 40

--	e3RecBlueAlarm	TRAP-TYPE
--		ENTERPRISE	dv2
--		VARIABLES	{ sysLastTrapMessage, slotNumber, sysLkLinkNo }
--		DESCRIPTION
--		"This is sent when a E3 AIS (BLUE) alarm is received"
--		::= 41

--	e3ClrBlueAlarm	TRAP-TYPE
--		ENTERPRISE	dv2
--		VARIABLES	{ sysLastTrapMessage, slotNumber, sysLkLinkNo }
--		DESCRIPTION
--		"This is sent when a E3 AIS (BLUE) alarm is cleared"
--		::= 42

--	e3RecLOF	TRAP-TYPE
--		ENTERPRISE	dv2
--		VARIABLES	{ sysLastTrapMessage , slotNumber, sysLkLinkNo}
--		DESCRIPTION
--		"This is sent when a E3 Loss of Frame alarm is received"
--		::= 43

--	e3ClrLOF	TRAP-TYPE
--		ENTERPRISE	dv2
--		VARIABLES	{ sysLastTrapMessage, slotNumber, sysLkLinkNo }
--		DESCRIPTION
--		"This is sent when a E3 Loss of Frame alarm is cleared"
--		::= 44

--	e3RecLOS	TRAP-TYPE
--		ENTERPRISE	dv2
--		VARIABLES	{ sysLastTrapMessage , slotNumber, sysLkLinkNo}
--		DESCRIPTION
--		"This is sent when a E3 Loss of Signal alarm is received"
--		::= 45

--	e3ClrLOS	TRAP-TYPE
--		ENTERPRISE	dv2
--		VARIABLES	{ sysLastTrapMessage, slotNumber, sysLkLinkNo }
--		DESCRIPTION
--		"This is sent when a E3 Loss of Signal alarm is cleared"
--		::= 46

--	ds3V2RecYelAlarm	TRAP-TYPE
--		ENTERPRISE	dv2
--		VARIABLES	{ sysLastTrapMessage, slotNumber, sysLkLinkNo }
--		DESCRIPTION
--		"This is sent when a DS3 yellow alarm is received"
--		::= 47

--	ds3V2ClrYelAlarm	TRAP-TYPE
--		ENTERPRISE	dv2
--		VARIABLES	{ sysLastTrapMessage, slotNumber, sysLkLinkNo }
--		DESCRIPTION
--		"This is sent when a DS3 yellow alarm is cleared"
--		::= 48

--	plcpV2RecYelAlarm	TRAP-TYPE
--		ENTERPRISE	dv2
--		VARIABLES	{ sysLastTrapMessage, slotNumber, sysLkLinkNo }
--		DESCRIPTION
--		"This is sent when a PLCP yellow alarm is received"
--		::= 49

--	plcpV2ClrYelAlarm	TRAP-TYPE
--		ENTERPRISE	dv2
--		VARIABLES	{ sysLastTrapMessage, slotNumber, sysLkLinkNo }
--		DESCRIPTION
--		"This is sent when a PLCP yellow alarm is cleared"
--		::= 50

--	ds3V2RecLOS	TRAP-TYPE
--		ENTERPRISE	dv2
--		VARIABLES	{ sysLastTrapMessage , slotNumber, sysLkLinkNo}
--		DESCRIPTION
--		"This is sent when a DS3 Loss of Signal alarm is received"
--		::= 51

--	ds3V2ClrLOS	TRAP-TYPE
--		ENTERPRISE	dv2
--		VARIABLES	{ sysLastTrapMessage, slotNumber, sysLkLinkNo }
--		DESCRIPTION
--		"This is sent when a DS3 Loss of Signal alarm is cleared"
--		::= 52

--	ds3V2RecLOF	TRAP-TYPE
--		ENTERPRISE	dv2
--		VARIABLES	{ sysLastTrapMessage , slotNumber, sysLkLinkNo}
--		DESCRIPTION
--		"This is sent when a DS3 Loss of Frame alarm is received"
--		::= 53

--	ds3V2ClrLOF	TRAP-TYPE
--		ENTERPRISE	dv2
--		VARIABLES	{ sysLastTrapMessage, slotNumber, sysLkLinkNo }
--		DESCRIPTION
--		"This is sent when a DS3 Loss of Frame alarm is cleared"
--		::= 54

--	ds3V2RecAIS	TRAP-TYPE
--		ENTERPRISE	dv2
--		VARIABLES	{ sysLastTrapMessage , slotNumber, sysLkLinkNo}
--		DESCRIPTION
--		"This is sent when a DS3 AIS alarm is received"
--		::= 55

--	ds3V2ClrAIS	TRAP-TYPE
--		ENTERPRISE	dv2
--		VARIABLES	{ sysLastTrapMessage , slotNumber, sysLkLinkNo}
--		DESCRIPTION
--		"This is sent when a DS3 AIS alarm is cleared"
--		::= 56

--	plcpV2RecLOF	TRAP-TYPE
--		ENTERPRISE	dv2
--		VARIABLES	{ sysLastTrapMessage, slotNumber, sysLkLinkNo }
--		DESCRIPTION
--		"This is sent when a PLCP Loss of frame alarm is received"
--		::= 57

--	plcpV2ClrLOF	TRAP-TYPE
--		ENTERPRISE	dv2
--		VARIABLES	{ sysLastTrapMessage, slotNumber, sysLkLinkNo }
--		DESCRIPTION
--		"This is sent when a PLCP Loss of frame alarm is cleared"
--		::= 58

--	plppFEFrmrDif    TRAP-TYPE
--		ENTERPRISE	dv2
--		VARIABLES	{ sysLastTrapMessage, slotNumber, sysLkLinkNo }
--		DESCRIPTION
--		"This is sent when a Far End Device is using a different DS3 Frame Format."
--		::= 59

--	sdhRecLOF	TRAP-TYPE
--		ENTERPRISE	dv2
--		VARIABLES	{ sysLastTrapMessage , slotNumber, sysLkLinkNo }
--		DESCRIPTION
--		"This is sent when a SONET/SDH Loss of Frame failure is declared"
--		::= 60

--	sdhClrLOF	TRAP-TYPE
--		ENTERPRISE	dv2
--		VARIABLES	{ sysLastTrapMessage, slotNumber, sysLkLinkNo }
--		DESCRIPTION
--		"This is sent when a SONET/SDH Loss of Frame failure is cleared"
--		::= 61

--	sdhRecLOS	TRAP-TYPE
--		ENTERPRISE	dv2
--		VARIABLES	{ sysLastTrapMessage , slotNumber, sysLkLinkNo }
--		DESCRIPTION
--		"This is sent when a SONET/SDH Loss of Signal failure is declared"
--		::= 62

--	sdhClrLOS	TRAP-TYPE
--		ENTERPRISE	dv2
--		VARIABLES	{ sysLastTrapMessage, slotNumber, sysLkLinkNo }
--		DESCRIPTION
--		"This is sent when a SONET/SDH Loss of Signal failure is cleared"
--		::= 63

--	sdhRecLOP	TRAP-TYPE
--		ENTERPRISE	dv2
--		VARIABLES	{ sysLastTrapMessage , slotNumber, sysLkLinkNo }
--		DESCRIPTION
--		"This is sent when a SONET/SDH Loss of Pointer failure is declared"
--		::= 64

--	sdhClrLOP	TRAP-TYPE
--		ENTERPRISE	dv2
--		VARIABLES	{ sysLastTrapMessage, slotNumber, sysLkLinkNo }
--		DESCRIPTION
--		"This is sent when a SONET/SDH Loss of Pointer failure is cleared"
--		::= 65

--	sdhRecLineAIS	TRAP-TYPE
--		ENTERPRISE	dv2
--		VARIABLES	{ sysLastTrapMessage , slotNumber, sysLkLinkNo }
--		DESCRIPTION
--		"This is sent when a SONET/SDH Line AIS failure is declared"
--		::= 66

--	sdhClrLineAIS	TRAP-TYPE
--		ENTERPRISE	dv2
--		VARIABLES	{ sysLastTrapMessage, slotNumber, sysLkLinkNo }
--		DESCRIPTION
--		"This is sent when a SONET/SDH Line AIS failure is cleared"
--		::= 67

--	sdhRecPathAIS	TRAP-TYPE
--		ENTERPRISE	dv2
--		VARIABLES	{ sysLastTrapMessage , slotNumber, sysLkLinkNo }
--		DESCRIPTION
--		"This is sent when a SONET/SDH Path AIS failure is declared"
--		::= 68

--	sdhClrPathAIS	TRAP-TYPE
--		ENTERPRISE	dv2
--		VARIABLES	{ sysLastTrapMessage, slotNumber, sysLkLinkNo }
--		DESCRIPTION
--		"This is sent when a SONET/SDH Path AIS failure is cleared"
--		::= 69

--	sdhRecLineFERF	TRAP-TYPE
--		ENTERPRISE	dv2
--		VARIABLES	{ sysLastTrapMessage , slotNumber, sysLkLinkNo }
--		DESCRIPTION
--		"This is sent when a SONET/SDH Line FERF failure is declared"
--		::= 70

--	sdhClrLineFERF	TRAP-TYPE
--		ENTERPRISE	dv2
--		VARIABLES	{ sysLastTrapMessage, slotNumber, sysLkLinkNo }
--		DESCRIPTION
--		"This is sent when a SONET/SDH Line FERF failure is cleared"
--		::= 71

--	sdhRecPathYel	TRAP-TYPE
--		ENTERPRISE	dv2
--		VARIABLES	{ sysLastTrapMessage , slotNumber, sysLkLinkNo }
--		DESCRIPTION
--		"This is sent when a SONET/SDH Path Yellow failure is declared"
--		::= 72

--	sdhClrPathYel	TRAP-TYPE
--		ENTERPRISE	dv2
--		VARIABLES	{ sysLastTrapMessage, slotNumber, sysLkLinkNo }
--		DESCRIPTION
--		"This is sent when a SONET/SDH Path Yellow failure is cleared"
--		::= 73

--	e3RecLCD	TRAP-TYPE
--		ENTERPRISE	dv2
--		VARIABLES	{ sysLastTrapMessage, slotNumber, sysLkLinkNo }
--		DESCRIPTION
--		"This is sent when a E3 LCD is declared"
--		::= 74

--	e3ClrLCD	TRAP-TYPE
--		ENTERPRISE	dv2
--		VARIABLES	{ sysLastTrapMessage, slotNumber, sysLkLinkNo }
--		DESCRIPTION
--		"This is sent when a E3 LCD is cleared"
--		::= 75

	mainInServ	TRAP-TYPE
		ENTERPRISE	dv2
		VARIABLES	{ sysLastTrapMessage, slot0InUse }
		DESCRIPTION
		"This is sent when the Main Slot 0 Controller goes into service"
		::= 76
	standbyInServ	TRAP-TYPE
		ENTERPRISE	dv2
		VARIABLES	{ sysLastTrapMessage, slot0InUse }
		DESCRIPTION
		"This is sent when the Standby Slot 0 Controller goes into service"
		::= 77

	bill25pstfull	TRAP-TYPE
		ENTERPRISE	dv2
		VARIABLES	{ billAvailable }
		DESCRIPTION
		"This is sent when billing table is 25% full."
		::= 78

	bill75pstfull	TRAP-TYPE
		ENTERPRISE	dv2
		VARIABLES	{ billAvailable }
		DESCRIPTION
		"This is sent when billing table is 75% full."
		::= 79

	restart040	TRAP-TYPE
		ENTERPRISE	dv2
		VARIABLES	 {slotNumber}
		DESCRIPTION
		"This is sent when the master processor has been restarted by
		 the 68302 processor."
		::= 80

	alcTxError	TRAP-TYPE
		ENTERPRISE	dv2
		VARIABLES	 {slotNumber}
		DESCRIPTION
		"This is sent after master processor has been reset due to
		 ALC-87 Transmitter Error."
		::= 81

--  e1-2C-LOS-SET   TRAP-TYPE
--      ENTERPRISE  dv2
--      VARIABLES   { sysLastTrapMessage, slotNumber, sysLkLinkNo }
--      DESCRIPTION
--      "This is sent for a Loss of Signal alarm declared"
--      ::= 82

--      e1-2C-LOS-CLR   TRAP-TYPE
--              ENTERPRISE  dv2
--              VARIABLES   { sysLastTrapMessage, slotNumber, sysLkLinkNo }
--              DESCRIPTION
--              "This is sent when a Loss of Signal alarm clears"
--              ::= 83

--	sdhRecPLM	TRAP-TYPE
--		ENTERPRISE	dv2
--		VARIABLES	{ sysLastTrapMessage , slotNumber, sysLkLinkNo }
--		DESCRIPTION
--		"This is sent when a SONET/SDH Path Label Mismatch failure is declared"
--		::= 84

--	sdhClrPLM	TRAP-TYPE
--		ENTERPRISE	dv2
--		VARIABLES	{ sysLastTrapMessage, slotNumber, sysLkLinkNo }
--		DESCRIPTION
--		"This is sent when a SONET/SDH Path Label Mismatch failure is cleared"
--		::= 85

--	plppFEFrmrSam    TRAP-TYPE
--		ENTERPRISE	dv2
--		VARIABLES	{ sysLastTrapMessage, slotNumber, sysLkLinkNo }
--		DESCRIPTION
--		"This is sent when a Far End Device is using a different DS3 Frame Format."
--		::= 86

--	e1RecFERF	TRAP-TYPE
--		ENTERPRISE	dv2
--		VARIABLES	{ sysLastTrapMessage, slotNumber, sysLkLinkNo }
--		DESCRIPTION
--		"This is sent when a E1 FERF is received"
--		::= 87

--	e1ClrFERF	TRAP-TYPE
--		ENTERPRISE	dv2
--		VARIABLES	{ sysLastTrapMessage, slotNumber, sysLkLinkNo }
--		DESCRIPTION
--		"This is sent when a E1 FERF is cleared"
--		::= 88

--	lOCD-active	TRAP-TYPE
--		ENTERPRISE	dv2
--		VARIABLES	{ sysLastTrapMessage, slotNumber, sysLkLinkNo }
--		DESCRIPTION
--		"Sent when a Loss Of Cell Delineation has occurred"
--		::= 89

--	lOCD-clear	TRAP-TYPE
--		ENTERPRISE	dv2
--		VARIABLES	{ sysLastTrapMessage, slotNumber, sysLkLinkNo }
--		DESCRIPTION
--		"Sent when Cell Delineation has been gained"
--		::= 90
--                                            #10: Add variables
	lim-fault      TRAP-TYPE
		ENTERPRISE	dv2
		VARIABLES	{ sysLastTrapMessage, slotNumber, limTypeStatus }
		DESCRIPTION
		"Configured LIM type does not match the LIM in slot"
		::= 91
--                                            #10: Add variables
	lim-oper      TRAP-TYPE
		ENTERPRISE	dv2
		VARIABLES	{ sysLastTrapMessage, slotNumber, limTypeStatus }
		DESCRIPTION
		"LIM operational"
		::= 92

	psuAbsent TRAP-TYPE
		ENTERPRISE	dv2
		VARIABLES	{ sysLastTrapMessage, slot0PsuIndex }
		DESCRIPTION
		"PSU Absent detected"
		::= 93

	psuPresent TRAP-TYPE
		ENTERPRISE	dv2
		VARIABLES	{ sysLastTrapMessage, slot0PsuIndex }
		DESCRIPTION
		"PSU Presence detected"
		::= 94

	switchFabricSwap TRAP-TYPE
		ENTERPRISE	dv2
		VARIABLES	{ sysLastTrapMessage }
		DESCRIPTION
		"Switch Fabric Redundant Swap"
		::= 95

--	exBERActive TRAP-TYPE
--		ENTERPRISE	dv2
--		VARIABLES	{ sysLastTrapMessage, slotNumber, sysLkLinkNo }
--		DESCRIPTION
--		"Excessive Bit Error Rate Active"
--		::= 96

--	exBERClear TRAP-TYPE
--		ENTERPRISE	dv2
--		VARIABLES	{ sysLastTrapMessage, slotNumber, sysLkLinkNo }
--		DESCRIPTION
--		"Excessive Bit Error Rate Clear"
--		::= 97

--	losAlrActive TRAP-TYPE
--		ENTERPRISE	dv2
--		VARIABLES	{ sysLastTrapMessage, slotNumber, sysLkLinkNo }
--		DESCRIPTION
--		"Loss Of Signal Alarm Active"
--		::= 98

--	losAlrClear TRAP-TYPE
--		ENTERPRISE	dv2
--		VARIABLES	{ sysLastTrapMessage, slotNumber, sysLkLinkNo }
--		DESCRIPTION
--		"Loss Of Signal Alarm Clear"
--		::= 99

--	lofAlrActive TRAP-TYPE
--		ENTERPRISE	dv2
--		VARIABLES	{ sysLastTrapMessage, slotNumber, sysLkLinkNo }
--		DESCRIPTION
--		"Loss Of Frame Alarm Active"
--		::= 100

--	lofAlrClear TRAP-TYPE
--		ENTERPRISE	dv2
--		VARIABLES	{ sysLastTrapMessage, slotNumber, sysLkLinkNo }
--		DESCRIPTION
--		"Loss Of Frame Alarm Clear"
--		::= 101

--	aisAlrActive TRAP-TYPE
--		ENTERPRISE	dv2
--		VARIABLES	{ sysLastTrapMessage, slotNumber, sysLkLinkNo }
--		DESCRIPTION
--		"AIS Alarm Active"
--		::= 102

--	aisAlrClear TRAP-TYPE
--		ENTERPRISE	dv2
--		VARIABLES	{ sysLastTrapMessage, slotNumber, sysLkLinkNo }
--		DESCRIPTION
--		"AIS Alarm Clear"
--		::= 103

--	yelAlrActive TRAP-TYPE
--		ENTERPRISE	dv2
--		VARIABLES	{ sysLastTrapMessage, slotNumber, sysLkLinkNo }
--		DESCRIPTION
--		"Yellow Alarm Active"
--		::= 104

--	yelAlrClear TRAP-TYPE
--		ENTERPRISE	dv2
--		VARIABLES	{ sysLastTrapMessage, slotNumber, sysLkLinkNo }
--		DESCRIPTION
--		"Yellow Alarm Clear"
--		::= 105


	internalReset	TRAP-TYPE
		ENTERPRISE	dv2
		VARIABLES	{ sysLastTrapMessage, slotNumber}
		DESCRIPTION
		"This is sent after the software has detected an internal
                 error and restarted itself."
		::= 106

	aal1Fault	TRAP-TYPE
		ENTERPRISE	dv2
		VARIABLES	{ sysLastTrapMessage, slotNumber, sysLkLinkNo }
		DESCRIPTION
		"This is sent when an AAL1 fault has occurred."
		::= 107

	aal1Clear	TRAP-TYPE
		ENTERPRISE	dv2
		VARIABLES	{ sysLastTrapMessage, slotNumber, sysLkLinkNo }
		DESCRIPTION
		"This is sent when an AAL1 fault has been cleared."
		::= 108


        ds1LOS             TRAP-TYPE
              ENTERPRISE      dv2
              VARIABLES      { sysLastTrapMessage, slotNumber, sysLkLinkNo, ds1LOSAlarm }
              DESCRIPTION
              "Loss of Signal alarm"
              ::= 109

        ds1LOF             TRAP-TYPE
              ENTERPRISE      dv2
              VARIABLES      { sysLastTrapMessage, slotNumber, sysLkLinkNo, ds1LOFAlarm }
              DESCRIPTION
              "Loss of Frame alarm"
              ::= 110

        ds1AIS             TRAP-TYPE
              ENTERPRISE      dv2
              VARIABLES      { sysLastTrapMessage, slotNumber, sysLkLinkNo, ds1AISAlarm }
              DESCRIPTION
              "AIS alarm"
              ::= 111

        ds1Yellow          TRAP-TYPE
              ENTERPRISE      dv2
              VARIABLES      { sysLastTrapMessage, slotNumber, sysLkLinkNo, ds1YellowAlarm }
              DESCRIPTION
              "Yellow alarm"
              ::= 112

        ds1ExBER           TRAP-TYPE
              ENTERPRISE      dv2
              VARIABLES      { sysLastTrapMessage, slotNumber, sysLkLinkNo, ds1ExBERAlarm }
              DESCRIPTION
              "Excessive Bit Error Rate Alarm"
              ::= 113

        ds1v2LOS             TRAP-TYPE
              ENTERPRISE      dv2
              VARIABLES      { sysLastTrapMessage, slotNumber, sysLkLinkNo, ds1V2LOSAlarm }
              DESCRIPTION
              "Loss of Signal alarm"
              ::= 114

        ds1v2LOF             TRAP-TYPE
              ENTERPRISE      dv2
              VARIABLES      { sysLastTrapMessage, slotNumber, sysLkLinkNo, ds1V2LOFAlarm }
              DESCRIPTION
              "Loss of Frame alarm"
              ::= 115

        ds1v2AIS             TRAP-TYPE
              ENTERPRISE      dv2
              VARIABLES      { sysLastTrapMessage, slotNumber, sysLkLinkNo, ds1V2AISAlarm }
              DESCRIPTION
              "AIS alarm"
              ::= 116

        ds1v2Yellow          TRAP-TYPE
              ENTERPRISE      dv2
              VARIABLES      { sysLastTrapMessage, slotNumber, sysLkLinkNo, ds1V2FerfAlarm }
              DESCRIPTION
              "Yellow alarm"
              ::= 117

        ds1v2ExBER           TRAP-TYPE
              ENTERPRISE      dv2
              VARIABLES      { sysLastTrapMessage, slotNumber, sysLkLinkNo, ds1V2BERAlarm }
              DESCRIPTION
              "Excessive Bit Error Rate Alarm"
              ::= 118

        ds3LOS             TRAP-TYPE
              ENTERPRISE      dv2
              VARIABLES      { sysLastTrapMessage, slotNumber, sysLkLinkNo, ds3LOSAlarm }
              DESCRIPTION
              "Loss of Signal alarm"
              ::= 119

        ds3V2LOS           TRAP-TYPE
              ENTERPRISE      dv2
              VARIABLES      { sysLastTrapMessage, slotNumber, sysLkLinkNo, ds3V2LOSAlarm }
              DESCRIPTION
              "Loss of Signal alarm"
              ::= 120

        ds3LOF             TRAP-TYPE
              ENTERPRISE      dv2
              VARIABLES      { sysLastTrapMessage, slotNumber, sysLkLinkNo, pdhDS3LOFAlarm }
              DESCRIPTION
              "Loss of Frame alarm"
              ::= 121

        ds3AIS             TRAP-TYPE
              ENTERPRISE      dv2
              VARIABLES      { sysLastTrapMessage, slotNumber, sysLkLinkNo, pdhDS3AISAlarm }
              DESCRIPTION
              "AIS alarm"
              ::= 122

        ds3Yellow          TRAP-TYPE
              ENTERPRISE      dv2
              VARIABLES      { sysLastTrapMessage, slotNumber, sysLkLinkNo, pdhDS3YellowAlarm }
              DESCRIPTION
              "Yellow alarm"
              ::= 123

        ds3ExBER           TRAP-TYPE
              ENTERPRISE      dv2
              VARIABLES      { sysLastTrapMessage, slotNumber, sysLkLinkNo, pdhDS3ExBERAlarm }
              DESCRIPTION
              "Excessive Bit Error Rate Alarm"
              ::= 124


	ds3FEFrmrDif    TRAP-TYPE
	      ENTERPRISE	dv2
	      VARIABLES	{ sysLastTrapMessage, slotNumber, sysLkLinkNo, pdhDS3RxFrmFmt }
	      DESCRIPTION
	      "Received frame format is different than configured frame format"
	      ::= 125

        e1LOS              TRAP-TYPE
              ENTERPRISE      dv2
              VARIABLES      { sysLastTrapMessage, slotNumber, sysLkLinkNo, e1LOSAlarm }
              DESCRIPTION
              "Loss of Signal alarm"
              ::= 126

        e1LOF              TRAP-TYPE
              ENTERPRISE      dv2
              VARIABLES      { sysLastTrapMessage, slotNumber, sysLkLinkNo, e1LOFAlarm }
              DESCRIPTION
              "Loss of Frame alarm"
              ::= 127

        e1AIS              TRAP-TYPE
              ENTERPRISE      dv2
              VARIABLES      { sysLastTrapMessage, slotNumber, sysLkLinkNo, e1AISAlarm }
              DESCRIPTION
              "AIS alarm"
              ::= 128

        e1Yellow           TRAP-TYPE
              ENTERPRISE      dv2
              VARIABLES      { sysLastTrapMessage, slotNumber, sysLkLinkNo, e1FerfAlarm }
              DESCRIPTION
              "Yellow alarm"
              ::= 129

        e1ExBER            TRAP-TYPE
              ENTERPRISE      dv2
              VARIABLES      { sysLastTrapMessage, slotNumber, sysLkLinkNo, e1ExBERAlarm }
              DESCRIPTION
              "Excessive Bit Error Rate Alarm"
              ::= 130

        e3LOS              TRAP-TYPE
              ENTERPRISE      dv2
              VARIABLES      { sysLastTrapMessage, slotNumber, sysLkLinkNo, e3LOSAlarm }
              DESCRIPTION
              "Loss of Signal alarm"
              ::= 131

        e3LOF              TRAP-TYPE
              ENTERPRISE      dv2
              VARIABLES      { sysLastTrapMessage, slotNumber, sysLkLinkNo, pdhE3LOFAlarm }
              DESCRIPTION
              "Loss of Frame alarm"
              ::= 132

        e3AIS              TRAP-TYPE
              ENTERPRISE      dv2
              VARIABLES      { sysLastTrapMessage, slotNumber, sysLkLinkNo, pdhE3AISAlarm }
              DESCRIPTION
              "AIS alarm"
              ::= 133

        e3Yellow           TRAP-TYPE
              ENTERPRISE      dv2
              VARIABLES      { sysLastTrapMessage, slotNumber, sysLkLinkNo, pdhE3FERFAlarm }
              DESCRIPTION
              "Yellow alarm"
              ::= 134

        e3ExBER            TRAP-TYPE
              ENTERPRISE      dv2
              VARIABLES      { sysLastTrapMessage, slotNumber, sysLkLinkNo, pdhE3ExBERAlarm }
              DESCRIPTION
              "Excessive Bit Error Rate Alarm"
              ::= 135


        locd               TRAP-TYPE
              ENTERPRISE      dv2
              VARIABLES      { sysLastTrapMessage, slotNumber, sysLkLinkNo, pdhPLCPLOCDAlarm }
              DESCRIPTION
              "Loss Of Cell Delineation"
              ::= 136

        plcpYellow         TRAP-TYPE
              ENTERPRISE      dv2
              VARIABLES      { sysLastTrapMessage, slotNumber, sysLkLinkNo, pdhPLCPYellowAlarm }
              DESCRIPTION
              "PLCP yellow alarm"
              ::= 137

        plcpLOF            TRAP-TYPE
              ENTERPRISE      dv2
              VARIABLES      { sysLastTrapMessage, slotNumber, sysLkLinkNo, pdhPLCPLOFAlarm }
              DESCRIPTION
              "PLCP Loss of Frame alarm"
              ::= 138

        sdhLOS             TRAP-TYPE
              ENTERPRISE      dv2
              VARIABLES      { sysLastTrapMessage, slotNumber, sysLkLinkNo, sdhSAlarmLOS }
              DESCRIPTION
              "SONET/SDH Loss of Signal"
              ::= 139

        sdhLOF             TRAP-TYPE
              ENTERPRISE      dv2
              VARIABLES      { sysLastTrapMessage, slotNumber, sysLkLinkNo, sdhSAlarmLOF }
              DESCRIPTION
              "SONET/SDH Loss of Frame"
              ::= 140

        sdhLineAIS         TRAP-TYPE
              ENTERPRISE      dv2
              VARIABLES      { sysLastTrapMessage, slotNumber, sysLkLinkNo, sdhSAlarmLineAIS }
              DESCRIPTION
              "SONET/SDH Line AIS failure"
              ::= 141

        sdhPathAIS         TRAP-TYPE
              ENTERPRISE      dv2
              VARIABLES      { sysLastTrapMessage, slotNumber, sysLkLinkNo, sdhSAlarmPathAIS }
              DESCRIPTION
              "SONET/SDH Path AIS failure"
              ::= 142

        sdhLOP             TRAP-TYPE
              ENTERPRISE      dv2
              VARIABLES      { sysLastTrapMessage, slotNumber, sysLkLinkNo, sdhSAlarmLOP }
              DESCRIPTION
              "SONET/SDH Loss of Pointer"
              ::= 143

        sdhPLM             TRAP-TYPE
              ENTERPRISE      dv2
              VARIABLES      { sysLastTrapMessage, slotNumber, sysLkLinkNo, sdhSAlarmPLM }
              DESCRIPTION
              "SONET/SDH Path Label Mismatch"
              ::= 144

        sdhLineYellow      TRAP-TYPE
              ENTERPRISE      dv2
              VARIABLES      { sysLastTrapMessage, slotNumber, sysLkLinkNo, sdhSAlarmLineRFI }
              DESCRIPTION
              "SONET/SDH Line FERF failure"
              ::= 145

        sdhPathYellow      TRAP-TYPE
              ENTERPRISE      dv2
              VARIABLES      { sysLastTrapMessage, slotNumber, sysLkLinkNo, sdhSAlarmPathRFI }
              DESCRIPTION
              "SONET/SDH Path Yellow failure"
              ::= 146

        sdhExBER           TRAP-TYPE
              ENTERPRISE      dv2
              VARIABLES      { sysLastTrapMessage, slotNumber, sysLkLinkNo, sdhSExBERAlarm }
              DESCRIPTION
              "SONET/SDH Excessive Bit Error Rate"
              ::= 147

	clockActiveRef	TRAP-TYPE
		ENTERPRISE	dv2
		VARIABLES	{inService}
		DESCRIPTION
		"Current Active Reference"
		::= 148

	outOfResource	TRAP-TYPE
		ENTERPRISE	dv2
		VARIABLES	{ sysLastTrapMessage, slotNumber, sysLkLinkNo}
		DESCRIPTION
		"Link cell rate is not sufficient for established connections"
		::= 149

	hssiLOS	TRAP-TYPE
		ENTERPRISE	dv2
		VARIABLES	{ sysLastTrapMessage, slotNumber, sysLkLinkNo, hssiLOSAlarm }
		DESCRIPTION
		"HSSI Loss of Signal"
		::= 150

	hssiDTEReady	TRAP-TYPE
		ENTERPRISE	dv2
		VARIABLES	{ sysLastTrapMessage, slotNumber, sysLkLinkNo }
		DESCRIPTION
		"DTE is Ready"
		::= 151

	hssiDCEReady	TRAP-TYPE
		ENTERPRISE	dv2
		VARIABLES	{ sysLastTrapMessage, slotNumber, sysLkLinkNo }
		DESCRIPTION
		"DCE is Ready"
		::= 152

	hssiDTENotReady	TRAP-TYPE
		ENTERPRISE	dv2
		VARIABLES	{ sysLastTrapMessage, slotNumber, sysLkLinkNo }
		DESCRIPTION
		"DTE is not Ready"
		::= 153

	hssiDCENotReady	TRAP-TYPE
		ENTERPRISE	dv2
		VARIABLES	{ sysLastTrapMessage, slotNumber, sysLkLinkNo }
		DESCRIPTION
		"DCE is not Ready"
		::= 154

	userstatus1  TRAP-TYPE
		ENTERPRISE     dv2
		VARIABLES      { sysLastTrapMessage, userInputStatus }
		DESCRIPTION
		""
		::= 155

	userstatus2  TRAP-TYPE
		ENTERPRISE     dv2
		VARIABLES      { sysLastTrapMessage, userInputStatus }
		DESCRIPTION
		""
		::= 156

	pntmoper	TRAP-TYPE
		ENTERPRISE	dv2
		VARIABLES	{ sysLastTrapMessage, pscatmode }
		DESCRIPTION
		"Sent when Primary NTM card operational status changes"
		::= 157
	sntmoper	TRAP-TYPE
		ENTERPRISE	dv2
		VARIABLES	{ sysLastTrapMessage, sscatmode }
		DESCRIPTION
		"Sent when Secondary NTM card operational status changes"
		::= 158
	pntmoscstatus	TRAP-TYPE
		ENTERPRISE	dv2
		VARIABLES	{ sysLastTrapMessage, pcatstr3oscstatus }
		DESCRIPTION
		"Sent when Primary NTM card oscillator status changes"
		::= 159
	sntmoscstatus	TRAP-TYPE
		ENTERPRISE	dv2
		VARIABLES	{ sysLastTrapMessage, scatstr3oscstatus }
		DESCRIPTION
		"Sent when secondary NTM card oscillator status changes"
		::= 160
	pbitslineok	TRAP-TYPE
		ENTERPRISE	dv2
		VARIABLES	{ sysLastTrapMessage, pbslineok }
		DESCRIPTION
		"Sent when Primary NTM card BITS line status changes"
		::= 161
	sbitslineok	TRAP-TYPE
		ENTERPRISE	dv2
		VARIABLES	{ sysLastTrapMessage, sbslineok }
		DESCRIPTION
		"Sent when secondary NTM card BITS line status changes"
		::= 162

	svcHalfConnect	TRAP-TYPE
		ENTERPRISE	dv2
		VARIABLES	{ slotNumber, svcHalfConCnt }
		DESCRIPTION
		"SVC half connect detected"
		::= 163

	duplicateIpAddr	TRAP-TYPE
		ENTERPRISE	dv2
		VARIABLES	{ sysLastTrapMessage, qeDocMacAddress}
		DESCRIPTION
		"Sent When a duplicate IP address is detected."
		::= 164

	svcQsaalReset	TRAP-TYPE
		ENTERPRISE	dv2
		VARIABLES	{ slotNumber }
		DESCRIPTION
		"Sent when SAP is reset"
		::= 165

	svcQsaalUpDown	TRAP-TYPE
		ENTERPRISE	dv2
		VARIABLES	{ slotNumber }
		DESCRIPTION
		"Sent when SAP transitions between Up and Down"
		::= 166

	svcT309Expiry   TRAP-TYPE
		ENTERPRISE      dv2
		VARIABLES       { slotNumber }
		DESCRIPTION
		"Sent when T309 timer expired and calls exist on a SAP"
		::= 167

        j2LOS             TRAP-TYPE
              ENTERPRISE      dv2
              VARIABLES      { sysLastTrapMessage, slotNumber, sysLkLinkNo, j2LOSAlarm }
              DESCRIPTION
              "Loss of Signal alarm"
              ::= 168

        j2LOF             TRAP-TYPE
              ENTERPRISE      dv2
              VARIABLES      { sysLastTrapMessage, slotNumber, sysLkLinkNo, j2LOFAlarm }
              DESCRIPTION
              "Loss of Frame alarm"
              ::= 169

        j2AIS             TRAP-TYPE
              ENTERPRISE      dv2
              VARIABLES      { sysLastTrapMessage, slotNumber, sysLkLinkNo, j2AISAlarm }
              DESCRIPTION
              "AIS alarm"
              ::= 170

        j2RAI          TRAP-TYPE
              ENTERPRISE      dv2
              VARIABLES      { sysLastTrapMessage, slotNumber, sysLkLinkNo, j2RAlmAlarm }
              DESCRIPTION
              "RAI alarm"
              ::= 171

        scfLOS             TRAP-TYPE
              ENTERPRISE      dv2
              VARIABLES      { sysLastTrapMessage, slotNumber, sysLkLinkNo, scfLOSAlarm }
              DESCRIPTION
              "Loss of Signal alarm"
              ::= 172

	routeLoadFail   TRAP-TYPE
		ENTERPRISE      dv2
		VARIABLES       { slotNumber }
		DESCRIPTION
		"def.rtb file load failure"
		::= 173

	dTLLoadFail     TRAP-TYPE
		ENTERPRISE      dv2
		VARIABLES       { slotNumber }
		DESCRIPTION
		"dtl.bin file load failure"
		::= 174

	redunNotAvail	TRAP-TYPE
		ENTERPRISE	dv2
		VARIABLES	{ sysLastTrapMessage, slot0IsStandbySlot0 }
		DESCRIPTION
		"This is sent when the Redundant Slot 0 Controller is not available"
		::= 175

	redunAvail	TRAP-TYPE
		ENTERPRISE	dv2
		VARIABLES	{ sysLastTrapMessage, slot0IsStandbySlot0 }
		DESCRIPTION
		"This is sent when the Redundant Slot 0 Controller is available"
		::= 176

	dQ7-error	TRAP-TYPE
		ENTERPRISE	dv2
		VARIABLES	{ slotNumber }
		DESCRIPTION
		"This trap is sent when edos discovers a DQ7 error in flash"
		::= 177

	oamVcaRcvAIS-RDI	TRAP-TYPE
		ENTERPRISE	dv2
		VARIABLES	{ sysLastTrapMessage, oamVcaVpi, oamVcaVci, oamVcaAisRdiState }
		DESCRIPTION
		"This trap is generated when an AIS or RDI is received on VCa port"
		::= 178

	oamVcbRcvAIS-RDI	TRAP-TYPE
		ENTERPRISE	dv2
		VARIABLES	{ sysLastTrapMessage, oamVcbVpi, oamVcbVci, oamVcbAisRdiState }
		DESCRIPTION
		"This trap is generated when an AIS or RDI is received on VCb port"
		::= 179


	END
