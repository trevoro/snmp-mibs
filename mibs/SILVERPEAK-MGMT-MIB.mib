-- ************************************************************
-- SILVERPEAK-MGMT-MIB.txt:   Silver Peak Systems, Inc
--                        System Status MIB
--
-- Copyright (c) 2011 Silver Peak Systems, Inc.
-- All rights reserved.
--
-- ************************************************************
--
                                                                                
SILVERPEAK-MGMT-MIB DEFINITIONS ::= BEGIN

IMPORTS
    MODULE-COMPLIANCE, OBJECT-GROUP, NOTIFICATION-GROUP
        FROM SNMPv2-CONF
    MODULE-IDENTITY, NOTIFICATION-TYPE, OBJECT-TYPE, TimeTicks
        FROM SNMPv2-SMI
    DisplayString
        FROM SNMPv2-TC
    SilverpeakAlarmSeverity,
    SilverpeakSeqNum,
    SilverpeakYesNo
        FROM SILVERPEAK-TC
    silverpeakMgmt,
    silverpeakNotifications
        FROM SILVERPEAK-SMI;

silverpeakMgmtMIB MODULE-IDENTITY
    LAST-UPDATED    "201101240000Z"
    ORGANIZATION    "Silver Peak Systems, Inc."
    CONTACT-INFO
            "  URL: http://www.silver-peak.com/contact
            E-mail: support@silver-peak.com "
    DESCRIPTION
        "This module defines the management variables used to manage
         and monitor appliance status."
    ::= { silverpeakMgmt 1 }

--
-- Base assignments
--

silverpeakMgmtMIBObjects        OBJECT IDENTIFIER ::= { silverpeakMgmtMIB 1 }
silverpeakMgmtMIBNotifications  OBJECT IDENTIFIER ::= { silverpeakNotifications 1 }
silverpeakMgmtMIBConformance    OBJECT IDENTIFIER ::= { silverpeakMgmtMIB 2 }

--
-- Status Scalars 
--
silverpeakMgmtMIBScalars        OBJECT IDENTIFIER ::= { silverpeakMgmtMIBObjects 1 }

spsSystemVersion OBJECT-TYPE
    SYNTAX      DisplayString
    MAX-ACCESS  read-only
    STATUS      current
    DESCRIPTION
        "System software version string"
    ::= { silverpeakMgmtMIBScalars 1 }

spsProductModel OBJECT-TYPE
    SYNTAX      DisplayString
    MAX-ACCESS  read-only
    STATUS      current
    DESCRIPTION
        "System product model"
    ::= { silverpeakMgmtMIBScalars 2 }

spsOperStatus OBJECT-TYPE
    SYNTAX      DisplayString
    MAX-ACCESS read-only
    STATUS     current
    DESCRIPTION
        "The current operational state of the appliance."
    ::= { silverpeakMgmtMIBScalars 3 }

spsActiveAlarmCount OBJECT-TYPE
    SYNTAX      INTEGER (0..65535)
    MAX-ACCESS  read-only
    STATUS      current
    DESCRIPTION
            "The number of active alarm entries in the alarm table -
             spsActiveAlarmTable, defined under silverpeakMgmtMIBTables
             subtree."
    ::= { silverpeakMgmtMIBScalars 4 }

spsSystemUptime OBJECT-TYPE
    SYNTAX     TimeTicks
    MAX-ACCESS read-only
    STATUS     current
    DESCRIPTION
            "The amount of time in hundredth of a second since
             this NX was last initialized.  Note that this is
             different from sysUpTime in the SNMPv2-MIB [RFC1907]
             because sysUpTime is the uptime of the network
             management portion of the system."
    ::= { silverpeakMgmtMIBScalars 5 }

--
-- Status Tables
--
silverpeakMgmtMIBTables  OBJECT IDENTIFIER ::= { silverpeakMgmtMIBObjects 2 }

--
-- Active alarm table
--

spsActiveAlarmTable OBJECT-TYPE
    SYNTAX     SEQUENCE OF ActiveAlarmEntry
    MAX-ACCESS not-accessible
    STATUS     current
    DESCRIPTION
        "A list of the active alarm entries. This represents the fault
         conditions that are still active in the appliance.
        "
    ::= { silverpeakMgmtMIBTables 1 }

activeAlarmEntry OBJECT-TYPE
    SYNTAX     ActiveAlarmEntry
    MAX-ACCESS not-accessible
    STATUS     current
    DESCRIPTION
        "The active alarm entries that are still valid system faults."
    INDEX { spsActiveAlarmIndex }
    ::= { spsActiveAlarmTable 1 }
 
ActiveAlarmEntry ::= SEQUENCE {
    spsActiveAlarmIndex            INTEGER,
    spsActiveAlarmSeqNum           SilverpeakSeqNum,
    spsActiveAlarmSeverity         SilverpeakAlarmSeverity,
    spsActiveAlarmName             DisplayString,
    spsActiveAlarmDescr            DisplayString,
    spsActiveAlarmSource           DisplayString,
    spsActiveAlarmType             DisplayString,
    spsActiveAlarmAcked            SilverpeakYesNo,
    spsActiveAlarmActive           SilverpeakYesNo,
    spsActiveAlarmClearable        SilverpeakYesNo,
    spsActiveAlarmLogTime          OCTET STRING,
    spsActiveAlarmServiceAffect    SilverpeakYesNo,
    spsActiveAlarmTypeId           INTEGER
}
 
spsActiveAlarmIndex OBJECT-TYPE
    SYNTAX     INTEGER (1..65535)
    MAX-ACCESS not-accessible
    STATUS     current
    DESCRIPTION
        "An index that uniquely identifies an entry in the
        active alarm table."
    ::= { activeAlarmEntry 1 }

spsActiveAlarmSeqNum OBJECT-TYPE
    SYNTAX     SilverpeakSeqNum
    MAX-ACCESS read-only
    STATUS     current
    DESCRIPTION
        "The active alarm's sequence number at the time it was generated."
    ::= { activeAlarmEntry 2 }

spsActiveAlarmSeverity OBJECT-TYPE
    SYNTAX     SilverpeakAlarmSeverity
    MAX-ACCESS read-only
    STATUS     current
    DESCRIPTION
        "The alarm severity for the active alarm."
    ::= { activeAlarmEntry 3 }

spsActiveAlarmName OBJECT-TYPE
    SYNTAX     DisplayString (SIZE(0..255))
    MAX-ACCESS read-only
    STATUS     current
    DESCRIPTION
        "A short name for the active alarm."
    ::= { activeAlarmEntry 4 }

spsActiveAlarmDescr OBJECT-TYPE
    SYNTAX     DisplayString (SIZE(0..255))
    MAX-ACCESS read-only
    STATUS     current
    DESCRIPTION
        "A description for the active alarm."
    ::= { activeAlarmEntry 5 }

spsActiveAlarmSource OBJECT-TYPE
    SYNTAX     DisplayString (SIZE(0..255))
    MAX-ACCESS read-only
    STATUS     current
    DESCRIPTION
        "The source for the active alarm."
    ::= { activeAlarmEntry 6 }

spsActiveAlarmType OBJECT-TYPE
    SYNTAX     DisplayString (SIZE(0..255))
    MAX-ACCESS read-only
    STATUS     current
    DESCRIPTION
        "The alarm type for the active alarm."
    ::= { activeAlarmEntry 7 }

spsActiveAlarmAcked OBJECT-TYPE
    SYNTAX     SilverpeakYesNo
    MAX-ACCESS read-only
    STATUS     current
    DESCRIPTION
        "Identifies if the user has acknowledged the alarm."
    ::= { activeAlarmEntry 8 }

spsActiveAlarmActive OBJECT-TYPE
    SYNTAX     SilverpeakYesNo
    MAX-ACCESS read-only
    STATUS     current
    DESCRIPTION
        "Identifies if the alarm is currently active."
    ::= { activeAlarmEntry 9 }

spsActiveAlarmClearable OBJECT-TYPE
    SYNTAX     SilverpeakYesNo
    MAX-ACCESS read-only
    STATUS     current
    DESCRIPTION
        "Identifies if the user can manually clear the alarm."
    ::= { activeAlarmEntry 10 }

spsActiveAlarmLogTime OBJECT-TYPE
    SYNTAX     OCTET STRING (SIZE(0..255))
    MAX-ACCESS read-only
    STATUS     current
    DESCRIPTION
        "The value of sysUpTime when the alarm was generated."
    ::= { activeAlarmEntry 11 }

spsActiveAlarmServiceAffect OBJECT-TYPE
    SYNTAX     SilverpeakYesNo
    MAX-ACCESS read-only
    STATUS     current
    DESCRIPTION
        "Identifies if the alarm is service affecting."
    ::= { activeAlarmEntry 12 }

spsActiveAlarmTypeId OBJECT-TYPE
    SYNTAX     INTEGER
    MAX-ACCESS read-only
    STATUS     current
    DESCRIPTION
        "An ID that uniquely identifies a type of alarm.
         The following is a list of currently defined type IDs
         (ID listed below is in hexadecimal):

            ID     Description
            -----  ------------------------------------------
            10000  Tunnel Remote ID is Misconfigured
            10001  Tunnel state is Down
            10002  Tunnel Vrrp IP is Misconfigured
            10003  Tunnel keepalive version mismatch
            10004  Tunnel wccp gid is misconfigured
            10005  Tunnel software version mismatch
            10006  Connecting to a non-VX-X is not supported. 
                   Please contact sales@silver-peak.com to discuss your options.
            10007  Duplicate Silver Peak license detected on peer device.
                  
            20000  Tunnel Unexpected Traffic Class Error
                  
            30000  RAID Array is Degraded
            30001  Disk is failed
            30002  Disk is degraded
            30003  FAN Failure detected
            30004  System BYPASS mode
            30005  LAN/WAN Fail-to-Wire Card Failure
            30006  LAN/WAN Fail-to-Wire Card Relay Failure
            30007  Encryption card H/W Failure
            30008  Network Interface Admin Down
            30009  Network Interface Link Down
            3000a  Management Interface Link Down
            3000b  Interface is Half Duplex
            3000c  Interface Speed is 10 Mbps
            3000d  Config DB disk full
            3000e  Operating System disk full
            3000f  File system disk full
            30010  Datapath Internal loopback Test Failed
            30011  WAN Next-Hop Unreachable
            30012  VRRP instance is down
            30013  VRRP State Master --> Backup
            30014  WAN next hop router is learned on a LAN port
                   (box is in backwards)
            30015  Disk is not in service
            30016  Disk is rebuilding
            30017  Disk removed by operator
            30018  LAN/WAN interfaces have different admin states
            30019  LAN/WAN interfaces have different link
                   carrier states
            3001a  LAN/WAN interface has been shutdown due to
                   link propagation of paired interface
            3001b  Disk SMART threshold exceeded
            3001c  Cluster peer is down
            3001d  Bonding members have different speed/duplex
            3001e  WCCP adjacency(ies) down
            3001f  WCCP assignment table mismatch
            30020  Power supply not connected, not powered or
                   failed
            30021  NIC interface failure
            30022  LAN Next-Hop Unreachable
            30023  Unexpected system restart
            30024  Insufficient configured memory size for this virtual appliance
            30025  Insufficient configured processor count for this virtual appliance
            30026  Insufficient configured disk storage for this virtual appliance
                  
                  
            40000  Software upgrade process has failed
            40001  System is Low on resources
            40002  Significant change in time of day has occurred,
                   and might compromise statistics.
            40003  The licensing for this virtual appliance has
                   expired.
            40004  There is no license installed on this virtual
                   appliance.
            40005  A disk self test has been performed. The system will
                   require a reboot after the test.
            40006  The private key is invalid.
            40007  The certificate is not yet valid.
            40008  The certificate has expired.
            40009  The NTP server is unreachable.
                 
            50001  WAN-side transmit throughput TCA
            50002  LAN-side receive throughput TCA
            50003  Total number of optimized flows TCA
            50004  Total number of flows TCA
            50005  File-system utilization TCA
            50006  Tunnel latency TCA
            50007  Tunnel loss pre-FEC TCA
            50008  Tunnel loss post-FEC TCA
            50009  Tunnel OOP pre-POC TCA
            5000a  Tunnel OOP post-POC TCA
            5000b  Tunnel utilization TCA
            5000c  Tunnel reduction TCA
            -----  ------------------------------------------"
    ::= { activeAlarmEntry 13 }

--
-- Notifications
--

spsNotifyAlarm  NOTIFICATION-TYPE
    OBJECTS        { spsActiveAlarmSource,
                     spsActiveAlarmSeverity,
                     spsActiveAlarmDescr
                   }
    STATUS         current
    DESCRIPTION
        "A notification that the system has just generated and alarm."
    ::= { silverpeakMgmtMIBNotifications 1 }


--
-- Conformance information 
--

silverpeakMgmtMIBCompliances  OBJECT IDENTIFIER ::= { silverpeakMgmtMIBConformance 1 }
silverpeakMgmtMIBGroups       OBJECT IDENTIFIER ::= { silverpeakMgmtMIBConformance 2 }

-- Compliance statements 

silverpeakMgmtCompliance MODULE-COMPLIANCE
    STATUS      current
    DESCRIPTION "The compliance statement for agents implementing 
                silverpeakMgmtMIB."
    MODULE
      MANDATORY-GROUPS {
                         silverpeakMgmtGroup,
                         silverpeakMgmtNotifyGroup
                       }
    ::= { silverpeakMgmtMIBCompliances 1 }

--
-- Units of conformance 
--

silverpeakMgmtGroup OBJECT-GROUP
    OBJECTS {
              spsSystemVersion,
              spsProductModel,
              spsOperStatus,
              spsActiveAlarmSeqNum,
              spsActiveAlarmSeverity,
              spsActiveAlarmName,
              spsActiveAlarmDescr,
              spsActiveAlarmSource,
              spsActiveAlarmType,
              spsActiveAlarmAcked,
              spsActiveAlarmActive,
              spsActiveAlarmClearable,
              spsActiveAlarmLogTime,
              spsActiveAlarmServiceAffect
            }
    STATUS       current
    DESCRIPTION "A collection of objects used to retrieve management
                 information from Silverpeak Systems appliances.
                "
    ::= { silverpeakMgmtMIBGroups 1 }

silverpeakMgmtNotifyGroup NOTIFICATION-GROUP
    NOTIFICATIONS {
              spsNotifyAlarm
            }
    STATUS       current
    DESCRIPTION "A collection of the Notifications supported in
                 the management MIB."
    ::= { silverpeakMgmtMIBGroups 3 }

END
