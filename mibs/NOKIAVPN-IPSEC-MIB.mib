NOKIAVPN-IPSEC-MIB DEFINITIONS ::= BEGIN

IMPORTS  ipsec, nokiaVPNModules
             FROM NOKIAVPN-MIB
         MODULE-IDENTITY, OBJECT-TYPE, Integer32, IpAddress
             FROM SNMPv2-SMI
         DisplayString
             FROM SNMPv2-TC;

nokiaVPNIPSECMIB MODULE-IDENTITY
    LAST-UPDATED "200101180000Z"
    ORGANIZATION "Nokia Internet Communications"
    CONTACT-INFO 
		 "	Nokia, Inc.
			Customer Support

		  Postal: 100 Enterprise Way, Module B
			Scotts Valley, CA 95066
			USA
                  E-Mail: snmp-contact@cips.nokia.com"

    DESCRIPTION "IPSEC MIB module."
    REVISION "200101180000Z"
    DESCRIPTION "Cleanup."
    ::= { nokiaVPNModules 3 }

replayStats     OBJECT IDENTIFIER ::= { ipsec 1 }
naIKEStats        OBJECT IDENTIFIER ::= { ipsec 2 }
naAHStats         OBJECT IDENTIFIER ::= { ipsec 3 }
naESPStats        OBJECT IDENTIFIER ::= { ipsec 4 }
naKeyStats        OBJECT IDENTIFIER ::= { ipsec 5 }

-- Replay Statistics

    replayStatsWraps OBJECT-TYPE
        SYNTAX      Integer32
        MAX-ACCESS  read-only
        STATUS      current
        DESCRIPTION "The number of wrapped sequence numbers detected."
	::= { replayStats 1 }

    replayStatsReplays OBJECT-TYPE
        SYNTAX      Integer32
        MAX-ACCESS  read-only
        STATUS      current
        DESCRIPTION "The number of legit replayed packets detected."
	::= { replayStats 2 }

    replayStatsoutofrange OBJECT-TYPE
        SYNTAX      Integer32
        MAX-ACCESS  read-only
        STATUS      current
        DESCRIPTION "The number of packets earlier than left edge detected."
	::= { replayStats 3 }

    replayStatstimewarps OBJECT-TYPE
        SYNTAX      Integer32
        MAX-ACCESS  read-only
        STATUS      current
        DESCRIPTION "The number of packets that warped the window's left edge."
	::= { replayStats 4 }

    replayStatsstale OBJECT-TYPE
        SYNTAX      Integer32
        MAX-ACCESS  read-only
        STATUS      current
        DESCRIPTION "The number of packets in replay update table."
	::= { replayStats 5 }

    replayStatsreset OBJECT-TYPE
        SYNTAX      Integer32
        MAX-ACCESS  read-only
        STATUS      current
        DESCRIPTION "Total resets performed."
	::= { replayStats 6 }

    replayStatsdeferred OBJECT-TYPE
        SYNTAX      Integer32
        MAX-ACCESS  read-only
        STATUS      current
        DESCRIPTION "The number of REPLAY-UPDATE messages on lookaside."
	::= { replayStats 7 }

-- IKE Stats

    naIKEStatsbadhash OBJECT-TYPE
        SYNTAX      Integer32
        MAX-ACCESS  read-only
        STATUS      current
        DESCRIPTION "Total authentication failures (pre-shared)."
        ::= { naIKEStats 1 }

    naIKEStatsbadsig OBJECT-TYPE
        SYNTAX      Integer32
        MAX-ACCESS  read-only
        STATUS      current
        DESCRIPTION "Total authentication failures (RSA/DSS)."
        ::= { naIKEStats 2 }

    naIKEStatsinvalidcookies OBJECT-TYPE
        SYNTAX      Integer32
        MAX-ACCESS  read-only
        STATUS      current
        DESCRIPTION "Total packets dropped due to bad cookies."
        ::= { naIKEStats 3 }

    naIKEStatsacounts OBJECT-TYPE
        SYNTAX      Integer32
        MAX-ACCESS  read-only
        STATUS      current
        DESCRIPTION "Total ISAKMP SAs."
        ::= { naIKEStats 4 }

    naIKEStatsmainmodes OBJECT-TYPE
        SYNTAX      Integer32
        MAX-ACCESS  read-only
        STATUS      current
        DESCRIPTION "Total main modes."
        ::= { naIKEStats 5 }

    naIKEStatsquickmodes OBJECT-TYPE
        SYNTAX      Integer32
        MAX-ACCESS  read-only
        STATUS      current
        DESCRIPTION "Total quick modes."
        ::= { naIKEStats 6 }

    naIKEStatsaggressivemodes OBJECT-TYPE
        SYNTAX      Integer32
        MAX-ACCESS  read-only
        STATUS      current
        DESCRIPTION "Total aggressive modes."
        ::= { naIKEStats 7 }

    naIKEStatsnewgroupmodes OBJECT-TYPE
        SYNTAX      Integer32
        MAX-ACCESS  read-only
        STATUS      current
        DESCRIPTION "Total Oakley new group modes."
        ::= { naIKEStats 8 }

    naIKEStatsfailedsend OBJECT-TYPE
        SYNTAX      Integer32
        MAX-ACCESS  read-only
        STATUS      current
        DESCRIPTION "Total number of failed ISAKMP sendtos."
        ::= { naIKEStats 9 }

    naIKEStatstotalnetwork OBJECT-TYPE
        SYNTAX      Integer32
        MAX-ACCESS  read-only
        STATUS      current
        DESCRIPTION "Total ISAKMP messages received."
        ::= { naIKEStats 10 }

    naIKEStatstotalsend OBJECT-TYPE
        SYNTAX      Integer32
        MAX-ACCESS  read-only
        STATUS      current
        DESCRIPTION "Total ISAKMP messages sent."
        ::= { naIKEStats 11 }

    naIKEStatstotalsaapi OBJECT-TYPE
        SYNTAX      Integer32
        MAX-ACCESS  read-only
        STATUS      current
        DESCRIPTION "Total PFKEY messages received."
        ::= { naIKEStats 12 }

    naIKEStatstotalipc OBJECT-TYPE
        SYNTAX      Integer32
        MAX-ACCESS  read-only
        STATUS      current
        DESCRIPTION "Total PF_LOCAL messages received."
        ::= { naIKEStats 13 }

    naIKEStatstotalmanual OBJECT-TYPE
        SYNTAX      Integer32
        MAX-ACCESS  read-only
        STATUS      current
        DESCRIPTION "Total number of manual key acquires."
        ::= { naIKEStats 14 }

    naIKEStatstotalauto OBJECT-TYPE
        SYNTAX      Integer32
        MAX-ACCESS  read-only
        STATUS      current
        DESCRIPTION "Total number of automatic key acquires."
        ::= { naIKEStats 15 }

    naIKEStatstransitions OBJECT-TYPE
        SYNTAX      Integer32
        MAX-ACCESS  read-only
        STATUS      current
        DESCRIPTION "Cluster state transitions."
        ::= { naIKEStats 16 }

-- Below are Clustering stats

    naIKEStatssentsa OBJECT-TYPE
        SYNTAX      Integer32
        MAX-ACCESS  read-only
        STATUS      current
        DESCRIPTION "SAs distributed."
        ::= { naIKEStats 17 }

    naIKEStatssentipsecsapair OBJECT-TYPE
        SYNTAX      Integer32
        MAX-ACCESS  read-only
        STATUS      current
        DESCRIPTION "IPSEC SA pairs distributed."
        ::= { naIKEStats 18 }

    naIKEStatssentpacket OBJECT-TYPE
        SYNTAX      Integer32
        MAX-ACCESS  read-only
        STATUS      current
        DESCRIPTION "Packets sent."
        ::= { naIKEStats 19 }

    naIKEStatsrecvsa OBJECT-TYPE
        SYNTAX      Integer32
        MAX-ACCESS  read-only
        STATUS      current
        DESCRIPTION "SA processed."
        ::= { naIKEStats 20 }

    naIKEStatsrecvipsecsapair OBJECT-TYPE
        SYNTAX      Integer32
        MAX-ACCESS  read-only
        STATUS      current
        DESCRIPTION "IPSEC SA pairs processed."
        ::= { naIKEStats 21 }

    naIKEStatsrecvpacket OBJECT-TYPE
        SYNTAX      Integer32
        MAX-ACCESS  read-only
        STATUS      current
        DESCRIPTION "Packets received."
        ::= { naIKEStats 22 }

--Additional cluster send

    naIKEStatssentinitialstate OBJECT-TYPE
        SYNTAX      Integer32
        MAX-ACCESS  read-only
        STATUS      current
        DESCRIPTION "IPSEC IKE stat sent_initial_state."
        ::= { naIKEStats 23 }

    naIKEStatssentflush OBJECT-TYPE
        SYNTAX      Integer32
        MAX-ACCESS  read-only
        STATUS      current
        DESCRIPTION "IPSEC IKE statsent_flush."
        ::= { naIKEStats 24 }

    naIKEStatssentcryptostate OBJECT-TYPE
        SYNTAX      Integer32
        MAX-ACCESS  read-only
        STATUS      current
        DESCRIPTION "IPSEC IKE stat sent_crypto_state."
        ::= { naIKEStats 25 }

    naIKEStatssentacquire OBJECT-TYPE
        SYNTAX      Integer32
        MAX-ACCESS  read-only
        STATUS      current
        DESCRIPTION "IPSEC IKE stat sent_acquire."
        ::= { naIKEStats 26 }

    naIKEStatssentipseclifetime OBJECT-TYPE
        SYNTAX      Integer32
        MAX-ACCESS  read-only
        STATUS      current
        DESCRIPTION "IPSEC IKE stat sent_ipsec_lifetime."
        ::= { naIKEStats 27 }

    naIKEStatssentikelifetime OBJECT-TYPE
        SYNTAX      Integer32
        MAX-ACCESS  read-only
        STATUS      current
        DESCRIPTION "IPSEC IKE statsent_ike_lifetime."
        ::= { naIKEStats 28 }

    naIKEStatssentdelete OBJECT-TYPE
        SYNTAX      Integer32
        MAX-ACCESS  read-only
        STATUS      current
        DESCRIPTION "IPSEC IKE sent_delete."
        ::= { naIKEStats 29 }

    naIKEStatssentselector OBJECT-TYPE
        SYNTAX      Integer32
        MAX-ACCESS  read-only
        STATUS      current
        DESCRIPTION "IPSEC IKE sent_selector."
        ::= { naIKEStats 30 }

--Additional cluster recv

    naIKEStatsrecvjoin OBJECT-TYPE
        SYNTAX      Integer32
        MAX-ACCESS  read-only
        STATUS      current
        DESCRIPTION "IPSEC IKE recv_join."
        ::= { naIKEStats 31 }

    naIKEStatsrecvrejoin OBJECT-TYPE
        SYNTAX      Integer32
        MAX-ACCESS  read-only
        STATUS      current
        DESCRIPTION "IPSEC IKE recv_rejoin."
        ::= { naIKEStats 32 }

    naIKEStatsrecvflush OBJECT-TYPE
        SYNTAX      Integer32
        MAX-ACCESS  read-only
        STATUS      current
        DESCRIPTION "IPSEC IKE recv_flush."
        ::= { naIKEStats 33 }

    naIKEStatsrecvcryptostate OBJECT-TYPE
        SYNTAX      Integer32
        MAX-ACCESS  read-only
        STATUS      current
        DESCRIPTION "IPSEC IKE recv_crypto_state."
        ::= { naIKEStats 34 }

    naIKEStatsrecvacquire OBJECT-TYPE
        SYNTAX      Integer32
        MAX-ACCESS  read-only
        STATUS      current
        DESCRIPTION "IPSEC IKE recv_acquire."
        ::= { naIKEStats 35 }

    naIKEStatsrecvipseclifetime OBJECT-TYPE
        SYNTAX      Integer32
        MAX-ACCESS  read-only
        STATUS      current
        DESCRIPTION "IPSEC IKE recv_ipsec_lifetime."
        ::= { naIKEStats 36 }

    naIKEStatsrecvikelifetime OBJECT-TYPE
        SYNTAX      Integer32
        MAX-ACCESS  read-only
        STATUS      current
        DESCRIPTION "IPSEC IKE recv_ike_lifetime."
        ::= { naIKEStats 37 }

    naIKEStatsrecvdelete OBJECT-TYPE
        SYNTAX      Integer32
        MAX-ACCESS  read-only
        STATUS      current
        DESCRIPTION "IPSEC IKE recv_delete."
        ::= { naIKEStats 38 }

    naIKEStatsrecvselector OBJECT-TYPE
        SYNTAX      Integer32
        MAX-ACCESS  read-only
        STATUS      current
        DESCRIPTION "IPSEC IKE recv_selector."
        ::= { naIKEStats 39 }

    naIKEStatssentinhibit OBJECT-TYPE
        SYNTAX      Integer32
        MAX-ACCESS  read-only
        STATUS      current
        DESCRIPTION "IPSEC IKE sent_inhibit."
        ::= { naIKEStats 40 }

    naIKEStatsrecvinhibit OBJECT-TYPE
        SYNTAX      Integer32
        MAX-ACCESS  read-only
        STATUS      current
        DESCRIPTION "IPSEC IKE recv_inhibit."
        ::= { naIKEStats 41 }

--AH Stats

    naAHStatssent OBJECT-TYPE
        SYNTAX      Integer32
        MAX-ACCESS  read-only
        STATUS      current
        DESCRIPTION "Total datagrams sent."
        ::= { naAHStats 1 }

    naAHStatstunnelsent OBJECT-TYPE
        SYNTAX      Integer32
        MAX-ACCESS  read-only
        STATUS      current
        DESCRIPTION "Total tunnelled datagrams sent."
        ::= { naAHStats 2 }

    naAHStatstransportsent OBJECT-TYPE
        SYNTAX      Integer32
        MAX-ACCESS  read-only
        STATUS      current
        DESCRIPTION "Total transport datagrams sent."
        ::= { naAHStats 3 }

    naAHStatsqueuesent OBJECT-TYPE
        SYNTAX      Integer32
        MAX-ACCESS  read-only
        STATUS      current
        DESCRIPTION "Output packets processed by crypto server process."
        ::= { naAHStats 4 }

    naAHStatscpusent OBJECT-TYPE
        SYNTAX      Integer32
        MAX-ACCESS  read-only
        STATUS      current
        DESCRIPTION "Output packets processed by secondary processor."
        ::= { naAHStats 5 }

    naAHStatsidlesent OBJECT-TYPE
        SYNTAX      Integer32
        MAX-ACCESS  read-only
        STATUS      current
        DESCRIPTION "Output packets processed by idle loop."
        ::= { naAHStats 6 }

    naAHStatshifnsent OBJECT-TYPE
        SYNTAX      Integer32
        MAX-ACCESS  read-only
        STATUS      current
        DESCRIPTION "Output packets processed by a HiFn 77x1 processor."
        ::= { naAHStats 7 }

    naAHStatsouterrors OBJECT-TYPE
        SYNTAX      Integer32
        MAX-ACCESS  read-only
        STATUS      current
        DESCRIPTION "Output errors."
        ::= { naAHStats 8 }

    naAHStatsoutdrops OBJECT-TYPE
        SYNTAX      Integer32
        MAX-ACCESS  read-only
        STATUS      current
        DESCRIPTION "Packets dropped due to resource allocation failures."
        ::= { naAHStats 9 }

    naAHStatsreceived OBJECT-TYPE
        SYNTAX      Integer32
        MAX-ACCESS  read-only
        STATUS      current
        DESCRIPTION "Total datagrams received."
        ::= { naAHStats 10 }

    naAHStatstunnelrcvd OBJECT-TYPE
        SYNTAX      Integer32
        MAX-ACCESS  read-only
        STATUS      current
        DESCRIPTION "Total tunnelled datagrams received."
        ::= { naAHStats 11 }

    naAHStatstransportrcvd OBJECT-TYPE
        SYNTAX      Integer32
        MAX-ACCESS  read-only
        STATUS      current
        DESCRIPTION "Total transport datagrams received."
        ::= { naAHStats 12 }

    naAHStatsqueuercvd OBJECT-TYPE
        SYNTAX      Integer32
        MAX-ACCESS  read-only
        STATUS      current
        DESCRIPTION "Input packets processed by crypto server process."
        ::= { naAHStats 13 }

    naAHStatscpurcvd OBJECT-TYPE
        SYNTAX      Integer32
        MAX-ACCESS  read-only
        STATUS      current
        DESCRIPTION "Input packets processed by secondary processor."
        ::= { naAHStats 14 }

    naAHStatsidlercvd OBJECT-TYPE
        SYNTAX      Integer32
        MAX-ACCESS  read-only
        STATUS      current
        DESCRIPTION "Input packets processed by idle loop."
        ::= { naAHStats 15 }

    naAHStatshifnrcvd OBJECT-TYPE
        SYNTAX      Integer32
        MAX-ACCESS  read-only
        STATUS      current
        DESCRIPTION "Input packets processed by a HiFn 77x1 processor."
        ::= { naAHStats 16 }

    naAHStatsinerrors OBJECT-TYPE
        SYNTAX      Integer32
        MAX-ACCESS  read-only
        STATUS      current
        DESCRIPTION "Input errors."
        ::= { naAHStats 17 }

    naAHStatsindrops OBJECT-TYPE
        SYNTAX      Integer32
        MAX-ACCESS  read-only
        STATUS      current
        DESCRIPTION "Packets dropped due to resource allocation failures."
        ::= { naAHStats 18 }

    naAHStatssafailures OBJECT-TYPE
        SYNTAX      Integer32
        MAX-ACCESS  read-only
        STATUS      current
        DESCRIPTION "Total SA lookup failures."
        ::= { naAHStats 19 }

    naAHStatsreplay OBJECT-TYPE
        SYNTAX      Integer32
        MAX-ACCESS  read-only
        STATUS      current
        DESCRIPTION "Total replayed packets detected."
        ::= { naAHStats 20 }

    naAHStatsfragments OBJECT-TYPE
        SYNTAX      Integer32
        MAX-ACCESS  read-only
        STATUS      current
        DESCRIPTION "Total fragmented datagrams received (and discarded)."
        ::= { naAHStats 21 }

    naAHStatshifnrefused OBJECT-TYPE
        SYNTAX      Integer32
        MAX-ACCESS  read-only
        STATUS      current
        DESCRIPTION "Total packets not sent to HiFn."
        ::= { naAHStats 22 }

    naAHStatscpurefused OBJECT-TYPE
        SYNTAX      Integer32
        MAX-ACCESS  read-only
        STATUS      current
        DESCRIPTION "Total packets refused by secondary CPU queue."
        ::= { naAHStats 23 }
				   
-- ESP Stats 

    naESPStatssent OBJECT-TYPE
        SYNTAX      Integer32
        MAX-ACCESS  read-only
        STATUS      current
        DESCRIPTION "Total datagrams sent."
        ::= { naESPStats 1 }

    naESPStatstunnelsent OBJECT-TYPE
        SYNTAX      Integer32
        MAX-ACCESS  read-only
        STATUS      current
        DESCRIPTION "Total tunnelled datagrams sent."
        ::= { naESPStats 2 }

    naESPStatstransportsent OBJECT-TYPE
        SYNTAX      Integer32
        MAX-ACCESS  read-only
        STATUS      current
        DESCRIPTION "Total transport datagrams sent."
        ::= { naESPStats 3 }

    naESPStatsqueuesent OBJECT-TYPE
        SYNTAX      Integer32
        MAX-ACCESS  read-only
        STATUS      current
        DESCRIPTION "Output packets processed by crypto server process."
        ::= { naESPStats 4 }

    naESPStatscpusent OBJECT-TYPE
        SYNTAX      Integer32
        MAX-ACCESS  read-only
        STATUS      current
        DESCRIPTION "Output packets processed by secondary processor."
        ::= { naESPStats 5 }

    naESPStatsidlesent OBJECT-TYPE
        SYNTAX      Integer32
        MAX-ACCESS  read-only
        STATUS      current
        DESCRIPTION "Output packets processed by idle loop."
        ::= { naESPStats 6 }

    naESPStatshifnsent OBJECT-TYPE
        SYNTAX      Integer32
        MAX-ACCESS  read-only
        STATUS      current
        DESCRIPTION "Output packets processed by a HiFn 77x1 processor."
        ::= { naESPStats 7 }

    naESPStatsouterrors OBJECT-TYPE
        SYNTAX      Integer32
        MAX-ACCESS  read-only
        STATUS      current
        DESCRIPTION "Output errors."
        ::= { naESPStats 8 }

    naESPStatsoutdrops OBJECT-TYPE
        SYNTAX      Integer32
        MAX-ACCESS  read-only
        STATUS      current
        DESCRIPTION "Packets dropped due to resource allocation failures."
        ::= { naESPStats 9 }

    naESPStatsreceived OBJECT-TYPE
        SYNTAX      Integer32
        MAX-ACCESS  read-only
        STATUS      current
        DESCRIPTION "Total datagrams received."
        ::= { naESPStats 10 }

    naESPStatstunnelrcvd OBJECT-TYPE
        SYNTAX      Integer32
        MAX-ACCESS  read-only
        STATUS      current
        DESCRIPTION "Total tunnelled datagrams received."
        ::= { naESPStats 11 }

    naESPStatstransportrcvd OBJECT-TYPE
        SYNTAX      Integer32
        MAX-ACCESS  read-only
        STATUS      current
        DESCRIPTION "Total transport datagrams received."
        ::= { naESPStats 12 }

    naESPStatsqueuercvd OBJECT-TYPE
        SYNTAX      Integer32
        MAX-ACCESS  read-only
        STATUS      current
        DESCRIPTION "Input packets processed by crypto server process."
        ::= { naESPStats 13 }

    naESPStatscpurcvd OBJECT-TYPE
        SYNTAX      Integer32
        MAX-ACCESS  read-only
        STATUS      current
        DESCRIPTION "Input packets processed by secondary processor."
        ::= { naESPStats 14 }

    naESPStatsidlercvd OBJECT-TYPE
        SYNTAX      Integer32
        MAX-ACCESS  read-only
        STATUS      current
        DESCRIPTION "Input packets processed by idle loop."
        ::= { naESPStats 15 }

    naESPStatshifnrcvd OBJECT-TYPE
        SYNTAX      Integer32
        MAX-ACCESS  read-only
        STATUS      current
        DESCRIPTION "Input packets processed by a HiFn 77x1 processor."
        ::= { naESPStats 16 }

    naESPStatsinerrors OBJECT-TYPE
        SYNTAX      Integer32
        MAX-ACCESS  read-only
        STATUS      current
        DESCRIPTION "Input errors."
        ::= { naESPStats 17 }

    naESPStatsindrops OBJECT-TYPE
        SYNTAX      Integer32
        MAX-ACCESS  read-only
        STATUS      current
        DESCRIPTION "Packets dropped due to resource allocation failures."
        ::= { naESPStats 18 }

    naESPStatssafailures OBJECT-TYPE
        SYNTAX      Integer32
        MAX-ACCESS  read-only
        STATUS      current
        DESCRIPTION "Total SA lookup failures."
        ::= { naESPStats 19 }

    naESPStatsreplay OBJECT-TYPE
        SYNTAX      Integer32
        MAX-ACCESS  read-only
        STATUS      current
        DESCRIPTION "Total replayed packets detected."
        ::= { naESPStats 20 }

    naESPStatsfragments OBJECT-TYPE
        SYNTAX      Integer32
        MAX-ACCESS  read-only
        STATUS      current
        DESCRIPTION "Total fragmented datagrams received (and discarded)."
        ::= { naESPStats 21 }

    naESPStatspadverifyfailures OBJECT-TYPE
        SYNTAX      Integer32
        MAX-ACCESS  read-only
        STATUS      current
        DESCRIPTION "Total packet padding verification failures."
        ::= { naESPStats 22 }

    naESPStatssignaturefailures OBJECT-TYPE
        SYNTAX      Integer32
        MAX-ACCESS  read-only
        STATUS      current
        DESCRIPTION "Total input packets rejected due to bad signature."
        ::= { naESPStats 23 }

    naESPStatsweakkey OBJECT-TYPE
        SYNTAX      Integer32
        MAX-ACCESS  read-only
        STATUS      current
        DESCRIPTION "Total weak cryptographic keys detected."
        ::= { naESPStats 24 }

    naESPStatskeyparity OBJECT-TYPE
        SYNTAX      Integer32
        MAX-ACCESS  read-only
        STATUS      current
        DESCRIPTION "Total DES key parity errors detected."
        ::= { naESPStats 25 }

    naESPStatshifnrefused OBJECT-TYPE
        SYNTAX      Integer32
        MAX-ACCESS  read-only
        STATUS      current
        DESCRIPTION "Total packets not sent to Hi/fn."
        ::= { naESPStats 26 }

    naESPStatscpurefused OBJECT-TYPE
        SYNTAX      Integer32
        MAX-ACCESS  read-only
        STATUS      current
        DESCRIPTION "Total packets refused by secondary CPU queue."
        ::= { naESPStats 27 }

    naESPNatEncapsulate OBJECT-TYPE
        SYNTAX      Integer32
        MAX-ACCESS  read-only
        STATUS      current
	DESCRIPTION "Total packets encapsulated after the NAT translation"
        ::= { naESPStats 28 }

    naESPNatDecapsulate OBJECT-TYPE
        SYNTAX      Integer32
        MAX-ACCESS  read-only
        STATUS      current
	DESCRIPTION "Total packets decapsulated before the NAT translation"
        ::= { naESPStats 29 }

-- Key Stats

    naKeyStatssyntax OBJECT-TYPE
        SYNTAX      Integer32
        MAX-ACCESS  read-only
        STATUS      current
        DESCRIPTION "Total malformed messages."
        ::= { naKeyStats 1 }

    naKeyStatsoutbound OBJECT-TYPE
        SYNTAX      Integer32
        MAX-ACCESS  read-only
        STATUS      current
        DESCRIPTION "Total SAs in general hash table."
        ::= { naKeyStats 2 }

    naKeyStatsinbound OBJECT-TYPE
        SYNTAX      Integer32
        MAX-ACCESS  read-only
        STATUS      current
        DESCRIPTION "Total SAs in inbound SPI table."
        ::= { naKeyStats 3 }

    naKeyStatspending OBJECT-TYPE
        SYNTAX      Integer32
        MAX-ACCESS  read-only
        STATUS      current
        DESCRIPTION "Total pending SAs in pending list."
        ::= { naKeyStats 4 }

    naKeyStatsselectors OBJECT-TYPE
        SYNTAX      Integer32
        MAX-ACCESS  read-only
        STATUS      current
        DESCRIPTION "Total number of selectors in SPD."
        ::= { naKeyStats 5 }

    naKeyStatsoutlast OBJECT-TYPE
        SYNTAX      Integer32
        MAX-ACCESS  read-only
        STATUS      current
        DESCRIPTION "Total outbound packets that matched last SA used."
        ::= { naKeyStats 6 }

    naKeyStatsouthash OBJECT-TYPE
        SYNTAX      Integer32
        MAX-ACCESS  read-only
        STATUS      current
        DESCRIPTION "Total outbound packets found in outbound hash table."
        ::= { naKeyStats 7 }

    naKeyStatsoutnew OBJECT-TYPE
        SYNTAX      Integer32
        MAX-ACCESS  read-only
        STATUS      current
        DESCRIPTION "Total outbound packets resulting in new KM requests."
        ::= { naKeyStats 8 }

    naKeyStatsinlast OBJECT-TYPE
        SYNTAX      Integer32
        MAX-ACCESS  read-only
        STATUS      current
        DESCRIPTION "Total inbound packets that matched last SA used."
        ::= { naKeyStats 9 }

    naKeyStatsinhash OBJECT-TYPE
        SYNTAX      Integer32
        MAX-ACCESS  read-only
        STATUS      current
        DESCRIPTION "Total inbound packets found in inbound hash table."
        ::= { naKeyStats 10 }

    naKeyStatsrefresh OBJECT-TYPE
        SYNTAX      Integer32
        MAX-ACCESS  read-only
        STATUS      current
        DESCRIPTION "Total key refresh messages delivered."
        ::= { naKeyStats 11 }

    naKeyStatsreaped OBJECT-TYPE
        SYNTAX      Integer32
        MAX-ACCESS  read-only
        STATUS      current
        DESCRIPTION "Total SAs reaped."
        ::= { naKeyStats 12 }

    naKeyStatsreapedlarval OBJECT-TYPE
        SYNTAX      Integer32
        MAX-ACCESS  read-only
        STATUS      current
        DESCRIPTION "Total pending entries deleted."
        ::= { naKeyStats 13 }

    naKeyStatsbypass OBJECT-TYPE
        SYNTAX      Integer32
        MAX-ACCESS  read-only
        STATUS      current
        DESCRIPTION "Total bypass selectors matched (output)."
        ::= { naKeyStats 14 }

    naKeyStatsdrop OBJECT-TYPE
        SYNTAX      Integer32
        MAX-ACCESS  read-only
        STATUS      current
        DESCRIPTION "Total drop selectors matched (output)."
        ::= { naKeyStats 15 }

    naKeyStatsprotect OBJECT-TYPE
        SYNTAX      Integer32
        MAX-ACCESS  read-only
        STATUS      current
        DESCRIPTION "Total protect selectors matched (output)."
        ::= { naKeyStats 16 }

    naKeyStatsinbypass OBJECT-TYPE
        SYNTAX      Integer32
        MAX-ACCESS  read-only
        STATUS      current
        DESCRIPTION "Total bypass selectors matched (input)."
        ::= { naKeyStats 17 }

    naKeyStatsindrop OBJECT-TYPE
        SYNTAX      Integer32
        MAX-ACCESS  read-only
        STATUS      current
        DESCRIPTION "Total drop selectors matched (input)."
        ::= { naKeyStats 18 }

    naKeyStatsinprotect OBJECT-TYPE
        SYNTAX      Integer32
        MAX-ACCESS  read-only
        STATUS      current
        DESCRIPTION "Total protect selectors matched (input)."
        ::= { naKeyStats 19 }

    naKeyStatsstallq OBJECT-TYPE
        SYNTAX      Integer32
        MAX-ACCESS  read-only
        STATUS      current
        DESCRIPTION "Total packets on stall queue."
        ::= { naKeyStats 20 }

    naKeyStatsnomatch OBJECT-TYPE
        SYNTAX      Integer32
        MAX-ACCESS  read-only
        STATUS      current
        DESCRIPTION "Total packets not matching any selector (output)."
        ::= { naKeyStats 21 }

    naKeyStatsinnomatch OBJECT-TYPE
        SYNTAX      Integer32
        MAX-ACCESS  read-only
        STATUS      current
        DESCRIPTION "Total packets not matching any selector (input)."
        ::= { naKeyStats 22 }

    naKeyStatsinmismatch OBJECT-TYPE
        SYNTAX      Integer32
        MAX-ACCESS  read-only
        STATUS      current
        DESCRIPTION "Total packets dropped due to security
                     policy mismatch (input)."
        ::= { naKeyStats 23 }

    naKeyStatsadvmtusent OBJECT-TYPE
        SYNTAX      Integer32
        MAX-ACCESS  read-only
        STATUS      current
        DESCRIPTION "Total advisory MTU ICMP messages sent."
        ::= { naKeyStats 24 }

    naKeyStatsadvmturcvd OBJECT-TYPE
        SYNTAX      Integer32
        MAX-ACCESS  read-only
        STATUS      current
        DESCRIPTION "Total advisory MTU ICMP messages received."
        ::= { naKeyStats 25 }

    naKeyStatsphantom OBJECT-TYPE
        SYNTAX      Integer32
        MAX-ACCESS  read-only
        STATUS      current
        DESCRIPTION "Total phantom SPIs causing reverse negotiations."
        ::= { naKeyStats 26 }

    naKeyStatsdynamicselectors OBJECT-TYPE
        SYNTAX      Integer32
        MAX-ACCESS  read-only
        STATUS      current
        DESCRIPTION "Total dynamic selectors."
        ::= { naKeyStats 27 }

    naKeyStatstoolarge OBJECT-TYPE
        SYNTAX      Integer32
        MAX-ACCESS  read-only
        STATUS      current
        DESCRIPTION "Total packets discarded because they would become
                     too large (output)."
        ::= { naKeyStats 28 }

END
