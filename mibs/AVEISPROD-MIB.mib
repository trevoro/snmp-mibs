-- ========================================================
--
-- MIB      : aveisprod.mib  Avaya Inc.
--
-- Version  : 1.3.18   04 Feb 2009
--
-- Object IDs for  Avaya/EIS  products
-- ========================================================
-- Source Safe data:
-- $Revision: 24 $
-- Check In: $Date: 23/02/09 2:01p $
-- $Author: Sbiton $
-- $Archive: /MIBs/Version 1.0/Source/Avaya/AVEISPROD-MIB.MY $
-- ========================================================
--
-- Copyright 2001,2002,2003,2004,2005,2006,2007 AVAYA,  inc.  
-- All Rights Reserved.  
--
-- Reproduction of this document is authorized on condition 
-- that the foregoing copyright notice is included.
--
-- This AVAYA SNMP Management Information Base Specification
-- (Specification) embodies AVAYA confidential and
-- Proprietary intellectual property.  AVAYA retains all
-- Title and ownership in the Specification, including any revisions
--
-- It is AVAYA's intent to encourage the widespread use of this
-- Specification in connection with the management of AVAYA products.
-- AVAYA grants vendors, end-users, and other interested parties
-- a non-exclusive license to use this Specification in connection
-- with the management of AVAYA products.
--
-- This Specification is supplied "as is," and AVAYA makes
-- no warranty, either express or implied, as to the use,
-- operation, condition, or performance of the Specification.
--
--========================================================
AVEISPROD-MIB DEFINITIONS ::= BEGIN
    IMPORTS
	MODULE-IDENTITY
	FROM SNMPv2-SMI
	products
	FROM AVAYAGEN-MIB;
lsg  MODULE-IDENTITY
LAST-UPDATED 	"0902041543Z"    -- 02 Feb 2009 
ORGANIZATION 	"Avaya Inc."
CONTACT-INFO	"Itai Zilbershtein - izilbers@avaya.com"
DESCRIPTION
    " Product OIDs for Avaya's EIS division
      This MIB includes OIDs for products developed in:
      LSG-C - Concord Technology Center (CTC)
      LSG-I - Israel Technology Center (ITC)
      WSG - Millipitas Technology Center (MTC)
    "         
REVISION "0902041543Z"    -- 02 Feb 2009 
DESCRIPTION "Rev 1.3.19 - Shlomi Biton
    Add G860."
REVISION "0811191850Z"    -- 25 Sep 2008 
DESCRIPTION "Rev 1.3.18 - Shlomi Biton
    Change Distributed Office names to Communication Manager Branch Edition names
    Change i40-14A to i40-A14 and G250-14A to G250-A14"
REVISION "0809251620Z"    -- 25 Sep 2008 
DESCRIPTION "Rev 1.3.17 - Dan Gluskin
    Add avayaS8300AppBlade"
REVISION "0809111620Z" -- 11 Sep 2008 
DESCRIPTION
    "Rev 1.3.16 - Shlomi Biton. 
    Add G430 H.248 sysObjectID.
    "
REVISION "0803271105Z"  
DESCRIPTION
    "Rev 1.3.15 - Shlomi Biton. 
    Update Products Names.
    "
    REVISION "0801310114Z"  
DESCRIPTION
    "Rev 1.3.14 - Shlomi Biton. 
    Add Venus OIDs.
    "
REVISION "0711252112Z"  
DESCRIPTION
    "Rev 1.3.13 - Shlomi Biton. 
    	1. Add Avaya Distributed Office Virtual Application Server                                 
    	avayaDistributedOfficei40VirtualApplicationServer OBJECT IDENTIFIER ::= { hostSoftware  2}
		avayaDistributedOfficei120VirtualApplicationServer OBJECT IDENTIFIER ::= { hostSoftware  3}	 
		avayaDistributedOfficei360VirtualApplicationServer OBJECT IDENTIFIER ::= { hostSoftware  4}	 
		2. Add G250-14A
		avayaG250-14A OBJECT IDENTIFIER ::= { chassisProducts 9 }      
		3. Add i360                                                    
		avayaDistributedOfficei360 OBJECT IDENTIFIER ::= { chassisProducts 17 } 
    "
REVISION "0707081616Z"  
DESCRIPTION
    "Rev 1.3.12 - Shlomi Biton. Add i40-14A     
		avayaDistributedOfficei40-14A OBJECT IDENTIFIER ::= { chassisProducts 16 }  
    "
REVISION "0706201422Z"  
DESCRIPTION
    "Rev 1.3.11 - Shlomi Biton. Add AMRB Product information:     
     avayaTRM480 OBJECT IDENTIFIER ::= { chassisProducts 15 }  
    "
REVISION "0701010807Z"  
DESCRIPTION
    "Rev 1.3.10 - Shlomi Biton. Rename Liverpool Gateways Names.
   avayaDistributedOfficei120 OBJECT IDENTIFIER ::= { chassisProducts 11 } 
   avayaDistributedOfficei40-Analog OBJECT IDENTIFIER ::= { chassisProducts 12 }      
   avayaDistributedOfficei40-BRI OBJECT IDENTIFIER ::= { chassisProducts 13 } 
   avayaDistributedOfficei40-DS1 OBJECT IDENTIFIER ::= { chassisProducts 14 }  
   avayaAM110ApplicationModule OBJECT IDENTIFIER ::= {smartModules 6 }  
    "
REVISION "0610221717Z"  
DESCRIPTION "Rev 1.3.9 - Add G450 gateway sysObjId value."
REVISION "0610221717Z"  
DESCRIPTION " 
     Rename avayaServerBlade to avayaLiverpoolServerBlade and move it under smartModules"
REVISION "0608201000Z"  
DESCRIPTION
    "Add Liverpool Gateways OID.
   avayaG350L OBJECT IDENTIFIER ::= { chassisProducts 11 } 
   avayaG250L OBJECT IDENTIFIER ::= { chassisProducts 12 }      
   avayaG250L-BRI OBJECT IDENTIFIER ::= { chassisProducts 13 } 
   avayaG250L-DS1 OBJECT IDENTIFIER ::= { chassisProducts 14 }  
   avayaServerBlade OBJECT IDENTIFIER ::= { chassisProducts 55 }  
    "
REVISION   	"0305281000Z" -- 28 May 2003 rev 1.3.3
DESCRIPTION
    " Rev 1.3.3 - Itai Zilbershtein
      Changed avayaBoxster to avayaG350. OID value stays the same.
      "
REVISION   	"0302191000Z" -- 19 February 2003 rev 1.3.2
DESCRIPTION
    " Rev 1.3.2 - Dan Gluskin
      Added AvayaBoxster.
      "
REVISION   	"0212241000Z" -- 24 December 2002 rev 1.3.1
DESCRIPTION
    " Rev 1.3.1 - Itai Zilbershtein
      Added avayaP460L3.
      "
REVISION   	"0207171000Z" -- 17 July 2002 rev 1.2.0
DESCRIPTION
    " Rev 1.2.0 - Itai Zilbershtein
      Added wireless products:
      1. wirelessProducts as name of branch
      2. avayaAP4 as first sibling.
      "
REVISION     "0207071000Z" -- 7 July 2002 rev 1.1.2
DESCRIPTION
    " Rev 1.1.2 - Itai Zilbershtein
      modified cajunX330W4DS1 to cajunX330W2DS1
      "
REVISION 	"0202041000Z" -- 4 Feb. 2002 rev 1.1.1
DESCRIPTION
    " Rev 1.1.1 - Itai Zilbershtein
      added cajunX330W2USP
      "

REVISION 	"0201310900Z" -- 31 January 2002 rev 1.1.0
DESCRIPTION
    " Rev 1.1.0 - Itai Zilbershtein
      added avayaP460 under chassisProducts
      "

REVISION 	"0201101500Z" -- 10 January 2002 rev 1.0.0
DESCRIPTION
    " Rev 1.0.0 - Itai Zilbershtein
      added Wasabi based devices:
      cajunL3P882S, cajunL3P580S    "
REVISION 	"0109091700Z" -- 09 September 2001 rev 0.2.0
DESCRIPTION
    "Rev 0.2.0 - Itai Zilbershtein
     1. Combined EIS products OID MIB. Includes MTC. MIB changed
       from avlsgprod to aveisprod.
     2. OID for CajunView Standalone (STORM)
     3. OID for M8000R-LB Load Balancing module
     4. OID for x330WAN-4DS1 (330 Wan uplink)
     "

REVISION 	"0108091700Z" -- 09 August 2001 rev 0.1.0
DESCRIPTION
    "Rev 0.1.0 - Itai Zilbershterin.
    Initial version.
    Includes the branches taken by CTC for the Cajun
    products. Note that the branches does not reside under
    ....avya.products.lsg, but directly under avaya.products.
    "
::= {  products 1 }
-- ****************************
-- Note that cajunSwitchProduct (880/550) 
-- is directly under products and not under 
-- products.lsg
   eisProducts OBJECT IDENTIFIER ::= {products 45}
   cajunL3P580    OBJECT IDENTIFIER ::= { eisProducts 2 }
   cajunL3P882    OBJECT IDENTIFIER ::= { eisProducts  10 }
-- Wasabi based devices:
   cajunL3P882S    OBJECT IDENTIFIER ::= { eisProducts  11 }
   cajunL3P580S    OBJECT IDENTIFIER ::= { eisProducts  12 }


   hostSoftware   OBJECT IDENTIFIER ::= { eisProducts  100 }
   cajunViewStandAlone OBJECT IDENTIFIER ::= { hostSoftware  1}
   avayaCommunicationManagerBranchEditioni40TelephonyServer OBJECT IDENTIFIER ::= { hostSoftware  2}
   avayaCommunicationManagerBranchEditioni120TelephonyServer OBJECT IDENTIFIER ::= { hostSoftware  3}
   avayaCommunicationManagerBranchEditionG450TelephonyServer OBJECT IDENTIFIER ::= { hostSoftware  4}	 
   avayaCommunicationManagerBranchEditionG430TelephonyServer OBJECT IDENTIFIER ::= { hostSoftware  6}	 
   smartModules OBJECT IDENTIFIER ::= { eisProducts  101 }
   cajunM8000RLB OBJECT IDENTIFIER ::= { smartModules  1 }
   cajunX330W2DS1 OBJECT IDENTIFIER ::= { smartModules 2 }
   cajunX330W2USP OBJECT IDENTIFIER ::= { smartModules 3 }
   avayaP460L3 OBJECT IDENTIFIER ::= { smartModules 4 }  
   avayaW310StackModule OBJECT IDENTIFIER ::= { smartModules 5} 
   avayaAM110ApplicationModule OBJECT IDENTIFIER ::= {smartModules 6 }  
   avayaS8300AppBlade OBJECT IDENTIFIER ::= {smartModules 7 }  
   chassisProducts OBJECT IDENTIFIER ::= { eisProducts  103 }
   avayaP460 OBJECT IDENTIFIER ::= { chassisProducts 1 }
   avayaG350 OBJECT IDENTIFIER ::= { chassisProducts 2 } 
   avayaW310Standalone OBJECT IDENTIFIER ::= { chassisProducts 3  }  
   avayaG250 OBJECT IDENTIFIER ::= { chassisProducts 4 }      
   avayaG250-BRI OBJECT IDENTIFIER ::= { chassisProducts 5 } 
   avayaG250-DS1 OBJECT IDENTIFIER ::= { chassisProducts 6 }
   avayaG250-DCP OBJECT IDENTIFIER ::= { chassisProducts 7 }     
   avayaG450 OBJECT IDENTIFIER ::= { chassisProducts 8 }  
   avayaG250-A14 OBJECT IDENTIFIER ::= { chassisProducts 9 }      
   avayaTGM550 OBJECT IDENTIFIER ::= { chassisProducts 10 }
   avayaCommunicationManagerBranchEditioni120 OBJECT IDENTIFIER ::= { chassisProducts 11 } 
   avayaCommunicationManagerBranchEditioni40-Analog OBJECT IDENTIFIER ::= { chassisProducts 12 }      
   avayaCommunicationManagerBranchEditioni40-BRI OBJECT IDENTIFIER ::= { chassisProducts 13 } 
   avayaCommunicationManagerBranchEditioni40-DS1 OBJECT IDENTIFIER ::= { chassisProducts 14 }  
   avayaTRM480 OBJECT IDENTIFIER ::= { chassisProducts 15 }                    
   avayaCommunicationManagerBranchEditioni40-A14 OBJECT IDENTIFIER ::= { chassisProducts 16 }  
   avayaCommunicationManagerBranchEditionG450 OBJECT IDENTIFIER ::= { chassisProducts 17 } 
   avayaCommunicationManagerBranchEditionG430 OBJECT IDENTIFIER ::= { chassisProducts 19 } 
   avayaG430 OBJECT IDENTIFIER ::= { chassisProducts 41 } 
   avayaG860 OBJECT IDENTIFIER ::= { chassisProducts 42 } 
   wirelessProducts OBJECT IDENTIFIER ::= { eisProducts  104 }
   avayaAP4 OBJECT IDENTIFIER ::= { wirelessProducts 1 }
END
