-- *****************************************************************
-- tiara-environment.mib:  Tiara Networks Environment Monitoring MIB file
--
-- April,1st 1998, Shyla
--
-- Copyright (c) 1998-2000 by Tiara Networks, Inc.
-- All rights reserved.
-- 
-- *****************************************************************
--
TIARA-NETWORKS-ENVIRONMENT-MIB DEFINITIONS ::= BEGIN

IMPORTS
        OBJECT-TYPE,
        MODULE-IDENTITY,
        Gauge32
                FROM SNMPv2-SMI
        TEXTUAL-CONVENTION,TruthValue
                FROM SNMPv2-TC
        TRAP-TYPE
                FROM RFC-1215
	tiaraMgmt
	        FROM TIARA-NETWORKS-SMI;

tiaraEnvironmentMib MODULE-IDENTITY 
  	LAST-UPDATED    "0008180000Z"
  	ORGANIZATION	"Tiara Networks, Inc."
  	CONTACT-INFO
                "       Tiara Networks
                        Customer Support
                        525 Race Street, Suite 100,
                        San Jose, CA 95126
                        USA

                   	Tel: +1 408-216-4700
                   	Fax: +1 408-216-4701

                		Email: support@tiaranetworks.com"

  	DESCRIPTION
  		""
  	REVISION	"0008180000Z"
  	DESCRIPTION
  		"Initial version of Environment MIB."
          ::= { tiaraMgmt 3 }

EnvState ::= TEXTUAL-CONVENTION
    STATUS  current
    DESCRIPTION
   	"Represents the state of a device being monitored."
    SYNTAX INTEGER 
        {
	normal(1),
	warning(2),
	critical(3),
	fail(4),
	turned-off(5)
	}

EnvInstalled ::= TEXTUAL-CONVENTION
    STATUS  current
    DESCRIPTION
   	"Installed flag for power supply."
    SYNTAX INTEGER 
        {
	not-installed(1),
	installed(2)
	}

EnvStatus ::= TEXTUAL-CONVENTION
    STATUS  current
    DESCRIPTION
   	"Installed flag for power supply."
    SYNTAX INTEGER 
        {
	up(1),
	down(2)
	}

EnvType ::= TEXTUAL-CONVENTION
    STATUS  current
    DESCRIPTION
   	"Installed flag for power supply."
    SYNTAX INTEGER 
        {
	unknown(1),
	minus48VDC(2)
	}

envObjects 		OBJECT IDENTIFIER ::= { tiaraEnvironmentMib 1 }
envNotificationEnables	OBJECT IDENTIFIER ::= { tiaraEnvironmentMib 2 }
envNotifications	OBJECT IDENTIFIER ::= { tiaraEnvironmentMib 3 }

--
-- envObjects group contains the management objects that 
-- decribe the current environmental state of the system, 
-- such as voltage, temperature, fan, power supply, etc.
-- 
envTempSensorTable 	OBJECT-TYPE
        SYNTAX        	SEQUENCE OF EnvTempSensorEntry
        MAX-ACCESS    	not-accessible
        STATUS        	current
        DESCRIPTION   "A list of module entries. The number 
			    of entries is given by the value of 
			    chassisNumSlots."
        ::= { envObjects 1 }

envTempSensorEntry 	OBJECT-TYPE
        SYNTAX        	EnvTempSensorEntry
        MAX-ACCESS    	not-accessible
        STATUS        	current
        DESCRIPTION   "Entry containing information about a 
			    temperature sensor within the chassis."
        INDEX         	{ envTempSensorUnitIndex }
        ::= { envTempSensorTable 1 }

EnvTempSensorEntry ::=
        SEQUENCE {
                envTempSensorUnitIndex	INTEGER,
                envTempSensorValue		Gauge32,
                envTempSensorState		EnvState
                }

envTempSensorUnitIndex 	OBJECT-TYPE
        SYNTAX        	INTEGER (0 ..1)
        MAX-ACCESS    	not-accessible
        STATUS        	current
        DESCRIPTION   "The index to access an entry in the table."
			
        ::= { envTempSensorEntry 1 }

envTempSensorValue 	OBJECT-TYPE
	SYNTAX     		Gauge32
--	UNITS      		"degrees Celsius"
	MAX-ACCESS 		read-only
	STATUS     		current
	DESCRIPTION
		"
		The current value of the temperature sensor.
		"
	::=  { envTempSensorEntry 2 }

envTempSensorState 	OBJECT-TYPE
	SYNTAX     		EnvState
	MAX-ACCESS 		read-only
	STATUS     		current
	DESCRIPTION
		"
		The current state of the temperature sensor.
		"
	::= { envTempSensorEntry 3 }


envFanTable OBJECT-TYPE
        SYNTAX        	SEQUENCE OF EnvFanEntry
        MAX-ACCESS    	not-accessible
        STATUS        	current
        DESCRIPTION   "A list of fan unit entries."
        ::= { envObjects 2 }

envFanEntry OBJECT-TYPE
        SYNTAX        	EnvFanEntry
        MAX-ACCESS    	not-accessible
        STATUS        	current
        DESCRIPTION   "Entry containing information about a fan
                      within the chassis."
        INDEX         	{ envFanUnitIndex }
        ::= { envFanTable 1 }

EnvFanEntry ::=
        SEQUENCE {
                envFanUnitIndex	INTEGER,
                envFanState		EnvState
                }

envFanUnitIndex 		OBJECT-TYPE
        SYNTAX        	INTEGER(0 ..1)
        MAX-ACCESS    	not-accessible
        STATUS        	current
        DESCRIPTION   "The index to access an entry in the table.
			"
        ::= { envFanEntry 1 }
envFanState 		OBJECT-TYPE
	SYNTAX     		EnvState
	MAX-ACCESS 		read-only
	STATUS     		current
	DESCRIPTION
		"
		The current state of fan 0, normal/fail.
		"
	::= { envFanEntry 2 }

envPwrsupPowerFailCount OBJECT-TYPE
	SYNTAX		INTEGER
	MAX-ACCESS	 	read-only
	STATUS		current
	DESCRIPTION	"Number of failures of either power supply 
			since boot-up."
	::= { envObjects 3 }

envPwrsupTable		OBJECT-TYPE
	SYNTAX		SEQUENCE OF EnvPwrsupEntry
	MAX-ACCESS		not-accessible
	STATUS		current
	DESCRIPTION	"A list of power supply status information."
	::= { envObjects 4 }

envPwrsupEntry		OBJECT-TYPE
	SYNTAX		EnvPwrsupEntry
	MAX-ACCESS		not-accessible
	STATUS		current
	DESCRIPTION	"Entry containing power supply information."
	INDEX			{ envPwrsupIndex }
	::= { envPwrsupTable 1 }

EnvPwrsupEntry ::=
	SEQUENCE {
		envPwrsupIndex		INTEGER,
		envPwrsupInstalled	EnvInstalled,
		envPwrsupStatus		EnvStatus,
		envPwrsupType		EnvType,
		envPwrsupUptime		INTEGER,
		envPwrsupDowntime		INTEGER
	}

envPwrsupIndex		OBJECT-TYPE
	SYNTAX		INTEGER (1..2)
	MAX-ACCESS		not-accessible
	STATUS		current
	DESCRIPTION	"Index to access entry."
	::= { envPwrsupEntry 1 }

envPwrsupInstalled	OBJECT-TYPE
	SYNTAX		EnvInstalled
	MAX-ACCESS		read-only
	STATUS		current
	DESCRIPTION	"Power supply installed flag."
	::= { envPwrsupEntry 2 }

envPwrsupStatus		OBJECT-TYPE
	SYNTAX		EnvStatus
	MAX-ACCESS		read-only
	STATUS		current
	DESCRIPTION	"Power supply up/down status."
	::= { envPwrsupEntry 3 }

envPwrsupType		OBJECT-TYPE
	SYNTAX		EnvType
	MAX-ACCESS		read-only
	STATUS		current
	DESCRIPTION	"Power supply type."
	::= { envPwrsupEntry 4 }

envPwrsupUptime		OBJECT-TYPE
	SYNTAX		INTEGER
	MAX-ACCESS		read-only
	STATUS		current
	DESCRIPTION	"Seconds since power supply came up."
	::= { envPwrsupEntry 5 }

envPwrsupDowntime		OBJECT-TYPE
	SYNTAX		INTEGER
	MAX-ACCESS		read-only
	STATUS		current
	DESCRIPTION	"Seconds since power supply went down."
	::= { envPwrsupEntry 6 }

	

--
-- envNotificationEnables contains the managed objects to 
-- enable notifications when the system is shut down due 
-- to one of the environmental causes.
-- 

envEnableTemperatureNotification 	OBJECT-TYPE
        SYNTAX 	   			TruthValue
        MAX-ACCESS  			read-write
        STATUS      			current
        DESCRIPTION
            "Indicates whether the system produces the 
		envTemperatureNotification. The default is yes.
		Note: implementation is TBD.
		"
        DEFVAL 				{ true }
        ::= { envNotificationEnables 1 }

envEnableFanNotification 		OBJECT-TYPE
        SYNTAX 	   			TruthValue
        MAX-ACCESS  			read-write
        STATUS      			current
        DESCRIPTION
            "Indicates whether the system produces the 
		envFanNotification. The default is yes.
		"
        DEFVAL 				{ true }
        ::= { envNotificationEnables 2 }

envEnablePowerNotification 		OBJECT-TYPE
        SYNTAX 	  			TruthValue
        MAX-ACCESS  			read-write
        STATUS      			current
        DESCRIPTION
            "Indicates whether the system produces the 
		envPowerNotification. The default is yes.
		"
        DEFVAL 				{ true }
        ::= { envNotificationEnables 3 }

--
-- envNotifications group is used to define shut down notifications.
--

envTemperatureNotification TRAP-TYPE
	ENTERPRISE envNotifications
	VARIABLES {
                envTempSensorUnitIndex,
                envTempSensorValue,
                envTempSensorState
		}
	DESCRIPTION
		"
		An envTemeratureNotification is sent if the 
		environmental monitoring detects that the temperature 
		is at a critical state. This may cause the system to 
		shut down. This notification is sent only if 
		envEnableTemperatureNotification is set to true.
		"
             --#TYPE "Temperature status"
             --#SUMMARY "Temperature notification for sensor Index: %s with Value: %s and State: %s"
             --#ARGUMENTS {0,1,2}
             --#SEVERITY CRITICAL
	::= 1

envFanNotification TRAP-TYPE
	ENTERPRISE envNotifications
	VARIABLES{
		envFanUnitIndex,
                envFanState
		}
	DESCRIPTION
		"
		An envFanNotification is sent if the environmental
		monitoring detects that a fan is in a critical state. 
		This may cause the system to shut down. This 
		notification is sent only if envEnableFanNotification 
		is set to true.
		"
             --#TYPE "Fan state change"
             --#SUMMARY "Fan unit index: %s State changed to: %s"
             --#ARGUMENTS {0,1}
             --#SEVERITY CRITICAL
	::= 2


envPowerSupply1DownNotification TRAP-TYPE
	ENTERPRISE envNotifications
	VARIABLES{
		envPwrsupPowerFailCount,
		envPwrsupIndex,
            envPwrsupInstalled,
		envPwrsupStatus,
		envPwrsupType,
		envPwrsupUptime,
		envPwrsupDowntime

		}
	DESCRIPTION
		"
		An envPowerNotification is sent if the environmental
		monitoring detects that a power supply has changed status. 
		This notification is sent only if 
		envEnablePowerNotification is set to true.
		"
             --#TYPE "Power supply 1 down"
             --#SUMMARY "Power supply 1 down. Fail count: %s Index: %s Installed: %s Status: %s Type: %s Uptime: %s Downtime: %s"
             --#ARGUMENTS {0,1,2,3,4,5,6}
             --#SEVERITY MAJOR
	::= 3


envPowerSupply1UpNotification TRAP-TYPE
	ENTERPRISE envNotifications
	VARIABLES{
		envPwrsupPowerFailCount,
		envPwrsupIndex,
            envPwrsupInstalled,
		envPwrsupStatus,
		envPwrsupType,
		envPwrsupUptime,
		envPwrsupDowntime

		}
	DESCRIPTION
		"
		An envPowerNotification is sent if the environmental
		monitoring detects that a power supply has changed status. 
		This notification is sent only if 
		envEnablePowerNotification is set to true.
		"
             --#TYPE "Power supply 1 Up"
             --#SUMMARY "Power supply 1 up. Fail count: %s Index: %s Installed: %s Status: %s Type: %s Uptime: %s Downtime: %s"
             --#ARGUMENTS {0,1,2,3,4,5,6}
             --#SEVERITY NORMAL                       
	::= 4


envPowerSupply2DownNotification TRAP-TYPE
	ENTERPRISE envNotifications
	VARIABLES{
		envPwrsupPowerFailCount,
		envPwrsupIndex,
            envPwrsupInstalled,
		envPwrsupStatus,
		envPwrsupType,
		envPwrsupUptime,
		envPwrsupDowntime

		}
	DESCRIPTION
		"
		An envPowerNotification is sent if the environmental
		monitoring detects that a power supply has changed status. 
		This notification is sent only if 
		envEnablePowerNotification is set to true.
		"
             --#TYPE "Power supply 2 down"
             --#SUMMARY "Power supply 2 down. Fail count: %s Index: %s Installed: %s Status: %s Type: %s Uptime: %s Downtime: %s"
             --#ARGUMENTS {0,1,2,3,4,5,6}
             --#SEVERITY MAJOR                        
	::= 5


envPowerSupply2UpNotification TRAP-TYPE
	ENTERPRISE envNotifications
	VARIABLES{
		envPwrsupPowerFailCount,
		envPwrsupIndex,
            envPwrsupInstalled,
		envPwrsupStatus,
		envPwrsupType,
		envPwrsupUptime,
		envPwrsupDowntime

		}
	DESCRIPTION
		"
		An envPowerNotification is sent if the environmental
		monitoring detects that a power supply has changed status. 
		This notification is sent only if 
		envEnablePowerNotification is set to true.
		"
             --#TYPE "Power supply 2 Up"
             --#SUMMARY "Power supply 2 up. Fail count: %s Index: %s Installed: %s Status: %s Type: %s Uptime: %s Downtime: %s"
             --#ARGUMENTS {0,1,2,3,4,5,6}
             --#SEVERITY NORMAL                        
	::= 6

END
