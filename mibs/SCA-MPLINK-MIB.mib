SCA-MPLINK-MIB DEFINITIONS ::= BEGIN

-- Copyright (C) 1997 Intel Corporation. All rights reserved.
--
-- Intel Multi Protocol Link MIB, 11-04-1997
--
-- Change History:
-- <date> <change>
--

IMPORTS
    Counter, TimeTicks                  FROM RFC1155-SMI
    DisplayString                       FROM RFC1213-MIB
    scanet                              FROM SCANET-MIB
    OBJECT-TYPE                         FROM RFC-1212;


OffOn ::= INTEGER { off(1), on(2) }



mplk                 OBJECT IDENTIFIER ::= { scanet 24 }
  service            OBJECT IDENTIFIER ::= { mplk 1 }
  lanSpecific        OBJECT IDENTIFIER ::= { mplk 2 }
  wanSpecific        OBJECT IDENTIFIER ::= { mplk 3 }



serviceTable OBJECT-TYPE
    SYNTAX SEQUENCE OF ServiceEntry
    ACCESS not-accessible
    STATUS mandatory
    DESCRIPTION ""
    ::= { service 1 }

serviceEntry OBJECT-TYPE
    SYNTAX ServiceEntry
    ACCESS not-accessible
    STATUS mandatory
    DESCRIPTION ""
    INDEX { serviceNumber1 }
    ::= { serviceTable 1 }

ServiceEntry ::=
    SEQUENCE {
        serviceNumber1
            INTEGER,
        serviceName
            DisplayString,
        serviceType
            INTEGER,
        slot
            INTEGER,
        plug
            INTEGER,
        serviceState
            INTEGER,
        bytesSent
            Counter,
        bytesReceived
            Counter,
        packetsSent
            Counter,
        packetsReceived
            Counter,
        maxPacketSize
             INTEGER
    }


serviceNumber1 OBJECT-TYPE
    SYNTAX INTEGER
    ACCESS read-only
    STATUS mandatory
    DESCRIPTION ""
    ::= { serviceEntry 1 }

serviceName OBJECT-TYPE
    SYNTAX DisplayString (SIZE (1..30))
    ACCESS read-only
    STATUS mandatory
    DESCRIPTION ""
    ::= { serviceEntry 2 }

serviceType OBJECT-TYPE
    SYNTAX INTEGER { static(1), aod(2), pod(3), pool(4), internal(5), lan(6) }
    ACCESS read-only
    STATUS mandatory
    DESCRIPTION ""
    ::= { serviceEntry 3 }

slot OBJECT-TYPE
    SYNTAX INTEGER
    ACCESS read-only
    STATUS mandatory
    DESCRIPTION ""
    ::= { serviceEntry 4 }

plug OBJECT-TYPE
    SYNTAX INTEGER
    ACCESS read-only
    STATUS mandatory
    DESCRIPTION ""
    ::= { serviceEntry 5 }

serviceState OBJECT-TYPE
    SYNTAX INTEGER { outOfService(1),noProvider(2),down(3),timeCut(4),up(5) }
    ACCESS read-only
    STATUS mandatory
    DESCRIPTION ""
    ::= { serviceEntry 6 }

bytesSent OBJECT-TYPE
    SYNTAX Counter
    ACCESS read-only
    STATUS mandatory
    DESCRIPTION ""
    ::= { serviceEntry 7 }

bytesReceived OBJECT-TYPE
    SYNTAX Counter
    ACCESS read-only
    STATUS mandatory
    DESCRIPTION ""
    ::= { serviceEntry 8 }

packetsSent OBJECT-TYPE
    SYNTAX Counter
    ACCESS read-only
    STATUS mandatory
    DESCRIPTION ""
    ::= { serviceEntry 9 }

packetsReceived OBJECT-TYPE
    SYNTAX Counter
    ACCESS read-only
    STATUS mandatory
    DESCRIPTION ""
    ::= { serviceEntry 10 }

maxPacketSize OBJECT-TYPE
    SYNTAX INTEGER
    ACCESS read-only
    STATUS mandatory
    DESCRIPTION ""
    ::= { serviceEntry 11 }

lanTable OBJECT-TYPE
    SYNTAX SEQUENCE OF LanEntry
    ACCESS not-accessible
    STATUS mandatory
    DESCRIPTION ""
    ::= { lanSpecific 1 }

lanEntry OBJECT-TYPE
    SYNTAX LanEntry
    ACCESS not-accessible
    STATUS mandatory
    DESCRIPTION ""
    INDEX { serviceNumber2 }
    ::= { lanTable 1 }

LanEntry ::=
    SEQUENCE {
        serviceNumber2
            INTEGER,
        ownSNPAAddress
            OCTET STRING,
        scaNetSubnet
            INTEGER,
        incomingAccessMask1
            OCTET STRING,
        outgoingAccessMask1
            OCTET STRING
    }

serviceNumber2 OBJECT-TYPE
    SYNTAX INTEGER
    ACCESS read-only
    STATUS mandatory
    DESCRIPTION ""
    ::= { lanEntry 1 }

ownSNPAAddress OBJECT-TYPE
    SYNTAX OCTET STRING (SIZE (6))
    ACCESS read-only
    STATUS mandatory
    DESCRIPTION ""
    ::= { lanEntry 2 }

scaNetSubnet OBJECT-TYPE
    SYNTAX INTEGER
    ACCESS read-only
    STATUS mandatory
    DESCRIPTION ""
    ::= { lanEntry 3 }

incomingAccessMask1 OBJECT-TYPE
    SYNTAX OCTET STRING (SIZE (4))
    ACCESS read-write
    STATUS mandatory
    DESCRIPTION ""
    ::= { lanEntry 4 }

outgoingAccessMask1 OBJECT-TYPE
    SYNTAX OCTET STRING (SIZE (4))
    ACCESS read-write
    STATUS mandatory
    DESCRIPTION ""
    ::= { lanEntry 5 }

wanTable OBJECT-TYPE
    SYNTAX SEQUENCE OF WanEntry
    ACCESS not-accessible
    STATUS mandatory
    DESCRIPTION ""
    ::= { wanSpecific 1 }

wanEntry OBJECT-TYPE
    SYNTAX WanEntry
    ACCESS not-accessible
    STATUS mandatory
    DESCRIPTION ""
    INDEX { serviceNumber3 }
    ::= { wanTable 1 }

WanEntry ::=
    SEQUENCE {
        serviceNumber3
            INTEGER,
        provider
            INTEGER,
        queueActualValue
            INTEGER,
        queueHighWaterTideMark
            INTEGER,
        queueRejectThreshold1
            INTEGER,
        dataCompressionSwitch1
            OffOn,
        dataCompressionState
            OffOn,
        acceptIncomingCalls1
            OffOn,
        permitOutgoingCalls1
            OffOn,
        acceptReverseCharge1
            OffOn,
        proposeReverseCharge1
            OffOn,
        permitTimeCut1
            OffOn,
        backupOnly
            OffOn,
        actualCallState
            INTEGER,
        actualCallDirection
            INTEGER,
        actualCallDuration
            INTEGER,
        minCallDuration1
            INTEGER,
        idleTime1
            INTEGER,
         actualTimer
            INTEGER,
        reserveTime1
            INTEGER,
        ownUserDataAddress1
            INTEGER,
        remoteSNPAaddress
            OCTET STRING,
        remoteUserDataAddress
            INTEGER,
        callsPlaced1
            Counter,
        callsFailed1
            Counter,
        actualErrorRetries
            Counter,
        maxErrorRetries1
            INTEGER,
        errorRetryInterval1
            INTEGER,
        maxCallSetupTime1
            INTEGER,
        mostRecentFailure1
            TimeTicks,
        backupForLink
            INTEGER,
        poolIndex
            INTEGER,
        incomingAccessMask2
            OCTET STRING,
        outgoingAccessMask2
            OCTET STRING,
        timecutAccessMask1
            OCTET STRING
    }


serviceNumber3 OBJECT-TYPE
    SYNTAX INTEGER
    ACCESS read-only
    STATUS mandatory
    DESCRIPTION ""
    ::= { wanEntry 1 }

provider OBJECT-TYPE
    SYNTAX INTEGER
    ACCESS read-only
    STATUS mandatory
    DESCRIPTION ""
    ::= { wanEntry 2 }

queueActualValue OBJECT-TYPE
    SYNTAX INTEGER
    ACCESS read-only
    STATUS mandatory
    DESCRIPTION ""
    ::= { wanEntry 3 }

queueHighWaterTideMark OBJECT-TYPE
    SYNTAX INTEGER
    ACCESS read-only
    STATUS mandatory
    DESCRIPTION ""
    ::= { wanEntry 4 }

queueRejectThreshold1 OBJECT-TYPE
    SYNTAX INTEGER
    ACCESS read-write
    STATUS mandatory
    DESCRIPTION ""
    ::= { wanEntry 5 }

dataCompressionSwitch1 OBJECT-TYPE
    SYNTAX OffOn
    ACCESS read-write
    STATUS mandatory
    DESCRIPTION ""
    ::= { wanEntry 6 }

dataCompressionState OBJECT-TYPE
    SYNTAX OffOn
    ACCESS read-only
    STATUS mandatory
    DESCRIPTION ""
    ::= { wanEntry 7 }

acceptIncomingCalls1 OBJECT-TYPE
    SYNTAX OffOn
    ACCESS read-write
    STATUS mandatory
    DESCRIPTION ""
    ::= { wanEntry 8 }

permitOutgoingCalls1 OBJECT-TYPE
    SYNTAX OffOn
    ACCESS read-write
    STATUS mandatory
    DESCRIPTION ""
    ::= { wanEntry 9 }

acceptReverseCharge1 OBJECT-TYPE
    SYNTAX OffOn
    ACCESS read-write
    STATUS mandatory
    DESCRIPTION ""
    ::= { wanEntry 10 }

proposeReverseCharge1 OBJECT-TYPE
    SYNTAX OffOn
    ACCESS read-write
    STATUS mandatory
    DESCRIPTION ""
    ::= { wanEntry 11 }

permitTimeCut1 OBJECT-TYPE
    SYNTAX OffOn
    ACCESS read-write
    STATUS mandatory
    DESCRIPTION ""
    ::= { wanEntry 12 }

backupOnly OBJECT-TYPE
    SYNTAX OffOn
    ACCESS read-write
    STATUS mandatory
    DESCRIPTION ""
    ::= { wanEntry 13 }

actualCallState OBJECT-TYPE
    SYNTAX INTEGER { outOfService(1), noProvider(2), error(3), down(4),
                     disconnecting(5), connecting(6), up(7) }
    ACCESS read-only
    STATUS mandatory
    DESCRIPTION ""
    ::= { wanEntry 14 }

actualCallDirection OBJECT-TYPE
    SYNTAX INTEGER { inc(1), outg(2) }
    ACCESS read-only
    STATUS mandatory
    DESCRIPTION ""
    ::= { wanEntry 15 }

actualCallDuration OBJECT-TYPE
    SYNTAX INTEGER
    ACCESS read-only
    STATUS mandatory
    DESCRIPTION ""
    ::= { wanEntry 16 }

minCallDuration1 OBJECT-TYPE
    SYNTAX INTEGER
    ACCESS read-write
    STATUS mandatory
    DESCRIPTION ""
    ::= { wanEntry 17 }

idleTime1 OBJECT-TYPE
    SYNTAX INTEGER
    ACCESS read-write
    STATUS mandatory
    DESCRIPTION ""
    ::= { wanEntry 18 }

actualTimer OBJECT-TYPE
    SYNTAX INTEGER
    ACCESS read-only
    STATUS mandatory
    DESCRIPTION ""
    ::= { wanEntry 19 }

reserveTime1 OBJECT-TYPE
    SYNTAX INTEGER
    ACCESS read-only
    STATUS mandatory
    DESCRIPTION ""
    ::= { wanEntry 20 }

ownUserDataAddress1 OBJECT-TYPE
    SYNTAX INTEGER
    ACCESS read-write
    STATUS mandatory
    DESCRIPTION ""
    ::= { wanEntry 21 }

remoteSNPAaddress OBJECT-TYPE
    SYNTAX OCTET STRING (SIZE (1..30))
    ACCESS read-write
    STATUS mandatory
    DESCRIPTION ""
    ::= { wanEntry 22 }

remoteUserDataAddress OBJECT-TYPE
    SYNTAX INTEGER
    ACCESS read-write
    STATUS mandatory
    DESCRIPTION ""
    ::= { wanEntry 23 }

callsPlaced1 OBJECT-TYPE
    SYNTAX Counter
    ACCESS read-only
    STATUS mandatory
    DESCRIPTION ""
    ::= { wanEntry 24 }

callsFailed1 OBJECT-TYPE
    SYNTAX Counter
    ACCESS read-only
    STATUS mandatory
    DESCRIPTION ""
    ::= { wanEntry 25 }

actualErrorRetries OBJECT-TYPE
    SYNTAX Counter
    ACCESS read-only
    STATUS mandatory
    DESCRIPTION ""
    ::= { wanEntry 26 }

maxErrorRetries1 OBJECT-TYPE
    SYNTAX INTEGER
    ACCESS read-write
    STATUS mandatory
    DESCRIPTION ""
    ::= { wanEntry 27 }

errorRetryInterval1 OBJECT-TYPE
    SYNTAX INTEGER
    ACCESS read-write
    STATUS mandatory
    DESCRIPTION ""
    ::= { wanEntry 28 }

maxCallSetupTime1 OBJECT-TYPE
    SYNTAX INTEGER
    ACCESS read-write
    STATUS mandatory
    DESCRIPTION ""
    ::= { wanEntry 29 }

mostRecentFailure1 OBJECT-TYPE
    SYNTAX TimeTicks
    ACCESS read-only
    STATUS mandatory
    DESCRIPTION ""
    ::= { wanEntry 30 }

backupForLink OBJECT-TYPE
    SYNTAX INTEGER
    ACCESS read-write
    STATUS mandatory
    DESCRIPTION ""
    ::= { wanEntry 31 }

poolIndex OBJECT-TYPE
    SYNTAX INTEGER
    ACCESS read-write
    STATUS mandatory
    DESCRIPTION ""
    ::= { wanEntry 32 }

incomingAccessMask2 OBJECT-TYPE
    SYNTAX OCTET STRING (SIZE (4))
    ACCESS read-write
    STATUS mandatory
    DESCRIPTION ""
    ::= { wanEntry 33 }

outgoingAccessMask2 OBJECT-TYPE
    SYNTAX OCTET STRING (SIZE (4))
    ACCESS read-write
    STATUS mandatory
    DESCRIPTION ""
    ::= { wanEntry 34 }

timecutAccessMask1 OBJECT-TYPE
    SYNTAX OCTET STRING (SIZE (4))
    ACCESS read-write
    STATUS mandatory
    DESCRIPTION ""
    ::= { wanEntry 35 }

poolTable OBJECT-TYPE
    SYNTAX SEQUENCE OF PoolEntry
    ACCESS not-accessible
    STATUS mandatory
    DESCRIPTION ""
    ::= { wanSpecific 2 }

poolEntry OBJECT-TYPE
    SYNTAX PoolEntry
    ACCESS not-accessible
    STATUS mandatory
    DESCRIPTION ""
    INDEX { serviceNumber4 }
    ::= { poolTable 1 }

PoolEntry ::=
    SEQUENCE {
        serviceNumber4
            INTEGER,
        poolName
            DisplayString,
        queueRejectThreshold2
            INTEGER,
        dataCompressionSwitch2
            OffOn,
        acceptIncomingCalls2
            OffOn,
        permitOutgoingCalls2
            OffOn,
        acceptReverseCharge2
            OffOn,
        proposeReverseCharge2
            OffOn,
        permitTimeCut2
            OffOn,
        minCallDuration2
            INTEGER,
        idleTime2
            INTEGER,
        reserveTime2
            INTEGER,
        ownUserDataAddress2
            INTEGER,
        callsPlaced2
            Counter,
        callsFailed2
            Counter,
         maxErrorRetries2
            INTEGER,
        errorRetryInterval2
            INTEGER,
        maxCallSetupTime2
            INTEGER,
        mostRecentFailure2
            TimeTicks,
        poolSize
            INTEGER,
        freeLinks
            INTEGER,
        incomingAccessMask3
            OCTET STRING,
        outgoingAccessMask3
            OCTET STRING,
        timecutAccessMask2
            OCTET STRING
    }


serviceNumber4 OBJECT-TYPE
    SYNTAX INTEGER
    ACCESS read-only
    STATUS mandatory
    DESCRIPTION ""
    ::= { poolEntry 1 }

poolName OBJECT-TYPE
    SYNTAX DisplayString (SIZE (1..30))
    ACCESS read-only
    STATUS mandatory
    DESCRIPTION ""
    ::= { poolEntry 2 }

queueRejectThreshold2 OBJECT-TYPE
    SYNTAX INTEGER
    ACCESS read-write
    STATUS mandatory
    DESCRIPTION ""
    ::= { poolEntry 3 }

dataCompressionSwitch2 OBJECT-TYPE
    SYNTAX OffOn
    ACCESS read-write
    STATUS mandatory
    DESCRIPTION ""
    ::= { poolEntry 4 }

acceptIncomingCalls2 OBJECT-TYPE
    SYNTAX OffOn
    ACCESS read-write
    STATUS mandatory
    DESCRIPTION ""
    ::= { poolEntry 5 }

permitOutgoingCalls2 OBJECT-TYPE
    SYNTAX OffOn
    ACCESS read-write
    STATUS mandatory
    DESCRIPTION ""
    ::= { poolEntry 6 }

acceptReverseCharge2 OBJECT-TYPE
    SYNTAX OffOn
    ACCESS read-write
    STATUS mandatory
    DESCRIPTION ""
    ::= { poolEntry 7 }

proposeReverseCharge2 OBJECT-TYPE
    SYNTAX OffOn
    ACCESS read-write
    STATUS mandatory
    DESCRIPTION ""
    ::= { poolEntry 8 }

permitTimeCut2 OBJECT-TYPE
    SYNTAX OffOn
    ACCESS read-write
    STATUS mandatory
    DESCRIPTION ""
    ::= { poolEntry 9 }

minCallDuration2 OBJECT-TYPE
    SYNTAX INTEGER
    ACCESS read-write
    STATUS mandatory
    DESCRIPTION ""
    ::= { poolEntry 10 }

idleTime2 OBJECT-TYPE
    SYNTAX INTEGER
    ACCESS read-write
    STATUS mandatory
    DESCRIPTION ""
    ::= { poolEntry 11 }

reserveTime2 OBJECT-TYPE
    SYNTAX INTEGER
    ACCESS read-write
    STATUS mandatory
    DESCRIPTION ""
    ::= { poolEntry 12 }

ownUserDataAddress2 OBJECT-TYPE
    SYNTAX INTEGER
    ACCESS read-write
    STATUS mandatory
    DESCRIPTION ""
    ::= { poolEntry 13 }

callsPlaced2 OBJECT-TYPE
    SYNTAX Counter
    ACCESS read-only
    STATUS mandatory
    DESCRIPTION ""
    ::= { poolEntry 14 }

callsFailed2 OBJECT-TYPE
    SYNTAX Counter
    ACCESS read-only
    STATUS mandatory
    DESCRIPTION ""
    ::= { poolEntry 15 }

maxErrorRetries2 OBJECT-TYPE
    SYNTAX INTEGER
    ACCESS read-write
    STATUS mandatory
    DESCRIPTION ""
    ::= { poolEntry 16 }

errorRetryInterval2 OBJECT-TYPE
    SYNTAX INTEGER
    ACCESS read-write
    STATUS mandatory
    DESCRIPTION ""
    ::= { poolEntry 17 }

maxCallSetupTime2 OBJECT-TYPE
    SYNTAX INTEGER
    ACCESS read-write
    STATUS mandatory
    DESCRIPTION ""
    ::= { poolEntry 18 }

mostRecentFailure2 OBJECT-TYPE
    SYNTAX TimeTicks
    ACCESS read-only
    STATUS mandatory
    DESCRIPTION ""
    ::= { poolEntry 19 }

poolSize OBJECT-TYPE
    SYNTAX INTEGER
    ACCESS read-only
    STATUS mandatory
    DESCRIPTION ""
    ::= { poolEntry 20 }

freeLinks OBJECT-TYPE
    SYNTAX INTEGER
    ACCESS read-only
    STATUS mandatory
    DESCRIPTION ""
    ::= { poolEntry 21 }

incomingAccessMask3 OBJECT-TYPE
    SYNTAX OCTET STRING
    ACCESS read-write
    STATUS mandatory
    DESCRIPTION ""
    ::= { poolEntry 22 }

outgoingAccessMask3 OBJECT-TYPE
    SYNTAX OCTET STRING (SIZE (4))
    ACCESS read-write
    STATUS mandatory
    DESCRIPTION ""
    ::= { poolEntry 23 }

timecutAccessMask2 OBJECT-TYPE
    SYNTAX OCTET STRING (SIZE (4))
    ACCESS read-write
    STATUS mandatory
    DESCRIPTION ""
    ::= { poolEntry 24 }

END
