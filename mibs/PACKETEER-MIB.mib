-- Packeteer PacketShaper v7.0 MIB
-- Sept 1, 2004
-- Copyright 1997-2004 Packeteer, Inc.

PACKETEER-MIB DEFINITIONS ::= BEGIN


   IMPORTS
      IpAddress, Counter, Gauge, enterprises
         FROM RFC1155-SMI
      OBJECT-TYPE
         FROM RFC-1212
      DisplayString
         FROM RFC1213-MIB
      DateAndTime
	 FROM SNMPv2-TC
      TRAP-TYPE
	 FROM RFC-1215;

   -- Packeteer MIB

   packeteer         OBJECT IDENTIFIER ::= { enterprises 2334 }
   products          OBJECT IDENTIFIER ::= { packeteer 1 }
   packetShaper      OBJECT IDENTIFIER ::= { products 1 }
   packetShaper-2000 OBJECT IDENTIFIER ::= { packetShaper 1 }
   packetShaper-4000 OBJECT IDENTIFIER ::= { packetShaper 2 }
   packetShaper-1000 OBJECT IDENTIFIER ::= { packetShaper 3 }
   packetShaper-2500 OBJECT IDENTIFIER ::= { packetShaper 4 }
   packetShaper-4500 OBJECT IDENTIFIER ::= { packetShaper 5 }
   packetShaper-1500 OBJECT IDENTIFIER ::= { packetShaper 6 }
   packetShaper-asm50 OBJECT IDENTIFIER ::= { packetShaper 7 }
   packetShaper-asm70 OBJECT IDENTIFIER ::= { packetShaper 8 }
   packetShaper-asm30 OBJECT IDENTIFIER ::= { packetShaper 9 }
   packetShaper-asm90 OBJECT IDENTIFIER ::= { packetShaper 10 }
   packetShaper-6500 OBJECT IDENTIFIER ::= { packetShaper 11 }
   packetShaper-8500 OBJECT IDENTIFIER ::= { packetShaper 12 }
   packetShaper-asm110 OBJECT IDENTIFIER ::= { packetShaper 13 }
   packetShaper-1550 OBJECT IDENTIFIER ::= { packetShaper 14 }
   packetShaper-9500 OBJECT IDENTIFIER ::= { packetShaper 15 }
   packetShaper-2550 OBJECT IDENTIFIER ::= { packetShaper 16 }
   packetShaper-10000 OBJECT IDENTIFIER ::= { packetShaper 17 }

   packeteerMibs     OBJECT IDENTIFIER ::= { packeteer 2 }
   psCommonMib       OBJECT IDENTIFIER ::= { packeteerMibs 1 }
   psSettings        OBJECT IDENTIFIER ::= { psCommonMib 1 }
   psLinks           OBJECT IDENTIFIER ::= { psCommonMib 2 }
   psPartitions      OBJECT IDENTIFIER ::= { psCommonMib 3 }
   psClasses         OBJECT IDENTIFIER ::= { psCommonMib 4 }
   psAlarms          OBJECT IDENTIFIER ::= { psCommonMib 5 }
   psAdmin           OBJECT IDENTIFIER ::= { psCommonMib 6 }

   psUserEvents      OBJECT IDENTIFIER ::= { psCommonMib 8 }
   psHighAv	     OBJECT IDENTIFIER ::= { psCommonMib 9 }
   psAgentEvent      OBJECT IDENTIFIER ::= { psCommonMib 10 }

   -- the psSettings group

   psShapingStatusOper	OBJECT-TYPE
      SYNTAX   INTEGER  { ok(1), off(2) }
      ACCESS  read-only
      STATUS  mandatory
      DESCRIPTION
         "This object reflects the current operational traffic shaping status
          of the PacketShaper.  The value of this object reflects the status
          of the front panel status LED. If all of the following conditions
          are true, then the object is set to 1, otherwise it is 2:  links are up,
          shaping is on, and the siterouter is usable (if configured)."
       ::= { psSettings 1 }


     -- the Link group

   linkTableSize OBJECT-TYPE
      SYNTAX   INTEGER
      ACCESS  read-only
      STATUS  mandatory
      DESCRIPTION
         "Number of entries in the linkTable"
      ::= { psLinks 1 }

   linkTable OBJECT-TYPE
      SYNTAX  SEQUENCE OF LinkEntry
      ACCESS  not-accessible
      STATUS  mandatory
      DESCRIPTION
         "A list of link entries."
      ::= { psLinks 2 }

   linkEntry OBJECT-TYPE
      SYNTAX  LinkEntry
      ACCESS  not-accessible
      STATUS  mandatory
      DESCRIPTION
         "A link entry containing containing statistical objects for
	  a link."
      INDEX   { linkIndex }
      ::= { linkTable 1 }

   LinkEntry ::=
      SEQUENCE {
	 linkIndex
	    INTEGER,
         linkName
            DisplayString,
         linkByteCount
            Counter,
         linkByteCountHi
            Counter,
         linkPkts
            Counter,
         linkDataPkts
            Counter,
         linkReTxs
            Counter,
         linkReTxTosses
            Counter,
	 linkCirFails
	    Counter,
	 linkCirAllocs
	    Counter,
	 linkEirAllocs
	    Counter,
	 linkPeakTcpConns
	    Gauge,
         linkTcpConnInits
            Counter,
         linkTcpConnExits
            Counter,
         linkTcpConnRefuses
            Counter,
         linkTcpConnIgnores
            Counter,
         linkTcpConnAborts
            Counter,
         linkTcpConnDenies
            Counter,
         linkTcpConnTimeouts
            Counter,
         linkPeakUdpConns
            Gauge,
         linkUdpConnInits
            Counter,
         linkUdpConnExits
            Counter,
         linkSize
            INTEGER,
	 linkRate
	    Gauge,
	 linkRateAllocations
	    Gauge,
	 linkPeakGuaranteedRateFlows
	    Gauge,
	 linkPeakRateFlows
	    Gauge,
	 linkReTxByteCount
	    Counter,
	 linkReTxByteCountHi
	    Counter,
	 linkTotalRxPkts
   		Counter,
	 linkTotalTxPkts
		Counter,
	 linkRxNoBufs
		Counter,
	 linkRxPktDrops
		Counter,
	 linkTxPktDrops
		Counter,
	 linkRxErrors
		Counter,
	 linkTxErrors
		Counter,
	 linkTcpAllocFails
		Counter,
	 linkIpdgAllocFails
		Counter,
	 linkHostdbAllocFails
		Counter,
     linkShapingMode
		INTEGER,
     linkAutoclassifyMode
		INTEGER,
     linkMacSameSidePkts
		Counter,
     linkPassthruPkts
		Counter,
     linkTotalRxBytes
		Counter,
     linkTotalRxBytesHi
		Counter,
     linkTotalTxBytes
		Counter,
     linkTotalTxBytesHi
		Counter,
     linkClassChecks
                Counter,
     linkPassthruBytes
                Counter,
     linkCompressionMode
                INTEGER,
     linkPeakPreCompressionRate
                Gauge,
     linkPeakPostCompressionRate
                Gauge,
     linkNonComprsnBytes
                Counter,
     linkNonComprsnBytesHi
                Counter,
     linkPostComprsnBytes
                Counter,
     linkPostComprsnBytesHi
                Counter,
     linkPreComprsnBytes
                Counter,
     linkPreComprsnBytesHi
                Counter
      }

   linkIndex OBJECT-TYPE
      SYNTAX  INTEGER
      ACCESS  read-only
      STATUS  mandatory
      DESCRIPTION
         "A unique ID for a link."
      ::= { linkEntry 1 }

   linkName OBJECT-TYPE
      SYNTAX  DisplayString
      ACCESS  read-only
      STATUS  mandatory
      DESCRIPTION
         "A unique name for a link."
      ::= { linkEntry 2 }

   linkByteCount OBJECT-TYPE
      SYNTAX  Counter
      ACCESS  read-only
      STATUS  mandatory
      DESCRIPTION
         "The byte count in the link"
      ::= { linkEntry 3 }

   linkByteCountHi OBJECT-TYPE
      SYNTAX  Counter
      ACCESS  read-only
      STATUS  mandatory
      DESCRIPTION
         "The High 32 bits of byte count in the link."
      ::= { linkEntry 4 }

   linkPkts OBJECT-TYPE
      SYNTAX  Counter
      ACCESS  read-only
      STATUS  mandatory
      DESCRIPTION
         "The packet count in the link"
      ::= { linkEntry 5 }

   linkDataPkts OBJECT-TYPE
      SYNTAX  Counter
      ACCESS  read-only
      STATUS  mandatory
      DESCRIPTION
         "The TCP data packet count in the link"
      ::= { linkEntry 6 }

   linkReTxs OBJECT-TYPE
      SYNTAX  Counter
      ACCESS  read-only
      STATUS  mandatory
      DESCRIPTION
         "The TCP retransmit packet count in the link"
      ::= { linkEntry 7 }

   linkReTxTosses OBJECT-TYPE
      SYNTAX  Counter
      ACCESS  read-only
      STATUS  mandatory
      DESCRIPTION
         "The TCP tossed retransmit packet count in the link"
      ::= { linkEntry 8 }

   linkCirFails OBJECT-TYPE
      SYNTAX  Counter
      ACCESS  read-only
      STATUS  mandatory
      DESCRIPTION
         "The count of CIR fails events in the link"
      ::= { linkEntry 9 }

   linkCirAllocs OBJECT-TYPE
      SYNTAX  Counter
      ACCESS  read-only
      STATUS  mandatory
      DESCRIPTION
         "The count of CIR alloc events in the link"
      ::= { linkEntry 10 }

   linkEirAllocs OBJECT-TYPE
      SYNTAX  Counter
      ACCESS  read-only
      STATUS  mandatory
      DESCRIPTION
         "The count of EIR alloc events in the link. This
		variable is obselete and should not be used."
      ::= { linkEntry 11 }

   linkPeakTcpConns OBJECT-TYPE
      SYNTAX  Gauge
      ACCESS  read-only
      STATUS  mandatory
      DESCRIPTION
         "The peak number of active TCP flows in the link."
      ::= { linkEntry 12 }

   linkTcpConnInits OBJECT-TYPE
      SYNTAX  Counter
      ACCESS  read-only
      STATUS  mandatory
      DESCRIPTION
         "The count of TCP flows started in the link"
      ::= { linkEntry 13 }

   linkTcpConnExits OBJECT-TYPE
      SYNTAX  Counter
      ACCESS  read-only
      STATUS  mandatory
      DESCRIPTION
         "The count of TCP flows exited in the link"
      ::= { linkEntry 14 }

   linkTcpConnRefuses OBJECT-TYPE
      SYNTAX  Counter
      ACCESS  read-only
      STATUS  mandatory
      DESCRIPTION
         "The count of TCP flows exited by TCP refuse in the link"
      ::= { linkEntry 15 }

   linkTcpConnIgnores OBJECT-TYPE
      SYNTAX  Counter
      ACCESS  read-only
      STATUS  mandatory
      DESCRIPTION
         "The count of TCP flows exited by being ignored in the link."
      ::= { linkEntry 16 }

   linkTcpConnAborts OBJECT-TYPE
      SYNTAX  Counter
      ACCESS  read-only
      STATUS  mandatory
      DESCRIPTION
         "The count of TCP flows aborted in the link."
      ::= { linkEntry 17 }

   linkTcpConnDenies OBJECT-TYPE
      SYNTAX  Counter
      ACCESS  read-only
      STATUS  mandatory
      DESCRIPTION
         "The count of TCP flows denied by CIR fail in the link."
      ::= { linkEntry 18 }

   linkTcpConnTimeouts OBJECT-TYPE
      SYNTAX  Counter
      ACCESS  read-only
      STATUS  deprecated
      DESCRIPTION
         "The count of TCP flows timed out by pshaper in the link.  This
	  variable is obsolete and should not be used."
      ::= { linkEntry 19 }

   linkPeakUdpConns OBJECT-TYPE
      SYNTAX  Gauge
      ACCESS  read-only
      STATUS  deprecated
      DESCRIPTION
         "The peak number of active UDP flows in the link.  This variable
          is deprecated, and should no longer be used."
      ::= { linkEntry 20 }

   linkUdpConnInits OBJECT-TYPE
      SYNTAX  Counter
      ACCESS  read-only
      STATUS  deprecated
      DESCRIPTION
         "The count of UDP flows started in the link.  This variable
          is deprecated, and should no longer be used."
      ::= { linkEntry 21 }

   linkUdpConnExits OBJECT-TYPE
      SYNTAX  Counter
      ACCESS  read-only
      STATUS  deprecated
      DESCRIPTION
         "The count of UDP flows exited in the link.  This variable
          is deprecated, and should no longer be used."
      ::= { linkEntry 22 }

   linkSize OBJECT-TYPE
      SYNTAX  INTEGER
      ACCESS  read-only
      STATUS  mandatory
      DESCRIPTION
         "The size in bps of the link."
      ::= { linkEntry 23 }

   linkRate OBJECT-TYPE
      SYNTAX  Gauge
      ACCESS  read-only
      STATUS  mandatory
      DESCRIPTION
         "The peak bps of the link."
      ::= { linkEntry 24 }

   linkRateAllocations OBJECT-TYPE
      SYNTAX  Gauge
      ACCESS  read-only
      STATUS  mandatory
      DESCRIPTION
         "The count of rate allocations on the link. This variable
		  is obsolete and should not be used."
      ::= { linkEntry 25 }

   linkPeakGuaranteedRateFlows OBJECT-TYPE
      SYNTAX  Gauge
      ACCESS  read-only
      STATUS  mandatory
      DESCRIPTION
         "The peak number of guaranteed rate flows active on the link."
      ::= { linkEntry 26 }

   linkPeakRateFlows OBJECT-TYPE
      SYNTAX  Gauge
      ACCESS  read-only
      STATUS  mandatory
      DESCRIPTION
         "The peak number of rate-based flows active on the link. This
		  variable is obsolete and should not be used."
      ::= { linkEntry 27 }

   linkReTxByteCount OBJECT-TYPE
      SYNTAX  Counter
      ACCESS  read-only
      STATUS  mandatory
      DESCRIPTION
         "The count of retransmitted bytes on the link.  This is the
          low-order 32 bits."
      ::= { linkEntry 28 }

   linkReTxByteCountHi OBJECT-TYPE
      SYNTAX  Counter
      ACCESS  read-only
      STATUS  mandatory
      DESCRIPTION
         "The count of retransmitted bytes on the link.  This is the
          high-order 32 bits."
      ::= { linkEntry 29 }

   linkTotalRxPkts OBJECT-TYPE
      SYNTAX  Counter
      ACCESS  read-only
      STATUS  mandatory
      DESCRIPTION
         "The total packets received on the link."
      ::= { linkEntry 30 }

   linkTotalTxPkts OBJECT-TYPE
      SYNTAX  Counter
      ACCESS  read-only
      STATUS  mandatory
      DESCRIPTION
         "The total packets transmitted on the link."
      ::= { linkEntry 31 }

   linkRxNoBufs OBJECT-TYPE
      SYNTAX  Counter
      ACCESS  read-only
      STATUS  mandatory
      DESCRIPTION
         "The count of packets that were dropped due to unavailable buffers."
      ::= { linkEntry 32 }

   linkRxPktDrops OBJECT-TYPE
      SYNTAX  Counter
      ACCESS  read-only
      STATUS  mandatory
      DESCRIPTION
         "The count of packets dropped due to no buffers, no connection blocks or random dropping."
      ::= { linkEntry 33 }

   linkTxPktDrops OBJECT-TYPE
      SYNTAX  Counter
      ACCESS  read-only
      STATUS  mandatory
      DESCRIPTION
         "The count of transmitted packets that were dropped due to no route available, an i/o error or no buffers."
      ::= { linkEntry 34 }

   linkRxErrors OBJECT-TYPE
      SYNTAX  Counter
      ACCESS  read-only
      STATUS  mandatory
      DESCRIPTION
         "The count of received packets that were dropped due to hardware errors."
      ::= { linkEntry 35 }

   linkTxErrors OBJECT-TYPE
      SYNTAX  Counter
      ACCESS  read-only
      STATUS  mandatory
      DESCRIPTION
         "The count of transmitted packets that were dropped due to hardware errors."
      ::= { linkEntry 36 }

   linkTcpAllocFails OBJECT-TYPE
      SYNTAX  Counter
      ACCESS  read-only
      STATUS  mandatory
      DESCRIPTION
         "The count of TCP alloc fails on a link."
      ::= { linkEntry 37 }

   linkIpdgAllocFails OBJECT-TYPE
      SYNTAX  Counter
      ACCESS  read-only
      STATUS  mandatory
      DESCRIPTION
         "The count of IPDG alloc fails on a link."
      ::= { linkEntry 38 }

   linkHostdbAllocFails OBJECT-TYPE
      SYNTAX  Counter
      ACCESS  read-only
      STATUS  mandatory
      DESCRIPTION
         "The count of Host DB alloc fails on a link."
      ::= { linkEntry 39 }

   linkShapingMode  OBJECT-TYPE
      SYNTAX  INTEGER {
		off(1),
		on(2),
		watch(4)
	}
      ACCESS  read-only
      STATUS  mandatory
      DESCRIPTION
         "The current shaping mode."
      ::= { linkEntry 40 }

   linkAutoclassifyMode OBJECT-TYPE
      SYNTAX  INTEGER {
		off(1),
		on(2)
	}
      ACCESS  read-only
      STATUS  mandatory
      DESCRIPTION
         "The current autoclassification mode."
      ::= { linkEntry 41 }

   linkMacSameSidePkts OBJECT-TYPE
      SYNTAX  Counter
      ACCESS  read-only
      STATUS  mandatory
      DESCRIPTION
         "The total number of same-side packets on the link."
      ::= { linkEntry 42 }

   linkPassthruPkts OBJECT-TYPE
      SYNTAX  Counter
      ACCESS  read-only
      STATUS  mandatory
      DESCRIPTION
         "The total packets passed through on the link."
      ::= { linkEntry 43 }

   linkTotalRxBytes OBJECT-TYPE
      SYNTAX  Counter
      ACCESS  read-only
      STATUS  mandatory
      DESCRIPTION
         "The total number of bytes received on the link.  This is the low-order 32 bits."
      ::= { linkEntry 44 }

   linkTotalRxBytesHi OBJECT-TYPE
      SYNTAX  Counter
      ACCESS  read-only
      STATUS  mandatory
      DESCRIPTION
         "The total number of bytes received on the link.  This is the high-order 32 bits."
      ::= { linkEntry 45 }

   linkTotalTxBytes OBJECT-TYPE
      SYNTAX  Counter
      ACCESS  read-only
      STATUS  mandatory
      DESCRIPTION
         "The total number of bytes transmitted on the link.  This is the low-order 32 bits."
      ::= { linkEntry 46 }

   linkTotalTxBytesHi OBJECT-TYPE
      SYNTAX  Counter
      ACCESS  read-only
      STATUS  mandatory
      DESCRIPTION
         "The total number of bytes transmitted on the link.  This is the high-order 32 bits."
      ::= { linkEntry 47 }

   linkClassChecks OBJECT-TYPE
      SYNTAX  Counter
      ACCESS  read-only
      STATUS  mandatory
      DESCRIPTION
         "The number of traversals of the class tree."
      ::= { linkEntry 48 }

   linkPassthruBytes OBJECT-TYPE
      SYNTAX  Counter
      ACCESS  read-only
      STATUS  mandatory
      DESCRIPTION
         "The total number of bytes passed through on the link."
      ::= { linkEntry 49 }


   linkCompressionMode  OBJECT-TYPE
      SYNTAX  INTEGER {
		off(1),
		on(2)
	}
      ACCESS  read-only
      STATUS  mandatory
      DESCRIPTION
         "The current compression mode."
      ::= { linkEntry 50 }

   linkPeakPreCompressionRate OBJECT-TYPE
      SYNTAX  Gauge
      ACCESS  read-only
      STATUS  mandatory
      DESCRIPTION
         "The peak pre-compression rate on the link."
      ::= { linkEntry 51 }

   linkPeakPostCompressionRate OBJECT-TYPE
      SYNTAX  Gauge
      ACCESS  read-only
      STATUS  mandatory
      DESCRIPTION
         "The peak post-compression rate on the link."
      ::= { linkEntry 52 }

   linkNonComprsnBytes OBJECT-TYPE
      SYNTAX  Counter
      ACCESS  read-only
      STATUS  mandatory
      DESCRIPTION
         "The total number of non-compressed bytes on the link."
      ::= { linkEntry 53 }

   linkNonComprsnBytesHi OBJECT-TYPE
      SYNTAX  Counter
      ACCESS  read-only
      STATUS  mandatory
      DESCRIPTION
         "The total number of non-compressed bytes on the link. This is the high-order 32 bits."
      ::= { linkEntry 54 }

   linkPreComprsnBytes OBJECT-TYPE
      SYNTAX  Counter
      ACCESS  read-only
      STATUS  mandatory
      DESCRIPTION
         "The total number of bytes before compression on the link."
      ::= { linkEntry 55 }

   linkPreComprsnBytesHi OBJECT-TYPE
      SYNTAX  Counter
      ACCESS  read-only
      STATUS  mandatory
      DESCRIPTION
         "The total number of bytes before compression on the link. This is the high-order 32 bits."
      ::= { linkEntry 56 }

   linkPostComprsnBytes OBJECT-TYPE
      SYNTAX  Counter
      ACCESS  read-only
      STATUS  mandatory
      DESCRIPTION
         "The total number of bytes after compression on the link."
      ::= { linkEntry 57 }

   linkPostComprsnBytesHi OBJECT-TYPE
      SYNTAX  Counter
      ACCESS  read-only
      STATUS  mandatory
      DESCRIPTION
         "The total number of bytes after compression on the link. This is the high-order 32 bits."
      ::= { linkEntry 58 }

  -- the Partitions group

   partitionTableSize OBJECT-TYPE
      SYNTAX   INTEGER
      ACCESS  read-only
      STATUS  mandatory
      DESCRIPTION
         "Number of entries in the partitionTable"
      ::= { psPartitions 1 }

   partitionTable OBJECT-TYPE
      SYNTAX  SEQUENCE OF PartitionEntry
      ACCESS  not-accessible
      STATUS  mandatory
      DESCRIPTION
         "A list of partition entries."
      ::= { psPartitions 2 }

   partitionEntry OBJECT-TYPE
      SYNTAX  PartitionEntry
      ACCESS  not-accessible
      STATUS  mandatory
      DESCRIPTION
         "A partition entry containing statistical objects for a
	  traffic partition."
      INDEX   { partitionIndex }
      ::= { partitionTable 1 }

   PartitionEntry ::=
      SEQUENCE {
	 partitionIndex
	    INTEGER,
         partitionName
            DisplayString,
	 partitionLinkDirection
	    INTEGER,
         partitionByteCount
            Counter,
         partitionByteCountHi
            Counter,
         partitionPkts
            Counter,
         partitionDataPkts
            Counter,
         partitionReTxs
            Counter,
         partitionReTxTosses
            Counter,
	 partitionCirFails
	    Counter,
	 partitionCirAllocs
	    Counter,
	 partitionEirAllocs
	    Counter,
	 partitionPeakTcpConns
	    Gauge,
         partitionTcpConnInits
            Counter,
         partitionTcpConnExits
            Counter,
         partitionTcpConnRefuses
            Counter,
         partitionTcpConnIgnores
            Counter,
         partitionTcpConnAborts
            Counter,
         partitionTcpConnDenies
            Counter,
         partitionTcpConnTimeouts
            Counter,
         partitionPeakUdpConns
            Gauge,
         partitionUdpConnInits
            Counter,
         partitionUdpConnExits
            Counter,
         partitionMinimumBps
            INTEGER,
	 partitionBurstLimit
	    INTEGER,
	 partitionRate
            Gauge,
	 partitionCirRate
            Gauge,
	 partitionEirRate
            Gauge,
	 partitionUnreservedRate
            Gauge,
	 partitionFirstSatisfiedPriority
            Gauge,
	 partitionTimeOverLimit
            Counter,
	 partitionRateAllocations
	    Counter,
	 partitionPeakGuaranteedRateFlows
	    Gauge,
	 partitionPeakRateFlows
	    Gauge,
	 partitionReTxByteCount
	    Counter,
	 partitionReTxByteCountHi
	    Counter,
	 partitionDynamicCapCount
		Counter,
	 partitionDynamicNoCount
		Counter,
	 partitionDynamicLiveUserCount
		Gauge,
	 partitionCommittmentFailures
                Counter,
        partitionLateDropPktCount
                Gauge,
         partitionLateDropPktCountHi
                Gauge,
         partitionLateDropByteCount
                Gauge,
         partitionLateDropByteCountHi
                Gauge,
         partitionSchedDropPktCount
                Gauge,
         partitionSchedDropPktCountHi
                Gauge,
         partitionSchedDropByteCount
                Gauge,
         partitionSchedDropByteCountHi
                Gauge,
         partitionFrameBytes
                Counter,
         partitionFrameBytesHi
                Counter,
         partitionFrameTargetRate
                Gauge,
         partitionFrameTargetRateHi
                Gauge,
         partitionFrameCount
                Counter,
         partitionEcnCount
                Counter,
         partitionNonComprsnBytes
                Counter,
         partitionNonComprsnBytesHi
                Counter,
         partitionPostComprsnBytes
                Counter,
         partitionPostComprsnBytesHi
                Counter,
         partitionPreComprsnBytes
                Counter,
         partitionPreComprsnBytesHi
                Counter
      }

   partitionIndex OBJECT-TYPE
      SYNTAX  INTEGER
      ACCESS  read-only
      STATUS  mandatory
      DESCRIPTION
         "A unique ID for a  partition."
      ::= { partitionEntry 1 }

   partitionName OBJECT-TYPE
      SYNTAX  DisplayString
      ACCESS  read-only
      STATUS  mandatory
      DESCRIPTION
         "A unique name for a partition."
      ::= { partitionEntry 2 }

   partitionLinkDirection OBJECT-TYPE
      SYNTAX  INTEGER {
	in-bound(1),
	out-bound(2)
	      }
      ACCESS  read-only
      STATUS  mandatory
      DESCRIPTION
         "The orientation of a partition."
      ::= { partitionEntry 3 }

   partitionByteCount OBJECT-TYPE
      SYNTAX  Counter
      ACCESS  read-only
      STATUS  mandatory
      DESCRIPTION
         "The byte count in the partition"
      ::= { partitionEntry 4 }

   partitionByteCountHi OBJECT-TYPE
      SYNTAX  Counter
      ACCESS  read-only
      STATUS  mandatory
      DESCRIPTION
         "The high 32 bits of byte count in the partition."
      ::= { partitionEntry 5 }

   partitionPkts OBJECT-TYPE
      SYNTAX  Counter
      ACCESS  read-only
      STATUS  mandatory
      DESCRIPTION
         "The packet count in the partition."
      ::= { partitionEntry 6 }

   partitionDataPkts OBJECT-TYPE
      SYNTAX  Counter
      ACCESS  read-only
      STATUS  mandatory
      DESCRIPTION
         "The TCP data packet count in the partition."
      ::= { partitionEntry 7 }

   partitionReTxs OBJECT-TYPE
      SYNTAX  Counter
      ACCESS  read-only
      STATUS  mandatory
      DESCRIPTION
         "The TCP retransmit packet count in the partition."
      ::= { partitionEntry 8 }

   partitionReTxTosses OBJECT-TYPE
      SYNTAX  Counter
      ACCESS  read-only
      STATUS  mandatory
      DESCRIPTION
         "The TCP tossed retransmit packet count in the partition"
      ::= { partitionEntry 9 }

   partitionCirFails OBJECT-TYPE
      SYNTAX  Counter
      ACCESS  read-only
      STATUS  mandatory
      DESCRIPTION
	 "The count of CIR fail events in the partition."
      ::= { partitionEntry 10 }

   partitionCirAllocs OBJECT-TYPE
      SYNTAX  Counter
      ACCESS  read-only
      STATUS  mandatory
      DESCRIPTION
         "The count of CIR alloc events in the partition."
      ::= { partitionEntry 11 }

   partitionEirAllocs OBJECT-TYPE
      SYNTAX  Counter
      ACCESS  read-only
      STATUS  mandatory
      DESCRIPTION
         "The count of EIR alloc events in the partition. This
		  variable is obsolete and should not be used."
      ::= { partitionEntry 12 }

   partitionPeakTcpConns OBJECT-TYPE
      SYNTAX  Gauge
      ACCESS  read-only
      STATUS  mandatory
      DESCRIPTION
         "The peak no. of active TCP flows in the partition."
      ::= { partitionEntry 13 }

   partitionTcpConnInits OBJECT-TYPE
      SYNTAX  Counter
      ACCESS  read-only
      STATUS  mandatory
      DESCRIPTION
         "The count of TCP flows started in the partition."
      ::= { partitionEntry 14 }

   partitionTcpConnExits OBJECT-TYPE
      SYNTAX  Counter
      ACCESS  read-only
      STATUS  mandatory
      DESCRIPTION
         "The count of TCP flows exited in the partition."
      ::= { partitionEntry 15 }

   partitionTcpConnRefuses OBJECT-TYPE
      SYNTAX  Counter
      ACCESS  read-only
      STATUS  mandatory
      DESCRIPTION
         "The count of TCP flows exited by TCP refuse in the partition."
      ::= { partitionEntry 16 }

   partitionTcpConnIgnores OBJECT-TYPE
      SYNTAX  Counter
      ACCESS  read-only
      STATUS  mandatory
      DESCRIPTION
         "The count of TCP flows exited by being ignored in the partition."
      ::= { partitionEntry 17 }

   partitionTcpConnAborts OBJECT-TYPE
      SYNTAX  Counter
      ACCESS  read-only
      STATUS  mandatory
      DESCRIPTION
         "The count of TCP flows aborted in the partition."
      ::= { partitionEntry 18 }

   partitionTcpConnDenies OBJECT-TYPE
      SYNTAX  Counter
      ACCESS  read-only
      STATUS  mandatory
      DESCRIPTION
         "The count of TCP flows denied by CIR fail in the partition."
      ::= { partitionEntry 19 }

   partitionTcpConnTimeouts OBJECT-TYPE
      SYNTAX  Counter
      ACCESS  read-only
      STATUS  deprecated
      DESCRIPTION
         "The count of TCP flows timed out by pshaper in the partition.   This
	  variable is obsolete and should not be used."
      ::= { partitionEntry 20 }


   partitionPeakUdpConns OBJECT-TYPE
      SYNTAX  Gauge
      ACCESS  read-only
      STATUS  deprecated
      DESCRIPTION
         "The peak no. of active UDP flows in the partition.  This variable
          is deprecated, and should no longer be used."
      ::= { partitionEntry 21 }

   partitionUdpConnInits OBJECT-TYPE
      SYNTAX  Counter
      ACCESS  read-only
      STATUS  deprecated
      DESCRIPTION
         "The count of UDP flows started in the partition.  This variable
          is deprecated, and should no longer be used."
      ::= { partitionEntry 22 }

   partitionUdpConnExits OBJECT-TYPE
      SYNTAX  Counter
      ACCESS  read-only
      STATUS  deprecated
      DESCRIPTION
         "The count of UDP flows exited in the partition.  This variable
          is deprecated, and should no longer be used."
      ::= { partitionEntry 23 }

   partitionMinimumBps OBJECT-TYPE
      SYNTAX  INTEGER
      ACCESS  read-only
      STATUS  mandatory
      DESCRIPTION
         "The minimum size in bps of the partition."
      ::= { partitionEntry 24 }

   partitionBurstLimit OBJECT-TYPE
      SYNTAX  INTEGER
      ACCESS  read-only
      STATUS  mandatory
      DESCRIPTION
         "The partition burst limit in bps."
      ::= { partitionEntry 25 }

   partitionRate OBJECT-TYPE
      SYNTAX  Gauge
      ACCESS  read-only
      STATUS  mandatory
      DESCRIPTION
         "The peak total rate in bps of the partition."
      ::= { partitionEntry 26 }

   partitionCirRate OBJECT-TYPE
      SYNTAX  Gauge
      ACCESS  read-only
      STATUS  mandatory
      DESCRIPTION
         "The peak guaranteed rate in bps of the partition. This
		  variable is obsolete and should not be used."
      ::= { partitionEntry 27 }

   partitionEirRate OBJECT-TYPE
      SYNTAX  Gauge
      ACCESS  read-only
      STATUS  mandatory
      DESCRIPTION
         "The peak excess rate in bps of the partition. This
		  variable is obsolete and should note be used."
      ::= { partitionEntry 28 }

   partitionUnreservedRate OBJECT-TYPE
      SYNTAX  Gauge
      ACCESS  read-only
      STATUS  mandatory
      DESCRIPTION
         "The peak unreserved rate in bps of the partition. This
		  variable is obsolete and should not be used."
      ::= { partitionEntry 29 }

   partitionFirstSatisfiedPriority OBJECT-TYPE
      SYNTAX  Gauge
      ACCESS  read-only
      STATUS  mandatory
      DESCRIPTION
         "The peak first priority level at which demand was satisfied (0-8)."
      ::= { partitionEntry 30 }

   partitionTimeOverLimit OBJECT-TYPE
      SYNTAX  Counter
      ACCESS  read-only
      STATUS  mandatory
      DESCRIPTION
         "The total time in seconds spent over partition
	  size for the partition"
      ::= { partitionEntry 31 }

   partitionRateAllocations OBJECT-TYPE
      SYNTAX  Counter
      ACCESS  read-only
      STATUS  mandatory
      DESCRIPTION
         "The count of rate allocations on the partition. This variable is
		  obsolete and should not be used."
      ::= { partitionEntry 32 }

   partitionPeakGuaranteedRateFlows OBJECT-TYPE
      SYNTAX  Gauge
      ACCESS  read-only
      STATUS  mandatory
      DESCRIPTION
         "The peak number of guaranteed rate flows active on the partition."
      ::= { partitionEntry 33 }

   partitionPeakRateFlows OBJECT-TYPE
      SYNTAX  Gauge
      ACCESS  read-only
      STATUS  mandatory
      DESCRIPTION
         "The peak number of rate-based flows active on the partition. This
		  variable is obsolete and should not be used."
      ::= { partitionEntry 34 }

   partitionReTxByteCount OBJECT-TYPE
      SYNTAX  Counter
      ACCESS  read-only
      STATUS  mandatory
      DESCRIPTION
         "The count of retransmitted bytes on the partition.  This is the
          low-order 32 bits."
      ::= { partitionEntry 35 }

   partitionReTxByteCountHi OBJECT-TYPE
      SYNTAX  Counter
      ACCESS  read-only
      STATUS  mandatory
      DESCRIPTION
         "The count of retransmitted bytes on the partition.  This is the
          high-order 32 bits."
      ::= { partitionEntry 36 }

   partitionDynamicCapCount OBJECT-TYPE
      SYNTAX  Counter
      ACCESS  read-only
      STATUS  mandatory
      DESCRIPTION
         "The count of dynamic partition reaching caps."
      ::= { partitionEntry 37 }

   partitionDynamicNoCount OBJECT-TYPE
      SYNTAX  Counter
      ACCESS  read-only
      STATUS  mandatory
      DESCRIPTION
         "The count of unavailable dynamic partition ."
      ::= { partitionEntry 38 }

   partitionDynamicLiveUserCount OBJECT-TYPE
      SYNTAX  Gauge
      ACCESS  read-only
      STATUS  mandatory
      DESCRIPTION
         "The count of total live dynamic partition user."
      ::= { partitionEntry 39 }

   partitionCommittmentFailures OBJECT-TYPE
      SYNTAX  Counter
      ACCESS  read-only
      STATUS  mandatory
      DESCRIPTION
         "The number of minute intervals that were not given the minimum programmed bandwidth."
      ::= { partitionEntry 40 }

   partitionLateDropPktCount OBJECT-TYPE
      SYNTAX  Gauge
      ACCESS  read-only
      STATUS  mandatory
      DESCRIPTION
         "The count of number of late drops in the partition.  This is the
          low-order 32 bits."
      ::= { partitionEntry 41 }

   partitionLateDropPktCountHi OBJECT-TYPE
      SYNTAX  Gauge
      ACCESS  read-only
      STATUS  mandatory
      DESCRIPTION
         "The count of number of late drops in the partition .  This is the
          high-order 32 bits."
      ::= { partitionEntry 42 }

    partitionLateDropByteCount OBJECT-TYPE
      SYNTAX  Gauge
      ACCESS  read-only
      STATUS  mandatory
      DESCRIPTION
         "The count of late drop bytes in the partition.  This is the
          low-order 32 bits."
      ::= { partitionEntry 43 }

   partitionLateDropByteCountHi OBJECT-TYPE
      SYNTAX  Gauge
      ACCESS  read-only
      STATUS  mandatory
      DESCRIPTION
         "The count of late drop bytes in the partition .  This is the
          high-order 32 bits."
      ::= { partitionEntry 44 }

   partitionSchedDropPktCount OBJECT-TYPE
      SYNTAX  Gauge
      ACCESS  read-only
      STATUS  mandatory
      DESCRIPTION
         "The count of number of scheduler drops in the partition.  This is the
          low-order 32 bits."
      ::= { partitionEntry 45 }

   partitionSchedDropPktCountHi OBJECT-TYPE
      SYNTAX  Gauge
      ACCESS  read-only
      STATUS  mandatory
      DESCRIPTION
         "The count of number of scheduler drops in the partition .  This is the
          high-order 32 bits."
      ::= { partitionEntry 46 }

   partitionSchedDropByteCount OBJECT-TYPE
      SYNTAX  Gauge
      ACCESS  read-only
      STATUS  mandatory
      DESCRIPTION
         "The count of scheduler drop bytes in the partition.  This is the
          low-order 32 bits."
      ::= { partitionEntry 47 }

   partitionSchedDropByteCountHi OBJECT-TYPE
      SYNTAX  Gauge
      ACCESS  read-only
      STATUS  mandatory
      DESCRIPTION
         "The count of scheduler drop bytes in the partition .  This is the
          high-order 32 bits."
      ::= { partitionEntry 48 }

   partitionFrameBytes OBJECT-TYPE
      SYNTAX  Counter
      ACCESS  read-only
      STATUS  mandatory
      DESCRIPTION
         "The number of PVC bytes in the partition.  This is the
          low-order 32 bits."
      ::= { partitionEntry 49 }

   partitionFrameBytesHi OBJECT-TYPE
      SYNTAX  Counter
      ACCESS  read-only
      STATUS  mandatory
      DESCRIPTION
         "The number of PVC bytes in the partition .  This is the
          high-order 32 bits."
      ::= { partitionEntry 50 }

   partitionFrameTargetRate OBJECT-TYPE
      SYNTAX  Gauge
      ACCESS  read-only
      STATUS  mandatory
      DESCRIPTION
         "The target frame rate in the partition.  This is the
          low-order 32 bits."
      ::= { partitionEntry 51 }

   partitionFrameTargetRateHi OBJECT-TYPE
      SYNTAX  Gauge
      ACCESS  read-only
      STATUS  mandatory
      DESCRIPTION
         "The target frame rate in the partition .  This is the
          high-order 32 bits."
      ::= { partitionEntry 52 }

   partitionFrameCount OBJECT-TYPE
      SYNTAX  Counter
      ACCESS  read-only
      STATUS  mandatory
      DESCRIPTION
         "The number of frames in the partition."
      ::= { partitionEntry 53 }

   partitionEcnCount OBJECT-TYPE
      SYNTAX  Counter
      ACCESS  read-only
      STATUS  mandatory
      DESCRIPTION
         "The number of ECNs in the partition."
      ::= { partitionEntry 54 }

   partitionNonComprsnBytes OBJECT-TYPE
      SYNTAX  Counter
      ACCESS  read-only
      STATUS  mandatory
      DESCRIPTION
         "The total number of non-compressed bytes in the partition."
      ::= { partitionEntry 55 }

   partitionNonComprsnBytesHi OBJECT-TYPE
      SYNTAX  Counter
      ACCESS  read-only
      STATUS  mandatory
      DESCRIPTION
         "The total number of non-compressed bytes in the partition. This is the high-order 32 bits."
      ::= { partitionEntry 56 }

   partitionPreComprsnBytes OBJECT-TYPE
      SYNTAX  Counter
      ACCESS  read-only
      STATUS  mandatory
      DESCRIPTION
         "The total number of bytes before compression in the partition."
      ::= { partitionEntry 57 }

   partitionPreComprsnBytesHi OBJECT-TYPE
      SYNTAX  Counter
      ACCESS  read-only
      STATUS  mandatory
      DESCRIPTION
         "The total number of bytes before compression in the partition. This is the high-order 32 bits."
      ::= { partitionEntry 58 }

   partitionPostComprsnBytes OBJECT-TYPE
      SYNTAX  Counter
      ACCESS  read-only
      STATUS  mandatory
      DESCRIPTION
         "The total number of bytes after compression in the partition."
      ::= { partitionEntry 59 }

   partitionPostComprsnBytesHi OBJECT-TYPE
      SYNTAX  Counter
      ACCESS  read-only
      STATUS  mandatory
      DESCRIPTION
         "The total number of bytes after compression in the partition. This is the high-order 32 bits."
      ::= { partitionEntry 60 }


   -- the Traffic Class group

   classTableSize OBJECT-TYPE
      SYNTAX   INTEGER
      ACCESS  read-only
      STATUS  mandatory
      DESCRIPTION
         "Number of entries in the classTable"
      ::= { psClasses 1 }

   classTable OBJECT-TYPE
      SYNTAX  SEQUENCE OF ClassEntry
      ACCESS  not-accessible
      STATUS  mandatory
      DESCRIPTION
         "A list of traffic class entries."
      ::= { psClasses 2 }

   classEntry OBJECT-TYPE
      SYNTAX  ClassEntry
      ACCESS  not-accessible
      STATUS  mandatory
      DESCRIPTION
         "A traffic class entry containing statistical objects
	  for a traffic class."
      INDEX   { classIndex }
      ::= { classTable 1 }

   ClassEntry ::=
      SEQUENCE {
	 classIndex
	    INTEGER,
         className
            DisplayString,
	 classOwningPartName
	    DisplayString,
	 classLinkDirection
	    INTEGER,
         classByteCount
            Counter,
         classByteCountHi
            Counter,
         classPkts
            Counter,
         classDataPkts
            Counter,
         classReTxs
            Counter,
         classReTxTosses
            Counter,
	 classCirFails
	    Counter,
	 classCirAllocs
	    Counter,
	 classEirAllocs
	    Counter,
	 classPeakTcpConns
	    Gauge,
         classTcpConnInits
            Counter,
         classTcpConnExits
            Counter,
         classTcpConnRefuses
            Counter,
         classTcpConnIgnores
            Counter,
         classTcpConnAborts
            Counter,
         classTcpConnDenies
            Counter,
         classTcpConnTimeouts
            Counter,
         classPeakUdpConns
            Gauge,
         classUdpConnInits
            Counter,
         classUdpConnExits
            Counter,
         classHits
            Counter,
         classPolicyHits
            Counter,
	 classRate
	    Gauge,
	 classRateAllocations
	    Gauge,
	 classPeakGuaranteedRateFlows
	    Gauge,
	 classPeakRateFlows
	    Gauge,
	 classDataDelayEvents
	    Counter,
	 classDataDelayTimeCum
	    INTEGER,
	 classReservedOne
	     Counter,
	 classReTxByteCount
	     Counter,
	 classReTxByteCountHi
             Counter,
         classFullName
             DisplayString,
         classCurrentRate
             Gauge,
         classPktExchangeTime
             Counter,
         classPktExchangeTimeHi
             Counter,
         classPktExchangeTimeSamples
             Counter,
	 classClientFloodBlock
	     Counter,
	 classServerFloodBlock
	     Counter,
	 classAppAvailability
             INTEGER,
	 classPeakIpdgConns
		Gauge,
 	 classWebResponse2XX
		Counter,
 	 classWebResponse3XX
		Counter,
 	 classWebResponse4XX
		Counter,
 	 classWebResponse5XX
                Counter,
         classNonComprsnBytes
                Counter,
         classNonComprsnBytesHi
                Counter,
         classPostComprsnBytes
                Counter,
         classPostComprsnBytesHi
                Counter,
         classPreComprsnBytes
                Counter,
         classPreComprsnBytesHi
                Counter
     }

   classIndex OBJECT-TYPE
      SYNTAX  INTEGER
      ACCESS  read-only
      STATUS  mandatory
      DESCRIPTION
         "A unique ID for a traffic class."
      ::= { classEntry 1 }

   className OBJECT-TYPE
      SYNTAX  DisplayString
      ACCESS  read-only
      STATUS  mandatory
      DESCRIPTION
         "A unique name for a traffic class."
      ::= { classEntry 2 }

   classOwningPartName OBJECT-TYPE
      SYNTAX  DisplayString
      ACCESS  read-only
      STATUS  mandatory
      DESCRIPTION
         "A unique name for the partition which owns the class."
      ::= { classEntry 3 }

   classLinkDirection OBJECT-TYPE
      SYNTAX  INTEGER {
	in-bound(1),
	out-bound(2)
              }
      ACCESS  read-only
      STATUS  mandatory
      DESCRIPTION
         "The orientation of the class."
      ::= { classEntry 4 }

   classByteCount OBJECT-TYPE
      SYNTAX  Counter
      ACCESS  read-only
      STATUS  mandatory
      DESCRIPTION
         "The byte count in the class."
      ::= { classEntry 5 }

   classByteCountHi OBJECT-TYPE
      SYNTAX  Counter
      ACCESS  read-only
      STATUS  mandatory
      DESCRIPTION
         "The High 32 bits of byte count in the class."
      ::= { classEntry 6 }

   classPkts OBJECT-TYPE
      SYNTAX  Counter
      ACCESS  read-only
      STATUS  mandatory
      DESCRIPTION
         "The packet count in the class."
      ::= { classEntry 7 }

   classDataPkts OBJECT-TYPE
      SYNTAX  Counter
      ACCESS  read-only
      STATUS  mandatory
      DESCRIPTION
         "The TCP data packet count in the class."
      ::= { classEntry 8 }

   classReTxs OBJECT-TYPE
      SYNTAX  Counter
      ACCESS  read-only
      STATUS  mandatory
      DESCRIPTION
         "The TCP retransmit packet count in the class."
      ::= { classEntry 9 }

   classReTxTosses OBJECT-TYPE
      SYNTAX  Counter
      ACCESS  read-only
      STATUS  mandatory
      DESCRIPTION
         "The TCP tossed retransmit packet count in the class."
      ::= { classEntry 10 }

   classCirFails OBJECT-TYPE
      SYNTAX  Counter
      ACCESS  read-only
      STATUS  mandatory
      DESCRIPTION
         "The count of CIR fails events in the class."
      ::= { classEntry 11 }

   classCirAllocs OBJECT-TYPE
      SYNTAX  Counter
      ACCESS  read-only
      STATUS  mandatory
      DESCRIPTION
         "The count of CIR alloc events in the class."
      ::= { classEntry 12 }

   classEirAllocs OBJECT-TYPE
      SYNTAX  Counter
      ACCESS  read-only
      STATUS  mandatory
      DESCRIPTION
         "The count of EIR alloc events in the class. This
		  variable is obsolete and should not be used."
      ::= { classEntry 13 }

   classPeakTcpConns OBJECT-TYPE
      SYNTAX  Gauge
      ACCESS  read-only
      STATUS  mandatory
      DESCRIPTION
         "The peak number of active TCP flows in the class."
      ::= { classEntry 14 }

   classTcpConnInits OBJECT-TYPE
      SYNTAX  Counter
      ACCESS  read-only
      STATUS  mandatory
      DESCRIPTION
         "The count of TCP flows started in the class."
      ::= { classEntry 15 }

   classTcpConnExits OBJECT-TYPE
      SYNTAX  Counter
      ACCESS  read-only
      STATUS  mandatory
      DESCRIPTION
         "The count of TCP flows exited in the class."
      ::= { classEntry 16 }

   classTcpConnRefuses OBJECT-TYPE
      SYNTAX  Counter
      ACCESS  read-only
      STATUS  mandatory
      DESCRIPTION
         "The count of TCP flows exited by TCP refuse in the class."
      ::= { classEntry 17 }

   classTcpConnIgnores OBJECT-TYPE
      SYNTAX  Counter
      ACCESS  read-only
      STATUS  mandatory
      DESCRIPTION
         "The count of TCP flows exited by being ignored in the class."
      ::= { classEntry 18 }

   classTcpConnAborts OBJECT-TYPE
      SYNTAX  Counter
      ACCESS  read-only
      STATUS  mandatory
      DESCRIPTION
         "The count of TCP flows aborted in the class."
      ::= { classEntry 19 }

   classTcpConnDenies OBJECT-TYPE
      SYNTAX  Counter
      ACCESS  read-only
      STATUS  mandatory
      DESCRIPTION
         "The count of TCP flows denied by CIR fail in the class."
      ::= { classEntry 20 }

   classTcpConnTimeouts OBJECT-TYPE
      SYNTAX  Counter
      ACCESS  read-only
      STATUS  deprecated
      DESCRIPTION
         "The count of TCP flows timed out by pshaper in the class.  This
	  variable is obsolete and should not be used."
      ::= { classEntry 21 }


   classPeakUdpConns OBJECT-TYPE
      SYNTAX  Gauge
      ACCESS  read-only
      STATUS  deprecated
      DESCRIPTION
         "The peak number of active UDP flows in the class.  This variable
          is deprecated, and should no longer be used."
      ::= { classEntry 22 }

   classUdpConnInits OBJECT-TYPE
      SYNTAX  Counter
      ACCESS  read-only
      STATUS  deprecated
      DESCRIPTION
         "The count of UDP flows started in the class.  This variable
          is deprecated, and should no longer be used."
      ::= { classEntry 23 }

   classUdpConnExits OBJECT-TYPE
      SYNTAX  Counter
      ACCESS  read-only
      STATUS  deprecated
      DESCRIPTION
         "The count of UDP flows exited in the class.  This variable
          is deprecated, and should no longer be used."
      ::= { classEntry 24 }

   classHits OBJECT-TYPE
      SYNTAX  Counter
      ACCESS  read-only
      STATUS  mandatory
      DESCRIPTION
         "Count of hits in the class"
      ::= { classEntry 25 }

   classPolicyHits OBJECT-TYPE
      SYNTAX  Counter
      ACCESS  read-only
      STATUS  mandatory
      DESCRIPTION
         "Count of policy hits in the class"
      ::= { classEntry 26 }

   classRate OBJECT-TYPE
      SYNTAX  Gauge
      ACCESS  read-only
      STATUS  mandatory
      DESCRIPTION
         "The peak total rate in bps of the class"
      ::= { classEntry 27 }

   classRateAllocations OBJECT-TYPE
      SYNTAX  Gauge
      ACCESS  read-only
      STATUS  mandatory
      DESCRIPTION
         "The count of rate allocations on the class. This variable is
		  obsolete and should not be used."
      ::= { classEntry 28 }

   classPeakGuaranteedRateFlows OBJECT-TYPE
      SYNTAX  Gauge
      ACCESS  read-only
      STATUS  mandatory
      DESCRIPTION
         "The peak number of guaranteed rate flows active on the class."
      ::= { classEntry 29 }

   classPeakRateFlows OBJECT-TYPE
      SYNTAX  Gauge
      ACCESS  read-only
      STATUS  mandatory
      DESCRIPTION
         "The peak number of rate-based flows active on the class. This
		  variable is obsolete and should not be used."
      ::= { classEntry 30 }

   classDataDelayEvents OBJECT-TYPE
      SYNTAX  Counter
      ACCESS  read-only
      STATUS  deprecated
      DESCRIPTION
         "The total number of data delay events measured for the class.

	  ** This variable is no longer used.  Consult PacketeerRTM.mib for
	  current response-time management variables."
      ::= { classEntry 31 }

   classDataDelayTimeCum OBJECT-TYPE
      SYNTAX  INTEGER
      ACCESS  read-only
      STATUS  deprecated
      DESCRIPTION
         "The cumulative data delay time in milliseconds measured for the class.
          classDataDelayTimeCum divided by classDataDelayEvents provides
	  an indication of average response time for the class.  (However,
          classDataDelayEvents MAY be zero, so you must check for that).

	  ** This variable is no longer used.  Consult PacketeerRTM.mib for
	  current response-time management variables."
      ::= { classEntry 32 }

   classReservedOne OBJECT-TYPE
      SYNTAX  Counter
      ACCESS  read-only
      STATUS  mandatory
      DESCRIPTION
         "This variable is for experimental use only."
      ::= { classEntry 33 }

   classReTxByteCount OBJECT-TYPE
      SYNTAX  Counter
      ACCESS  read-only
      STATUS  mandatory
      DESCRIPTION
         "The count of retransmitted bytes on the class.  This is the low-order
          32 bits."
      ::= { classEntry 34 }

   classReTxByteCountHi OBJECT-TYPE
      SYNTAX  Counter
      ACCESS  read-only
      STATUS  mandatory
      DESCRIPTION
         "The count of retransmitted bytes on the class.  This is the high-order
          32 bits."
      ::= { classEntry 35 }

   classFullName OBJECT-TYPE
      SYNTAX  DisplayString
      ACCESS  read-only
      STATUS  mandatory
      DESCRIPTION
         "The complete name of the class, e.g. /Inbound/Inside/HTTP.
          Note that the className variable gives only the last part,
          in this example HTTP."
      ::= { classEntry 36 }

   classCurrentRate OBJECT-TYPE
      SYNTAX  Gauge
      ACCESS  read-only
      STATUS  mandatory
      DESCRIPTION
         "The current rate in bits per second."
      ::= { classEntry 37 }

   classPktExchangeTime OBJECT-TYPE
      SYNTAX  Counter
      ACCESS  read-only
      STATUS  mandatory
      DESCRIPTION
         "(PacketShaper only).  The packet exchange time for TCP
          data packets, between PacketShaper and the server side.
          This is the low-order 32 bits."
      ::= { classEntry 38 }

   classPktExchangeTimeHi OBJECT-TYPE
      SYNTAX  Counter
      ACCESS  read-only
      STATUS  mandatory
      DESCRIPTION
         "(PacketShaper only).  The packet exchange time for TCP
          data packets, between PacketShaper and the server side.
          This is the high-order 32 bits."
      ::= { classEntry 39 }

   classPktExchangeTimeSamples OBJECT-TYPE
      SYNTAX  Counter
      ACCESS  read-only
      STATUS  mandatory
      DESCRIPTION
         "(PacketShaper only).  The total number of packet exchanges
         counted for the classPktExchangeTime /
         classPktExchangeTimeHi number."
      ::= { classEntry 40}

   classClientFloodBlock OBJECT-TYPE
      SYNTAX  Counter
      ACCESS  read-only
      STATUS  mandatory
      DESCRIPTION
         "The total number of client side SYN flood attacks blocked."
      ::= { classEntry 41}

   classServerFloodBlock OBJECT-TYPE
      SYNTAX  Counter
      ACCESS  read-only
      STATUS  mandatory
      DESCRIPTION
         "The total number of server side SYN flood attacks blocked."
      ::= { classEntry 42}

   classAppAvailability OBJECT-TYPE
      SYNTAX  INTEGER
      ACCESS  read-only
      STATUS  deprecated
      DESCRIPTION
         "The cumulative average application availability."
      ::= { classEntry 43 }

   classPeakIpdgConns OBJECT-TYPE
      SYNTAX  Gauge
      ACCESS  read-only
      STATUS  mandatory
      DESCRIPTION
         "The peak number of active IPDG flows in the class."
      ::= { classEntry 47 }

   classWebResponse2XX OBJECT-TYPE
      SYNTAX  Counter
      ACCESS  read-only
      STATUS  mandatory
      DESCRIPTION
         "The count of HTTP response messages having 2XX status codes (successful)."
      ::= { classEntry 48 }

   classWebResponse3XX OBJECT-TYPE
      SYNTAX  Counter
      ACCESS  read-only
      STATUS  mandatory
      DESCRIPTION
         "The count of HTTP response messages having 3XX status codes (redirection)."
      ::= { classEntry 49 }

   classWebResponse4XX OBJECT-TYPE
      SYNTAX  Counter
      ACCESS  read-only
      STATUS  mandatory
      DESCRIPTION
         "The count of HTTP response messages having 4XX status codes (client error)."
      ::= { classEntry 50 }

   classWebResponse5XX OBJECT-TYPE
      SYNTAX  Counter
      ACCESS  read-only
      STATUS  mandatory
      DESCRIPTION
         "The count of HTTP response messages having 5XX status codes (server error)."
      ::= { classEntry 51 }

   classNonComprsnBytes OBJECT-TYPE
      SYNTAX  Counter
      ACCESS  read-only
      STATUS  mandatory
      DESCRIPTION
         "The total number of non-compressed bytes in the class."
      ::= { classEntry 52 }

   classNonComprsnBytesHi OBJECT-TYPE
      SYNTAX  Counter
      ACCESS  read-only
      STATUS  mandatory
      DESCRIPTION
         "The total number of non-compressed bytes in the class. This is the high-order 32 bits."
      ::= { classEntry 53 }

   classPreComprsnBytes OBJECT-TYPE
      SYNTAX  Counter
      ACCESS  read-only
      STATUS  mandatory
      DESCRIPTION
         "The total number of bytes before compression in the class."
      ::= { classEntry 54 }

   classPreComprsnBytesHi OBJECT-TYPE
      SYNTAX  Counter
      ACCESS  read-only
      STATUS  mandatory
      DESCRIPTION
         "The total number of bytes before compression in the class. This is the high-order 32 bits."
      ::= { classEntry 58 }

   classPostComprsnBytes OBJECT-TYPE
      SYNTAX  Counter
      ACCESS  read-only
      STATUS  mandatory
      DESCRIPTION
         "The total number of bytes after compression in the class."
      ::= { classEntry 55 }

   classPostComprsnBytesHi OBJECT-TYPE
      SYNTAX  Counter
      ACCESS  read-only
      STATUS  mandatory
      DESCRIPTION
         "The total number of bytes after compression in the class. This is the high-order 32 bits."
      ::= { classEntry 56 }


  -- the psAlarms group.  In each case, a trap is paired with a variable
  -- Since traps are unreliable, managers should also poll the relevant
  -- variable.

   -- traps for InsideLink and OutsideLink do not exist here, since the MIB-II
   -- LinkDown traps are used instead.

   psAlarmInsideLinkCount    OBJECT-TYPE
      SYNTAX  Counter
      ACCESS   read-only
      STATUS   mandatory
      DESCRIPTION
	  "The number of MIB-II LinkDown traps sent by
	   the agent since the last reset, where ifIndex
           was for the Inside link."
      ::= { psAlarms 1}

   psAlarmOutsideLinkCount    OBJECT-TYPE
      SYNTAX  Counter
      ACCESS   read-only
      STATUS   mandatory
      DESCRIPTION
	  "The number of MIB-II LinkDown traps sent by
	   the agent since the last reset, where ifIndex
           was for the Outside link. "
      ::= { psAlarms 3 }


   psAlarmSiteRouterCount    OBJECT-TYPE
      SYNTAX  Counter
      ACCESS   read-only
      STATUS   mandatory
      DESCRIPTION
	  "The number of psAlarmSiteRouter traps sent by
	   the agent since the last reset."
      ::= { psAlarms 5 }


   psAlarmSiteRouterStatus OBJECT-TYPE
      SYNTAX   INTEGER  {
	ready(1),
	gone(2),
	error-inside(3),
	none(4)
	}
      ACCESS  read-only
      STATUS  mandatory
      DESCRIPTION
         "Status of the site router.  A status of gone(2) means that PacketShaper
          has stopped getting arp replies from the router.  error-inside(3)
          means that it most recently got a reply, but from the inside.  none(4)
	  means that no site router was configured."
      ::= { psAlarms 6 }

   psAlarmSiteRouter TRAP-TYPE
      ENTERPRISE packetShaper
      VARIABLES { psAlarmSiteRouterStatus }
      DESCRIPTION
      "A psSiteRouter trap signifies that the site router
       attached to the device has changed to a state of less
       readiness.  The psAlarmSiteRouterStatus variable included with
       this trap provides more information."
      ::= 3


    psAlarmPowerSystemOne TRAP-TYPE
      ENTERPRISE packetShaper
      DESCRIPTION
      "A psPowerSystemOne trap signifies that the first power
       supply of the device has failed."
      ::= 4

   psAlarmPowerSystemOneCount    OBJECT-TYPE
      SYNTAX  Counter
      ACCESS   read-only
      STATUS   mandatory
      DESCRIPTION
	  "The number of psAlarmPowerSystemOne traps sent by
	   the agent since the last reset."
      ::= { psAlarms 7 }

   psAlarmPowerSystemOneStatus OBJECT-TYPE
      SYNTAX   INTEGER  {
	ok(1),
	not-ok(2)
	}
      ACCESS  read-only
      STATUS  mandatory
      DESCRIPTION
         "The operational status of the first power system
         of the device.
         (1) UP
         (2) DOWN"
      ::= { psAlarms 8 }


    psAlarmPowerSystemTwo TRAP-TYPE
      ENTERPRISE packetShaper
      DESCRIPTION
      "A psSitePowerSystemTwo trap signifies that
      the second power supply of the device has failed."
      ::= 5

   psAlarmPowerSystemTwoCount    OBJECT-TYPE
      SYNTAX  Counter
      ACCESS   read-only
      STATUS   mandatory
      DESCRIPTION
	  "The number of psAlarmPowerSystemTwo traps sent by
	   the agent since the last reset."
      ::= { psAlarms 9 }

   psAlarmPowerSystemTwoStatus OBJECT-TYPE
      SYNTAX   INTEGER  {
	ok(1),
	not-ok(2)
	}
      ACCESS  read-only
      STATUS  mandatory
      DESCRIPTION
         "The operational status of the second power supply
         of the device.
         (1) UP
         (2) DOWN"
      ::= { psAlarms 10 }

    psAlarmFanOne TRAP-TYPE
      ENTERPRISE packetShaper
      DESCRIPTION
      "A psFanOne trap signifies that the first fan
      of the device has failed."
      ::= 6

   psAlarmFanOneCount    OBJECT-TYPE
      SYNTAX  Counter
      ACCESS   read-only
      STATUS   mandatory
      DESCRIPTION
	  "The number of psAlarmFanOne traps sent by
	   the agent since the last reset."
      ::= { psAlarms 11 }


   psAlarmFanOneStatus OBJECT-TYPE
      SYNTAX   INTEGER  {
	non-existant(0),
	ok(1),
	not-ok(2)
	}
      ACCESS  read-only
      STATUS  mandatory
      DESCRIPTION
         "The operational status of the first fan of the device.
		(0) Not existant
		(1) UP
		(2) DOWN"
      ::= { psAlarms 12 }

    psAlarmFanTwo TRAP-TYPE
      ENTERPRISE packetShaper
      DESCRIPTION
      "A psAlarmFanTwo trap signifies that second fan
      of the device has failed."
      ::= 7

   psAlarmFanTwoCount    OBJECT-TYPE
      SYNTAX  Counter
      ACCESS   read-only
      STATUS   mandatory
      DESCRIPTION
	  "The number of psAlarmFanTwo traps sent by
	   the agent since the last reset."
      ::= { psAlarms 13 }


   psAlarmFanTwoStatus OBJECT-TYPE
      SYNTAX   INTEGER  {
	non-existant(0),
	ok(1),
	not-ok(2)
	}
      ACCESS  read-only
      STATUS  mandatory
      DESCRIPTION
         "The operational status of the second fan of the device.
		(0) Not existant
		(1) UP
		(2) DOWN"
      ::= { psAlarms 14 }

   psAlarmCfgFile TRAP-TYPE
      ENTERPRISE packetShaper
      DESCRIPTION
      "A psAlarmCfgFile trap signifies that the configuration
      file of the device has been corrupted, or otherwise changed
      to a state of less readiness. This trap is obsolete and
      should not be used."
      ::= 8

   psAlarmCfgFileCount    OBJECT-TYPE
      SYNTAX  Counter
      ACCESS   read-only
      STATUS   mandatory
      DESCRIPTION
	  "The number of psAlarmCfgFile traps sent by
	   the agent since the last reset. This variable is obsolete
       and should not be used."
      ::= { psAlarms 15 }


   psAlarmCfgFileStatus	OBJECT-TYPE
      SYNTAX   INTEGER  {
	valid(1),
	corrupted(2)
	}
      ACCESS  read-only
      STATUS  mandatory
      DESCRIPTION
         "Whether the configuration file has been corrupted.  A value
	  of valid(1) signifies no problems, corrupted(2) that the
	  configuration file has been corrupted. "
      ::= { psAlarms 16 }

   psAlarmMeasurementEngineCount    OBJECT-TYPE
      SYNTAX  Counter
      ACCESS   read-only
      STATUS   mandatory
      DESCRIPTION
          "The number of psAlarmMeasurementEngine traps sent by
	   the agent since the last reset."
      ::= { psAlarms 17 }

   psAlarmMeasurementEngineStatus OBJECT-TYPE
      SYNTAX   INTEGER  {
		initiallyStarting(1),
		starting(2),
		running(3),
		errorOnVolume(4),
		disabled(5),
		waitToStart(6),
		suspended(7),
                backup(8),
                restore(9)
	}
      ACCESS  read-only
      STATUS  mandatory
      DESCRIPTION
         "The current status of the Measurement Engine.  The values
          enumerated above correspond to those shown in the command
          line 'me show' command.
          (1) initially starting
          (2) starting
          (3) running
          (4) error on volume
          (5) disabled
	  (6) wait to start
	  (7) suspended
	  (8) backing up data
	  (9) restoring data"
      ::= { psAlarms 18 }

   psAlarmMeasurementEngine TRAP-TYPE
      ENTERPRISE packetShaper
      VARIABLES { psAlarmMeasurementEngineStatus }
      DESCRIPTION
      "A psAlarmMeasurementEngine trap signifies that the Measurement
       Engine has changed to a state of less readiness, or failed on
       startup. "
      ::= 10

   psAlarmStandbyCount    OBJECT-TYPE
      SYNTAX  Counter
      ACCESS   read-only
      STATUS   mandatory
      DESCRIPTION
	  "The number of psAlarmStandby traps sent by
	   the agent since the last reset."
      ::= { psAlarms 19 }

   psAlarmStandbyStatus OBJECT-TYPE
      SYNTAX   INTEGER  {
	not-configured(1),
	active(2),
	passive(3),
	down(4),
	direct(5),
	disconnected(6),
	leak(7),
	disable(8)
	}
      ACCESS  read-only
      STATUS  mandatory
      DESCRIPTION
         "Status of the standby feature.  A status of not-configured(1) means that
          standby is not configured for this PacketShaper.  active(2) means hot standby is
		  processing traffic according to its shaping mode.  passive(3) means hot standby
		  is not processing traffic but is monitoring the active partner of the paired
		  PacketShapers.  down(4) means hot standby has declared itself ineligible for
		  active mode due to a self-detected fault. direct(5) means standby direct is
		  processing and copying traffic to its partner. disconnected(6) means standby
		  direct is non-functional since it cannot reach its partner. leak(7) means the
		  Packetshaper has detected a loop in the network and so has disabled the stanby
		  direct functionality and is only processing traffic flowing through it. disable(8)
		  means that the standby direct feature has been disabled and is non-functional."
      ::= { psAlarms 20 }

   psAlarmStandby TRAP-TYPE
      ENTERPRISE packetShaper
      VARIABLES { psAlarmStandbyStatus }
      DESCRIPTION
      	"A psAlarmStandby trap signifies that the standby
      	status of the device has changed to a state of less
      	readiness.  The psAlarmStandbyStatus variable included with
      	this trap provides more information."
      ::= 11

    psAlarmFanThree TRAP-TYPE
      ENTERPRISE packetShaper
      DESCRIPTION
      "A psAlarmFanThree trap signifies that 3rd fan
      of the device has failed."
      ::= 14

   psAlarmFanThreeCount    OBJECT-TYPE
      SYNTAX  Counter
      ACCESS   read-only
      STATUS   mandatory
      DESCRIPTION
	  "The number of psAlarmFanThree traps sent by
	   the agent since the last reset."
      ::= { psAlarms 21 }


   psAlarmFanThreeStatus OBJECT-TYPE
      SYNTAX   INTEGER  {
	non-existant(0),
	ok(1),
	not-ok(2)
	}
      ACCESS  read-only
      STATUS  mandatory
      DESCRIPTION
         "The operational status of the 3rd fan of the device.
		(0) Not existant
		(1) UP
		(2) DOWN"
      ::= { psAlarms 22 }

    psAlarmFanFour TRAP-TYPE
      ENTERPRISE packetShaper
      DESCRIPTION
      "A psAlarmFanFour trap signifies that 4th fan
      of the device has failed."
      ::= 15

   psAlarmFanFourCount    OBJECT-TYPE
      SYNTAX  Counter
      ACCESS   read-only
      STATUS   mandatory
      DESCRIPTION
	  "The number of psAlarmFanFour traps sent by
	   the agent since the last reset."
      ::= { psAlarms 23 }


   psAlarmFanFourStatus OBJECT-TYPE
      SYNTAX   INTEGER  {
	non-existant(0),
	ok(1),
	not-ok(2)
	}
      ACCESS  read-only
      STATUS  mandatory
      DESCRIPTION
         "The operational status of the 4th fan of the device.
		(0) Not existant
		(1) UP
		(2) DOWN"
      ::= { psAlarms 24}
   -- the Admin group
   trapDestTable OBJECT-TYPE
      SYNTAX SEQUENCE OF TrapDestEntry
      ACCESS not-accessible
      STATUS mandatory
      DESCRIPTION
	 "A list of destinations for traps emitted from this PacketShaper"
      ::= { psAdmin  1 }

   trapDestEntry OBJECT-TYPE
      SYNTAX TrapDestEntry
      ACCESS not-accessible
      STATUS mandatory
      DESCRIPTION
	 "A trap destination entry containing the IP address (and possibly
          other information in the future)"
      INDEX  { trapDestIpAddr }
      ::= { trapDestTable 1 }

   TrapDestEntry ::=
      SEQUENCE {
  	 trapDestIpAddr
	     IpAddress,

	 trapDestStatus
	     INTEGER
      }

   trapDestIpAddr OBJECT-TYPE
      SYNTAX IpAddress
      ACCESS read-only
      STATUS mandatory
      DESCRIPTION
	 "An address to which traps are sent"
      ::= {trapDestEntry 1}

   trapDestStatus OBJECT-TYPE
      SYNTAX INTEGER {
	      valid(1),
	      invalid(2)
      }
      ACCESS read-write
      STATUS mandatory
      DESCRIPTION
	 "Status of this trap destination.  Setting to invalid(2) is equivalent
          to removing the address from the table.
          See also trapDestRemove for a shortcut for removal."
      ::= { trapDestEntry 2 }

   trapDestAdd OBJECT-TYPE
      SYNTAX DisplayString
      ACCESS write-only
      STATUS mandatory
      DESCRIPTION
	 "A shortcut for adding a host to trapDestTable.  If the name is not
	  in n.n.n.n IP address form, then the agent attempts to look it up
	  via DNS.  If the operation fails with BADVALUE, try again with
	  an IP address.  The associated
	  IP address is added to the trapDestTable if the operation succeeded.
          The table should be queried afterward to
          insure that the action took place.  "
      ::= { psAdmin 2}

   trapDestRemove OBJECT-TYPE
      SYNTAX DisplayString
      ACCESS write-only
      STATUS mandatory
      DESCRIPTION
	 "A shortcut for removing an IP address from trapDestTable.
	  If the name is not
	  in n.n.n.n IP address form, then the agent attempts to look it up
	  via DNS.  If the operation fails with BADVALUE, try again with
	  an IP address.  The table should be queried
          afterward to insure that the action took place."
      ::= { psAdmin 3}

   psShapingStatusAdmin OBJECT-TYPE
      SYNTAX   INTEGER  { on(1), off(2), bypass(3), other(4), watch(5) }
      ACCESS  read-write
      STATUS  mandatory
      DESCRIPTION
         "This object reflects the current configured traffic shaping status
          of the PacketShaper.  The value of other(4) may occur in certain
	  cases which can only be caused through the PacketShaper's user
	  interface, and cannot be set through this variable   "
      ::= { psAdmin 4 }

   -- the User Events group

   psUserEventTrapVars      OBJECT IDENTIFIER ::= { psUserEvents 1 }

   --  The variables described here are strictly for use as VarBinds
   --  in the 'trapUserEvent' trap.  In SNMPv2 syntax as in RFC 1902,
   --  they would have a MAX-ACCESS value of "accessible-for-notify"
   --  since that captures exactly what is intended.
   --  As this is V1 syntax, they're "not-accessible" instead.



   userEventTrapName OBJECT-TYPE
      SYNTAX  DisplayString
      ACCESS  not-accessible
      STATUS  mandatory
      DESCRIPTION
         "The name of the user event which has occurred."
      ::= { psUserEventTrapVars 1 }

   userEventTrapExpression OBJECT-TYPE
      SYNTAX  DisplayString
      ACCESS  not-accessible
      STATUS  mandatory
      DESCRIPTION
         "The expression defining this user event."
      ::= { psUserEventTrapVars 2 }

   userEventTrapVariable OBJECT-TYPE
      SYNTAX  DisplayString
      ACCESS  not-accessible
      STATUS  mandatory
      DESCRIPTION
         "The name of the Measurement Engine variable which is
          tested in this user event."
      ::= { psUserEventTrapVars 3 }

   userEventTrapElementType OBJECT-TYPE
      SYNTAX  INTEGER { link(1), class(2), partition(3)}
      ACCESS  not-accessible
      STATUS  mandatory
      DESCRIPTION
         "The type of element which is tested in this user event."
      ::= { psUserEventTrapVars 4 }

   userEventTrapRegid OBJECT-TYPE
      SYNTAX  INTEGER
      ACCESS  not-accessible
      STATUS  mandatory
      DESCRIPTION
         "The registration of this user event."
      ::= { psUserEventTrapVars 5 }

   userEventTrapDate OBJECT-TYPE
      SYNTAX  DateAndTime
      ACCESS  not-accessible
      STATUS  mandatory
      DESCRIPTION
         "The time the event occurred."
      ::= { psUserEventTrapVars 6 }

   userEventTrapValue OBJECT-TYPE
      SYNTAX  INTEGER
      ACCESS  not-accessible
      STATUS  mandatory
      DESCRIPTION
         "The value of userEventTrapVariable which triggered the event."
      ::= { psUserEventTrapVars 7 }

   userEventTrapTarget OBJECT-TYPE
      SYNTAX  DisplayString
      ACCESS  not-accessible
      STATUS  mandatory
      DESCRIPTION
         "The name of the link, class, or partition,
          as given in userEventTrapElementType, which is
          the target of this event regiatration."
      ::= { psUserEventTrapVars 8 }

   userEventTrapThreshold OBJECT-TYPE
      SYNTAX  INTEGER
      ACCESS  not-accessible
      STATUS  mandatory
      DESCRIPTION
         "The threshold value which triggers this event.
		  See the value of userEventTrapExpression
		  for the signedness with respect to the threshold (<, >, etc.)"
      ::= { psUserEventTrapVars 9 }

   userEventTrapRearm OBJECT-TYPE
      SYNTAX  INTEGER
      ACCESS  not-accessible
      STATUS  mandatory
      DESCRIPTION
         "The rearm value which must be hit after an occurrence
          of this event in order to rearm it.
		  See the value of userEventTrapExpression
		  for the signedness with respect to the threshold (<, >, etc.)"
      ::= { psUserEventTrapVars 10 }

   userEventTrapDayCount OBJECT-TYPE
      SYNTAX  INTEGER
      ACCESS  not-accessible
      STATUS  mandatory
      DESCRIPTION
         "The number of times this event has occurred on this
          day (as counted from midnight to midnight, local time).
		  If this value is greater than or equal to userEventTrapDayLimit,
		  and that value is non-zero, then no more instances of this
		  event will be reported until the next day."
      ::= { psUserEventTrapVars 11 }

   userEventTrapDayLimit OBJECT-TYPE
      SYNTAX  INTEGER
      ACCESS  not-accessible
      STATUS  mandatory
      DESCRIPTION
         "The maximum number of times this event is allowed to occur per
          day (as counted from midnight to midnight, local time),
		  as configured by the user.  A value of zero denotes no limit."
      ::= { psUserEventTrapVars 12 }


   psAlarmUserEvent TRAP-TYPE
      ENTERPRISE packetShaper
      VARIABLES {
         userEventTrapName,
         userEventTrapExpression,
         userEventTrapVariable,
         userEventTrapElementType,
         userEventTrapRegid,
         userEventTrapDate,
         userEventTrapValue,
         userEventTrapTarget,
         userEventTrapThreshold,
		 userEventTrapRearm,
		 userEventTrapDayCount,
		 userEventTrapDayLimit
      }
      DESCRIPTION
      "A psAlarmUserEvent trap signifies that a user event, which has
       been registered by the user, has occurred.  The associated variables
	   give more information on the event."
      ::= 9

   psAgentEventTrapVars      OBJECT IDENTIFIER ::= { psAgentEvent 1 }

   --  The variables described here are strictly for use as VarBinds
   --  in the 'trapAgentEvent' trap.  In SNMPv2 syntax as in RFC 1902,
   --  they would have a MAX-ACCESS value of "accessible-for-notify"
   --  since that captures exactly what is intended.
   --  As this is V1 syntax, they're "not-accessible" instead.

   agentEventTrapName OBJECT-TYPE
      SYNTAX  DisplayString
      ACCESS  not-accessible
      STATUS  mandatory
      DESCRIPTION
         "The name of the agent instance which has fired the event."
      ::= { psAgentEventTrapVars 1 }

   agentEventTrapDate OBJECT-TYPE
      SYNTAX  DateAndTime
      ACCESS  not-accessible
      STATUS  mandatory
      DESCRIPTION
         "The time the event occurred."
      ::= { psAgentEventTrapVars 2 }

   agentEventTrapType OBJECT-TYPE
      SYNTAX   INTEGER  {
	green(0),
	red(1),
	yellow(2),
	blue(3)
	}
      ACCESS  not-accessible
      STATUS  mandatory
      DESCRIPTION
         "The type of event that occurred, 0 = GREEN, 1 = RED, 2 = YELLOW, 3 = BLUE."
      ::= { psAgentEventTrapVars 3 }


   agentEventTrapDescription OBJECT-TYPE
      SYNTAX  DisplayString
      ACCESS  not-accessible
      STATUS  mandatory
      DESCRIPTION
         "A description of the event that has occurred."
      ::= { psAgentEventTrapVars 4 }

   psAlarmAgentEvent TRAP-TYPE
      ENTERPRISE packetShaper
      VARIABLES {
         agentEventTrapName,
         agentEventTrapDate,
         agentEventTrapType,
         agentEventTrapDescription
      }
      DESCRIPTION
      "A psAlarmAgentEvent trap signifies that an agent event, which has
       been triggered by the user, has occurred.  The associated variables
	   give more information on the event."
      ::= 13

-- the psFeatures group

   psFeatureHighAvDeviceDown TRAP-TYPE
      ENTERPRISE packetShaper
      VARIABLES { psFeatureHighAvDeviceDownStatus,
		  psFeatureHighAvDeviceDownRouter,
		  psFeatureHighAvDeviceDownInterface
		}
      DESCRIPTION
      "A psFeatureHighAvDeviceFailed trap signifies that an interface
       or router we are tracking has gone down. If it is an interface that
       went down, the bindings will show the corresponding router and the
       name of the interface which went down. The name will be specified
       as 'unknown' if we could not resolve the interface name. But if it
       is the router that went down, the interface name will not be specified."
      ::= 12

   psFeatureHighAvDeviceDownCount OBJECT-TYPE
      SYNTAX  Counter
      ACCESS   read-only
      STATUS   mandatory
      DESCRIPTION
	  "The number of psFeatureHighAvDevice traps sent by
	   the agent since the last reset."
      ::= { psHighAv 1 }

   psFeatureHighAvDeviceDownStatus OBJECT-TYPE
      SYNTAX   INTEGER  {
	up(1),
	down(2)
	}
      ACCESS  read-only
      STATUS  mandatory
      DESCRIPTION
         "The operational status of the interface of the router
         we are polling.
         (1) UP
         (2) DOWN."
      ::= { psHighAv 2 }

   psFeatureHighAvDeviceDownRouter OBJECT-TYPE
      SYNTAX  DisplayString
      ACCESS   read-only
      STATUS   mandatory
      DESCRIPTION
	  "The name of a router that has gone down
	   or the name of the router whose one of the
	   interfaces has gone down."
      ::= { psHighAv 3 }

   psFeatureHighAvDeviceDownInterface OBJECT-TYPE
      SYNTAX  DisplayString
      ACCESS   read-only
      STATUS   mandatory
      DESCRIPTION
	  "The name of the interface that has gone down. The name
	   will be specified as 'unknown' in the cases where we
	   could not resolve the interface name. The interface
	   name will have a value of NULL or zero-length value
	   if the router goes down."
      ::= { psHighAv 4 }




END
