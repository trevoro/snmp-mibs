CXBCM-MIB DEFINITIONS ::= BEGIN

--#CURRENT-VERSION 2

IMPORTS
   Counter,TimeTicks    FROM RFC1155-SMI
   OBJECT-TYPE          FROM RFC-1212
   TRAP-TYPE            FROM RFC-1215
   DisplayString        FROM RFC1213-MIB
   cxBCM,SapIndex,Alias FROM CXProduct-SMI;

-- Propietary Data Types
LSapIndex   ::=   INTEGER (0..30)
CHIndex     ::=   INTEGER (1..1)

bcmTraps       OBJECT-TYPE
      SYNTAX   INTEGER {
               disabled (1),
               enabled  (2)
            }
      ACCESS   read-write
      STATUS   obsolete
      DESCRIPTION
"Determines whether this software layers produces the 
'bcmUSapStatusIndication' and 'bcmLSapStatusIndication' traps whose 
accumulated values can be retrieved by an SNMP-compliant network management 
device.

Options:
disabled  (1):layer does not produce upper SAP and lower SAP status 
traps

enabled  (2) :layer produces upper SAP and lower SAP status traps

Default Value: disabled

Configuration Changed: administrative "
      DEFVAL { disabled }
      --#ENDING-VERSION 2
      ::= { cxBCM  1 }


bcmCallHistoryTraps     OBJECT-TYPE
      SYNTAX   INTEGER {
               disabled (1),
               enabled  (2)
            }
      ACCESS   read-write
      STATUS   mandatory
      DESCRIPTION
"Determines whether this software layers produces the
'bcmCallHistoryStatusIndication' trap whose accumulated value can be 
retrieved by an SNMP-compliant network management device.

WARNING: This object is not supported yet.

Options:
disabled (1):layer does not produce call history trap

enabled (2):layer produces call history trap

Default Value: disabled

Configuration Changed: administrative "
      DEFVAL { disabled }
      ::= { cxBCM  2 }


bcmSoftwareVersion      OBJECT-TYPE
      SYNTAX   DisplayString
      ACCESS   read-only
      STATUS   mandatory
      DESCRIPTION
"Identifies the main version and revision numbers (separated by a period) of  
the BCM software layer. The first digit is changed when the software has passed
a certification. The second digit is changed each time a new functionality is 
added to the software.

Version  1.00: ISDN BRI User U interface - Not certified 
               (Supports data only)
         2.00: Added ISDN BRI User S/T interface - CTR3 certified 
               (Supports Data only)
         2.10: Added ISDN PRI User/Network CEPT (E1) - Not certified
               (Supports voice on PRI and data on BRI and PRI)"
      ::= { cxBCM 3 }


bcmMibLevel       OBJECT-TYPE
      SYNTAX   INTEGER
      ACCESS   read-only
      STATUS   mandatory
      DESCRIPTION
"Used to determine current MIB module release supported
by the agent. Object is in decimal."
      DEFVAL { 2 }
      --#STARTING-VERSION 1
      ::= { cxBCM 4 }


bcmModuleState          OBJECT-TYPE
      SYNTAX   INTEGER {
               uninitialized (1),
               initializing (2),
               registering (3),
               operational (4) 
            }
      ACCESS   read-only
      STATUS   mandatory
      DESCRIPTION
"Indicates the operational state of the BCM software 
layer.

Options:
uninitialized (1): not initialized

initializing (2): in initializing state

registering (3):in registration state

operational (4): in operational state

Default Value: none"
      ::= { cxBCM 40 }


bcmNbActiveUSap      OBJECT-TYPE
      SYNTAX   INTEGER (0..64)
      ACCESS   read-only
      STATUS   mandatory
      DESCRIPTION
"Indicates the number of upper SAPS that have been initialized.

Range of Values: 0-20 for BRI ISDN
                 0-64 for PRI ISDN

Default Value: none"
      ::= { cxBCM 41 }


bcmNbActiveDsl       OBJECT-TYPE
      SYNTAX   INTEGER (0..8)
      ACCESS   read-only
      STATUS   mandatory
      DESCRIPTION
"Indicates the number of Digital Subscriber Lines (DSLs) which 
are synchronized and therefore ready to process calls.

Range of Values: 0-2 for DI600
                 0-6 for CX900
                 0-8 for CX950

Default Value: none"
      ::= { cxBCM 42 }


--  Lower Service Access Point Configuration Table

--  The table describing:
-- parameters required to configure a lower service access point
-- controls available to manipulate a lower service access point
-- status available for monitoring the current state of the lower service 
-- access point
-- statistics available for monitoring any lower service access point

-- The Lower Service Access Points of the B Channel Manager (BCM) module
-- are considered as the Access Point for the Digital Subscriber Line (DSL).
-- These Lower Service Access Points are used to communicate with the 
-- "Call Control" (Q.931), BOP or PCM modules; further connection will be 
-- added on a need basis.


bcmLSapTable      OBJECT-TYPE
      SYNTAX   SEQUENCE OF BcmLSapEntry
      ACCESS   not-accessible
      STATUS   mandatory
      DESCRIPTION
"A table containing configuration, controls, status and statistics 
information about each BCM module layer lower service access point."
      ::= { cxBCM 50 }


bcmLSapEntry      OBJECT-TYPE
      SYNTAX   BcmLSapEntry
      ACCESS   not-accessible
      STATUS   mandatory
      DESCRIPTION
"The parameters for a specific lower service access point."

      INDEX { bcmLSapDslNumber,
              bcmLSapNumber }
      ::= { bcmLSapTable 1 }


BcmLSapEntry   ::=
      SEQUENCE {
-- Parameters
         bcmLSapDslNumber           SapIndex,
         bcmLSapNumber              LSapIndex,
         bcmLSapAlias               Alias,
         bcmLSapCompanionAlias      Alias,
--
         bcmLSapDirectoryIndex      INTEGER,
         bcmLSapLowDirectoryIndex   INTEGER,
         bcmLSapHighDirectoryIndex  INTEGER,
-- Status
         bcmLSapState               INTEGER,
         bcmLSapStatusEvent         INTEGER,       -- obsolete
         bcmLSapPeerAddress         DisplayString,
         bcmLSapPeerSubAddress      DisplayString,
         bcmLSapCallOrigin          INTEGER,
         bcmLSapInfoType            INTEGER,
         bcmLSapCallId              DisplayString,
         bcmLSapUSapId              INTEGER,
         bcmLSapChannelCES          INTEGER,
         bcmLSapCallSetupTime       TimeTicks,
         bcmLSapCallConnectTime     TimeTicks,
         bcmLSapCallDisconnectTime  TimeTicks,
-- Statistics
         bcmLSapNbInCalls           Counter,
         bcmLSapNbInCallsConnected  Counter,
         bcmLSapNbOutCalls          Counter,
         bcmLSapNbOutCallsConnected Counter
         }

bcmLSapDslNumber     OBJECT-TYPE
      SYNTAX   SapIndex
      ACCESS   read-only
      STATUS   mandatory
      DESCRIPTION
"Indicates the Digital Subscriber Line number associated 
with this lower SAP.

Range of Values: 1-2 for DI600 (port)
                 1-6 for CX900 (slot)
                 1-8 for CX950 (slot)

Default Value: none"
      ::= { bcmLSapEntry 1 }


bcmLSapNumber        OBJECT-TYPE
      SYNTAX   LSapIndex
      ACCESS   read-only
      STATUS   mandatory
      DESCRIPTION
"Indicates the row containing objects for configuring or monitoring a SAP 
associated with one of the ISDN channels.

Range of Values:
      0-2 for BRI
      0-30 for PRI (ANSI (T1) will only make use of 0-23)

NOTE: Entry 0 must always be connected to the D channel.

Default Value:none"
      ::= { bcmLSapEntry 2 }

   
bcmLSapAlias         OBJECT-TYPE
      SYNTAX   Alias
      ACCESS   read-write
      STATUS   mandatory
      DESCRIPTION
"Determines the textual name that uniquely identifies this lower SAP.

Range of Values: 0-16 alphanumeric characters beginning with a 
non-numeric character and ending with up to three numeric characters

Default Value: none

Configuration Changed: administrative "
      ::= { bcmLSapEntry 3 }


bcmLSapCompanionAlias      OBJECT-TYPE
      SYNTAX   Alias
      ACCESS   read-write
      STATUS   mandatory
      DESCRIPTION
"Determines the textual name identifying this SAP's companion SAP in the 
Bit-Oriented Protocol (BOP) Driver or Q.931 software layer.

Range of Values: 0-16 alphanumeric characters beginning with an alpha character

Default Value: none

Configuration Changed: administrative "
      ::= { bcmLSapEntry 4 }


bcmLSapDirectoryIndex      OBJECT-TYPE
      SYNTAX   INTEGER (1..128)
      ACCESS   read-write
      STATUS   mandatory
      DESCRIPTION
"Determines the ISDN Address, Subaddress and SPID of this lower SAP.

Range of Values: 1-40 for BRI ISDN
                 1-128 for PRI ISDN

Default Value: 1

Configuration Changed: administrative "
      DEFVAL { 1 }
      ::= { bcmLSapEntry 10 }


bcmLSapLowDirectoryIndex   OBJECT-TYPE
      SYNTAX   INTEGER (1..128)
      ACCESS   read-write
      STATUS   mandatory
      DESCRIPTION
"Determines the start of an ISDN Address that can be called 
from this lower SAP.

Range of Values: 1-40 for BRI ISDN
                 1-128 for PRI ISDN

NOTE: Only used for DATA calls

Default Value: 1

Configuration Changed: administrative "
      DEFVAL {1 }
      --#STARTING-VERSION 1
      ::= { bcmLSapEntry 11 }


bcmLSapHighDirectoryIndex  OBJECT-TYPE
      SYNTAX   INTEGER (1..128)
      ACCESS   read-write
      STATUS   mandatory
      DESCRIPTION
"Determines the end of an ISDN Address that can be called 
from this lower SAP.

Range of Values: 1-40 for BRI ISDN
                 1-128 for PRI ISDN

NOTE: Only used for DATA calls

Default Value: 40

Configuration Changed: administrative "
      DEFVAL {40 }
      --#STARTING-VERSION 1
      ::= { bcmLSapEntry 12 }


bcmLSapState         OBJECT-TYPE
      SYNTAX   INTEGER {
               not-used    (1),
               unbound     (2),
               bound       (3),
               registering (4),
               idle        (5),
               outgoing    (6),
               incoming    (7),
               active      (8),
               release     (9),
               pending     (10),
               overlap-rx  (11)
            }
      ACCESS   read-only
      STATUS   mandatory
      DESCRIPTION
"Indicates the current state of this lower SAP.

Options:
not-used (1): SAP not in use

unbound (2): SAP not bound to another software layer

bound (3):SAP bound to another software layer

registering (4):SAP waits for SPID-EID exchange
(this state is for BRI North American switches only)

idle (5): SAP is idle

outgoing (6):SAP process call request from upper application

incoming (7):SAP process call indication from Digital Subscriber
Line (DSL)

active (8):SAP is active

release (9):SAP released from call

pending (10):SAP bound, wait for link to go up

overlap-rx (11): SAP is receiving calling information over several messages

Default Value: none"
      ::= { bcmLSapEntry 40 }


bcmLSapStatusEvent      OBJECT-TYPE
      SYNTAX   INTEGER {
               noEvent                       (1),
               dslOutOfRange                 (2),
               lsapOutOfRange                (3),
               lsapMngmtRegistrationFailed   (4)
            }
      ACCESS   read-only
      STATUS   obsolete
      DESCRIPTION
"Indicates a status generated by the 'bcmLSapStatusIndication' trap.

Note: This value will always read 'noEvent' unless 'bcmTraps' has been enabled and 
an event has been trapped.

Options:
noEvent (1): no trapped event

dslOutOfRange (2): Digital Subscriber Line number out of range

lsapOutOfRange (3): lower SAP number out of range

lsapMngmtRegistrationFailed (4): lower SAP SPID registration failed

Default Value: noEvent"
      ::= { bcmLSapEntry  41 }


bcmLSapPeerAddress      OBJECT-TYPE
      SYNTAX   DisplayString
      ACCESS   read-only
      STATUS   mandatory
      DESCRIPTION
"Indicates the ISDN Address of the remote location currently or last called.

Range of Values: 0-16 non-alpha characters (namely, 0123456789*#)

Default Value: none (0 if peer address unknown)"
      ::= { bcmLSapEntry 42 }


bcmLSapPeerSubAddress      OBJECT-TYPE
      SYNTAX   DisplayString
      ACCESS   read-only
      STATUS   mandatory
      DESCRIPTION
"Indicates the ISDN Subaddress of the remote location currently or last called.

Range of Values: 0-20

Default Value: none (0 if peer address unknown)"
      ::= { bcmLSapEntry 43 }


bcmLSapCallOrigin    OBJECT-TYPE
      SYNTAX   INTEGER {
               unknown     (1),
               originate   (2),
               answer      (3),
               callback    (4)
            }
      ACCESS   read-only
      STATUS   mandatory
      DESCRIPTION
"Indicates how the current or last call began at this lower SAP.

Options:
unknown (1): SAP had no call since last system startup

originate (2): SAP originated call

answer (3): SAP answered call

callback (4): SAP called back once not busy

Default Value: unknown"
      DEFVAL { unknown }
      ::= { bcmLSapEntry 44 }


bcmLSapInfoType      OBJECT-TYPE
      SYNTAX   INTEGER {
               unknown              (1),
               speech               (2),
               unrestricted-digital (3),
               restricted-digital   (4),
               audio-31             (5),
               audio-7              (6),
               video                (7),
               packet               (8)
            }
      ACCESS   read-only
      STATUS   mandatory
      DESCRIPTION
"Indicates the transfer capability of the current or last call.

Options:
unknown (1): SAP had no call since last system startup

speech (2): voice call

unrestricted-digital (3): unrestricted data stream

restricted-digital (4): restricted data stream

audio-31 (5): voice call

audio-7 (6): high-quality voice call

video (7): video stream

packet (8): data packets

Default Value: unknown"
DEFVAL { unknown }
      ::= { bcmLSapEntry 45 }


bcmLSapCallId        OBJECT-TYPE
      SYNTAX   DisplayString (SIZE (0..4))
      ACCESS   read-only
      STATUS   mandatory
      DESCRIPTION
"Indicates the new call ID in the 'setup' message.

Range of Values: 0-FFFF (hexadecimal)

Note: ID in received messages from 1-7FFF; ID in sent messages 
from 8000-FFFF. ID '0' reserved for broadcast messages.

Default Value: none"
      ::= { bcmLSapEntry 46 }


bcmLSapUSapId        OBJECT-TYPE
      SYNTAX  INTEGER ( 1..64 )
      ACCESS   read-only
      STATUS   mandatory
      DESCRIPTION
"Specifies the upper SAP associated with this lower SAP's Digital Subscriber Line.

Range of Values: 1-20 for BRI ISDN
                 1-64 for PRI ISDN

Default Value: none"
      ::= { bcmLSapEntry 47 }


bcmLSapChannelCES    OBJECT-TYPE
      SYNTAX   INTEGER ( 0..2 )
      ACCESS   read-only
      STATUS   mandatory
      DESCRIPTION
"Indicates the Connection Endpoint Suffix (CES) of this lower SAP's channel. 
For BRI North American switches, when SPIDs are used, the CES will be '1' and 
'2' accordingly. But in the case of BRI and PRI which does not use SPID, the 
CES is always '1'. When this lower SAP refers to a D channel or if this lower 
SAP isn't configured, then the CES is 0 to signal that it is not used.

Range of Values: 0 not used
                 1-2
                 
Default Value: none"
      ::= { bcmLSapEntry 48 }


bcmLSapCallSetupTime    OBJECT-TYPE
      SYNTAX   TimeTicks
      ACCESS   read-only
      STATUS   mandatory
      DESCRIPTION
"Indicates the system time when the ISDN setup message was sent or received 
for the current or last call.

Range of Values: 0-4, 294, 967, 295

Default Value: 0 (= no call since system startup)"
      ::= { bcmLSapEntry 49 }


bcmLSapCallConnectTime  OBJECT-TYPE
      SYNTAX   TimeTicks
      ACCESS   read-only
      STATUS   mandatory
      DESCRIPTION
"Indicates the system time when the ISDN connect message was sent or received 
for the current or last call.

Range of Values: 0-4, 294, 967, 295

Default Value: 0 (= no call since system startup)"
      ::= { bcmLSapEntry 50 }


bcmLSapCallDisconnectTime  OBJECT-TYPE
      SYNTAX   TimeTicks
      ACCESS   read-only
      STATUS   mandatory
      DESCRIPTION
"Indicates the system time when the ISDN disconnect or release message was 
sent or received for the current or last call.

Range of Values: 0-4, 294, 967, 295

Default Value: 0 (= no call since system startup)"
      ::= { bcmLSapEntry 51 }


bcmLSapNbInCalls     OBJECT-TYPE
      SYNTAX   Counter
      ACCESS   read-only
      STATUS   mandatory
      DESCRIPTION
"Indicates the number of incoming calls on this lower SAP since system 
startup.

Range of Values: 0-4, 294, 967, 295

Default Value: none"
      ::= { bcmLSapEntry 60 }


bcmLSapNbInCallsConnected  OBJECT-TYPE
      SYNTAX   Counter
      ACCESS   read-only
      STATUS   mandatory
      DESCRIPTION
"Indicates the number of incoming calls that connected successfully through 
this lower SAP since system startup.

Range of Values: 0-4, 294, 967, 295

Default Value: none"
      ::= { bcmLSapEntry 61 }


bcmLSapNbOutCalls    OBJECT-TYPE
      SYNTAX   Counter
      ACCESS   read-only
      STATUS   mandatory
      DESCRIPTION
"Indicates the number of outgoing calls on this lower SAP 
since system startup.

Range of Values: 0-4, 294, 967, 295

Default Value: none"
      ::= { bcmLSapEntry 62 }


bcmLSapNbOutCallsConnected      OBJECT-TYPE
      SYNTAX   Counter
      ACCESS   read-only
      STATUS   mandatory
      DESCRIPTION
"Indicates the number of outgoing calls that connected successfully through 
this lower SAP since system startup.

Range of Values: 0-4, 294, 967, 295

Default Value: none"
      ::= { bcmLSapEntry 63 }


--  Digital Subscriber Line (DSL) Configuration Table.

--  The table describing:
-- parameters required to modify parameters of a DSL access point
-- controls available to manipulate a DSL access point
-- status available for monitoring the current state of a DSL access point
-- statistics available for monitoring a DSL access point

-- This table is used to configure a DSL access point, which is used for the 
-- handling of the D and Bs channels (lower SAP) being part of a DSL 
-- (Digital Subscriber Line).

bcmDslTable       OBJECT-TYPE
      SYNTAX   SEQUENCE OF BcmDslEntry
      ACCESS   not-accessible
      STATUS   mandatory
      DESCRIPTION
"A table containing information about a DSL control block. This DSL access  
point is used for the handling of the D and Bs channels that are part of a 
DSL (Digital Subscriber Line)"
      ::= { cxBCM 51 }


bcmDslEntry       OBJECT-TYPE
      SYNTAX   BcmDslEntry
      ACCESS   not-accessible
      STATUS   mandatory
      DESCRIPTION
"The parameters for a specific DSL control block."

      INDEX { bcmDslNumber }
      ::= { bcmDslTable 1 }


BcmDslEntry ::=
      SEQUENCE {
-- Parameters
            bcmDslNumber            SapIndex,
            bcmDslRowStatus         INTEGER,
--
            bcmDslSwitchType        INTEGER,    -- obsolete
            bcmDslBChannelCount     INTEGER,
            bcmDslBChannelType      INTEGER,
            bcmDslMngmtTimer        INTEGER,
            bcmDslInfoRate          INTEGER,
            bcmDslSendingProceed    INTEGER,    -- obsolete
-- Status
            bcmDslInterfaceType     INTEGER,
            bcmDslBriType           INTEGER,
            bcmDslPriType           INTEGER,
            bcmDslNbChannelInUse    INTEGER,
            bcmDslOutGoingCallId    DisplayString,
            bcmDslEffectiveRetries  INTEGER
         }

bcmDslNumber         OBJECT-TYPE
      SYNTAX   SapIndex
      ACCESS   read-only
      STATUS   mandatory
      DESCRIPTION
"Indicates the Digital Subscriber Line's access point number.

Range of Values: 1-2 for DI600 (port)
                 1-6 for CX900 (slot)
                 1-8 for CX950 (slot)

Default Value: none"
      ::= { bcmDslEntry 1 }

bcmDslRowStatus      OBJECT-TYPE
      SYNTAX   INTEGER {
               invalid  (1),
               valid    (2)
            }
      ACCESS   read-write
      STATUS   mandatory
      DESCRIPTION
"Determines whether this DSL is to be removed from service 
(i.e. invalidated)  within the B-Channel Manager software layer.

Options:
invalid (1): row is flagged; after next reset values will be disabled and row 
will be deleted from table

valid (2): values are enabled

Default Value: valid

Configuration Changed: administrative "
      ::= { bcmDslEntry 2 }


bcmDslSwitchType     OBJECT-TYPE
      SYNTAX   INTEGER {
               unspecified (1),
               bri-5ESS    (3),  -- U.S.A / At&T 5ESS
               bri-DMS100  (5),  -- U.S.A / Norther Telecom 
               bri-NI1     (8),  -- U.S.A / National ISDN 1
               bri-NI2     (9)   -- U.S.A / National ISDN 2 (NA)
            }
      ACCESS   read-write
      STATUS   obsolete
      DESCRIPTION
"Determines the ISDN switch type supported on the D channel.

Options:
unspecified (1)

bri-5ESS (3): U.S.A  / At&T 5ESS

bri-DMS100 (5): U.S.A / Norther Telecom

bri-NI1 (8): U.S.A / National ISDN 1

bri-NI2 (9): U.S.A / National ISDN 2

Default Value: bri-NI1 (8)

Configuration Changed: administrative "
      DEFVAL { bri-NI1 }
      --#ENDING-VERSION 1
      ::= { bcmDslEntry 10 }


bcmDslBChannelCount     OBJECT-TYPE
      SYNTAX   INTEGER (1..30)
      ACCESS   read-write
      STATUS   mandatory
      DESCRIPTION
"Determines the total number of B channels managed by the signaling interface.

Range of Values: 1-30

NOTE: It has to be set to: 2 for BRI
                           23 for ANSI (T1)
                           30 for CEPT (E1)

Default Value: 2 for BRI
               30 for PRI

Configuration Changed: administrative "
      ::= { bcmDslEntry 11 }


bcmDslBChannelType      OBJECT-TYPE
      SYNTAX   INTEGER {
               dialup   (1),
               leased   (2)
            }
      ACCESS   read-write
      STATUS   mandatory
      DESCRIPTION
"Determines the type of ISDN line.

Options:
dialup (1): B channels controlled by associated signaling D channel

leased (2): B channels always connected and not controlled by D channel
            (This option is not supported yet)

Default Value: dialup

Configuration Changed: administrative "
      DEFVAL { dialup }
      ::= { bcmDslEntry 12 }


 bcmDslMngmtTimer    OBJECT-TYPE
      SYNTAX   INTEGER (1..255)
      ACCESS   read-write
      STATUS   mandatory
      DESCRIPTION
"Determines the interval in seconds that the BCM software 
layer will wait between two SPIDs transmission when no
answer form the network is received.

Range of Values: 1-255

NOTE: Only used for BRI North American switches in Fully
Initialized Terminal (FIT) mode

Default Value: 45

Configuration Changed: administrative "
      DEFVAL { 45 }
      ::= { bcmDslEntry 13 }


bcmDslInfoRate          OBJECT-TYPE
      SYNTAX   INTEGER {
               rate56kbps  (1),
               rate64kbps  (2)
            }
      ACCESS   read-write
      STATUS   mandatory
      DESCRIPTION
"Determines the speed of the B channel connected to the Digital Subscriber 
Line when a call is initiated on that DSL.

Options:
rate56kbps (1): B channel speed is 56 kbps

rate64kbps (2): B channel speed is 64 kbps

Default Value: rate64kbps (1)

Configuration Changed: administrative "
      DEFVAL { rate64kbps }
      ::= { bcmDslEntry 14 }


bcmDslSendingProceed         OBJECT-TYPE
      SYNTAX   INTEGER {
               en-bloc          (1),
               overlap          (2)
            }
      ACCESS   read-write
      STATUS   obsolete
      DESCRIPTION
"Indicates the way calling information for the switch is generated.
'en-bloc' means that all calling information is sent in the first message.
overlap means that calling information is spread over several messages"
      DEFVAL { en-bloc }
      --#ENDING-VERSION 2
      ::= { bcmDslEntry 15 }


bcmDslInterfaceType     OBJECT-TYPE
      SYNTAX   INTEGER {
               none  (1),
               bri   (2),
               pri   (3)
            }
      ACCESS   read-only
      STATUS   mandatory
      DESCRIPTION
"Indicates the type of physical interface for the specified 
Digital Subscriber Line.

Options:
none (1): not specified

bri (2): Basic Rate Interface

pri (3): Primary Rate Interface

Default Value: none"
      ::= { bcmDslEntry 40 }


bcmDslBriType        OBJECT-TYPE
      SYNTAX   INTEGER {
               none  (1),
               u     (2),
               s-t   (3)
            }
      ACCESS   read-only
      STATUS   mandatory
      DESCRIPTION
"Indicates the type of BRI interface for the specified 
Digital Subscriber Line.

Options:
none (1): SAP has no BRI interface

u (2): BRI type is 'U'

s-t (3): BRI type is 'S/T'

Default Value: none"
      DEFVAL { none }
      ::= { bcmDslEntry 41 }


bcmDslPriType        OBJECT-TYPE
      SYNTAX   INTEGER {
               none  (1),
               ansi  (2),
               cept  (3)
            }
      ACCESS   read-only
      STATUS   mandatory
      DESCRIPTION
"Indicates the type of PRI interface for the specified 
Digital Subscriber Line.

Options: 
none (1): SAP has no PRI interface

ansi (2): PRI type is 'ANSI' (T1)

cept (3): PRI type is 'CEPT' (E1)

Default Value: none"
      DEFVAL { none }
     ::= { bcmDslEntry 42 }


bcmDslNbChannelInUse    OBJECT-TYPE
      SYNTAX   INTEGER (0..30)
      ACCESS   read-only
      STATUS   mandatory
      DESCRIPTION
"Indicates the number of B channels connected, connecting, or active on this 
Digital Subscriber Line.

Range of Values: 0-2 for BRI
                 0-23 for ANSI (T1)
                 0-30 for CEPT (E1)

Default Value: 0"
      DEFVAL { 0 }
      ::= { bcmDslEntry 43 }


bcmDslOutGoingCallId    OBJECT-TYPE
      SYNTAX   DisplayString (SIZE (0..4))
      ACCESS   read-only
      STATUS   mandatory
      DESCRIPTION
"Indicates the call ID used in the 'setup' message sent.

Range of Values: 8000-FFFF (hexadecimal)

Default Value: none"
      ::= { bcmDslEntry 44 }


bcmDslEffectiveRetries     OBJECT-TYPE
      SYNTAX   INTEGER (0..255)
      ACCESS   read-only
      STATUS   mandatory
      DESCRIPTION
"Indicates the number of times a management request has been sent to 
initialize the ISDN switch.

Range of Values: 0-255

NOTE: Only used for BRI North American switches

Default Value: 0"
      ::= { bcmDslEntry 45 }


--  Upper Service Access Point Configuration Table

--  The table describing:
-- parameters required to modify parameters at a upper service access point
-- controls available to manipulate a upper service access point
-- status available for monitoring the current state of the upper service 
-- access point
-- statistics available for monitoring any upper service access point


bcmUSapTable         OBJECT-TYPE
      SYNTAX   SEQUENCE OF BcmUSapEntry
      ACCESS   not-accessible
      STATUS   mandatory
      DESCRIPTION
"A table containing configuration information about each upper service access 
point."
      ::= { cxBCM 52 }


bcmUSapEntry         OBJECT-TYPE
      SYNTAX   BcmUSapEntry
      ACCESS   not-accessible
      STATUS   mandatory
      DESCRIPTION
"The parameters for a specific upper service access point."
      INDEX { bcmUSapNumber }
      ::= { bcmUSapTable 1 }

BcmUSapEntry ::=
            SEQUENCE {
-- Parameters
               bcmUSapNumber                    SapIndex,
               bcmUSapRowStatus                 INTEGER,
               bcmUSapAlias                     Alias,
--
               bcmUSapLowDirectoryIndex         INTEGER,
               bcmUSapHighDirectoryIndex        INTEGER,
               bcmUSapAnswerMode                INTEGER,
               bcmUSapPermission                INTEGER,
               bcmUSapCallTypeAccepted          INTEGER,
               bcmUSapSendingProceed            INTEGER,
               bcmUSapVoiceInterDigitTimer      INTEGER,
               bcmUSapVoiceHuntGroup            INTEGER,
               bcmUSapVoiceHuntDsl              INTEGER,
               bcmUSapVoiceAddressPlan          INTEGER,
               bcmUSapVoiceAddressType          INTEGER,
               bcmUSapVoiceCodingScheme         INTEGER,
               bcmUSapVoiceCallRoutingMode      INTEGER,
-- Status
               bcmUSapState                     INTEGER,
               bcmUSapStatusEvent               INTEGER,    -- obsolete
               bcmUSapNbChannelBound            INTEGER,
               bcmUSapTotalConnectTime          TimeTicks,
               bcmUSapLastSetupTime             TimeTicks,
               bcmUSapLastConnectTime           TimeTicks,
               bcmUSapLastDisconnectTime        TimeTicks,
               bcmUSapLastDisconnectCause       INTEGER,
               bcmUSapDslId                     INTEGER,
               bcmUSapLocalSapId                INTEGER,    -- obsolete
               bcmUSapSpeedDialDirectoryIndex   INTEGER,
               bcmUSapVoiceChannelUsed          INTEGER,
-- Statistics
               bcmUSapNbSuccessCalls            Counter,
               bcmUSapNbFailedCalls             Counter,
               bcmUSapNbRefusedCalls            Counter
}


bcmUSapNumber OBJECT-TYPE
      SYNTAX   SapIndex
      ACCESS   read-only
      STATUS   mandatory
      DESCRIPTION
"Indicates the row containing objects for configuring or monitoring a SAP 
associated with one of the ISDN channels.

Range of Values: 1-20 for BRI ISDN
                 1-64 for PRI ISDN

Default Value: none"
      ::= { bcmUSapEntry 1 }


bcmUSapRowStatus     OBJECT-TYPE
      SYNTAX   INTEGER {
               invalid  (1),
               valid    (2)
            }
      ACCESS   read-write
      STATUS   mandatory
      DESCRIPTION
"Determines whether this SAP is to be removed from service (i.e. invalidated) 
within the B-Channel Manager software layer.

Options:
invalid (1): = row is flagged; after next reset values will be disabled and 
row will be deleted from table

valid (2): values are enabled

Default Value: invalid

Configuration Changed: administrative "
      DEFVAL {invalid }
      ::= { bcmUSapEntry 2 }


bcmUSapAlias         OBJECT-TYPE
      SYNTAX   Alias
      ACCESS   read-write
      STATUS   mandatory
      DESCRIPTION
"Determines the textual name uniquely identifying this upper SAP.

Range of Values: 0-16 alphanumeric characters beginning with an alpha 
character

Default Value: none

Configuration Changed: administrative "
      ::= { bcmUSapEntry 3 }


bcmUSapLowDirectoryIndex   OBJECT-TYPE
      SYNTAX   INTEGER (1..128)
      ACCESS   read-write
      STATUS   mandatory
      DESCRIPTION
"Determines the start of an ISDN Address that can call this upper SAP 
according to 'bcmUSapAnswerMode'.

Range of Values: 1-40 for BRI ISDN
                 1-128 for PRI ISDN

Default Value: 1

Configuration Changed: administrative "
      DEFVAL {1 }
      ::= { bcmUSapEntry 10 }


bcmUSapHighDirectoryIndex  OBJECT-TYPE
      SYNTAX   INTEGER (1..128)
      ACCESS   read-write
      STATUS   mandatory
      DESCRIPTION
"Determines the end of an ISDN Address that can call this upper SAP according 
to 'bcmUSapAnswerMode'.

Range of Values: 1-40 for BRI ISDN
                 1-128 for PRI ISDN

Default Value: 40

Configuration Changed: administrative "
      DEFVAL {40 }
      ::= { bcmUSapEntry 11 }


bcmUSapAnswerMode    OBJECT-TYPE
      SYNTAX   INTEGER{
               answer-none       (1),
               answer-all        (2),
               answer-address    (3),
               answer-subaddress (4)
            }
      ACCESS   read-write
      STATUS   mandatory
      DESCRIPTION
"Determines security for accepting incoming call indications
from the DSL.

Options:
answer-none (1): incoming calls not accepted

answer-all (2): incoming calls accepted even without match between 
'bcmUSapLowDirectoryIndex' and 'bcmUSapHighDirectoryIndex'

answer-address (3): incoming calls accepted if there is an ISDN address fit 
between 'bcmUSapLowDirectoryIndex' and 'bcmUSapHighDirectoryIndex'

answer-subaddress (4): incoming calls accepted if there is an ISDN subaddress 
fit between 'bcmUSapLowDirectoryIndex' and 'bcmUSapHighDirectoryIndex'

Default Value: answer-none (1)

Configuration Changed: administrative "
      DEFVAL { answer-all }
      ::= { bcmUSapEntry 12 }


bcmUSapPermission    OBJECT-TYPE
      SYNTAX   INTEGER{
               originate   (1),
               answer      (2),
               both        (3),
               callback    (4)
            }
      ACCESS   read-write
      STATUS   mandatory
      DESCRIPTION
"Determines what actions this upper SAP permits regarding outgoing and 
incoming calls.

Options:
originate (1): SAP permits calls to originate through it

answer (2): SAP permits calls to be answered through it

both (3): SAP permits calls both to originate and to be answered through it

callback(4): SAP permits callback after rejecting a call (may use reverse 
charging information if available)

Default Value: both

Configuration Changed: administrative "
      DEFVAL { both }
      ::= { bcmUSapEntry 13 }


bcmUSapCallTypeAccepted OBJECT-TYPE
      SYNTAX   INTEGER{
               voice-call  (1),
               data-call   (2),
               packet-call (3)
            }
      ACCESS   read-write
      STATUS   mandatory
      DESCRIPTION
"Determines the type of call this upper SAP will accept.

Options:
voice-call (1): SAP accepts calls using 'speech', 'audio-31', or 'audio-7' 
value in 'bcmSapInfoType'

data-call (2): SAP accepts calls using 'digital', 'digital-56', or 
'restricted-digital' value in 'bcmSapInfoType'

packet-call (3): SAP accepts calls using 'packet' value in 
'bcmSapInfoType' (this option is not supported)

Default Value: data-call

Configuration Changed: administrative "
      DEFVAL { data-call }
      ::= { bcmUSapEntry 14 }


bcmUSapSendingProceed   OBJECT-TYPE
      SYNTAX   INTEGER {
               en-bloc          (1),
               overlap          (2)
            }
      ACCESS   read-write
      STATUS   mandatory
      DESCRIPTION
"Indicates the way calling information for the switch is generated.
'en-bloc' means that all calling information is sent in the call request 
message (for voice application the message will be sent at the 
bcmUSapVoiceInterDigitTimer expiry or if the '#' tone is dialed)

'overlap' means that calling information is spread over several messages."
      DEFVAL { en-bloc }
      --#STARTING-VERSION 2
      ::= { bcmUSapEntry 15 }


bcmUSapVoiceInterDigitTimer   OBJECT-TYPE
      SYNTAX   INTEGER (1 .. 255)
      ACCESS   read-write
      STATUS   mandatory
      DESCRIPTION
"Indicates the maximum time in seconds to wait for another digit in 'en-bloc'
sending mode. When this timer expires, a connection attempt will be made with
all the gathered digits

NOTE: This object is used for Voice Applications only."
      DEFVAL { 7 }
      --#STARTING-VERSION 2
      ::= { bcmUSapEntry 16 }


bcmUSapVoiceHuntGroup     OBJECT-TYPE
     SYNTAX  INTEGER
     ACCESS  read-write
     STATUS  mandatory
     DESCRIPTION 
"Determines the voice ports number included in the Hunt Group as a bitmap.

A Voice Hunt Group identifies multiple voice ports that can be used locally
to process an incoming call indication from the Digital Subscriber Line (DSL). 
It is also used to specify which voice ports can access this upper SAP to make
an outgoing call request. A maximum of 30 voice ports can be mapped in a 
single hunt group.

Range of Values:'0000 0000'h to '3FFF FFFF'h 

Default Value: '3FFF FFFF'h equals 1073741823

NOTE: This object is used for Voice Applications only."
      DEFVAL { '3FFFFFFF'h }
      --#STARTING-VERSION 2
      ::= { bcmUSapEntry 17 }


bcmUSapVoiceHuntDsl       OBJECT-TYPE
     SYNTAX  INTEGER
     ACCESS  read-write
     STATUS  mandatory
     DESCRIPTION 
"Determines the Digital Subscriber Line (DSL) numbers included in the DSL 
Hunt Group as a bitmap.

The DSL Hunt Group identifies which DSL could be used by this upper SAP when 
an outgoing call request from the Voice module is made. It also identifies 
which DSL could be used when an incoming call indication from the DSL is 
received. A maximum of 2 ports can be mapped in a single DSL hunt group.

Range of Values:'0000 0000'h to '0000 0003'h 

Default Value: '0000 0003'h equals 3

NOTE: This object is used for Voice Applications only."
      DEFVAL { '3'h }
      --#STARTING-VERSION 2
      ::= { bcmUSapEntry 18 }


bcmUSapVoiceAddressPlan      OBJECT-TYPE
      SYNTAX   INTEGER {
               unknown     (1),
               isdn        (2),
               telephony   (3),
               x-121       (4),
               telex       (5),
               national    (9),
               private     (10)
            }
      ACCESS   read-write
      STATUS   mandatory
      DESCRIPTION
"Determines the Address Plan (corresponding to the Q.931 Information Element 
0x70, octet 3, bit 4 to 1) associated to a voice call request from an upper
application (FR/PPP/VOICE).

NOTE: This object is used for Voice Applications only.

Options:
unknown (1): unknown plan

isdn (2): ISDN

telephony (3): telephony

x-121 (4): X.121

telex (5): telex

national (9): national

private (10): private

Default Value: isdn (2)

Configuration Changed: administrative "
      DEFVAL {isdn }
      --#STARTING-VERSION 2
      ::= { bcmUSapEntry 19 }


bcmUSapVoiceAddressType      OBJECT-TYPE
      SYNTAX   INTEGER {
               unknown        (1),
               international  (2),
               national       (3),
               private        (4),
               subscriber     (5)
            } 
      ACCESS   read-write
      STATUS   mandatory
      DESCRIPTION
"Determines the Address Type (corresponding to the Q.931 Information Element 
0x70, octet 3, bit 7 to 5) associated to a voice call request from an upper
application (FR/PPP/VOICE).

NOTE: This object is used for Voice Applications only.

Options:
unknown (1): unknown type

international (2): international

national (3): national

private (4): private

subscriber (5): subscriber

Default Value: international (2)

Configuration Changed: administrative "
      DEFVAL {international }
      --#STARTING-VERSION 2
      ::= { bcmUSapEntry 20 }


bcmUSapVoiceCodingScheme     OBJECT-TYPE
      SYNTAX   INTEGER {
               mu-law   (1),
               a-law    (2)
            }
      ACCESS   read-write
      STATUS   mandatory
      DESCRIPTION
"Indicates the voice encoding scheme used for voice calls
that will be initiated locally. This object won't be used 
when using the NET3 or NET5 switch types because in that case
the 'A-law' encoding is enforced.

NOTE: This object is used for Voice Applications only.

Default Value: 1

Configuration Changed: administrative "
      DEFVAL { mu-law }
      --#STARTING-VERSION 2
      ::= { bcmUSapEntry 21 }


bcmUSapVoiceCallRoutingMode   OBJECT-TYPE
      SYNTAX   INTEGER {
               not-used                (1),
               address                 (2),
               subaddress              (3),
               address-and-subaddress  (4)
            } 
      ACCESS   read-write
      STATUS   mandatory
      DESCRIPTION
"Indicates how this Upper SAP will provide the routing information
to the upper voice layer application. When an incoming call indication 
from the Digital Subscriber Line (DSL) is received, the called party 
can be used to route this voice call to a remote.

NOTE: This object is used for Voice Applications only.

Options:
not-used (1): incoming call indication called party information is 
not used. Routing information has to be provided in-band.

address (2): complete address is used to route the voice call

subaddress (3): complete subaddress is used to route the voice call

address-and-subaddress (4): complete address and subaddress is used to 
route the voice call. The address is sent first followed by the subaddress.

Default Value: not-used (1)

Configuration Changed: administrative "
      DEFVAL { not-used }
      --#STARTING-VERSION 2
      ::= { bcmUSapEntry 22 }


bcmUSapState         OBJECT-TYPE
      SYNTAX   INTEGER {
               not-used    (1),
               unbound     (2),
               bound       (3),
               registering (4),
               idle        (5),
               outgoing    (6),
               incoming    (7),
               active      (8),
               release     (9),
               overlap-rx  (11)
            }
      ACCESS   read-only
      STATUS   mandatory
      DESCRIPTION
"Indicates the current state of this upper SAP.

Options:
not-used (1): SAP not in use

unbound (2): SAP not bound to another software layer

bound (3): SAP bound to another software layer

registering (4): SAP in process of being registered

idle (5): SAP is idle

outgoing (6): SAP process call indication from DSL

incoming (7): SAP process call request from upper application 

active (8): SAP is active

release (9): SAP released from call

overlap-rx (11): SAP is receiving calling information over 
several messages

Default Value: none"
      --#STARTING-VERSION 2
      ::= { bcmUSapEntry 40 }


bcmUSapStatusEvent      OBJECT-TYPE
      SYNTAX   INTEGER {
               noEvent        (1),
               usapOutOfRange (2)
            }
      ACCESS   read-only
      STATUS   obsolete
      DESCRIPTION
"Indicates a status generated by the 'bcmUSapStatusIndication' 
trap.

Note: This value will always read 'noEvent' unless 'bcmTraps' has been 
enabled and an event has been trapped.

Options:
noEvent (1): no event trapped

usapOutOfRange (2): upper SAP number out of range

Default Value: noEvent"
      ::= { bcmUSapEntry  41 }


bcmUSapNbChannelBound   OBJECT-TYPE
      SYNTAX   INTEGER (0..30)
      ACCESS   read-only
      STATUS   mandatory
      DESCRIPTION
"Indicates the number of B channels bound in the current or last call.

Range of Values: 0-30

Default Value: 0 (no call since system startup)"
      DEFVAL { 0 }
      ::= { bcmUSapEntry 42 }


bcmUSapTotalConnectTime OBJECT-TYPE
      SYNTAX   TimeTicks
      ACCESS   read-only
      STATUS   mandatory
      DESCRIPTION
"Indicates the total time connected to remote parties on both incoming and 
outgoing calls since system startup.

Range of Values: 0-4, 294, 967, 295

Default Value: 0 (no call since system startup)"
      ::= { bcmUSapEntry 43 }


bcmUSapLastSetupTime    OBJECT-TYPE
      SYNTAX   TimeTicks
      ACCESS   read-only
      STATUS   mandatory
      DESCRIPTION
"Indicates the system time when an ISDN setup message for the current or last 
call was last sent or received by this upper SAP.

Range of Values: 0-4, 294, 967, 295
               
Default Value: 0 (no call since system startup)"
      ::= { bcmUSapEntry 44 }


bcmUSapLastConnectTime  OBJECT-TYPE
      SYNTAX   TimeTicks
      ACCESS   read-only
      STATUS   mandatory
      DESCRIPTION
"Indicates the system time when an ISDN connect message for the current of 
last call was last sent or received by this upper SAP.

Range of Values: 0-4, 294, 967, 295
               
Default Value: 0 (no call since system startup)"
      ::= { bcmUSapEntry 45 }


bcmUSapLastDisconnectTime  OBJECT-TYPE
      SYNTAX   TimeTicks
      ACCESS   read-only
      STATUS   mandatory
      DESCRIPTION
"Indicates the system time when an ISDN disconnect or release message for the 
current or last call was last sent or received by this upper SAP.

Range of Values: 0-4, 294, 967, 295
               
Default Value: 0 (no call since system startup)"
      ::= { bcmUSapEntry 46 }


bcmUSapLastDisconnectCause OBJECT-TYPE
      SYNTAX   INTEGER (0..127)
      ACCESS   read-only
      STATUS   mandatory
      DESCRIPTION
"Indicates the codes for the cause of a disconnect.

Cause Values:
   For each class, the description of its cause
   value is given. Note that the value corresponds
   to the decimal value of the 7 least significant
   bits since the bit 8 is always set to 1.

Class 000, Normal Events:
   1	Unassigned number
   2	No route to specified transit network
   3	No route to destination
   6	Channel unacceptable
   7	Call awarded and deliivered in an established channel
   16	Normal call clearing
   17	User busy
   18	No user responding
   19	User alerting, no answer
   21	Call rejected
   22	Number changed
   26	Non-selected user clearing
   27	Destination out of order
   28	Invalid number format (incompatible number)
   29	Facility rejected
   30	Response to STATUS ENQUIRY
   31	Normal unspecified

Class 010, Network Congestion:
   34	No circuit/channel available
   38	Network out of order
   41	Temporary failure
   42	Switching equipment congestion
   43	User info discarded
   44	Requested channel not available
   47	Resources unavailable - unspecified

Class 011, Service or Option Not Available:
   49	Quality of service unavailable
   50	Requested facility not subscribed
   57	Bearer capability not authorized
   58	Bearer capability not presently authorized
   63	Service or option not available, unspecified
or Option Not Implemented:
   65	Bearer capability not implemented
   66	Channel type not implemented
   69	Requested facility not implemented
   70	Only restricted digital information bearer 
      capability is available
   79	Service or option not implemented, unspecified

Class 101, Invalid Message:
   81	Invalid call reference value
   82	Identified channel does not exist
   83	Suspended call exits, but this call identity does not
   84	Call identity in use
   85	No call suspended
   86	Call having the requested call identity has been cleared
   88	Incompatible destination
   91	Invalid transit network selection
   95	Invalid message, unspecified

Class 110, Protocol Error:
   96	   Mandatory information element is missing
   97	   Message type non-existent or not implemented
   98	   Message not compatible with call state or message type
         non-existent of not implemented
   99	   Information element non-existent or not implemented
   100	Invalid information element contents
   101	Message not compatible with call state
   102	Recovery on time expiry
   111	Protocol error, unspecified

Class 111, Interworking:
   127	Interworking, unspecified

Range of Values: 0-127

Default Value: none"
      ::= { bcmUSapEntry 47 }


bcmUSapDslId         OBJECT-TYPE
      SYNTAX   INTEGER (0..8)
      ACCESS   read-only
      STATUS   mandatory
      DESCRIPTION
"Indicates the Digital Subscriber Line used by the current or last 
call.

Range of Values: 0-2 for DI600 (port)
                 0-6 for CX900 (slot)
                 0-8 for CX950 (slot)

Default Value: 0 (no call since system startup)"
      DEFVAL {0}
      ::= { bcmUSapEntry 48 }


bcmUSapLocalSapId       OBJECT-TYPE
      SYNTAX   INTEGER (1..64)
      ACCESS   read-only
      STATUS   obsolete
      DESCRIPTION
"Indicates the upper SAP's ID.

Range of Values: 1-20 for BRI ISDN
                 1-64 for PRI ISDN

Default Value: none"
    ::= { bcmUSapEntry 49 }


bcmUSapSpeedDialDirectoryIndex   OBJECT-TYPE
      SYNTAX   INTEGER (1..128)
      ACCESS   read-only
      STATUS   mandatory
      DESCRIPTION
"Indicates an address associated with this upper SAP that is used for 
speed-dialing by ISDN applications.

Range of Values: 1-40 for BRI ISDN
                 1-128 for PRI ISDN

NOTE: Only used for DATA calls

Default Value: none"
      ::= { bcmUSapEntry 50 }


bcmUSapVoiceChannelUsed     OBJECT-TYPE
      SYNTAX   INTEGER (1..30)
      ACCESS   read-only
      STATUS   mandatory
      DESCRIPTION
"Indicates which voice port used in the current or last call.

Range of Values: 1-15 indicates respective DVDBs 1-15 on DVC 1
                 16-30 indicates respective DVDBs 1-15 on DVC 2

NOTE: This object is used for Voice Applications only."
      --#STARTING-VERSION 2
      ::= { bcmUSapEntry 51 }


bcmUSapNbSuccessCalls      OBJECT-TYPE
      SYNTAX   Counter
      ACCESS   read-only
      STATUS   mandatory
      DESCRIPTION
"Indicates the number of completed calls to remote parties through this upper 
SAP since system startup.

Range of Values: 0-4, 294, 967, 295

Default Value: none"
      ::= { bcmUSapEntry 60 }


bcmUSapNbFailedCalls    OBJECT-TYPE
      SYNTAX   Counter
      ACCESS   read-only
      STATUS   mandatory
      DESCRIPTION
"Indicates the number of failed calls
to remote parties through this upper
SAP since system startup.

Range of Values: 0-4,294,967,295

Default Value: none"
      ::= { bcmUSapEntry 61 }


bcmUSapNbRefusedCalls      OBJECT-TYPE
      SYNTAX   Counter
      ACCESS   read-only
      STATUS   mandatory
      DESCRIPTION
"Indicates the number of refused calls to remote parties through this upper 
SAP since system startup.

Range of Values: 0-4, 294, 967, 295

Default Value: none"
      ::= { bcmUSapEntry 62 }


-- Directory Table
-- This table is used to define ISDN access point containing addresses, 
-- subaddresses and SPID. 
-- These access points can be used as speed dial number (upper application) 
-- or for calls filtering (see lower and upper SAP objects 
-- 'bcmUSapLowDirectoryIndex', 'bcmUSapHighDirectoryIndex', 
-- 'bcmLSapLowDirectoryIndex', 'bcmLSapHighDirectoryIndex', 
-- 'bcmUSapAnswerMode' and 'bcmUSapPermission').
-- This table is restricted to 128 entries to start with for PRI applications
-- and 40 for BRI applications.  If more entries are necessary in the future, 
-- they will be added on demand.


bcmDirectoryTable    OBJECT-TYPE
      SYNTAX   SEQUENCE OF BcmDirectoryEntry
      ACCESS   not-accessible
      STATUS   mandatory
      DESCRIPTION
"A table containing the ISDN access points."
      ::= { cxBCM 53 }


bcmDirectoryEntry    OBJECT-TYPE
      SYNTAX   BcmDirectoryEntry
      ACCESS   not-accessible
      STATUS   mandatory
      DESCRIPTION
"The parameters for a specific ISDN access point."
      INDEX { bcmDirectoryNumber }
      ::= { bcmDirectoryTable 1 }


BcmDirectoryEntry ::=
            SEQUENCE {
-- Parameters
               bcmDirectoryNumber         SapIndex,
               bcmDirectoryRowStatus      INTEGER,
--
               bcmDirectoryAddress        DisplayString,
               bcmDirectoryAddressPlan    INTEGER,
               bcmDirectoryAddressType    INTEGER,
               bcmDirectorySubAddress     DisplayString,
               bcmDirectorySubAddressType INTEGER,
               bcmDirectorySpid           DisplayString
}


bcmDirectoryNumber      OBJECT-TYPE
      SYNTAX   SapIndex
      ACCESS   read-only
      STATUS   mandatory
      DESCRIPTION
"Indicates the row containing objects for configuring an ISDN access 
point.

Range of Values: 1-40 for BRI ISDN
                 1-128 for PRI ISDN

Default Value: none"
      ::= { bcmDirectoryEntry 1 }


bcmDirectoryRowStatus      OBJECT-TYPE
      SYNTAX   INTEGER {
               invalid     (1),
               valid       (2)
            }
      ACCESS   read-write
      STATUS   mandatory
      DESCRIPTION
"Determines whether this ISDN access point is to be removed from service 
(i.e. invalidated) within the B-Channel Manager software layer.

Options:
invalid (1): row is flagged; after next reset values will be disabled and row 
will be deleted from table

valid (2): values are enabled

Default Value: invalid

Configuration Changed: administrative "
      DEFVAL {invalid }
      ::= { bcmDirectoryEntry 2 }


bcmDirectoryAddress     OBJECT-TYPE
      SYNTAX   DisplayString
      ACCESS   read-write
      STATUS   mandatory
      DESCRIPTION
"Determines the ISDN address or phone
number.

Range of Values: 0-16 non-alpha characters (namely, 0123456789*#)

Default Value: none

Configuration Changed: administrative "
      ::= { bcmDirectoryEntry 10 }


bcmDirectoryAddressPlan    OBJECT-TYPE
      SYNTAX   INTEGER {
               unknown     (1),
               isdn        (2),
               telephony   (3),
               x-121       (4),
               telex       (5),
               national    (9),
               private     (10)
            }
      ACCESS   read-write
      STATUS   mandatory
      DESCRIPTION
"Determines the Address Plan (corresponding to the Q.931 Information Element 
0x70, octet 3, bit 4 to 1) associated with 'bcmDirectoryAddress'.

Options:
unknown (1): unknown plan

isdn (2): ISDN

telephony (3): telephony

x-121 (4): X.121

telex (5): telex

national (9): national

private (10): private

Default Value: isdn (2)

Configuration Changed: administrative "
      DEFVAL {isdn }
      ::= { bcmDirectoryEntry 11 }


bcmDirectoryAddressType OBJECT-TYPE
      SYNTAX   INTEGER {
               unknown        (1),
               international  (2),
               national       (3),
               private        (4),
               subscriber     (5)
            } 
      ACCESS   read-write
      STATUS   mandatory
      DESCRIPTION
"Determines the Address Type (corresponding to the Q.931 Information Element 
0x70, octet 3, bit 7 to 5) associated with 'bcmDirectoryAddress'.

Options:
unknown (1): unknown type

international (2): international

national (3): national

private (4): private

subscriber (5): subscriber

Default Value: international (2)

Configuration Changed: administrative "
      DEFVAL {international }
      ::= { bcmDirectoryEntry 12 }


bcmDirectorySubAddress     OBJECT-TYPE
      SYNTAX   DisplayString
      ACCESS   read-write
      STATUS   mandatory
      DESCRIPTION
"Determines the ISDN subaddress or phone extension number.

Range of Values: 0-20 non-alpha characters (namely, 0123456789*#)

Note: If the subaddress is not known, this value is left blank.

Default Value: none

Configuration Changed: administrative "
      ::= { bcmDirectoryEntry 13 }


bcmDirectorySubAddressType OBJECT-TYPE
      SYNTAX   INTEGER {
               nsap           (1),
               user-defines   (3)
            }
      ACCESS   read-write
      STATUS   mandatory
      DESCRIPTION
"Determines the Subaddress Type (corresponding to the Q.931 Information 
Element 0x71, octet 3, bit 7 to 5) associated with 'bcmDirectoryAddress'.

Options:
nsap (1): NSAP (CCITT rec. X-213 [23]/ISO 8348 AD2[24])

user-defines (3): private network

Default Value: user-defines (3)

Configuration Changed: administrative "
      DEFVAL {user-defines }
      ::= { bcmDirectoryEntry 14 }


bcmDirectorySpid     OBJECT-TYPE
      SYNTAX   DisplayString
      ACCESS   read-write
      STATUS   mandatory
      DESCRIPTION
"Determines the SPID (Service Profile Identifier) for DMS-100, NI-1, NI-2 
and, optionally, 5ESS switches supporting BRI.

Range of Values: 0-20 non-alpha characters (namely, 0123456789*#)

Note: If switch does not use SPID, this value is left blank.

Default Value: none

Configuration Changed: administrative "
      ::= { bcmDirectoryEntry 15 }


-- Call History Table
-- Table to store the current call information.  History of each and every 
-- call is stored, successful calls as well as unsuccessful and rejected 
-- calls.  An entry will be created when a call is setup.

bcmCallHistoryTable     OBJECT-TYPE
      SYNTAX   SEQUENCE OF BcmCallHistoryEntry
      ACCESS   not-accessible
      STATUS   mandatory
      DESCRIPTION
"A table containing information about specific calls to specific 
destination."
      ::= { cxBCM 54 }


bcmCallHistoryEntry     OBJECT-TYPE
      SYNTAX   BcmCallHistoryEntry
      ACCESS   not-accessible
      STATUS   mandatory
      DESCRIPTION
"The information regarding a single upper SAP connection."
      INDEX { 
bcmCallHistoryUSapNumber,
           bcmCallHistoryNumber }
      ::= { bcmCallHistoryTable 1 }


BcmCallHistoryEntry ::=
            SEQUENCE {
-- Parameters
               bcmCallHistoryUSapNumber      SapIndex,
               bcmCallHistoryNumber          CHIndex,
-- Status
               bcmCallHistoryDslChannelUsed  INTEGER,
               bcmCallHistoryBChannelsUsed   DisplayString,
               bcmCallHistoryPeerAddress     DisplayString,
               bcmCallHistoryPeerSubAddress  DisplayString,
               bcmCallHistoryOrigin          INTEGER,
               bcmCallHistorySetupTime       TimeTicks,
               bcmCallHistoryConnectTime     TimeTicks,
               bcmCallHistoryDisconnectTime  TimeTicks
}


bcmCallHistoryUSapNumber   OBJECT-TYPE
      SYNTAX   SapIndex
      ACCESS   read-only
      STATUS   mandatory
      DESCRIPTION
"Indicates the upper SAP involved in this call history.

Range of Values: 1-20 for BRI ISDN
                 1-64 for PRI ISDN

Default Value: none"
      ::= { bcmCallHistoryEntry 1 }


bcmCallHistoryNumber    OBJECT-TYPE
      SYNTAX   CHIndex
      ACCESS   read-only
      STATUS   mandatory
      DESCRIPTION
"Indicates the unique identifier for this call history.

Range of Values: 1

Default Value: none"
      ::= { bcmCallHistoryEntry 2 }


bcmCallHistoryDslChannelUsed  OBJECT-TYPE
      SYNTAX   INTEGER (1 .. 8)
      ACCESS   read-only
      STATUS   mandatory
      DESCRIPTION
"Indicates the Digital Subscriber Line involved in this call history.

Range of Values: 1-2 for DI600 (port)
                 1-6 for CX900 (slot)
                 1-8 for CX950 (slot)

Default Value: none"
      ::= { bcmCallHistoryEntry 40 }


bcmCallHistoryBChannelsUsed   OBJECT-TYPE
      SYNTAX   DisplayString (SIZE (0..8))
      ACCESS   read-only
      STATUS   mandatory
      DESCRIPTION
"Indicates a the B channel(s) that have been used in this call 
history (each B channel identified by one-bit position in 32-bit object)

Range of Values: 0-FFFFFFFF hexadecimal

Default Value: none"
      ::= { bcmCallHistoryEntry 41 }


bcmCallHistoryPeerAddress  OBJECT-TYPE
      SYNTAX   DisplayString
      ACCESS   read-only
      STATUS   mandatory
      DESCRIPTION
"Indicates the address to which a call connected in this call history.

Range of Values: 0-16 non-alpha characters (namely, 0123456789*#)

Note: If the number is not known, this value is left blank.

Default Value: none"
     ::= { bcmCallHistoryEntry 42 }


bcmCallHistoryPeerSubAddress  OBJECT-TYPE
      SYNTAX   DisplayString
      ACCESS   read-only
      STATUS   mandatory
      DESCRIPTION
"Indicates the subaddress to which a call connected in this call history.

Range of Values: 0-20 non-alpha characters (namely, 0123456789*#)

Note: If the number is not known, this value is left blank.

Default Value: none"
    ::= { bcmCallHistoryEntry 43 }

bcmCallHistoryOrigin    OBJECT-TYPE
      SYNTAX   INTEGER {
               unknown-src    (1),
               originate-src  (2),
               answer-src     (3),
               callback-src   (4)
            }
      ACCESS   read-only
      STATUS   mandatory
      DESCRIPTION
"Indicates the origin of a call in this call history.

Options:
unknown-src (1): unknown origin

originate-src (2): SAP originated call

answer-src (3): SAP answered call

callback-src (4): SAP called back

Default Value: unknown-src (1)"
      DEFVAL { unknown-src }
      ::= { bcmCallHistoryEntry 44 }


bcmCallHistorySetupTime OBJECT-TYPE
      SYNTAX   TimeTicks
      ACCESS   read-only
      STATUS   mandatory
      DESCRIPTION
"Indicates the system time when the call in this call history was setup.

Range of Values: 0-4, 294, 967, 295

Default Value: none"
      ::= { bcmCallHistoryEntry 45 }


bcmCallHistoryConnectTime  OBJECT-TYPE
      SYNTAX   TimeTicks
      ACCESS   read-only
      STATUS   mandatory
      DESCRIPTION
"Indicates the system time when the call in this call history was connected.

Range of Values: 0-4, 294, 967, 295

Default Value: none"
      ::= { bcmCallHistoryEntry 46 }


bcmCallHistoryDisconnectTime  OBJECT-TYPE
      SYNTAX   TimeTicks
      ACCESS   read-only
      STATUS   mandatory
      DESCRIPTION
"Indicates the system time when the call in this call history was 
disconnected or released.

Range of Values: 0-4, 294, 967, 295

Default Value: none"
      ::= { bcmCallHistoryEntry 47 }


-- Debug Table

-- This table is used to display different structures of the code to be 
-- debugged.
-- The table are the following:
--    DslCB       (Digital Subscriber Line Control Block structure)
--    LSapCB  ( Lower Sap Control Block structure)
--    USapCB   (Upper Sap Control Block structure)
--    CallHistoryCB  (Call Control Block structures)
--    Data Scope  (Information Elements of a Dsl)
-- "L3" being the "layer 3", and "CC" being the "Call Control" layer.


bcmDebugTable     OBJECT-TYPE
   SYNTAX   SEQUENCE OF BcmDebugEntry
   ACCESS   not-accessible
   STATUS   mandatory
   DESCRIPTION
"A table containing control to access debugging information."
   ::= { cxBCM 55 }


   bcmDebugEntry     OBJECT-TYPE
      SYNTAX   BcmDebugEntry
      ACCESS   not-accessible
      STATUS   mandatory
      DESCRIPTION
"The parameters for a specific structure debugging information."
      INDEX {  bcmDebugNumber }
      ::= { bcmDebugTable 1 }


   BcmDebugEntry ::=
      SEQUENCE {
         bcmDebugNumber          SapIndex,
-- Controls
         bcmDebugDslCB           INTEGER,
         bcmDebugLSapCB          INTEGER,
         bcmDebugUSapCB          INTEGER,
         bcmDebugCallHistoryCB   INTEGER,
         bcmDebugDataScope       INTEGER,
         bcmDebugDisconnect      INTEGER
         }


   bcmDebugNumber OBJECT-TYPE
      SYNTAX   SapIndex
      ACCESS   read-only
      STATUS   mandatory
      DESCRIPTION
"Indicates the row containing objects for creating files of debugging 
information.

Default Value: none"
      ::= { bcmDebugEntry 1 }

   bcmDebugDslCB     OBJECT-TYPE
      SYNTAX   INTEGER ( 1 .. 8 )
      ACCESS   write-only
      STATUS   mandatory
      DESCRIPTION
"Creates a file that includes debugging information about DSL 
control block structures for the specified DSL.

Range of Values: 1-2 for DI600 (port)
                 1-6 for CX900 (slot)
                 1-8 for CX950 (slot)

Warning: You should not modify this object without advice of Memotec 
personnel."
      ::= { bcmDebugEntry 10 }


   bcmDebugLSapCB    OBJECT-TYPE
      SYNTAX   INTEGER ( 1 .. 256 )
      ACCESS   write-only
      STATUS   mandatory
      DESCRIPTION
"Creates a file that includes debugging information about lower 
SAP control block structures for the specified SAP.

Range of Values: 1-64 for DI600
                 1-192 for CX900
                 1-256 for CX950

Warning: You should not modify this object without advice of Memotec 
personnel."
                ::= { bcmDebugEntry 11 }

   bcmDebugUSapCB    OBJECT-TYPE
      SYNTAX   INTEGER ( 1 .. 64 )
      ACCESS   write-only
      STATUS   mandatory
      DESCRIPTION
"Creates a file that includes debugging information about upper 
SAP control block structures for the specified SAP.

Range of Values: 1-20 for BRI ISDN
                 1-64 for PRI ISDN

Warning: You should not modify this object without advice of Memotec 
personnel."
      ::= { bcmDebugEntry 12 }

bcmDebugCallHistoryCB      OBJECT-TYPE
      SYNTAX   INTEGER ( 1 .. 64 )
      ACCESS   write-only
      STATUS   mandatory
      DESCRIPTION
"Creates a file that includes debugging information about call 
history for the specified SAP.

Range of Values: 1-20 for BRI ISDN
                 1-64 for PRI ISDN

Warning: You should not modify this object without advice of Memotec 
personnel."
      ::= { bcmDebugEntry 13 }


bcmDebugDataScope    OBJECT-TYPE
      SYNTAX   INTEGER ( 1 .. 8 )
      ACCESS   write-only
      STATUS   mandatory
      DESCRIPTION
"Creates a running display of hexadecimal values over a period measured in 
milliseconds for a given SAP.

Range of Values: 1-2 for DI600 (port)
                 1-6 for CX900 (slot)
                 1-8 for CX950 (slot)

Warning: You should not modify this object without advice of Memotec 
personnel."
      ::= { bcmDebugEntry 14 }


bcmDebugDisconnect    OBJECT-TYPE
      SYNTAX   INTEGER ( 1 .. 64 )
      ACCESS   write-only
      STATUS   mandatory
      DESCRIPTION
"Sends a DISConnect message to a given BCM Upper SAP.

Range of Values: 1-20 for BRI ISDN
                 1-64 for PRI ISDN

Warning: You should not modify this object without advice of Memotec 
personnel."
      --#STARTING-VERSION 1
      ::= { bcmDebugEntry 15 }


-- Traps

bcmLSapStatusIndication TRAP-TYPE
   ENTERPRISE cxBCM
   VARIABLES      {  
                  bcmLSapDslNumber,
                  bcmLSapNumber,
                  bcmLSapStatusEvent
            }
   DESCRIPTION
"Indicates that the event identified by global object bcmLSapStatusEvent has 
occured at lower access point. This trap is only generated when the global 
object bcmTraps is set to value 'enabled'."
::= 1


bcmCallHistoryStatusIndication   TRAP-TYPE
   ENTERPRISE cxBCM
   VARIABLES      {  
               bcmCallHistoryUSapNumber,
               bcmCallHistoryNumber,
               bcmCallHistoryDslChannelUsed,
               bcmCallHistoryBChannelsUsed,
               bcmCallHistoryPeerAddress,
               bcmCallHistoryPeerSubAddress,
               bcmCallHistoryOrigin ,
               bcmCallHistorySetupTime,
               bcmCallHistoryConnectTime,
               bcmCallHistoryDisconnectTime
            }
   DESCRIPTION
"Indicates that the event identified by global object bcmCallHistoryTable has 
occured at upper access point. This trap is only generated when the global 
object bcmCallHistoryTraps is set to value 'enabled'."
::= 2

END
