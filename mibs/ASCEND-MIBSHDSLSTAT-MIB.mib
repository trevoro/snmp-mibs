--			Ascend mibshdslstat MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBSHDSLSTAT-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibshdslDslLineStatus  OBJECT IDENTIFIER ::= { configuration 157}

	-- The mibshdslDslLineStatus table
	--
	-- This table contains parameters for the mibshdslDslLineStatus profile
	--

    mibshdslDslLineStatusTable	OBJECT-TYPE
	SYNTAX		SEQUENCE OF MibshdslDslLineStatusEntry
	ACCESS		not-accessible
	STATUS		mandatory
	DESCRIPTION	"A list of mibshdslDslLineStatus profile entries."
	::= { mibshdslDslLineStatus 1 }

    mibshdslDslLineStatusEntry	OBJECT-TYPE
	SYNTAX		MibshdslDslLineStatusEntry
	ACCESS		not-accessible
	STATUS		mandatory
	DESCRIPTION	"A mibshdslDslLineStatus entry containing objects that
			 maps to the parameters of mibshdslDslLineStatus profile."
	INDEX		{ shdslDslLineStatus-Shelf-o, shdslDslLineStatus-Slot-o, shdslDslLineStatus-Item-o }
	::= { mibshdslDslLineStatusTable 1 }

    MibshdslDslLineStatusEntry ::=
	SEQUENCE {
	    shdslDslLineStatus-Shelf-o
		INTEGER,
	    shdslDslLineStatus-Slot-o
		INTEGER,
	    shdslDslLineStatus-Item-o
		INTEGER,
	    shdslDslLineStatus-PhysicalAddress-Shelf
		INTEGER,
	    shdslDslLineStatus-PhysicalAddress-Slot
		INTEGER,
	    shdslDslLineStatus-PhysicalAddress-ItemNumber
		INTEGER,
	    shdslDslLineStatus-LineState
		INTEGER,
	    shdslDslLineStatus-SparePhysicalAddress-Shelf
		INTEGER,
	    shdslDslLineStatus-SparePhysicalAddress-Slot
		INTEGER,
	    shdslDslLineStatus-SparePhysicalAddress-ItemNumber
		INTEGER,
	    shdslDslLineStatus-SparingState
		INTEGER,
	    shdslDslLineStatus-SparingChangeReason
		INTEGER,
	    shdslDslLineStatus-SparingChangeTime
		INTEGER,
	    shdslDslLineStatus-SparingChangeCounter
		INTEGER,
	    shdslDslLineStatus-VpiVciRange
		INTEGER,
	    shdslDslLineStatus-VpSwitchingVpi
		INTEGER,
	    shdslDslLineStatus-PhysicalStatus-IfGroupIndex
		INTEGER,
	    shdslDslLineStatus-PhysicalStatus-UnitType
		INTEGER,
	    shdslDslLineStatus-PhysicalStatus-InterfaceType
		INTEGER,
	    shdslDslLineStatus-PhysicalStatus-DevLineState
		INTEGER,
	    shdslDslLineStatus-PhysicalStatus-OperationalRate
		INTEGER,
	    shdslDslLineStatus-PhysicalStatus-FirmwareVer
		DisplayString,
	    shdslDslLineStatus-PhysicalStatus-HardwareVer
		INTEGER,
	    shdslDslLineStatus-PhysicalStatus-NetworkType
		INTEGER,
	    shdslDslLineStatus-PhysicalStatistic-LineUpTimer-Days
		INTEGER,
	    shdslDslLineStatus-PhysicalStatistic-LineUpTimer-Hours
		INTEGER,
	    shdslDslLineStatus-PhysicalStatistic-LineUpTimer-Minutes
		INTEGER,
	    shdslDslLineStatus-PhysicalStatistic-RxSignalPresent
		INTEGER,
	    shdslDslLineStatus-PhysicalStatistic-LineQuality
		INTEGER,
	    shdslDslLineStatus-PhysicalStatistic-UpDwnCntr
		INTEGER,
	    shdslDslLineStatus-PhysicalStatistic-SelfTest
		INTEGER,
	    shdslDslLineStatus-PhysicalStatistic-TransmitPower
		INTEGER,
	    shdslDslLineStatus-PhysicalStatistic-FramerSyncStatus
		INTEGER,
	    shdslDslLineStatus-PhysicalStatistic-CodeViolations
		INTEGER,
	    shdslDslLineStatus-PhysicalStatistic-ErroredSecond
		INTEGER,
	    shdslDslLineStatus-PhysicalStatistic-SeverelyErroredSecond
		INTEGER,
	    shdslDslLineStatus-PhysicalStatistic-LoswSecond
		INTEGER,
	    shdslDslLineStatus-PhysicalStatistic-UnavailableSecond
		INTEGER,
	    shdslDslLineStatus-PhysicalStatistic-LoopAttenuation
		INTEGER,
	    shdslDslLineStatus-PhysicalStatistic-Snr
		INTEGER,
	    shdslDslLineStatus-PhysicalStatistic-SturLoopAttenuation
		INTEGER,
	    shdslDslLineStatus-PhysicalStatistic-SturSnr
		INTEGER,
	    shdslDslLineStatus-Action-o
		INTEGER
	}

    shdslDslLineStatus-Shelf-o	OBJECT-TYPE
	SYNTAX	INTEGER
	ACCESS	read-only
	STATUS	mandatory
	DESCRIPTION	""
	::= { mibshdslDslLineStatusEntry 1 }

    shdslDslLineStatus-Slot-o	OBJECT-TYPE
	SYNTAX	INTEGER
	ACCESS	read-only
	STATUS	mandatory
	DESCRIPTION	""
	::= { mibshdslDslLineStatusEntry 2 }

    shdslDslLineStatus-Item-o	OBJECT-TYPE
	SYNTAX	INTEGER
	ACCESS	read-only
	STATUS	mandatory
	DESCRIPTION	""
	::= { mibshdslDslLineStatusEntry 3 }

    shdslDslLineStatus-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibshdslDslLineStatusEntry 4 }

    shdslDslLineStatus-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibshdslDslLineStatusEntry 5 }

    shdslDslLineStatus-PhysicalAddress-ItemNumber	OBJECT-TYPE
	SYNTAX	INTEGER
	ACCESS	read-write
	STATUS	mandatory
	DESCRIPTION	"A number that specifies an addressable entity within the context of shelf and slot."
	::= { mibshdslDslLineStatusEntry 6 }

    shdslDslLineStatus-LineState	OBJECT-TYPE
	SYNTAX	INTEGER {
		    doesNotExist (1),
		    disabled (2),
		    active (3)
		}
	ACCESS	read-only
	STATUS	mandatory
	DESCRIPTION	"The overall state of the line."
	::= { mibshdslDslLineStatusEntry 7 }

    shdslDslLineStatus-SparePhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibshdslDslLineStatusEntry 8 }

    shdslDslLineStatus-SparePhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibshdslDslLineStatusEntry 9 }

    shdslDslLineStatus-SparePhysicalAddress-ItemNumber	OBJECT-TYPE
	SYNTAX	INTEGER
	ACCESS	read-write
	STATUS	mandatory
	DESCRIPTION	"A number that specifies an addressable entity within the context of shelf and slot."
	::= { mibshdslDslLineStatusEntry 10 }

    shdslDslLineStatus-SparingState	OBJECT-TYPE
	SYNTAX	INTEGER {
		    sparingNone (1),
		    primaryActive (2),
		    primaryInactive (3),
		    secondaryActive (4),
		    secondaryInactive (5)
		}
	ACCESS	read-only
	STATUS	mandatory
	DESCRIPTION	"The sparing state of the line."
	::= { mibshdslDslLineStatusEntry 11 }

    shdslDslLineStatus-SparingChangeReason	OBJECT-TYPE
	SYNTAX	INTEGER {
		    unknown (1),
		    manual (2),
		    automatic (3),
		    test (4)
		}
	ACCESS	read-only
	STATUS	mandatory
	DESCRIPTION	"The reson for the last sparing state change."
	::= { mibshdslDslLineStatusEntry 12 }

    shdslDslLineStatus-SparingChangeTime	OBJECT-TYPE
	SYNTAX	INTEGER
	ACCESS	read-only
	STATUS	mandatory
	DESCRIPTION	"The time of the last sparing state change."
	::= { mibshdslDslLineStatusEntry 13 }

    shdslDslLineStatus-SparingChangeCounter	OBJECT-TYPE
	SYNTAX	INTEGER
	ACCESS	read-only
	STATUS	mandatory
	DESCRIPTION	"The number of sparing state changes."
	::= { mibshdslDslLineStatusEntry 14 }

    shdslDslLineStatus-VpiVciRange	OBJECT-TYPE
	SYNTAX	INTEGER {
		    vpi01Vci321023 (6),
		    vpi03Vci32511 (1),
		    vpi07Vci32255 (2),
		    vpi015Vci32127 (3),
		    vpi031Vci3263 (4),
		    notApplicable (5)
		}
	ACCESS	read-only
	STATUS	mandatory
	DESCRIPTION	"The valid range of vpi and vci for the circuits established for the line. This range can change only after LIM reboot."
	::= { mibshdslDslLineStatusEntry 15 }

    shdslDslLineStatus-VpSwitchingVpi	OBJECT-TYPE
	SYNTAX	INTEGER
	ACCESS	read-only
	STATUS	mandatory
	DESCRIPTION	"VPI to be used for the VP switching. Rest of the VPIs will be used for the VC switching."
	::= { mibshdslDslLineStatusEntry 16 }

    shdslDslLineStatus-PhysicalStatus-IfGroupIndex	OBJECT-TYPE
	SYNTAX	INTEGER
	ACCESS	read-only
	STATUS	mandatory
	DESCRIPTION	"Interface groups index assigned to this physical port."
	::= { mibshdslDslLineStatusEntry 17 }

    shdslDslLineStatus-PhysicalStatus-UnitType	OBJECT-TYPE
	SYNTAX	INTEGER {
		    coe (1),
		    cpe (2)
		}
	ACCESS	read-only
	STATUS	mandatory
	DESCRIPTION	"Unit types defines if the node is operating Central Office or Customer Premise equipment software."
	::= { mibshdslDslLineStatusEntry 18 }

    shdslDslLineStatus-PhysicalStatus-InterfaceType	OBJECT-TYPE
	SYNTAX	INTEGER {
		    default (1),
		    gShdsl (2),
		    hdsl2 (3)
		}
	ACCESS	read-only
	STATUS	mandatory
	DESCRIPTION	"Interface type defines if the node is operating on SHDSL or GSHDSL"
	::= { mibshdslDslLineStatusEntry 19 }

    shdslDslLineStatus-PhysicalStatus-DevLineState	OBJECT-TYPE
	SYNTAX	INTEGER {
		    portUp (2),
		    test (3),
		    startupHandshake (4),
		    startupTraining (5),
		    startupDownload (6),
		    idle (7),
		    down (8),
		    outOfService (9),
		    unknown (10),
		    analogLoopback (11),
		    digitalLoopback (12)
		}
	ACCESS	read-only
	STATUS	mandatory
	DESCRIPTION	"Display of current interface state."
	::= { mibshdslDslLineStatusEntry 20 }

    shdslDslLineStatus-PhysicalStatus-OperationalRate	OBJECT-TYPE
	SYNTAX	INTEGER
	ACCESS	read-only
	STATUS	mandatory
	DESCRIPTION	"Operational up and down stream rate. Zero means unknown."
	::= { mibshdslDslLineStatusEntry 21 }

    shdslDslLineStatus-PhysicalStatus-FirmwareVer	OBJECT-TYPE
	SYNTAX	DisplayString
	ACCESS	read-only
	STATUS	mandatory
	DESCRIPTION	"Firmware version ID."
	::= { mibshdslDslLineStatusEntry 22 }

    shdslDslLineStatus-PhysicalStatus-HardwareVer	OBJECT-TYPE
	SYNTAX	INTEGER
	ACCESS	read-only
	STATUS	mandatory
	DESCRIPTION	"Hardware chip version."
	::= { mibshdslDslLineStatusEntry 23 }

    shdslDslLineStatus-PhysicalStatus-NetworkType	OBJECT-TYPE
	SYNTAX	INTEGER {
		    no (1),
		    yes (2)
		}
	ACCESS	read-only
	STATUS	mandatory
	DESCRIPTION	"Current Standard Network type. Either Annex A, Annex B or Annex B ANFP."
	::= { mibshdslDslLineStatusEntry 43 }

    shdslDslLineStatus-PhysicalStatistic-LineUpTimer-Days	OBJECT-TYPE
	SYNTAX	INTEGER
	ACCESS	read-only
	STATUS	mandatory
	DESCRIPTION	"Number of days that the DSL line has been up."
	::= { mibshdslDslLineStatusEntry 24 }

    shdslDslLineStatus-PhysicalStatistic-LineUpTimer-Hours	OBJECT-TYPE
	SYNTAX	INTEGER
	ACCESS	read-only
	STATUS	mandatory
	DESCRIPTION	"Number of hours that the DSL line has been up."
	::= { mibshdslDslLineStatusEntry 25 }

    shdslDslLineStatus-PhysicalStatistic-LineUpTimer-Minutes	OBJECT-TYPE
	SYNTAX	INTEGER
	ACCESS	read-only
	STATUS	mandatory
	DESCRIPTION	"Number of minutes that the DSL line has been up."
	::= { mibshdslDslLineStatusEntry 26 }

    shdslDslLineStatus-PhysicalStatistic-RxSignalPresent	OBJECT-TYPE
	SYNTAX	INTEGER {
		    yes (3),
		    no (2)
		}
	ACCESS	read-only
	STATUS	mandatory
	DESCRIPTION	"State if the receive signal is present or not."
	::= { mibshdslDslLineStatusEntry 27 }

    shdslDslLineStatus-PhysicalStatistic-LineQuality	OBJECT-TYPE
	SYNTAX	INTEGER
	ACCESS	read-only
	STATUS	mandatory
	DESCRIPTION	"While the port is in the up state, this parameter displays the line quality."
	::= { mibshdslDslLineStatusEntry 28 }

    shdslDslLineStatus-PhysicalStatistic-UpDwnCntr	OBJECT-TYPE
	SYNTAX	INTEGER
	ACCESS	read-only
	STATUS	mandatory
	DESCRIPTION	"Interface Up Down counter value displays the number of times the interface trasitions from a down to up state."
	::= { mibshdslDslLineStatusEntry 29 }

    shdslDslLineStatus-PhysicalStatistic-SelfTest	OBJECT-TYPE
	SYNTAX	INTEGER {
		    passed (1),
		    selfTestFailed (2),
		    localLoopBackFailed (3)
		}
	ACCESS	read-only
	STATUS	mandatory
	DESCRIPTION	"Hardware/firmware self test results."
	::= { mibshdslDslLineStatusEntry 30 }

    shdslDslLineStatus-PhysicalStatistic-TransmitPower	OBJECT-TYPE
	SYNTAX	INTEGER
	ACCESS	read-only
	STATUS	mandatory
	DESCRIPTION	"Transmit power in DB."
	::= { mibshdslDslLineStatusEntry 31 }

    shdslDslLineStatus-PhysicalStatistic-FramerSyncStatus	OBJECT-TYPE
	SYNTAX	INTEGER {
		    inSync (2),
		    outOfSync (1)
		}
	ACCESS	read-only
	STATUS	mandatory
	DESCRIPTION	"Framer sync status"
	::= { mibshdslDslLineStatusEntry 32 }

    shdslDslLineStatus-PhysicalStatistic-CodeViolations	OBJECT-TYPE
	SYNTAX	INTEGER
	ACCESS	read-only
	STATUS	mandatory
	DESCRIPTION	"Line is defined as a count of SHDSL CRC anomalies occuring during the accumuation period."
	::= { mibshdslDslLineStatusEntry 33 }

    shdslDslLineStatus-PhysicalStatistic-ErroredSecond	OBJECT-TYPE
	SYNTAX	INTEGER
	ACCESS	read-only
	STATUS	mandatory
	DESCRIPTION	"Errored second is defined as a count of 1 second intervals during which one or more CRC anomalies are declaired and/or one or more LOSW defects are declared."
	::= { mibshdslDslLineStatusEntry 34 }

    shdslDslLineStatus-PhysicalStatistic-SeverelyErroredSecond	OBJECT-TYPE
	SYNTAX	INTEGER
	ACCESS	read-only
	STATUS	mandatory
	DESCRIPTION	"Line is defined as a count of 1 second intervals for during which at least 50 CRC anomalies are declared or one or more LOSW defects are declared."
	::= { mibshdslDslLineStatusEntry 35 }

    shdslDslLineStatus-PhysicalStatistic-LoswSecond	OBJECT-TYPE
	SYNTAX	INTEGER
	ACCESS	read-only
	STATUS	mandatory
	DESCRIPTION	"Line is defined as a count of 1 second intervals during which one or more SHDSL LOSW defects are declared."
	::= { mibshdslDslLineStatusEntry 36 }

    shdslDslLineStatus-PhysicalStatistic-UnavailableSecond	OBJECT-TYPE
	SYNTAX	INTEGER
	ACCESS	read-only
	STATUS	mandatory
	DESCRIPTION	"Line is a count of 1 second intervals for which the SHDSL line is unavailable. The SHDSL line becomes unavailable at the onset of 10 contiguous SES-L's. Once unavailable the SHDSL line becomes available at the onset of 10 contiguous seconds with no SES-L's."
	::= { mibshdslDslLineStatusEntry 37 }

    shdslDslLineStatus-PhysicalStatistic-LoopAttenuation	OBJECT-TYPE
	SYNTAX	INTEGER
	ACCESS	read-only
	STATUS	mandatory
	DESCRIPTION	"Current loop attenuation in DB. "
	::= { mibshdslDslLineStatusEntry 38 }

    shdslDslLineStatus-PhysicalStatistic-Snr	OBJECT-TYPE
	SYNTAX	INTEGER
	ACCESS	read-only
	STATUS	mandatory
	DESCRIPTION	"While the port is in the up state, this parameter displays the Signal to Noise Ratio."
	::= { mibshdslDslLineStatusEntry 40 }

    shdslDslLineStatus-PhysicalStatistic-SturLoopAttenuation	OBJECT-TYPE
	SYNTAX	INTEGER
	ACCESS	read-only
	STATUS	mandatory
	DESCRIPTION	"Current loop attenuation in DB from the STU-R. "
	::= { mibshdslDslLineStatusEntry 41 }

    shdslDslLineStatus-PhysicalStatistic-SturSnr	OBJECT-TYPE
	SYNTAX	INTEGER
	ACCESS	read-only
	STATUS	mandatory
	DESCRIPTION	"While the port is in the up state, this parameter displays the Signal to Noise Ratio from the STU-R."
	::= { mibshdslDslLineStatusEntry 42 }

    shdslDslLineStatus-Action-o	OBJECT-TYPE
	SYNTAX	INTEGER {
		    noAction (1),
		    createProfile (2),
		    deleteProfile (3)
		}
	ACCESS	read-write
	STATUS	mandatory
	DESCRIPTION	""
	::= { mibshdslDslLineStatusEntry 39 }

END
