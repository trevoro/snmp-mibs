TERAWAVE-teraAlarm-MIB DEFINITIONS ::= BEGIN
        -- Created by sml2mib compiler 
        IMPORTS

	Counter32 FROM SNMPv2-SMI
 enterprises,  OBJECT-TYPE,  Counter,  Gauge,  TimeTicks
        FROM RFC1155-SMI;

terawave OBJECT IDENTIFIER ::=  { enterprises 4513 }

teratraps OBJECT IDENTIFIER ::=  { terawave 1 }

teraAlarms OBJECT IDENTIFIER ::=  { teratraps 1 }

     -- teraAlarmMiscTable (special)

teraConfig OBJECT IDENTIFIER ::=  { teraAlarms 1 }

teraLocalNextAlarmSequence OBJECT-TYPE
          SYNTAX Counter32
          ACCESS read-only
          STATUS mandatory
          DESCRIPTION
               ""
          ::= { teraConfig 2 }

teraResetAlarmHistoryTable OBJECT-TYPE
          SYNTAX INTEGER
                  {
                  noAction(1),
                  reset(2)
                  }
          ACCESS read-write
          STATUS mandatory
          DESCRIPTION
               ""
          ::= { teraConfig 3 }

teraResetEventTable OBJECT-TYPE
          SYNTAX INTEGER
                  {
                  noAction(1),
                  reset(2)
                  }
          ACCESS read-write
          STATUS mandatory
          DESCRIPTION
               ""
          ::= { teraConfig 4 }

     -- teraNextAlarmSequenceTable

teraNextAlarmSequenceTable OBJECT-TYPE
     SYNTAX SEQUENCE OF TeraNextAlarmSequenceTableEntryType
     ACCESS not-accessible
     STATUS mandatory
     DESCRIPTION
          " table teraNextAlarmSequenceTable"
     ::= { teraConfig 1 }

teraNextAlarmSequenceTableEntry OBJECT-TYPE
          SYNTAX TeraNextAlarmSequenceTableEntryType
          ACCESS not-accessible
          STATUS mandatory
          DESCRIPTION
               " table entry teraNextAlarmSequenceTableEntry "
          INDEX {                   teraActiveAlarmSlot,                  teraPonIndex }
     ::= { teraNextAlarmSequenceTable 1 }

TeraNextAlarmSequenceTableEntryType ::= SEQUENCE {
          teraNextAlarmSequence   
             Counter32
}

teraNextAlarmSequence OBJECT-TYPE
          SYNTAX Counter32
          ACCESS read-only
          STATUS mandatory
          DESCRIPTION
               ""
          ::= { teraNextAlarmSequenceTableEntry 1 }

     -- teraAlarmReportingTable

teraAlarmReportingTable OBJECT-TYPE
     SYNTAX SEQUENCE OF TeraAlarmReportingTableEntryType
     ACCESS not-accessible
     STATUS mandatory
     DESCRIPTION
          " table teraAlarmReportingTable"
     ::= { teraConfig 5 }

teraAlarmReportingTableEntry OBJECT-TYPE
          SYNTAX TeraAlarmReportingTableEntryType
          ACCESS not-accessible
          STATUS mandatory
          DESCRIPTION
               " table entry teraAlarmReportingTableEntry "
          INDEX {                   teraAlarmReportingTableIndex }
     ::= { teraAlarmReportingTable 1 }

TeraAlarmReportingTableEntryType ::= SEQUENCE {
          teraAlarmReportingTableIndex   
             INTEGER (1..3),
          teraAlarmReportingIPaddress   
             OCTET STRING,
          teraAlarmReportingCommunity   
             OCTET STRING
}

teraAlarmReportingTableIndex OBJECT-TYPE
          SYNTAX INTEGER (1..3)
          ACCESS read-only
          STATUS mandatory
          DESCRIPTION
               ""
          ::= { teraAlarmReportingTableEntry 1 }

teraAlarmReportingIPaddress OBJECT-TYPE
          SYNTAX OCTET STRING
          ACCESS read-write
          STATUS mandatory
          DESCRIPTION
               ""
          ::= { teraAlarmReportingTableEntry 2 }

teraAlarmReportingCommunity OBJECT-TYPE
          SYNTAX OCTET STRING
          ACCESS read-write
          STATUS mandatory
          DESCRIPTION
               ""
          ::= { teraAlarmReportingTableEntry 3 }

     -- teraActiveAlarmTable

teraActiveAlarmTable OBJECT-TYPE
     SYNTAX SEQUENCE OF TeraActiveAlarmTableEntryType
     ACCESS not-accessible
     STATUS mandatory
     DESCRIPTION
          " table teraActiveAlarmTable"
     ::= { teraAlarms 2 }

teraActiveAlarmTableEntry OBJECT-TYPE
          SYNTAX TeraActiveAlarmTableEntryType
          ACCESS not-accessible
          STATUS mandatory
          DESCRIPTION
               " table entry teraActiveAlarmTableEntry "
          INDEX {                   teraInstallSlotNumber,                  teraPonIndex,                  teraActiveAlarmSequence }
     ::= { teraActiveAlarmTable 1 }

TeraActiveAlarmTableEntryType ::= SEQUENCE {
          teraActiveAlarmSequence   
             Counter32 (1..65535),
          teraActiveAlarmPort   
             INTEGER,
          teraActiveAlarmPortType   
             INTEGER,
          teraActiveAlarmCardType   
             INTEGER,
          teraActiveAlarmSlot   
             INTEGER,
          teraActiveAlarmPhysPort   
             INTEGER,
          teraActiveAlarmType   
             INTEGER,
          teraActiveAlarmSeverity   
             INTEGER,
          teraActiveAlarmTime   
             OCTET STRING,
          teraActiveAlarmMessage   
             OCTET STRING,
          teraActiveAlarmTimeInSecs   
             INTEGER,
          teraActiveAlarmNEClli   
             OCTET STRING
}

teraActiveAlarmSequence OBJECT-TYPE
          SYNTAX Counter32 (1..65535)
          ACCESS read-only
          STATUS mandatory
          DESCRIPTION
               ""
          ::= { teraActiveAlarmTableEntry 1 }

teraActiveAlarmPort OBJECT-TYPE
          SYNTAX INTEGER
          ACCESS read-only
          STATUS mandatory
          DESCRIPTION
               ""
          ::= { teraActiveAlarmTableEntry 2 }

teraActiveAlarmPortType OBJECT-TYPE
          SYNTAX INTEGER
          ACCESS read-only
          STATUS mandatory
          DESCRIPTION
               ""
          ::= { teraActiveAlarmTableEntry 3 }

teraActiveAlarmCardType OBJECT-TYPE
          SYNTAX INTEGER
          ACCESS read-only
          STATUS mandatory
          DESCRIPTION
               ""
          ::= { teraActiveAlarmTableEntry 4 }

teraActiveAlarmSlot OBJECT-TYPE
          SYNTAX INTEGER
          ACCESS read-only
          STATUS mandatory
          DESCRIPTION
               ""
          ::= { teraActiveAlarmTableEntry 5 }

teraActiveAlarmPhysPort OBJECT-TYPE
          SYNTAX INTEGER
          ACCESS read-only
          STATUS mandatory
          DESCRIPTION
               ""
          ::= { teraActiveAlarmTableEntry 6 }

teraActiveAlarmType OBJECT-TYPE
          SYNTAX INTEGER
          ACCESS read-only
          STATUS mandatory
          DESCRIPTION
               ""
          ::= { teraActiveAlarmTableEntry 7 }

teraActiveAlarmSeverity OBJECT-TYPE
          SYNTAX INTEGER
                  {
                  nominal(1),
                  informational(2),
                  minor(3),
                  major(4),
                  critical(5)
                  }
          ACCESS read-only
          STATUS mandatory
          DESCRIPTION
               ""
          ::= { teraActiveAlarmTableEntry 8 }

teraActiveAlarmTime OBJECT-TYPE
          SYNTAX OCTET STRING
          ACCESS read-only
          STATUS mandatory
          DESCRIPTION
               ""
          ::= { teraActiveAlarmTableEntry 9 }

teraActiveAlarmMessage OBJECT-TYPE
          SYNTAX OCTET STRING
          ACCESS read-only
          STATUS mandatory
          DESCRIPTION
               ""
          ::= { teraActiveAlarmTableEntry 10 }

teraActiveAlarmTimeInSecs OBJECT-TYPE
          SYNTAX INTEGER
          ACCESS read-only
          STATUS mandatory
          DESCRIPTION
               ""
          ::= { teraActiveAlarmTableEntry 11 }

teraActiveAlarmNEClli OBJECT-TYPE
          SYNTAX OCTET STRING
          ACCESS read-only
          STATUS mandatory
          DESCRIPTION
               ""
          ::= { teraActiveAlarmTableEntry 12 }

     -- teraHistoryAlarmTable

teraHistoryAlarmTable OBJECT-TYPE
     SYNTAX SEQUENCE OF TeraHistoryAlarmTableEntryType
     ACCESS not-accessible
     STATUS mandatory
     DESCRIPTION
          " table teraHistoryAlarmTable"
     ::= { teraAlarms 3 }

teraHistoryAlarmTableEntry OBJECT-TYPE
          SYNTAX TeraHistoryAlarmTableEntryType
          ACCESS not-accessible
          STATUS mandatory
          DESCRIPTION
               " table entry teraHistoryAlarmTableEntry "
          INDEX {                   teraInstallSlotNumber,                  teraPonIndex,                  teraHistoryAlarmSequence }
     ::= { teraHistoryAlarmTable 1 }

TeraHistoryAlarmTableEntryType ::= SEQUENCE {
          teraHistoryAlarmSequence   
             Counter32 (1..65535),
          teraHistoryAlarmPort   
             INTEGER,
          teraHistoryAlarmPortType   
             INTEGER,
          teraHistoryAlarmCardType   
             INTEGER,
          teraHistoryAlarmSlot   
             INTEGER,
          teraHistoryAlarmPhysPort   
             INTEGER,
          teraHistoryAlarmType   
             INTEGER,
          teraHistoryAlarmSeverity   
             INTEGER,
          teraHistoryAlarmStart   
             OCTET STRING,
          teraHistoryAlarmStop   
             OCTET STRING,
          teraHistoryActiveAlarmSequence   
             Counter32 (1..65535),
          teraHistoryAlarmMessage   
             OCTET STRING,
          teraHistoryAlarmStartInSecs   
             INTEGER,
          teraHistoryAlarmStopInSecs   
             INTEGER,
          teraHistoryAlarmNEClli   
             OCTET STRING
}

teraHistoryAlarmSequence OBJECT-TYPE
          SYNTAX Counter32 (1..65535)
          ACCESS read-only
          STATUS mandatory
          DESCRIPTION
               ""
          ::= { teraHistoryAlarmTableEntry 1 }

teraHistoryAlarmPort OBJECT-TYPE
          SYNTAX INTEGER
          ACCESS read-only
          STATUS mandatory
          DESCRIPTION
               ""
          ::= { teraHistoryAlarmTableEntry 2 }

teraHistoryAlarmPortType OBJECT-TYPE
          SYNTAX INTEGER
          ACCESS read-only
          STATUS mandatory
          DESCRIPTION
               ""
          ::= { teraHistoryAlarmTableEntry 3 }

teraHistoryAlarmCardType OBJECT-TYPE
          SYNTAX INTEGER
          ACCESS read-only
          STATUS mandatory
          DESCRIPTION
               ""
          ::= { teraHistoryAlarmTableEntry 4 }

teraHistoryAlarmSlot OBJECT-TYPE
          SYNTAX INTEGER
          ACCESS read-only
          STATUS mandatory
          DESCRIPTION
               ""
          ::= { teraHistoryAlarmTableEntry 5 }

teraHistoryAlarmPhysPort OBJECT-TYPE
          SYNTAX INTEGER
          ACCESS read-only
          STATUS mandatory
          DESCRIPTION
               ""
          ::= { teraHistoryAlarmTableEntry 6 }

teraHistoryAlarmType OBJECT-TYPE
          SYNTAX INTEGER
          ACCESS read-only
          STATUS mandatory
          DESCRIPTION
               ""
          ::= { teraHistoryAlarmTableEntry 7 }

teraHistoryAlarmSeverity OBJECT-TYPE
          SYNTAX INTEGER
                  {
                  nominal(1),
                  informational(2),
                  minor(3),
                  major(4),
                  critical(5)
                  }
          ACCESS read-only
          STATUS mandatory
          DESCRIPTION
               ""
          ::= { teraHistoryAlarmTableEntry 8 }

teraHistoryAlarmStart OBJECT-TYPE
          SYNTAX OCTET STRING
          ACCESS read-only
          STATUS mandatory
          DESCRIPTION
               ""
          ::= { teraHistoryAlarmTableEntry 9 }

teraHistoryAlarmStop OBJECT-TYPE
          SYNTAX OCTET STRING
          ACCESS read-only
          STATUS mandatory
          DESCRIPTION
               ""
          ::= { teraHistoryAlarmTableEntry 10 }

teraHistoryActiveAlarmSequence OBJECT-TYPE
          SYNTAX Counter32 (1..65535)
          ACCESS read-only
          STATUS mandatory
          DESCRIPTION
               ""
          ::= { teraHistoryAlarmTableEntry 11 }

teraHistoryAlarmMessage OBJECT-TYPE
          SYNTAX OCTET STRING
          ACCESS read-only
          STATUS mandatory
          DESCRIPTION
               ""
          ::= { teraHistoryAlarmTableEntry 12 }

teraHistoryAlarmStartInSecs OBJECT-TYPE
          SYNTAX INTEGER
          ACCESS read-only
          STATUS mandatory
          DESCRIPTION
               ""
          ::= { teraHistoryAlarmTableEntry 13 }

teraHistoryAlarmStopInSecs OBJECT-TYPE
          SYNTAX INTEGER
          ACCESS read-only
          STATUS mandatory
          DESCRIPTION
               ""
          ::= { teraHistoryAlarmTableEntry 14 }

teraHistoryAlarmNEClli OBJECT-TYPE
          SYNTAX OCTET STRING
          ACCESS read-only
          STATUS mandatory
          DESCRIPTION
               ""
          ::= { teraHistoryAlarmTableEntry 15 }

     -- teraEventTable

teraEventTable OBJECT-TYPE
     SYNTAX SEQUENCE OF TeraEventTableEntryType
     ACCESS not-accessible
     STATUS mandatory
     DESCRIPTION
          " table teraEventTable"
     ::= { teraAlarms 4 }

teraEventTableEntry OBJECT-TYPE
          SYNTAX TeraEventTableEntryType
          ACCESS not-accessible
          STATUS mandatory
          DESCRIPTION
               " table entry teraEventTableEntry "
          INDEX {                   teraInstallSlotNumber,                  teraPonIndex,                  teraEventIndex }
     ::= { teraEventTable 1 }

TeraEventTableEntryType ::= SEQUENCE {
          teraEventIndex   
             Counter32 (1..65535),
          teraEventPort   
             INTEGER,
          teraEventPortType   
             INTEGER,
          teraEventCardType   
             INTEGER,
          teraEventSlot   
             INTEGER,
          teraEventPhysPort   
             INTEGER,
          teraEventType   
             INTEGER,
          teraEventSeverity   
             INTEGER,
          teraEventTime   
             OCTET STRING,
          teraEventMessage   
             OCTET STRING,
          teraEventTimeInSecs   
             INTEGER,
          teraEventNEClli   
             OCTET STRING
}

teraEventIndex OBJECT-TYPE
          SYNTAX Counter32 (1..65535)
          ACCESS read-only
          STATUS mandatory
          DESCRIPTION
               ""
          ::= { teraEventTableEntry 1 }

teraEventPort OBJECT-TYPE
          SYNTAX INTEGER
          ACCESS read-only
          STATUS mandatory
          DESCRIPTION
               ""
          ::= { teraEventTableEntry 2 }

teraEventPortType OBJECT-TYPE
          SYNTAX INTEGER
          ACCESS read-only
          STATUS mandatory
          DESCRIPTION
               ""
          ::= { teraEventTableEntry 3 }

teraEventCardType OBJECT-TYPE
          SYNTAX INTEGER
          ACCESS read-only
          STATUS mandatory
          DESCRIPTION
               ""
          ::= { teraEventTableEntry 4 }

teraEventSlot OBJECT-TYPE
          SYNTAX INTEGER
          ACCESS read-only
          STATUS mandatory
          DESCRIPTION
               ""
          ::= { teraEventTableEntry 5 }

teraEventPhysPort OBJECT-TYPE
          SYNTAX INTEGER
          ACCESS read-only
          STATUS mandatory
          DESCRIPTION
               ""
          ::= { teraEventTableEntry 6 }

teraEventType OBJECT-TYPE
          SYNTAX INTEGER
          ACCESS read-only
          STATUS mandatory
          DESCRIPTION
               ""
          ::= { teraEventTableEntry 7 }

teraEventSeverity OBJECT-TYPE
          SYNTAX INTEGER
                  {
                  nominal(1),
                  informational(2),
                  minor(3),
                  major(4),
                  critical(5)
                  }
          ACCESS read-only
          STATUS mandatory
          DESCRIPTION
               ""
          ::= { teraEventTableEntry 8 }

teraEventTime OBJECT-TYPE
          SYNTAX OCTET STRING
          ACCESS read-only
          STATUS mandatory
          DESCRIPTION
               ""
          ::= { teraEventTableEntry 9 }

teraEventMessage OBJECT-TYPE
          SYNTAX OCTET STRING
          ACCESS read-only
          STATUS mandatory
          DESCRIPTION
               ""
          ::= { teraEventTableEntry 10 }

teraEventTimeInSecs OBJECT-TYPE
          SYNTAX INTEGER
          ACCESS read-only
          STATUS mandatory
          DESCRIPTION
               ""
          ::= { teraEventTableEntry 11 }

teraEventNEClli OBJECT-TYPE
          SYNTAX OCTET STRING
          ACCESS read-only
          STATUS mandatory
          DESCRIPTION
               ""
          ::= { teraEventTableEntry 12 }

     -- teraAlarmConfigTable

teraAlarmConfigTable OBJECT-TYPE
     SYNTAX SEQUENCE OF TeraAlarmConfigTableEntryType
     ACCESS not-accessible
     STATUS mandatory
     DESCRIPTION
          " table teraAlarmConfigTable"
     ::= { teraAlarms 5 }

teraAlarmConfigTableEntry OBJECT-TYPE
          SYNTAX TeraAlarmConfigTableEntryType
          ACCESS not-accessible
          STATUS mandatory
          DESCRIPTION
               " table entry teraAlarmConfigTableEntry "
          INDEX {                   teraActiveAlarmType }
     ::= { teraAlarmConfigTable 1 }

TeraAlarmConfigTableEntryType ::= SEQUENCE {
          teraAlarmConfigFilter   
             INTEGER,
          teraAlarmConfigSeverity   
             INTEGER
}

teraAlarmConfigFilter OBJECT-TYPE
          SYNTAX INTEGER
                  {
                  ignore(1),
                  log(2),
                  report(3)
                  }
          ACCESS read-write
          STATUS mandatory
          DESCRIPTION
               ""
          ::= { teraAlarmConfigTableEntry 1 }

teraAlarmConfigSeverity OBJECT-TYPE
          SYNTAX INTEGER
                  {
                  nominal(1),
                  informational(2),
                  minor(3),
                  major(4),
                  critical(5)
                  }
          ACCESS read-write
          STATUS mandatory
          DESCRIPTION
               ""
          ::= { teraAlarmConfigTableEntry 2 }

     -- teraEventConfigTable

teraEventConfigTable OBJECT-TYPE
     SYNTAX SEQUENCE OF TeraEventConfigTableEntryType
     ACCESS not-accessible
     STATUS mandatory
     DESCRIPTION
          " table teraEventConfigTable"
     ::= { teraAlarms 6 }

teraEventConfigTableEntry OBJECT-TYPE
          SYNTAX TeraEventConfigTableEntryType
          ACCESS not-accessible
          STATUS mandatory
          DESCRIPTION
               " table entry teraEventConfigTableEntry "
          INDEX {                   teraEventType }
     ::= { teraEventConfigTable 1 }

TeraEventConfigTableEntryType ::= SEQUENCE {
          teraEventConfigFilter   
             INTEGER,
          teraEventConfigSeverity   
             INTEGER
}

teraEventConfigFilter OBJECT-TYPE
          SYNTAX INTEGER
                  {
                  ignore(1),
                  log(2),
                  report(3)
                  }
          ACCESS read-write
          STATUS mandatory
          DESCRIPTION
               ""
          ::= { teraEventConfigTableEntry 1 }

teraEventConfigSeverity OBJECT-TYPE
          SYNTAX INTEGER
                  {
                  nominal(1),
                  informational(2),
                  minor(3),
                  major(4),
                  critical(5)
                  }
          ACCESS read-write
          STATUS mandatory
          DESCRIPTION
               ""
          ::= { teraEventConfigTableEntry 2 }

     -- teraAllActiveAlarmTable

teraAllActiveAlarmTable OBJECT-TYPE
     SYNTAX SEQUENCE OF TeraAllActiveAlarmTableEntryType
     ACCESS not-accessible
     STATUS mandatory
     DESCRIPTION
          " table teraAllActiveAlarmTable"
     ::= { teraAlarms 7 }

teraAllActiveAlarmTableEntry OBJECT-TYPE
          SYNTAX TeraAllActiveAlarmTableEntryType
          ACCESS not-accessible
          STATUS mandatory
          DESCRIPTION
               " table entry teraAllActiveAlarmTableEntry "
          INDEX {                   teraAllActiveAlarmIndex }
     ::= { teraAllActiveAlarmTable 1 }

TeraAllActiveAlarmTableEntryType ::= SEQUENCE {
          teraAllActiveAlarmIndex   
             Counter32,
          teraAllActiveAlarmPort   
             INTEGER,
          teraAllActiveAlarmPortType   
             INTEGER,
          teraAllActiveAlarmCardType   
             INTEGER,
          teraAllActiveAlarmSlot   
             INTEGER,
          teraAllActiveAlarmPhysPort   
             INTEGER,
          teraAllActiveAlarmType   
             INTEGER,
          teraAllActiveAlarmSeverity   
             INTEGER,
          teraAllActiveAlarmTime   
             OCTET STRING,
          teraAllActiveAlarmMessage   
             OCTET STRING,
          teraAllActiveAlarmTimeInSecs   
             INTEGER
}

teraAllActiveAlarmIndex OBJECT-TYPE
          SYNTAX Counter32
          ACCESS read-only
          STATUS mandatory
          DESCRIPTION
               ""
          ::= { teraAllActiveAlarmTableEntry 1 }

teraAllActiveAlarmPort OBJECT-TYPE
          SYNTAX INTEGER
          ACCESS read-only
          STATUS mandatory
          DESCRIPTION
               ""
          ::= { teraAllActiveAlarmTableEntry 2 }

teraAllActiveAlarmPortType OBJECT-TYPE
          SYNTAX INTEGER
          ACCESS read-only
          STATUS mandatory
          DESCRIPTION
               ""
          ::= { teraAllActiveAlarmTableEntry 3 }

teraAllActiveAlarmCardType OBJECT-TYPE
          SYNTAX INTEGER
          ACCESS read-only
          STATUS mandatory
          DESCRIPTION
               ""
          ::= { teraAllActiveAlarmTableEntry 4 }

teraAllActiveAlarmSlot OBJECT-TYPE
          SYNTAX INTEGER
          ACCESS read-only
          STATUS mandatory
          DESCRIPTION
               ""
          ::= { teraAllActiveAlarmTableEntry 5 }

teraAllActiveAlarmPhysPort OBJECT-TYPE
          SYNTAX INTEGER
          ACCESS read-only
          STATUS mandatory
          DESCRIPTION
               ""
          ::= { teraAllActiveAlarmTableEntry 6 }

teraAllActiveAlarmType OBJECT-TYPE
          SYNTAX INTEGER
          ACCESS read-only
          STATUS mandatory
          DESCRIPTION
               ""
          ::= { teraAllActiveAlarmTableEntry 7 }

teraAllActiveAlarmSeverity OBJECT-TYPE
          SYNTAX INTEGER
                  {
                  nominal(1),
                  informational(2),
                  minor(3),
                  major(4),
                  critical(5)
                  }
          ACCESS read-only
          STATUS mandatory
          DESCRIPTION
               ""
          ::= { teraAllActiveAlarmTableEntry 8 }

teraAllActiveAlarmTime OBJECT-TYPE
          SYNTAX OCTET STRING
          ACCESS read-only
          STATUS mandatory
          DESCRIPTION
               ""
          ::= { teraAllActiveAlarmTableEntry 9 }

teraAllActiveAlarmMessage OBJECT-TYPE
          SYNTAX OCTET STRING
          ACCESS read-only
          STATUS mandatory
          DESCRIPTION
               ""
          ::= { teraAllActiveAlarmTableEntry 10 }

teraAllActiveAlarmTimeInSecs OBJECT-TYPE
          SYNTAX INTEGER
          ACCESS read-only
          STATUS mandatory
          DESCRIPTION
               ""
          ::= { teraAllActiveAlarmTableEntry 11 }

     -- teraLocalActiveAlarmTable

teraLocalActiveAlarmTable OBJECT-TYPE
     SYNTAX SEQUENCE OF TeraLocalActiveAlarmTableEntryType
     ACCESS not-accessible
     STATUS mandatory
     DESCRIPTION
          " table teraLocalActiveAlarmTable"
     ::= { teraAlarms 8 }

teraLocalActiveAlarmTableEntry OBJECT-TYPE
          SYNTAX TeraLocalActiveAlarmTableEntryType
          ACCESS not-accessible
          STATUS mandatory
          DESCRIPTION
               " table entry teraLocalActiveAlarmTableEntry "
          INDEX {                   teraLocalActiveAlarmSequence }
     ::= { teraLocalActiveAlarmTable 1 }

TeraLocalActiveAlarmTableEntryType ::= SEQUENCE {
          teraLocalActiveAlarmSequence   
             Counter32 (1..65535),
          teraLocalActiveAlarmPort   
             INTEGER,
          teraLocalActiveAlarmPortType   
             INTEGER,
          teraLocalActiveAlarmCardType   
             INTEGER,
          teraLocalActiveAlarmSlot   
             INTEGER,
          teraLocalActiveAlarmPhysPort   
             INTEGER,
          teraLocalActiveAlarmType   
             INTEGER,
          teraLocalActiveAlarmSeverity   
             INTEGER,
          teraLocalActiveAlarmTime   
             OCTET STRING,
          teraLocalActiveAlarmMessage   
             OCTET STRING,
          teraLocalActiveAlarmTimeInSecs   
             INTEGER
}

teraLocalActiveAlarmSequence OBJECT-TYPE
          SYNTAX Counter32 (1..65535)
          ACCESS read-only
          STATUS mandatory
          DESCRIPTION
               ""
          ::= { teraLocalActiveAlarmTableEntry 1 }

teraLocalActiveAlarmPort OBJECT-TYPE
          SYNTAX INTEGER
          ACCESS read-only
          STATUS mandatory
          DESCRIPTION
               ""
          ::= { teraLocalActiveAlarmTableEntry 2 }

teraLocalActiveAlarmPortType OBJECT-TYPE
          SYNTAX INTEGER
          ACCESS read-only
          STATUS mandatory
          DESCRIPTION
               ""
          ::= { teraLocalActiveAlarmTableEntry 3 }

teraLocalActiveAlarmCardType OBJECT-TYPE
          SYNTAX INTEGER
          ACCESS read-only
          STATUS mandatory
          DESCRIPTION
               ""
          ::= { teraLocalActiveAlarmTableEntry 4 }

teraLocalActiveAlarmSlot OBJECT-TYPE
          SYNTAX INTEGER
          ACCESS read-only
          STATUS mandatory
          DESCRIPTION
               ""
          ::= { teraLocalActiveAlarmTableEntry 5 }

teraLocalActiveAlarmPhysPort OBJECT-TYPE
          SYNTAX INTEGER
          ACCESS read-only
          STATUS mandatory
          DESCRIPTION
               ""
          ::= { teraLocalActiveAlarmTableEntry 6 }

teraLocalActiveAlarmType OBJECT-TYPE
          SYNTAX INTEGER
          ACCESS read-only
          STATUS mandatory
          DESCRIPTION
               ""
          ::= { teraLocalActiveAlarmTableEntry 7 }

teraLocalActiveAlarmSeverity OBJECT-TYPE
          SYNTAX INTEGER
                  {
                  nominal(1),
                  informational(2),
                  minor(3),
                  major(4),
                  critical(5)
                  }
          ACCESS read-only
          STATUS mandatory
          DESCRIPTION
               ""
          ::= { teraLocalActiveAlarmTableEntry 8 }

teraLocalActiveAlarmTime OBJECT-TYPE
          SYNTAX OCTET STRING
          ACCESS read-only
          STATUS mandatory
          DESCRIPTION
               ""
          ::= { teraLocalActiveAlarmTableEntry 9 }

teraLocalActiveAlarmMessage OBJECT-TYPE
          SYNTAX OCTET STRING
          ACCESS read-only
          STATUS mandatory
          DESCRIPTION
               ""
          ::= { teraLocalActiveAlarmTableEntry 10 }

teraLocalActiveAlarmTimeInSecs OBJECT-TYPE
          SYNTAX INTEGER
          ACCESS read-only
          STATUS mandatory
          DESCRIPTION
               ""
          ::= { teraLocalActiveAlarmTableEntry 11 }

     -- teraLocalHistoryAlarmTable

teraLocalHistoryAlarmTable OBJECT-TYPE
     SYNTAX SEQUENCE OF TeraLocalHistoryAlarmTableEntryType
     ACCESS not-accessible
     STATUS mandatory
     DESCRIPTION
          " table teraLocalHistoryAlarmTable"
     ::= { teraAlarms 9 }

teraLocalHistoryAlarmTableEntry OBJECT-TYPE
          SYNTAX TeraLocalHistoryAlarmTableEntryType
          ACCESS not-accessible
          STATUS mandatory
          DESCRIPTION
               " table entry teraLocalHistoryAlarmTableEntry "
          INDEX {                   teraLocalHistoryAlarmSequence }
     ::= { teraLocalHistoryAlarmTable 1 }

TeraLocalHistoryAlarmTableEntryType ::= SEQUENCE {
          teraLocalHistoryAlarmSequence   
             Counter32 (1..65535),
          teraLocalHistoryAlarmPort   
             INTEGER,
          teraLocalHistoryAlarmPortType   
             INTEGER,
          teraLocalHistoryAlarmCardType   
             INTEGER,
          teraLocalHistoryAlarmSlot   
             INTEGER,
          teraLocalHistoryAlarmPhysPort   
             INTEGER,
          teraLocalHistoryAlarmType   
             INTEGER,
          teraLocalHistoryAlarmSeverity   
             INTEGER,
          teraLocalHistoryAlarmStart   
             OCTET STRING,
          teraLocalHistoryAlarmStop   
             OCTET STRING,
          teraLocalHistoryActiveAlarmSequence   
             Counter32 (1..65535),
          teraLocalHistoryActiveAlarmMessage   
             OCTET STRING,
          teraLocalHistoryAlarmStartInSecs   
             INTEGER,
          teraLocalHistoryAlarmStopInSecs   
             INTEGER
}

teraLocalHistoryAlarmSequence OBJECT-TYPE
          SYNTAX Counter32 (1..65535)
          ACCESS read-only
          STATUS mandatory
          DESCRIPTION
               ""
          ::= { teraLocalHistoryAlarmTableEntry 1 }

teraLocalHistoryAlarmPort OBJECT-TYPE
          SYNTAX INTEGER
          ACCESS read-only
          STATUS mandatory
          DESCRIPTION
               ""
          ::= { teraLocalHistoryAlarmTableEntry 2 }

teraLocalHistoryAlarmPortType OBJECT-TYPE
          SYNTAX INTEGER
          ACCESS read-only
          STATUS mandatory
          DESCRIPTION
               ""
          ::= { teraLocalHistoryAlarmTableEntry 3 }

teraLocalHistoryAlarmCardType OBJECT-TYPE
          SYNTAX INTEGER
          ACCESS read-only
          STATUS mandatory
          DESCRIPTION
               ""
          ::= { teraLocalHistoryAlarmTableEntry 4 }

teraLocalHistoryAlarmSlot OBJECT-TYPE
          SYNTAX INTEGER
          ACCESS read-only
          STATUS mandatory
          DESCRIPTION
               ""
          ::= { teraLocalHistoryAlarmTableEntry 5 }

teraLocalHistoryAlarmPhysPort OBJECT-TYPE
          SYNTAX INTEGER
          ACCESS read-only
          STATUS mandatory
          DESCRIPTION
               ""
          ::= { teraLocalHistoryAlarmTableEntry 6 }

teraLocalHistoryAlarmType OBJECT-TYPE
          SYNTAX INTEGER
          ACCESS read-only
          STATUS mandatory
          DESCRIPTION
               ""
          ::= { teraLocalHistoryAlarmTableEntry 7 }

teraLocalHistoryAlarmSeverity OBJECT-TYPE
          SYNTAX INTEGER
                  {
                  nominal(1),
                  informational(2),
                  minor(3),
                  major(4),
                  critical(5)
                  }
          ACCESS read-only
          STATUS mandatory
          DESCRIPTION
               ""
          ::= { teraLocalHistoryAlarmTableEntry 8 }

teraLocalHistoryAlarmStart OBJECT-TYPE
          SYNTAX OCTET STRING
          ACCESS read-only
          STATUS mandatory
          DESCRIPTION
               ""
          ::= { teraLocalHistoryAlarmTableEntry 9 }

teraLocalHistoryAlarmStop OBJECT-TYPE
          SYNTAX OCTET STRING
          ACCESS read-only
          STATUS mandatory
          DESCRIPTION
               ""
          ::= { teraLocalHistoryAlarmTableEntry 10 }

teraLocalHistoryActiveAlarmSequence OBJECT-TYPE
          SYNTAX Counter32 (1..65535)
          ACCESS read-only
          STATUS mandatory
          DESCRIPTION
               ""
          ::= { teraLocalHistoryAlarmTableEntry 11 }

teraLocalHistoryActiveAlarmMessage OBJECT-TYPE
          SYNTAX OCTET STRING
          ACCESS read-only
          STATUS mandatory
          DESCRIPTION
               ""
          ::= { teraLocalHistoryAlarmTableEntry 12 }

teraLocalHistoryAlarmStartInSecs OBJECT-TYPE
          SYNTAX INTEGER
          ACCESS read-only
          STATUS mandatory
          DESCRIPTION
               ""
          ::= { teraLocalHistoryAlarmTableEntry 13 }

teraLocalHistoryAlarmStopInSecs OBJECT-TYPE
          SYNTAX INTEGER
          ACCESS read-only
          STATUS mandatory
          DESCRIPTION
               ""
          ::= { teraLocalHistoryAlarmTableEntry 14 }

     -- teraAlarmPortFilterTable

teraAlarmPortFilterTable OBJECT-TYPE
     SYNTAX SEQUENCE OF TeraAlarmPortFilterTableEntryType
     ACCESS not-accessible
     STATUS mandatory
     DESCRIPTION
          " table teraAlarmPortFilterTable"
     ::= { teraAlarms 10 }

teraAlarmPortFilterTableEntry OBJECT-TYPE
          SYNTAX TeraAlarmPortFilterTableEntryType
          ACCESS not-accessible
          STATUS mandatory
          DESCRIPTION
               " table entry teraAlarmPortFilterTableEntry "
          INDEX {                   teraActiveAlarmPort }
     ::= { teraAlarmPortFilterTable 1 }

TeraAlarmPortFilterTableEntryType ::= SEQUENCE {
          teraAlarmPortFilter   
             INTEGER,
          teraEventPortFilter   
             INTEGER,
          teraAlarmPortFilterTableStatus   
             INTEGER
}

teraAlarmPortFilter OBJECT-TYPE
          SYNTAX INTEGER
                  {
                  no(1),
                  yes(2)
                  }
          ACCESS read-write
          STATUS mandatory
          DESCRIPTION
               ""
          ::= { teraAlarmPortFilterTableEntry 1 }

teraEventPortFilter OBJECT-TYPE
          SYNTAX INTEGER
                  {
                  no(1),
                  yes(2)
                  }
          ACCESS read-write
          STATUS mandatory
          DESCRIPTION
               ""
          ::= { teraAlarmPortFilterTableEntry 2 }

teraAlarmPortFilterTableStatus OBJECT-TYPE
          SYNTAX INTEGER
                  {
                  ok(1),
                  delete(2)
                  }
          ACCESS read-write
          STATUS mandatory
          DESCRIPTION
               ""
          ::= { teraAlarmPortFilterTableEntry 3 }

     -- teraAlarmPortMaskTable

teraAlarmPortMaskTable OBJECT-TYPE
     SYNTAX SEQUENCE OF TeraAlarmPortMaskTableEntryType
     ACCESS not-accessible
     STATUS mandatory
     DESCRIPTION
          " table teraAlarmPortMaskTable"
     ::= { teraAlarms 14 }

teraAlarmPortMaskTableEntry OBJECT-TYPE
          SYNTAX TeraAlarmPortMaskTableEntryType
          ACCESS not-accessible
          STATUS mandatory
          DESCRIPTION
               " table entry teraAlarmPortMaskTableEntry "
          INDEX {                   teraAlarmPortMaskSlot,                  teraAlarmPortMaskPort }
     ::= { teraAlarmPortMaskTable 1 }

TeraAlarmPortMaskTableEntryType ::= SEQUENCE {
          teraAlarmPortMaskSlot   
             INTEGER,
          teraAlarmPortMaskPort   
             INTEGER,
          teraAlarmPortUnMask   
             INTEGER
}

teraAlarmPortMaskSlot OBJECT-TYPE
          SYNTAX INTEGER
          ACCESS read-only
          STATUS mandatory
          DESCRIPTION
               ""
          ::= { teraAlarmPortMaskTableEntry 1 }

teraAlarmPortMaskPort OBJECT-TYPE
          SYNTAX INTEGER
          ACCESS read-only
          STATUS mandatory
          DESCRIPTION
               ""
          ::= { teraAlarmPortMaskTableEntry 2 }

teraAlarmPortUnMask OBJECT-TYPE
          SYNTAX INTEGER
                  {
                  mask(1),
                  unmask(2),
                  delete(3)
                  }
          ACCESS read-write
          STATUS mandatory
          DESCRIPTION
               ""
          ::= { teraAlarmPortMaskTableEntry 3 }

END
