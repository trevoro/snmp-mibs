Nortel-Magellan-Passport-FraDpnTrunksMIB
DEFINITIONS ::= BEGIN



IMPORTS

      OBJECT-TYPE
   FROM RFC-1212

      passportMIBs
   FROM Nortel-Magellan-Passport-UsefulDefinitionsMIB

      Counter32,
      RowPointer,
      DisplayString,
      StorageType,
      RowStatus,
      Gauge32,
      Unsigned32
   FROM Nortel-Magellan-Passport-StandardTextualConventionsMIB

      NonReplicated,
      Link
   FROM Nortel-Magellan-Passport-TextualConventionsMIB

      dpnGate,
      dpnGateIndex
   FROM Nortel-Magellan-Passport-DpnTrunksMIB;




-- LAST-UPDATED   "9808030000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     FraDpnTrunks Enterprise MIB."

fraDpnTrunksMIB OBJECT IDENTIFIER ::= { passportMIBs 68 }










-- DpnGate/n FrAccess
-- This component provides Layer 2 trunking protocol, to be used by 
-- DpnGateway running over FrMux frame relay interface.

dpnGateFrAccess OBJECT IDENTIFIER ::= { dpnGate 4 }



dpnGateFrAccessRowStatusTable OBJECT-TYPE
   SYNTAX     SEQUENCE OF DpnGateFrAccessRowStatusEntry
   ACCESS     not-accessible
   STATUS     mandatory
   DESCRIPTION
     "This entry controls the addition and deletion of 
      dpnGateFrAccess components."
::= { dpnGateFrAccess 1 }

dpnGateFrAccessRowStatusEntry OBJECT-TYPE
   SYNTAX     DpnGateFrAccessRowStatusEntry
   ACCESS     not-accessible
   STATUS     mandatory
   DESCRIPTION
     "A single entry in the table represents a single 
      dpnGateFrAccess component."
   INDEX {
      dpnGateIndex,
      dpnGateFrAccessIndex }
::= { dpnGateFrAccessRowStatusTable 1 }

DpnGateFrAccessRowStatusEntry ::= SEQUENCE {
   dpnGateFrAccessRowStatus
      RowStatus,
   dpnGateFrAccessComponentName
      DisplayString,
   dpnGateFrAccessStorageType
      StorageType,
   dpnGateFrAccessIndex
      NonReplicated }

dpnGateFrAccessRowStatus OBJECT-TYPE
   SYNTAX     RowStatus 
   ACCESS     read-write
   STATUS     mandatory
   DESCRIPTION
     "This variable is used as the basis for SNMP naming of
      dpnGateFrAccess components.
      These components can be added and deleted."
::= { dpnGateFrAccessRowStatusEntry 1 }

dpnGateFrAccessComponentName OBJECT-TYPE
   SYNTAX     DisplayString 
   ACCESS     read-only
   STATUS     mandatory
   DESCRIPTION
     "This variable provides the component's string name for
      use with the ASCII Console Interface"
::= { dpnGateFrAccessRowStatusEntry 2 }

dpnGateFrAccessStorageType OBJECT-TYPE
   SYNTAX     StorageType 
   ACCESS     read-only
   STATUS     mandatory
   DESCRIPTION
     "This variable represents the storage type value for the
      dpnGateFrAccess tables."
::= { dpnGateFrAccessRowStatusEntry 4 }

dpnGateFrAccessIndex OBJECT-TYPE
   SYNTAX     NonReplicated 
   ACCESS     not-accessible
   STATUS     mandatory
   DESCRIPTION
     "This variable represents the index for the dpnGateFrAccess tables."
::= { dpnGateFrAccessRowStatusEntry 10 }

dpnGateFrAccessProvTable OBJECT-TYPE
   SYNTAX     SEQUENCE OF DpnGateFrAccessProvEntry
   ACCESS     not-accessible
   STATUS     mandatory
   DESCRIPTION
     "This group of provisionable attributes contains the parameters used 
      by Unacknowledged, Utp, and FrAccess for monitoring link quality."
::= { dpnGateFrAccess 10 }

dpnGateFrAccessProvEntry OBJECT-TYPE
   SYNTAX     DpnGateFrAccessProvEntry
   ACCESS     not-accessible
   STATUS     mandatory
   DESCRIPTION
     "An entry in the dpnGateFrAccessProvTable."
   INDEX {
      dpnGateIndex,
      dpnGateFrAccessIndex }
::= { dpnGateFrAccessProvTable 1 }

DpnGateFrAccessProvEntry ::= SEQUENCE {
   dpnGateFrAccessMaximumErroredInterval
      Unsigned32,
   dpnGateFrAccessReceiveErrorSensitivity
      Unsigned32 }

dpnGateFrAccessMaximumErroredInterval OBJECT-TYPE
   SYNTAX     Unsigned32 (0 | 1..15)
   ACCESS     read-write
   STATUS     mandatory
   DESCRIPTION
     "This attribute specifies the interval time over which the error 
      threshold (as specified by receiveErrorSensitivity) must be 
      continuously exceeded before the Unacknowledged, Utp, or 
      FrAccess component can be degraded. Once the error interval count 
      exceeds the provisioned value, the Unacknowledged, Utp, or 
      FrAccess component issues an alarm indicating that link quality has 
      degraded, and it disables its parent component. The exception to 
      this is a value of zero, the default, which indicates that the 
      mechanism is completely disabled."
   DEFVAL     { 0 }
::= { dpnGateFrAccessProvEntry 1 }

dpnGateFrAccessReceiveErrorSensitivity OBJECT-TYPE
   SYNTAX     Unsigned32 (0 | 1..10)
   ACCESS     read-write
   STATUS     mandatory
   DESCRIPTION
     "This attribute is the allowable error rate beyond which the 
      Unacknowledged, Utp, or FrAccess component can be degraded if it 
      persists for a duration longer than the maximumErrorInterval. The 
      threshold is expressed as a percentage of number of errored frames 
      in the last interval per number of frames received in the last interval. 
      The exception to this is a value of zero, which indicates that the 
      mechanism is completely disabled. The configurable values are:
      0 = the mechanism is completely disabled
      1 = 1/(2**1)
      2 = 1/(2**2)
      3 = 1/(2**3)
      :
      10 = 1/(2**10)"
   DEFVAL     { 3 }
::= { dpnGateFrAccessProvEntry 2 }

dpnGateFrAccessStateTable OBJECT-TYPE
   SYNTAX     SEQUENCE OF DpnGateFrAccessStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { dpnGateFrAccess 11 }

dpnGateFrAccessStateEntry OBJECT-TYPE
   SYNTAX     DpnGateFrAccessStateEntry
   ACCESS     not-accessible
   STATUS     mandatory
   DESCRIPTION
     "An entry in the dpnGateFrAccessStateTable."
   INDEX {
      dpnGateIndex,
      dpnGateFrAccessIndex }
::= { dpnGateFrAccessStateTable 1 }

DpnGateFrAccessStateEntry ::= SEQUENCE {
   dpnGateFrAccessAdminState
      INTEGER,
   dpnGateFrAccessOperationalState
      INTEGER,
   dpnGateFrAccessUsageState
      INTEGER,
   dpnGateFrAccessAvailabilityStatus
      OCTET STRING,
   dpnGateFrAccessProceduralStatus
      OCTET STRING,
   dpnGateFrAccessControlStatus
      OCTET STRING,
   dpnGateFrAccessAlarmStatus
      OCTET STRING,
   dpnGateFrAccessStandbyStatus
      INTEGER,
   dpnGateFrAccessUnknownStatus
      INTEGER }

dpnGateFrAccessAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { dpnGateFrAccessStateEntry 1 }

dpnGateFrAccessOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { dpnGateFrAccessStateEntry 2 }

dpnGateFrAccessUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { dpnGateFrAccessStateEntry 3 }

dpnGateFrAccessAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { dpnGateFrAccessStateEntry 4 }

dpnGateFrAccessProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { dpnGateFrAccessStateEntry 5 }

dpnGateFrAccessControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { dpnGateFrAccessStateEntry 6 }

dpnGateFrAccessAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { dpnGateFrAccessStateEntry 7 }

dpnGateFrAccessStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { dpnGateFrAccessStateEntry 8 }

dpnGateFrAccessUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { dpnGateFrAccessStateEntry 9 }

dpnGateFrAccessOpTable OBJECT-TYPE
   SYNTAX     SEQUENCE OF DpnGateFrAccessOpEntry
   ACCESS     not-accessible
   STATUS     mandatory
   DESCRIPTION
     "This group of attributes contains the set of LTP operational 
      parameters measured and maintained by this component."
::= { dpnGateFrAccess 12 }

dpnGateFrAccessOpEntry OBJECT-TYPE
   SYNTAX     DpnGateFrAccessOpEntry
   ACCESS     not-accessible
   STATUS     mandatory
   DESCRIPTION
     "An entry in the dpnGateFrAccessOpTable."
   INDEX {
      dpnGateIndex,
      dpnGateFrAccessIndex }
::= { dpnGateFrAccessOpTable 1 }

DpnGateFrAccessOpEntry ::= SEQUENCE {
   dpnGateFrAccessRoundTripDelay
      Gauge32 }

dpnGateFrAccessRoundTripDelay OBJECT-TYPE
   SYNTAX     Gauge32 (0..1500)
   ACCESS     read-only
   STATUS     mandatory
   DESCRIPTION
     "This is the measured Round Trip Delay (ms) discovered with the 
      remote through the LTP staging protocol. The value includes 
      emission, propagation, and queuing delays. A 2 byte control frame 
      is used to perform the measurement. A value of zero is displayed 
      when the link is disabled or the measured Round Trip Delay is 
      unknown."
::= { dpnGateFrAccessOpEntry 1 }

dpnGateFrAccessStatsTable OBJECT-TYPE
   SYNTAX     SEQUENCE OF DpnGateFrAccessStatsEntry
   ACCESS     not-accessible
   STATUS     mandatory
   DESCRIPTION
     "This group contains the operational statistics for FrAccess."
::= { dpnGateFrAccess 13 }

dpnGateFrAccessStatsEntry OBJECT-TYPE
   SYNTAX     DpnGateFrAccessStatsEntry
   ACCESS     not-accessible
   STATUS     mandatory
   DESCRIPTION
     "An entry in the dpnGateFrAccessStatsTable."
   INDEX {
      dpnGateIndex,
      dpnGateFrAccessIndex }
::= { dpnGateFrAccessStatsTable 1 }

DpnGateFrAccessStatsEntry ::= SEQUENCE {
   dpnGateFrAccessReceivedBytesFromIf
      Counter32,
   dpnGateFrAccessLostFramesFromIf
      Counter32,
   dpnGateFrAccessDiscardBadFromIf
      Counter32,
   dpnGateFrAccessDiscardExcessToIf
      Counter32 }

dpnGateFrAccessReceivedBytesFromIf OBJECT-TYPE
   SYNTAX     Counter32 
   ACCESS     read-only
   STATUS     mandatory
   DESCRIPTION
     "This attribute counts the number of bytes received by FrAccess in 
      information frames. When the maximum count is reached the count 
      wraps to zero."
::= { dpnGateFrAccessStatsEntry 1 }

dpnGateFrAccessLostFramesFromIf OBJECT-TYPE
   SYNTAX     Counter32 
   ACCESS     read-only
   STATUS     mandatory
   DESCRIPTION
     "This attribute counts the frames lost in the direction from interface, 
      the loss of which is detected based on the sequence number 
      mechanism. The reason for a loss may be the congestion-related 
      loss in the external frame relay network, or errors/congestion 
      developing in the FrMux service. When FrMux statistics do not 
      show errors/congestion developing internally in FrMux, then the 
      losses visible through this statistic should be attributed to the 
      external frame relay network. When the maximum count is reached 
      the count wraps to zero."
::= { dpnGateFrAccessStatsEntry 2 }

dpnGateFrAccessDiscardBadFromIf OBJECT-TYPE
   SYNTAX     Counter32 
   ACCESS     read-only
   STATUS     mandatory
   DESCRIPTION
     "This attribute counts the number of frames discarded in the 
      direction 'from interface', because they are unknown to the 
      FrAccess protocol. When the maximum count is reached the count 
      wraps to zero."
::= { dpnGateFrAccessStatsEntry 3 }

dpnGateFrAccessDiscardExcessToIf OBJECT-TYPE
   SYNTAX     Counter32 
   ACCESS     read-only
   STATUS     mandatory
   DESCRIPTION
     "This attribute counts the number of frames discarded in the 
      direction 'to interface' because of congestion on the transmit queue. 
      When the maximum count is reached the count wraps to zero."
::= { dpnGateFrAccessStatsEntry 4 }


-- DpnGate/n FrAccess FrMuxSetup
-- This component contains operational and provisionable attributes 
-- for setting up a FrMux Dlci to act as a transport for DpnGate/n 
-- FrAccess. 

dpnGateFrAccessFrMuxSetup OBJECT IDENTIFIER ::= { dpnGateFrAccess 2 }



dpnGateFrAccessFrMuxSetupRowStatusTable OBJECT-TYPE
   SYNTAX     SEQUENCE OF DpnGateFrAccessFrMuxSetupRowStatusEntry
   ACCESS     not-accessible
   STATUS     mandatory
   DESCRIPTION
     "This entry controls the addition and deletion of 
      dpnGateFrAccessFrMuxSetup components."
::= { dpnGateFrAccessFrMuxSetup 1 }

dpnGateFrAccessFrMuxSetupRowStatusEntry OBJECT-TYPE
   SYNTAX     DpnGateFrAccessFrMuxSetupRowStatusEntry
   ACCESS     not-accessible
   STATUS     mandatory
   DESCRIPTION
     "A single entry in the table represents a single 
      dpnGateFrAccessFrMuxSetup component."
   INDEX {
      dpnGateIndex,
      dpnGateFrAccessIndex,
      dpnGateFrAccessFrMuxSetupIndex }
::= { dpnGateFrAccessFrMuxSetupRowStatusTable 1 }

DpnGateFrAccessFrMuxSetupRowStatusEntry ::= SEQUENCE {
   dpnGateFrAccessFrMuxSetupRowStatus
      RowStatus,
   dpnGateFrAccessFrMuxSetupComponentName
      DisplayString,
   dpnGateFrAccessFrMuxSetupStorageType
      StorageType,
   dpnGateFrAccessFrMuxSetupIndex
      NonReplicated }

dpnGateFrAccessFrMuxSetupRowStatus OBJECT-TYPE
   SYNTAX     RowStatus 
   ACCESS     read-only
   STATUS     mandatory
   DESCRIPTION
     "This variable is used as the basis for SNMP naming of
      dpnGateFrAccessFrMuxSetup components.
      These components cannot be added nor deleted."
::= { dpnGateFrAccessFrMuxSetupRowStatusEntry 1 }

dpnGateFrAccessFrMuxSetupComponentName OBJECT-TYPE
   SYNTAX     DisplayString 
   ACCESS     read-only
   STATUS     mandatory
   DESCRIPTION
     "This variable provides the component's string name for
      use with the ASCII Console Interface"
::= { dpnGateFrAccessFrMuxSetupRowStatusEntry 2 }

dpnGateFrAccessFrMuxSetupStorageType OBJECT-TYPE
   SYNTAX     StorageType 
   ACCESS     read-only
   STATUS     mandatory
   DESCRIPTION
     "This variable represents the storage type value for the
      dpnGateFrAccessFrMuxSetup tables."
::= { dpnGateFrAccessFrMuxSetupRowStatusEntry 4 }

dpnGateFrAccessFrMuxSetupIndex OBJECT-TYPE
   SYNTAX     NonReplicated 
   ACCESS     not-accessible
   STATUS     mandatory
   DESCRIPTION
     "This variable represents the index for the dpnGateFrAccessFrMuxSetup tables."
::= { dpnGateFrAccessFrMuxSetupRowStatusEntry 10 }

dpnGateFrAccessFrMuxSetupTrafficDescrTable OBJECT-TYPE
   SYNTAX     SEQUENCE OF DpnGateFrAccessFrMuxSetupTrafficDescrEntry
   ACCESS     not-accessible
   STATUS     mandatory
   DESCRIPTION
     "This group contains the provisionable attributes for the application 
      of which this FrMuxSetup is a subcomponent. The parameters are 
      used for maximum frame size checking and traffic shaping and are 
      to be passed over to FrMux Dlci associated with the application. 
      The attributes in this group are defined in T1.606 Addendum 1."
::= { dpnGateFrAccessFrMuxSetup 10 }

dpnGateFrAccessFrMuxSetupTrafficDescrEntry OBJECT-TYPE
   SYNTAX     DpnGateFrAccessFrMuxSetupTrafficDescrEntry
   ACCESS     not-accessible
   STATUS     mandatory
   DESCRIPTION
     "An entry in the dpnGateFrAccessFrMuxSetupTrafficDescrTable."
   INDEX {
      dpnGateIndex,
      dpnGateFrAccessIndex,
      dpnGateFrAccessFrMuxSetupIndex }
::= { dpnGateFrAccessFrMuxSetupTrafficDescrTable 1 }

DpnGateFrAccessFrMuxSetupTrafficDescrEntry ::= SEQUENCE {
   dpnGateFrAccessFrMuxSetupCommittedInformationRate
      Unsigned32,
   dpnGateFrAccessFrMuxSetupCommittedBurstSize
      Unsigned32,
   dpnGateFrAccessFrMuxSetupMaximumFrameSize
      Unsigned32 }

dpnGateFrAccessFrMuxSetupCommittedInformationRate OBJECT-TYPE
   SYNTAX     Unsigned32 (4800..2048000)
   ACCESS     read-write
   STATUS     mandatory
   DESCRIPTION
     "This attribute specifies, in bit/s, the committed information rate 
      (CIR) to which the traffic transmitted towards the interface is 
      shaped. The minimum value is 4800 bit/s."
   DEFVAL     { 64000 }
::= { dpnGateFrAccessFrMuxSetupTrafficDescrEntry 1 }

dpnGateFrAccessFrMuxSetupCommittedBurstSize OBJECT-TYPE
   SYNTAX     Unsigned32 (0..2048000)
   ACCESS     read-write
   STATUS     obsolete
   DESCRIPTION
     "THIS ATTRIBUTE IS NOT BEING USED."
   DEFVAL     { 64000 }
::= { dpnGateFrAccessFrMuxSetupTrafficDescrEntry 2 }

dpnGateFrAccessFrMuxSetupMaximumFrameSize OBJECT-TYPE
   SYNTAX     Unsigned32 (1..4096)
   ACCESS     read-write
   STATUS     mandatory
   DESCRIPTION
     "This attribute specifies the maximum number of octets which may 
      be included in the information field. The frame relay header and 
      CRC octets are not included in this definition. This attribute 
      corresponds to the dN1 parameter described in the Vendor Forum 
      Specification."
   DEFVAL     { 4096 }
::= { dpnGateFrAccessFrMuxSetupTrafficDescrEntry 3 }

dpnGateFrAccessFrMuxSetupDlciCompNameOpTable OBJECT-TYPE
   SYNTAX     SEQUENCE OF DpnGateFrAccessFrMuxSetupDlciCompNameOpEntry
   ACCESS     not-accessible
   STATUS     mandatory
   DESCRIPTION
     "This group contains the component name of the Dlci which carries 
      the traffic for this application."
::= { dpnGateFrAccessFrMuxSetup 11 }

dpnGateFrAccessFrMuxSetupDlciCompNameOpEntry OBJECT-TYPE
   SYNTAX     DpnGateFrAccessFrMuxSetupDlciCompNameOpEntry
   ACCESS     not-accessible
   STATUS     mandatory
   DESCRIPTION
     "An entry in the dpnGateFrAccessFrMuxSetupDlciCompNameOpTable."
   INDEX {
      dpnGateIndex,
      dpnGateFrAccessIndex,
      dpnGateFrAccessFrMuxSetupIndex }
::= { dpnGateFrAccessFrMuxSetupDlciCompNameOpTable 1 }

DpnGateFrAccessFrMuxSetupDlciCompNameOpEntry ::= SEQUENCE {
   dpnGateFrAccessFrMuxSetupDlciCompName
      RowPointer }

dpnGateFrAccessFrMuxSetupDlciCompName OBJECT-TYPE
   SYNTAX     RowPointer 
   ACCESS     read-only
   STATUS     mandatory
   DESCRIPTION
     "This attribute specifies the component name of the Dlci with which 
      the application using this FrMuxSetup component is associated. The 
      name is a string FrMux/n Dlci/m. For a PVC this is the same 
      component name as provisioned under the subcomponent 
      FrMuxPvcSetup."
::= { dpnGateFrAccessFrMuxSetupDlciCompNameOpEntry 1 }


-- DpnGate/n FrAccess FrMuxSetup PvcSetup
-- This component contains provisionable attributes for setting up a 
-- Dlci associated with the application using this component. The Dlci 
-- is of a PVC type. 

dpnGateFrAccessFrMuxSetupPvcSetup OBJECT IDENTIFIER ::= { dpnGateFrAccessFrMuxSetup 2 }



dpnGateFrAccessFrMuxSetupPvcSetupRowStatusTable OBJECT-TYPE
   SYNTAX     SEQUENCE OF DpnGateFrAccessFrMuxSetupPvcSetupRowStatusEntry
   ACCESS     not-accessible
   STATUS     mandatory
   DESCRIPTION
     "This entry controls the addition and deletion of 
      dpnGateFrAccessFrMuxSetupPvcSetup components."
::= { dpnGateFrAccessFrMuxSetupPvcSetup 1 }

dpnGateFrAccessFrMuxSetupPvcSetupRowStatusEntry OBJECT-TYPE
   SYNTAX     DpnGateFrAccessFrMuxSetupPvcSetupRowStatusEntry
   ACCESS     not-accessible
   STATUS     mandatory
   DESCRIPTION
     "A single entry in the table represents a single 
      dpnGateFrAccessFrMuxSetupPvcSetup component."
   INDEX {
      dpnGateIndex,
      dpnGateFrAccessIndex,
      dpnGateFrAccessFrMuxSetupIndex,
      dpnGateFrAccessFrMuxSetupPvcSetupIndex }
::= { dpnGateFrAccessFrMuxSetupPvcSetupRowStatusTable 1 }

DpnGateFrAccessFrMuxSetupPvcSetupRowStatusEntry ::= SEQUENCE {
   dpnGateFrAccessFrMuxSetupPvcSetupRowStatus
      RowStatus,
   dpnGateFrAccessFrMuxSetupPvcSetupComponentName
      DisplayString,
   dpnGateFrAccessFrMuxSetupPvcSetupStorageType
      StorageType,
   dpnGateFrAccessFrMuxSetupPvcSetupIndex
      NonReplicated }

dpnGateFrAccessFrMuxSetupPvcSetupRowStatus OBJECT-TYPE
   SYNTAX     RowStatus 
   ACCESS     read-only
   STATUS     mandatory
   DESCRIPTION
     "This variable is used as the basis for SNMP naming of
      dpnGateFrAccessFrMuxSetupPvcSetup components.
      These components cannot be added nor deleted."
::= { dpnGateFrAccessFrMuxSetupPvcSetupRowStatusEntry 1 }

dpnGateFrAccessFrMuxSetupPvcSetupComponentName OBJECT-TYPE
   SYNTAX     DisplayString 
   ACCESS     read-only
   STATUS     mandatory
   DESCRIPTION
     "This variable provides the component's string name for
      use with the ASCII Console Interface"
::= { dpnGateFrAccessFrMuxSetupPvcSetupRowStatusEntry 2 }

dpnGateFrAccessFrMuxSetupPvcSetupStorageType OBJECT-TYPE
   SYNTAX     StorageType 
   ACCESS     read-only
   STATUS     mandatory
   DESCRIPTION
     "This variable represents the storage type value for the
      dpnGateFrAccessFrMuxSetupPvcSetup tables."
::= { dpnGateFrAccessFrMuxSetupPvcSetupRowStatusEntry 4 }

dpnGateFrAccessFrMuxSetupPvcSetupIndex OBJECT-TYPE
   SYNTAX     NonReplicated 
   ACCESS     not-accessible
   STATUS     mandatory
   DESCRIPTION
     "This variable represents the index for the dpnGateFrAccessFrMuxSetupPvcSetup tables."
::= { dpnGateFrAccessFrMuxSetupPvcSetupRowStatusEntry 10 }

dpnGateFrAccessFrMuxSetupPvcSetupProvTable OBJECT-TYPE
   SYNTAX     SEQUENCE OF DpnGateFrAccessFrMuxSetupPvcSetupProvEntry
   ACCESS     not-accessible
   STATUS     mandatory
   DESCRIPTION
     "This group contains provisionable attributes for setting up a Dlci 
      associated with the application using the FrMuxSetup component. 
      The Dlci is of the PVC type."
::= { dpnGateFrAccessFrMuxSetupPvcSetup 10 }

dpnGateFrAccessFrMuxSetupPvcSetupProvEntry OBJECT-TYPE
   SYNTAX     DpnGateFrAccessFrMuxSetupPvcSetupProvEntry
   ACCESS     not-accessible
   STATUS     mandatory
   DESCRIPTION
     "An entry in the dpnGateFrAccessFrMuxSetupPvcSetupProvTable."
   INDEX {
      dpnGateIndex,
      dpnGateFrAccessIndex,
      dpnGateFrAccessFrMuxSetupIndex,
      dpnGateFrAccessFrMuxSetupPvcSetupIndex }
::= { dpnGateFrAccessFrMuxSetupPvcSetupProvTable 1 }

DpnGateFrAccessFrMuxSetupPvcSetupProvEntry ::= SEQUENCE {
   dpnGateFrAccessFrMuxSetupPvcSetupDlciName
      Link }

dpnGateFrAccessFrMuxSetupPvcSetupDlciName OBJECT-TYPE
   SYNTAX     Link 
   ACCESS     read-write
   STATUS     mandatory
   DESCRIPTION
     "This attribute is the link to the Dlci which is associated with the 
      application using the FrMuxSetup component."
::= { dpnGateFrAccessFrMuxSetupPvcSetupProvEntry 1 }




-- 
-- Version and Compliance statements
-- 



-- Object-Group Statement:
-- A list of all current accessible leaf objects.

-- OBJECTS { dpnGateFrAccessStandbyStatus,
--           dpnGateFrAccessAlarmStatus,
--           dpnGateFrAccessRoundTripDelay,
--           dpnGateFrAccessUnknownStatus,
--           dpnGateFrAccessOperationalState,
--           dpnGateFrAccessComponentName,
--           dpnGateFrAccessFrMuxSetupPvcSetupRowStatus,
--           dpnGateFrAccessLostFramesFromIf,
--           dpnGateFrAccessStorageType,
--           dpnGateFrAccessFrMuxSetupPvcSetupDlciName,
--           dpnGateFrAccessFrMuxSetupRowStatus,
--           dpnGateFrAccessReceiveErrorSensitivity,
--           dpnGateFrAccessFrMuxSetupMaximumFrameSize,
--           dpnGateFrAccessFrMuxSetupPvcSetupComponentName,
--           dpnGateFrAccessMaximumErroredInterval,
--           dpnGateFrAccessFrMuxSetupCommittedInformationRate,
--           dpnGateFrAccessControlStatus,
--           dpnGateFrAccessAdminState,
--           dpnGateFrAccessFrMuxSetupDlciCompName,
--           dpnGateFrAccessFrMuxSetupPvcSetupStorageType,
--           dpnGateFrAccessUsageState,
--           dpnGateFrAccessReceivedBytesFromIf,
--           dpnGateFrAccessFrMuxSetupComponentName,
--           dpnGateFrAccessRowStatus,
--           dpnGateFrAccessDiscardExcessToIf,
--           dpnGateFrAccessProceduralStatus,
--           dpnGateFrAccessFrMuxSetupStorageType,
--           dpnGateFrAccessAvailabilityStatus,
--           dpnGateFrAccessDiscardBadFromIf }
-- STATUS  mandatory
-- DESCRIPTION
--   "A list of all current accessible leaf objects."

fraDpnTrunksGroup OBJECT IDENTIFIER ::= { fraDpnTrunksMIB 1 }
fraDpnTrunksGroupBE OBJECT IDENTIFIER ::= { fraDpnTrunksGroup 5 }
fraDpnTrunksGroupBE00 OBJECT IDENTIFIER ::= { fraDpnTrunksGroupBE 1 }
fraDpnTrunksGroupBE00A OBJECT IDENTIFIER ::= { fraDpnTrunksGroupBE00 2 }



-- Agent-Capabilities Statement:

-- PRODUCT-RELEASE "Passport Release 7.0 FraDpnTrunks."
-- STATUS          mandatory
-- DESCRIPTION     "FraDpnTrunks MIB: MIB Version BE00A,
--                  Software Version BG00S4C."
-- SUPPORTS        Nortel-Magellan-Passport-FraDpnTrunksMIB
--    INCLUDES     { fraDpnTrunksGroupBE00A }

fraDpnTrunksCapabilities OBJECT IDENTIFIER ::= { fraDpnTrunksMIB 3 }
fraDpnTrunksCapabilitiesBE OBJECT IDENTIFIER ::= { fraDpnTrunksCapabilities 5 }
fraDpnTrunksCapabilitiesBE00 OBJECT IDENTIFIER ::= { fraDpnTrunksCapabilitiesBE 1 }
fraDpnTrunksCapabilitiesBE00A OBJECT IDENTIFIER ::= { fraDpnTrunksCapabilitiesBE00 2 }





END
