-- LLC-2 LAN Convergence MIB
--#CURRENT_VERSION 1

CXLlcLanConv-MIB DEFINITIONS ::= BEGIN


IMPORTS
   Counter         FROM RFC1155-SMI
   OBJECT-TYPE     FROM RFC-1212
   cxLlcLanConv,SapIndex,Alias
            FROM CXProduct-SMI;


    -- All representations of MAC addresses in this MIB Module
    -- use, as a textual convention (i.e. this convention does
    -- not affect their encoding), the data type:

    MacAddress ::= OCTET STRING (SIZE (6))    



--  Service Access Point Configuration Table

--     The table defining all the parameters, status, control and statistics 
--     required to manipulate a LLC-2 LAN Service Access Point (SAP).


llcLanSapTable OBJECT-TYPE
   SYNTAX  SEQUENCE OF LlcLanSapEntry
   ACCESS  not-accessible
   STATUS  mandatory
   DESCRIPTION
"A table containing configuration information about each LLC-2 LAN Service 
Access Point."
   ::= { cxLlcLanConv 10 }


   llcLanSapEntry OBJECT-TYPE
      SYNTAX  LlcLanSapEntry
      ACCESS  not-accessible
      STATUS  mandatory
      DESCRIPTION
"The parameters for a particular LLC-2 LAN Service Access Point."
      INDEX { llcLanSapNumber }
      ::= { llcLanSapTable 1 }


   LlcLanSapEntry ::=
      SEQUENCE {
-- Parameters
         llcLanSapNumber                        SapIndex,
         llcLanSapRowStatus                     INTEGER,
         llcLanSapAlias                         Alias,
         llcLanSapCompanionAlias                Alias,
         llcLanSapRemoteAddress                 MacAddress,
         llcLanSapSrcLlcSap                     INTEGER,
         llcLanSapDstLlcSap                     INTEGER,
-- Control
         llcLanSapControl                       INTEGER,
-- Status
         llcLanSapState                         INTEGER,
-- Statistics
         llcLanSapTxFrames                      Counter,
         llcLanSapRxFrames                      Counter,
         llcLanSapTxOctets                      Counter,
         llcLanSapRxOctets                      Counter,
-- Parameters (enhanced)
         llcLanSapLocalAddress                  MacAddress,
         llcLanSapPhysicalInterface             INTEGER
         }


   llcLanSapNumber OBJECT-TYPE
      SYNTAX  SapIndex
      ACCESS  read-only
      STATUS  mandatory
      DESCRIPTION
"Identifies the Service Access Point by a numerical value. Values are 
unique per Service Access Point."
      ::= { llcLanSapEntry 1 }


   llcLanSapRowStatus OBJECT-TYPE
      SYNTAX  INTEGER {
               invalid         (1),
               valid           (2)
               }
      ACCESS  read-write
      STATUS  mandatory
      DESCRIPTION
"Indicates whether the particular Service Access Point is configured 
within the MIB. Service Access Point entries (rows) may be created by 
setting this object  value to 'valid', or deleted by changing this object 
value to 'invalid'.  Whether or not the row actually disappears is left to 
the implementation so  this object may actually read as 'invalid' for some 
arbitrary length of time."
          ::= { llcLanSapEntry 2 }


   llcLanSapAlias OBJECT-TYPE
      SYNTAX  Alias
      ACCESS  read-write
      STATUS  mandatory
      DESCRIPTION
"Identifies the Service Access Point by a textual name. Names are unique 
per Service Access Point."
      ::= { llcLanSapEntry 3 }


   llcLanSapCompanionAlias OBJECT-TYPE
      SYNTAX  Alias
      ACCESS  read-write
      STATUS  mandatory
      DESCRIPTION
"Identifies the LAN Service Access Point which provides LAN services for 
this LLC-2 LAN SAP. Different LLC-2 SAPs may use the same Companion Alias 
provided that they use a different llcLanSapRemoteAddress or 
llcLanSapSrcLlcSap/ llcLanSapDstLlcSap pair."
      ::= { llcLanSapEntry 4 }
      

   llcLanSapRemoteAddress OBJECT-TYPE
      SYNTAX  MacAddress
      ACCESS  read-write
      STATUS  mandatory
      DESCRIPTION
"This object specifies the MAC address of the remote LAN station to which 
the LLC-2 LAN connection will be established."
      ::= { llcLanSapEntry 5 }


   llcLanSapSrcLlcSap OBJECT-TYPE
      SYNTAX  INTEGER (2..254)
      ACCESS  read-write
      STATUS  mandatory
      DESCRIPTION
"Identifies the source LLC-2 SAP address associated with the connection. 
Only even values are allowed."
      DEFVAL{ 4 }
      ::= { llcLanSapEntry 6 }


   llcLanSapDstLlcSap OBJECT-TYPE
      SYNTAX  INTEGER (2..254)
      ACCESS  read-write
      STATUS  mandatory
      DESCRIPTION
"Identifies the destination LLC SAP address associated with the 
connection. Only even values are allowed."
      DEFVAL{ 4 }
      ::= { llcLanSapEntry 7 }


   llcLanSapControl OBJECT-TYPE
      SYNTAX  INTEGER {
               clearStats              (1),
	       releaseRemoteAddress    (2)
            }
      ACCESS  write-only
      STATUS  mandatory
      DESCRIPTION
"Control associated with the specified service access point. When set to  
'clearStats, statistics counters are reset to zero."
      ::= { llcLanSapEntry 8 }


   llcLanSapState OBJECT-TYPE
      SYNTAX  INTEGER (1..255)
      ACCESS  read-only
      STATUS  mandatory
      DESCRIPTION
"Indicates the current SAP state. This object is a bit map 
which represents the different SAP status:

Type of Status             llcLanSapState Object Value
                           Hex      Decimal
SAP Offline                0x01     001
SAP Unbound from LAPBD     0x02     002
SAP Bound from LAPBD       0x04     004
SAP Connected from LAPBD   0x08     008
SAP Binding to LAN Driver  0x40     064
SAP Bound to LAN Driver    0x80     128

In data transfer mode, the value of this object should be:  

128 + 8 + 4 = 140

The SAP is 'offLine' if it is not configured at the layer
(i.e. just added to the configuration)."
      ::= { llcLanSapEntry 9 }


   llcLanSapTxFrames OBJECT-TYPE
      SYNTAX  Counter
      ACCESS  read-only
      STATUS  mandatory
      DESCRIPTION
"Indicates the number of frames sent from this Service Access Point."
      ::= { llcLanSapEntry 10 }


   llcLanSapRxFrames OBJECT-TYPE
      SYNTAX  Counter
      ACCESS  read-only
      STATUS  mandatory
      DESCRIPTION
"Indicates the number of frames received at this Service Access Point."
      ::= { llcLanSapEntry 11 }


   llcLanSapTxOctets OBJECT-TYPE
      SYNTAX  Counter
      ACCESS  read-only
      STATUS  mandatory
      DESCRIPTION
"Indicates the number of octets sent from this Service Access Point."
      ::= { llcLanSapEntry 12 }


   llcLanSapRxOctets OBJECT-TYPE
      SYNTAX  Counter
      ACCESS  read-only
      STATUS  mandatory
      DESCRIPTION
"Indicates the number of octets received at this Service Access Point."
      ::= { llcLanSapEntry 13 }


   llcLanSapLocalAddress OBJECT-TYPE
      SYNTAX  MacAddress
      ACCESS  read-write
      STATUS  mandatory
      DESCRIPTION
"This object specifies the (Virtual/Real) MAC address of the local LAN port to which 
the LLC-2 layer will bind. LLC-2 will send the value of this object as Virtual
MAC Address to LAN driver in the BindReq message ONLY if it is NOT 0x00000000. The final 
value of this object will be the MAC address provided by lower local LAN driver in 
BindConfirm message.
Default value: 0x0000000000000000."
   --#STARTING_VERSION 1
      ::= { llcLanSapEntry 19 }

   llcLanSapPhysicalInterface OBJECT-TYPE
      SYNTAX  INTEGER {
               ethernet(1),
               tokenring(2)
            }
      ACCESS  read-write
      STATUS  mandatory
      DESCRIPTION
"Identifies the type of physical interface that this Service Access Point uses.

Options
ethernet (1)

tokenring (2)"

      ::= { llcLanSapEntry 20 }

-- Add LLCL MIB level J.Ma March 27,1998
cxLlcLanConvMibLevel OBJECT-TYPE
   SYNTAX  INTEGER
   ACCESS  read-only
   STATUS  mandatory
   DESCRIPTION
"Used to determine current MIB module release supported
by the agent. Object is in decimal."
   DEFVAL { 0 }
   --#STARTING_VERSION 1
   ::= { cxLlcLanConv 20 }

END
