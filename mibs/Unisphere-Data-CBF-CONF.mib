-- *****************************************************************************
-- Unisphere-Data-CBF-CONF
--
-- SNMP Agent Capabilities definitions for the CBF MIB.
--
-- Copyright (c) 2001 Unisphere Networks, Inc.  All rights reserved.
-- *****************************************************************************

Unisphere-Data-CBF-CONF DEFINITIONS ::= BEGIN

IMPORTS
    MODULE-IDENTITY
        FROM SNMPv2-SMI
    AGENT-CAPABILITIES
        FROM SNMPv2-CONF
    usDataAgents
        FROM Unisphere-Data-Agents
    usdCbfGroup
        FROM Unisphere-Data-CBF-MIB;

usdCbfAgent MODULE-IDENTITY
    LAST-UPDATED "200103292023Z"  -- 29-Mar-01 03:23 PM EST
    ORGANIZATION "Unisphere Networks, Inc."
    CONTACT-INFO
        "       Unisphere Networks, Inc.
        Postal: 10 Technology Park Drive
                Westford, MA 01886
                USA
        Tel:    +1 978 589 5800
        E-mail: mib@UnisphereNetworks.com"
    DESCRIPTION
        "The agent capabilities definitions for the Connection-Based Forwarding
        (CBF) protocol management component of the SNMP agent in the Unisphere
        Routing Switch family of products."
    -- Revision History
    REVISION    "200103292023Z"  -- 29-Mar-01 03:23 PM EST  - RX 3.2
    DESCRIPTION
        "The initial release of this management information module."
    ::= { usDataAgents 48 }

usdCbfAgentV1 AGENT-CAPABILITIES
    PRODUCT-RELEASE
        "Version 1 of the Connection-Based Forwarding (CBF) component of the
        Unisphere Routing Switch SNMP agent.  This version of the CBF component
        is supported in the Unisphere RX 3.2 and subsequent system releases."
    STATUS      current
    DESCRIPTION
        "The MIB supported by the SNMP agent for the CBF application
        in the Unisphere Routing Switch."

    SUPPORTS    Unisphere-Data-CBF-MIB
        INCLUDES  { usdCbfGroup }

    ::= { usdCbfAgent 1 }

END
