-- 
-- SPINS-DS1-MIB module definition  
--
-- The definitions in this module specify an initial version of 
-- SPINS mib.
-- 
--

SPINS-DS1-MIB DEFINITIONS ::= BEGIN
IMPORTS
    enterprises, Counter
        FROM RFC1155-SMI
    OBJECT-TYPE
        FROM RFC-1212
    DisplayString
        FROM RFC1213-MIB
    MODULE-IDENTITY, ObjectName, Integer32, Counter32, snmpModules
        FROM SNMPv2-SMI
    TruthValue, DisplayString, TestAndIncr, TimeStamp, RowStatus
        FROM SNMPv2-TC;

	lucent		        OBJECT IDENTIFIER  ::=  {  enterprises  1751  }
	products	        OBJECT IDENTIFIER  ::=  {  lucent  1  }
	softSwitch	        OBJECT IDENTIFIER  ::=  {  products 1198  }
	spinsDeviceServer   OBJECT IDENTIFIER  ::=  {  softSwitch 8 }

	spinsDS1      MODULE-IDENTITY    
        LAST-UPDATED "240701"
        ORGANIZATION "Lucent Technologies"    
        CONTACT-INFO 
                ""    
        DESCRIPTION
                "The MIB module for entities implementing the xxxx
                protocol."  

::=  {  spinsDeviceServer 1 }


	-- mib groups
	-- the sipSystem group - contains information about this deviceServer

	spinsSystem	OBJECT IDENTIFIER  ::=  {  spinsDS1 1 }	
	

END
