TVD-MIB DEFINITIONS ::= BEGIN

IMPORTS
    enterprises                        FROM RFC1155-SMI
    OBJECT-TYPE                        FROM RFC-1212
    TRAP-TYPE                          FROM RFC-1215
    DisplayString 		       FROM RFC1213-MIB
    nai,
	naiTrapAgent,				
	naiTrapShortDescription,	
	naiTrapSeverity,            
	naiTrapAgentVersion,
	naiTrapLongDescription,		 
	naiTrapProblemResolution,	
	naiTrapDiagID,              
	naiTrapURL,                 
	naiTrapSourceDNSName,		
	naiTrapTargetDNSName		FROM NAI-MIB;
 

-- 
-- McAfee MIB DEFINITION
-- 
-- mcafee was assigned the new ID of 12 (as opposed to the older 4)
-- for SNMP structures conforming to the NAI and mcafee standards


mcafee					OBJECT IDENTIFIER ::= { nai 12 }
-- mcafeeTVDTrapBase			OBJECT IDENTIFIER ::= { mcafee 0 }
mcafeeTVDTrap				OBJECT IDENTIFIER ::= { mcafee 0 }
mcafeeStandardTrapField			OBJECT IDENTIFIER ::= { mcafee 1 }

--
-- The following trap is a sample that contains all of the nai standard 
-- trap fields. 



-- 
-- mcafee MIB DEFINITION
-- 
-- mcafee was assigned the new ID of 12 (as opposed to the older 4)
-- for SNMP structures conforming to the NAI and mcafee standards

--  
 
--mcafeeFields MODULE-IDENTITY
--	LAST-UPDATED  "Wed August 1, 1999"
--    ORGANIZATION "Network Associates Inc. mcafee Div."
--    CONTACT-INFO
--    	"Postal:   Network Associates, Inc.
--                   3965 Freedom Circle
--                   Santa Clara, CA  95054
--        Phone:     +1 408 988-3832
--        Internet:  www.nai.com"
--	DESCRIPTION
--    	"mcafee agent MIB definition"
--        	::= { mcafee 1 }
--
--

--
	-- The nai standard trap group
	-- This group contains objects describing NAI standard alarm variable 
	-- definitions which shall be included in each product's trap extension
	-- resulting in transmission of a SNMP trap message.



mcafee-TRAPID  OBJECT-TYPE	
	SYNTAX	INTEGER
	ACCESS  read-only
    STATUS  mandatory
    DESCRIPTION
    "mcafee Event/Alert Id number"		
	::= { mcafeeStandardTrapField 1 }             


mcafee-ENGINEVERSION OBJECT-TYPE		        
        SYNTAX          DisplayString
        ACCESS          read-only
        STATUS          mandatory
        DESCRIPTION
	  "Version string for the current Av Scanner Engine"
            ::= { mcafeeStandardTrapField 2 }

mcafee-DATVERSION OBJECT-TYPE		        
        SYNTAX          DisplayString
        ACCESS          read-only
        STATUS          mandatory
        DESCRIPTION
	  "Version string for the current Av DAT File"
        ::= { mcafeeStandardTrapField 3 }

mcafee-ENGINESTATUS OBJECT-TYPE
	SYNTAX  INTEGER
	ACCESS  read-only
    STATUS  mandatory
    DESCRIPTION
		"The status at the end of the last engine scan"
    ::= { mcafeeStandardTrapField 4  }

mcafee-VIRUSNAME OBJECT-TYPE		        
    SYNTAX          DisplayString
    ACCESS          read-only
    STATUS          mandatory
    DESCRIPTION
	"Name of virus detected"
     ::= { mcafeeStandardTrapField 5 }
    
mcafee-VIRUSTYPE	OBJECT-TYPE	
    SYNTAX          DisplayString
    ACCESS          read-only
    STATUS          mandatory
    DESCRIPTION
	"Type of infection (virus/trojan/etc)"
	 ::= { mcafeeStandardTrapField 6 }
	 
mcafee-FILENAME	OBJECT-TYPE	
    SYNTAX          DisplayString
    ACCESS          read-only
    STATUS          mandatory
    DESCRIPTION
	"File name and path"
	 ::= { mcafeeStandardTrapField 7 }
	 
mcafee-USERNAME	OBJECT-TYPE	
    SYNTAX          DisplayString
    ACCESS          read-only
    STATUS          mandatory
    DESCRIPTION
	"User Name"
	 ::= { mcafeeStandardTrapField 8 }   
	 
mcafee-OS	OBJECT-TYPE	
    SYNTAX          DisplayString
    ACCESS          read-only
    STATUS          mandatory
    DESCRIPTION
	"Operating System and Version"
	 ::= { mcafeeStandardTrapField 9 }
	 
mcafee-PROCESSORSERIAL	OBJECT-TYPE	
    SYNTAX          DisplayString
    ACCESS          read-only
    STATUS          mandatory
    DESCRIPTION
	"Processor Serial number"
	 ::= { mcafeeStandardTrapField 10 }
	 
mcafee-TASKNAME	OBJECT-TYPE	
    SYNTAX          DisplayString
    ACCESS          read-only
    STATUS          mandatory
    DESCRIPTION
	"Sub Task Name"
	 ::= { mcafeeStandardTrapField 11 }

mcafee-NUMVIRS		OBJECT-TYPE	
	SYNTAX  INTEGER
    ACCESS  read-only
    STATUS  mandatory
    DESCRIPTION
    "Number of infections detected."
	 ::= { mcafeeStandardTrapField 15 }
	 
mcafee-NUMCLEANED	OBJECT-TYPE	
	SYNTAX  INTEGER
    ACCESS  read-only
    STATUS  mandatory
    DESCRIPTION
    "Number of infections cleaned."
	 ::= { mcafeeStandardTrapField 16 }
	 
mcafee-NUMDELETED		OBJECT-TYPE	
	SYNTAX  INTEGER
    ACCESS  read-only
    STATUS  mandatory
    DESCRIPTION
    "Number of infected files deleted."
	 ::= { mcafeeStandardTrapField 17 }
	 
mcafee-NUMQUARANTINED	OBJECT-TYPE	
	SYNTAX  INTEGER
    ACCESS  read-only
    STATUS  mandatory
    DESCRIPTION
    "Number of viruses quarantined."
	 ::= { mcafeeStandardTrapField 18 }
	 
mcafee-SCANRETURNCODE	OBJECT-TYPE	
	SYNTAX  INTEGER
    ACCESS  read-only
    STATUS  mandatory
    DESCRIPTION
    "Return Code from Scan Engine"
	 ::= { mcafeeStandardTrapField 19 }
	 
mcafee-MAILFROMNAME	OBJECT-TYPE	
    SYNTAX          DisplayString
    ACCESS          read-only
    STATUS          mandatory
    DESCRIPTION
	"Mail From Field"
	 ::= { mcafeeStandardTrapField 30 }
	 
mcafee-MAILTONAME	OBJECT-TYPE	
    SYNTAX          DisplayString
    ACCESS          read-only
    STATUS          mandatory
    DESCRIPTION
	"Mail To Field Contents"
	 ::= { mcafeeStandardTrapField 31 }
	 
mcafee-MAILCCNAME	OBJECT-TYPE	
    SYNTAX          DisplayString
    ACCESS          read-only
    STATUS          mandatory
    DESCRIPTION
	"Mail CC Name"
	 ::= { mcafeeStandardTrapField 32 }
	 
mcafee-MAILSUBJECTLINE		OBJECT-TYPE	
    SYNTAX          DisplayString
    ACCESS          read-only
    STATUS          optional
    DESCRIPTION
	"Mail Subject Line"
	 ::= { mcafeeStandardTrapField 33 }
	 
mcafee-MAILIDENTIFIERINFO	OBJECT-TYPE	
    SYNTAX          DisplayString
    ACCESS          read-only
    STATUS          optional
    DESCRIPTION
	"Mail item identifier info"
	 ::= { mcafeeStandardTrapField 34 }

mcafee-NOTEID	OBJECT-TYPE	
    SYNTAX          DisplayString
    ACCESS          read-only
    STATUS          optional
    DESCRIPTION
	"Notes identifier info"
	 ::= { mcafeeStandardTrapField 35 }

mcafee-NOTESSERVERNAME	OBJECT-TYPE	
    SYNTAX          DisplayString
    ACCESS          read-only
    STATUS          optional
    DESCRIPTION
	"Notes Server Name"
	 ::= { mcafeeStandardTrapField 36 }

mcafee-NOTESDBNAME	OBJECT-TYPE	
    SYNTAX          DisplayString
    ACCESS          read-only
    STATUS          optional
    DESCRIPTION
	"Notes Database Name "
	 ::= { mcafeeStandardTrapField 37 }

mcafee-DOMAIN	OBJECT-TYPE	
    SYNTAX          DisplayString
    ACCESS          read-only
    STATUS          optional
    DESCRIPTION
	"Domain Name."
	 ::= { mcafeeStandardTrapField 38 }

mcafee-OBRULE	OBJECT-TYPE	
    SYNTAX          DisplayString
    ACCESS          read-only
    STATUS          optional
    DESCRIPTION
	"OB Rule "
	 ::= { mcafeeStandardTrapField 39 }

mcafee-LANGUAGECODE	OBJECT-TYPE	
    SYNTAX          DisplayString
    ACCESS          read-only
    STATUS          optional
    DESCRIPTION
	"Language Code of Machine where Event Originated"
	 ::= { mcafeeStandardTrapField 40 }
		
mcafee-CLIENTCOMPUTER	OBJECT-TYPE	
    SYNTAX          DisplayString
    ACCESS          read-only
    STATUS          optional
    DESCRIPTION
	"Name of Terminal Services Client Computer"
	 ::= { mcafeeStandardTrapField 41 }


mcafee-TSCLIENTID	OBJECT-TYPE	
    SYNTAX          INTEGER
    ACCESS          read-only
    STATUS          optional
    DESCRIPTION
	"Terminal Services Client Id number"
	 ::= { mcafeeStandardTrapField 42 }

mcafee-ACCESSPROCESSNAME	OBJECT-TYPE	
    SYNTAX          DisplayString
    ACCESS          read-only
    STATUS          optional
    DESCRIPTION
	"Name of Process triggering on-access scan"
	 ::= { mcafeeStandardTrapField 43 }

mcafee-EVENTNAME	OBJECT-TYPE	
    SYNTAX          DisplayString
    ACCESS          read-only
    STATUS          optional
    DESCRIPTION
	"Name of this event for McAfee Diagnostics"
	 ::= { mcafeeStandardTrapField 44 }

mcafee-GMTTIME	OBJECT-TYPE	
    SYNTAX          DisplayString
    ACCESS          read-only
    STATUS          optional
    DESCRIPTION
	"GMT time at the time the event was sent"
	 ::= { mcafeeStandardTrapField 45 }

mcafee-TIME	OBJECT-TYPE	
    SYNTAX          DisplayString
    ACCESS          read-only
    STATUS          optional
    DESCRIPTION
	"Local Time when the event was sent"
	 ::= { mcafeeStandardTrapField 46 }

mcafee-SOURCEIP	OBJECT-TYPE	
    SYNTAX          DisplayString
    ACCESS          read-only
    STATUS          optional
    DESCRIPTION
	"Source IP where event was generated"
	 ::= { mcafeeStandardTrapField 47 }

mcafee-TARGETIP	OBJECT-TYPE	
    SYNTAX          DisplayString
    ACCESS          read-only
    STATUS          optional
    DESCRIPTION
	"IP of machine which the infection occurred if different from Source IP"
	 ::= { mcafeeStandardTrapField 48 }


-- mcafee TRAP DEFINITIONS
--
-- sample with all fields NOTE all mcafee traps for 4.5 will have all fields




mcafee-EVENT-TEST-TRAP TRAP-TYPE
	ENTERPRISE mcafeeTVDTrap
	VARIABLES
	{
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		

		mcafee-TIME,           
		mcafee-TARGETIP,
		naiTrapTargetDNSName,
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME
	}
	DESCRIPTION
		"mcafee Alert Manager Test Trap"
	::= 9999



mcafee-EVENT-VIRFOUND TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		mcafee-TIME,           
		mcafee-TARGETIP,
		naiTrapTargetDNSName,

		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME

	}
	DESCRIPTION
  	"Infected file found."
  ::= 1024

mcafee-EVENT-FILECLEANED 	TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		mcafee-TIME,           
		mcafee-TARGETIP,
		naiTrapTargetDNSName,
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"File was cleaned."
  ::=             1025
  
mcafee-EVENT-FILECLEANERROR	 TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
	 
		mcafee-TIME,           
		mcafee-TARGETIP,
		naiTrapTargetDNSName,

		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Error while cleaning file."
  ::=        1026
  
mcafee-EVENT-FILEDELETED	TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		mcafee-TIME,           
		mcafee-TARGETIP,
		naiTrapTargetDNSName,
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Infected file deleted."
  ::=             1027
  
mcafee-EVENT-FILEDELETEERROR	TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		mcafee-TIME,           
		mcafee-TARGETIP,
		naiTrapTargetDNSName,

		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Error while deleting Infected file."
  ::=         1028
  
mcafee-EVENT-FILEEXCLUDING	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		mcafee-TIME,           
		mcafee-TARGETIP,
		naiTrapTargetDNSName,
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Excluding file while scanning"
  ::=       1029	
 

  
mcafee-EVENT-EXCLUDEERR	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		mcafee-TIME,           
		mcafee-TARGETIP,
		naiTrapTargetDNSName,
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Unable to exclude from scan"
  ::=       1030
 


  
mcafee-EVENT-INFECTION-ACESSDENIED	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		mcafee-TIME,           
		mcafee-TARGETIP,
		naiTrapTargetDNSName,

		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Infected file access denied"
  ::= 1031       
 
   
mcafee-EVENT-VIRUS-QUARANTINED	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		mcafee-TIME,           
		mcafee-TARGETIP,
		naiTrapTargetDNSName,
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Infected file moved to quarantine"
  ::=       1032
 

  
mcafee-EVENT-VIRUS-QUARANTINE-FAILURE	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Unable to move infected file to quarantine"
  ::=       1033
 
  
mcafee-EVENT-SCANEND-NO-VIRUSES	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Scan complete no viruses found"
  ::=       1034
 
  
mcafee-EVENT-SCAN-CANCELED	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Scan canceled"
  ::=       1035
 
   
mcafee-EVENT-VIRUS-FOUND-IN-MEMORY	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Virus found in memory"
  ::=       1036
 
  
mcafee-EVENT-VIRUS-IN-BOOT-RECORD	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Infected boot record found"
  ::=       1037
 
  
mcafee-EVENT-SCAN-FOUND-INFECTED-FILES	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Scan found infected files"
  ::=       1038
 
  
mcafee-EVENT-SCAN-FOUND-AND-CLEANED-INFECTIONS	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Scan found and cleaned infected files"
  ::=       1039
 
  
mcafee-EVENT-ALOG-ERROR	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Error accessing activity log file"
  ::=       1040
 
  
mcafee-EVENT-MEMALLOC-ERROR	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Memory allocation error while scanning"
  ::=       1041
 
  
mcafee-EVENT-DIR-ACCESS-ERROR	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Directory access error (path too long)"
  ::=       1042
 
  
mcafee-EVENT-WRITE-PROTECT-ERR	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Media write protected"
  ::=       1043
 
  
mcafee-EVENT-MEDIA-NOT-FOUND-ERR	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Specified media not found"
  ::=       1044
 
  
mcafee-EVENT-SCAN-ITEM-INVALID	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Specified scan item invalid"
  ::=       1045
 
  
mcafee-EVENT-FILE-IO-ERRORS	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"File i/o errors"
  ::=       1046
 
  
mcafee-EVENT-DISK-IO-ERR	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Disk I/O errors"
  ::=       1047
 
  
mcafee-EVENT-GEN-SYSTEM-ERROR      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Scan reports general system error"
  ::=       1048
 
  
mcafee-EVENT-INTERNAL-APP-ERROR	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Scan reported internal application error"
  ::=       1049
 
  
mcafee-EVENT-INFECTION-PASSWORD-PROTECTED	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Infected file password protected"
  ::=       1050
 
  
mcafee-EVENT-NOT-SCANNED-PASSWORD	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Not scanned password protected"
  ::=       1051
 
  
mcafee-EVENT-INFECTED-BINDARY	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Infected bindery object"
  ::=       1052
 
  
mcafee-EVENT-INFECTED-HEURISTICS	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Heuristics detected infected file"
  ::=       1053
 
  
mcafee-EVENT-DELETED-HEURISTICS	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Heuristics deleted infected file"
  ::=       1054
 
  
mcafee-EVENT-DELETE-ERR-HEURISTICS	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Delete error Heuristics detected infection"
  ::=       1055
 
  
mcafee-EVENT-QUARANTINED-HEURISTICS	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Heuristics detected infection quarantined"
  ::=       1056
 
  
mcafee-EVENT-QUAR-ERROR-HEURISTICS	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Move error on heuristics detected infection"
  ::=       1057
 
  
mcafee-EVENT-SCAN-TIMEOUT	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Scan timed out"
  ::=       1059
 
  
mcafee-EVENT-BOOT-SECTOR-CLEANED	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Boot sector cleaned"
  ::=       1060
 
  
mcafee-EVENT-CLEANERROR-BOOTSECTOR	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Clean error on boot sector"
  ::=       1061
 
  
mcafee-EVENT-ALERTERROR	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Alert error"
  ::=       1062
 
  
mcafee-EVENT-OPTIONSERROR      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Options error"
  ::=       1063
 
  
mcafee-EVENT-SERVICE-STARTED-1064	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Service started"
  ::=       1064
 
  
mcafee-EVENT-SERVICE-ENDING-1065	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Service ending"
  ::=       1065
 
  
mcafee-EVENT-SCED-START-TASK-OK      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Scheduled task started ok"
  ::=       1066
 
  
mcafee-EVENT-SCHED-START-TASK-ERROR	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Scheduled task start error"
  ::=       1067
 
  
mcafee-EVENT-SCED-TASK-END-OK	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Scheduled task completed ok"
  ::=       1068
 
  
mcafee-EVENT-SCHED-TASK-STOP-ERROR     TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Scheduled task stop error"
  ::=       1069
 
  
mcafee-EVENT-SCHED-TASK-SUCCESS      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Task success"
  ::=       1070
 
  
mcafee-EVENT-SCHED-TASK-CANCELED	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Task canceled"
  ::=       1071
 
  
mcafee-EVENT-TASKERR-LOGFILE	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Task error logfile"
  ::=       1076
 
  
mcafee-EVENT-TASK-ERR-MEMALLOC     TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Task error memory allocation"
  ::=       1077
 
  
mcafee-EVENT-SCAN-PROC-ERR     TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Scan proc error"
  ::=       1086
 
  
mcafee-EVENT-OAS-START	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"On access Scan starting"
  ::=       1087
 
  
mcafee-EVENT-OAS-STOP      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"On access scan stopping"
  ::=       1088
 
  
mcafee-EVENT-SCAN-SETTINGS	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Scan settings"
  ::=       1089
 
  
mcafee-EVENT-MACRO-VIRUS-DETECTED	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Macro virus detected"
  ::=     1100  
 
  
mcafee-EVENT-MACRO-VIRUS-DELETED	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Macro virus deleted"
  ::=       1101
 
  
mcafee-EVENT-UPDATEOK	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Update was successful"
  ::=       1118
 
  
mcafee-EVENT-UPDATEFAILED	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Update failed see event log"
  ::=       1119
 
  
mcafee-EVENT-UPDATE-RUNNING	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Update is running"
  ::=       1120
 
  
mcafee-EVENT-UPDATECANCELED      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Update was canceled"
  ::=       1121
 
  
mcafee-EVENT-UPGRADE-RUNNING      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Upgrade is running"
  ::=       1122
 
  
mcafee-EVENT-UPGRADE-FAILED	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Upgrade failed see event log"
  ::=       1123
 
  
mcafee-EVENT-UPGRADE-CANCELED	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Upgrade was canceled"
  ::=       1124
 
  
mcafee-EVENT-UPDATE-VERSION-OLDER	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"DAT version is older than current"
  ::=       1125
 
  
mcafee-EVENT-SCAN-CANCELED-BY-UPD	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Scan canceled by autoupdate or autoupgrade"
  ::=       1126
 
  
mcafee-EVENT-SCANNER-DISABLED	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Scanner disabled"
  ::=       1127
 
  
mcafee-EVENT-START-PROCESS	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Process started"
  ::=       1200
 
  
mcafee-EVENT-PROCESS-ENDED	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Process Ended"
  ::=       1201
 
  
mcafee-EVENT-ODS-SCAN-STARTED	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"On demand scan started"
  ::=       1202
 


mcafee-EVENT-ODS-SCAN-ENDED	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"On Demand Scan Complete"
  ::=       1203	
 
  
mcafee-EVENT-SCAN-REPORT-OS	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Report P3 OS and Serial Number"
  ::=       1204
 
  
mcafee-EVENT-MAIL-VIRUSCLEANED	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Mail Virus cleaned"
  ::=       1500
 
  
mcafee-EVENT-MAIL-VIRUSQUARANTINED	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Mail virus quarantined"
  ::=       1501
 
  
mcafee-EVENT-MAIL-VIRUS-NOTCLEANED	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Mail Virus not cleaned"
  ::=       1502
 
  
mcafee-EVENT-MAIL-VIRUS-DETECTED	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Mail Virus detected"
  ::=       1503
 
  
mcafee-EVENT-MAIL-VIRUS-DELETED	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Mail Virus Deleted"
  ::=       1504
 
  
mcafee-EVENT-MAIL-VIRUS-FILTERED	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Mail Content Filtered"
  ::=       1505
 
  
mcafee-EVENT-MAIL-CONTENTBLOCK	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Mail Content blocked"
  ::=       1506
 
  
mcafee-EVENT-MAIL-LOWDISKLIMIT      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Mail Low Disk Limit"
  ::=       1507
 
  
mcafee-EVENT-MAIL-UPPERDISKLIMIT	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Mail Upper Disk Limit"
  ::=       1508
 
  
mcafee-EVENT-MAIL-SERVICE-START	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Mail service startup"
  ::=       1509
 
  
mcafee-EVENT-MAIL-SERVICE-SHUTDOWN-OK	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Mail service shutdown successful"
  ::=       1510
 
  
mcafee-EVENT-MAIL-SERVICE-ABEND	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Mail service abnormal shutdown"
  ::=       1511
 
  
mcafee-EVENT-MAIL-SERVICE-MAX-LOAD	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Mail Maximum load"
  ::=       1512
 
  
mcafee-EVENT-MAIL-VIRUS-QUARANTINEDCLEANED	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Mail virus quarantined and cleaned"
  ::=       1513
 
  
mcafee-EVENT-MAIL-VIRUS-QUARANTINED	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Mail virus quarantined (not cleaned)"
  ::=       1514
 
  
mcafee-EVENT-NEW-MIB	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Alert Manager New MIB available"
  ::=       1900
 
  
mcafee-EVENT-EPO-FAILE-INSTPRODUCT	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Epo agent failed to install a software product"
  ::=       2201
 
  
mcafee-EVENT-EPO-AGENT-RETRYLIMIT	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Epo agent retry limit for a product"
  ::=       2202
 
  
mcafee-EVENT-EPO-AGENT-DISKSPACE	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Epo agent not enough disk space"
  ::=       2204
 
  
mcafee-EVENT-EPO-SPIPE-DISKSPACE	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Epo agent spipe not enough disk space"
  ::=       2208
 
  
mcafee-EVENT-EPO-AGENT-WRONG-PLATFORM	      TRAP-TYPE	
	ENTERPRISE mcafeeTVDTrap
    VARIABLES
    {
		naiTrapAgent,				
		naiTrapShortDescription,	
		naiTrapSeverity,            
		mcafee-SOURCEIP,		
		mcafee-GMTTIME,             
		naiTrapAgentVersion,
		naiTrapLongDescription,		 
		naiTrapProblemResolution,	
		naiTrapDiagID,              
		naiTrapURL,                 
		naiTrapSourceDNSName,		
		 
			 
		mcafee-TIME,           
		mcafee-TARGETIP,
		naiTrapTargetDNSName,
		
		
		mcafee-TRAPID,             
		mcafee-ENGINEVERSION,
		mcafee-DATVERSION,
		mcafee-ENGINESTATUS,
		mcafee-VIRUSNAME,
		mcafee-VIRUSTYPE,         
		mcafee-FILENAME,         
		mcafee-USERNAME,          
		mcafee-OS,          
		mcafee-PROCESSORSERIAL,
		
		mcafee-NUMVIRS,  
		mcafee-NUMCLEANED,
		mcafee-NUMDELETED,
		mcafee-NUMQUARANTINED,
		mcafee-SCANRETURNCODE,

		mcafee-MAILFROMNAME,   
		mcafee-MAILTONAME,
		mcafee-MAILCCNAME,
		mcafee-MAILSUBJECTLINE,
		mcafee-MAILIDENTIFIERINFO,

		mcafee-LANGUAGECODE,
		mcafee-CLIENTCOMPUTER,
		mcafee-TSCLIENTID,
		mcafee-ACCESSPROCESSNAME,

		mcafee-NOTEID,
		mcafee-NOTESSERVERNAME,
		mcafee-NOTESDBNAME,
		mcafee-DOMAIN,
		mcafee-OBRULE,
		mcafee-EVENTNAME


	}
	DESCRIPTION
  	"Epo agent wrong software platform"
  ::=       2216
 


END
