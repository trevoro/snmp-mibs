-- ****************************************************************************
--
--                     Dialogic Global Registration
--         Management Information Base for SNMP Network Management
--
--
--      Copyright 1997, Dialogic Corporation.
--      All Rights Reserved.
--
--      The information in this document is subject to change without notice.
--
--      The Dialogic Enterprise number is 3028.
--      The ASN.1 prefix to, and including the Dialogic Enterprise is:
--           1.3.6.1.4.1.3028
--
-- ****************************************************************************

DLGC-GLOBAL-REG DEFINITIONS ::= BEGIN

    IMPORTS
        enterprises             FROM RFC1155-SMI
        OBJECT-TYPE             FROM RFC1155-SMI;
--
-- The Dialogic enterprise node
--
    dialogic           OBJECT IDENTIFIER ::= { enterprises 3028 }

--
-- Top level nodes within Dialogic Private MIB. The MIB is designed
-- to allow access for monitoring, configuring and controlling all
-- levels of the architecture from the hardware platform all the way
-- up to the application
--
    dlgPlatform          OBJECT IDENTIFIER ::= { dialogic 1 }
    dlgResources         OBJECT IDENTIFIER ::= { dialogic 2 }
    dlgNetworkInterfaces OBJECT IDENTIFIER ::= { dialogic 3 }
    dlgServiceProviders  OBJECT IDENTIFIER ::= { dialogic 4 }
    dlgApplications      OBJECT IDENTIFIER ::= { dialogic 5 }
    dlgProducts          OBJECT IDENTIFIER ::= { dialogic 6 }

--
-- Platform portion of the MIB includes Hardware inventory and
-- current status as well as Driver and Kernel Performance Info.
--
    dlgHardwareInfo      OBJECT IDENTIFIER ::= { dlgPlatform 1 }
    dlgPerformanceInfo   OBJECT IDENTIFIER ::= { dlgPlatform 2 }

--
-- Resources MIBs includes device level information for Release 4 D4x 
-- and Span technologies like the Voice channel, T1/E1 timeslots, ISDN
-- B channels and MSI station sets.
--
    dlgR4Resources   OBJECT IDENTIFIER ::= { dlgResources 1 }
    dlgDM3Resources  OBJECT IDENTIFIER ::= { dlgResources 2 }

--
-- Network Interface MIBs include DS1 (T1/E1) and ISDN MIBs. 
--
   dlgTransmissions  OBJECT IDENTIFIER ::= { dlgNetworkInterfaces 1 }

--
-- Service Provider MIBs are defined for Dialogic Windows-NT 
-- WOSA components like TAPI and Wave
--
   dlgTapi          OBJECT IDENTIFIER  ::= { dlgServiceProviders 1 }

END
