-- Version 2.15.1.1, modified 2001-05-31 17:28:39-04

        SPP-OPT-MIB DEFINITIONS ::= BEGIN

        IMPORTS
            Counter, Gauge, enterprises
                FROM RFC1155-SMI

            OBJECT-TYPE
                FROM RFC-1212;

        -- Codex MIB Group definitions

                           codex OBJECT IDENTIFIER ::= { enterprises 449 }
                  cdxProductSpecific OBJECT IDENTIFIER ::= { codex 2 }
                             cdx6500 OBJECT IDENTIFIER ::= { cdxProductSpecific 1 }

               cdx6500Configuration  OBJECT IDENTIFIER ::= { cdx6500 2 }
             cdx6500CfgProtocolGroup OBJECT IDENTIFIER ::= { cdx6500Configuration 1 }
         cdx6500PCTPortProtocolGroup OBJECT IDENTIFIER ::= { cdx6500CfgProtocolGroup 1 }
  cdx6500PCTStationProtocolGroup OBJECT IDENTIFIER ::= { cdx6500CfgProtocolGroup 3 }

                   cdx6500Statistics OBJECT IDENTIFIER ::= { cdx6500 3 }
            cdx6500StatProtocolGroup OBJECT IDENTIFIER ::= { cdx6500Statistics 1 }
         cdx6500PSTPortProtocolGroup OBJECT IDENTIFIER ::= { cdx6500StatProtocolGroup 1 }
  cdx6500PSTStationProtocolGroup OBJECT IDENTIFIER ::= { cdx6500StatProtocolGroup 3 }

                     cdx6500Controls OBJECT IDENTIFIER ::= { cdx6500 4 }

        -- Textual Conventions

        DisplayString ::= OCTET STRING


        -- The SPP Port Configuration Table
        -- This table contains Configuration parameters
        -- related to a SPP PAD port.

        cdx6500PPCTSPPPortTable OBJECT-TYPE
            SYNTAX SEQUENCE OF Cdx6500PPCTSPPPortEntry
            ACCESS not-accessible
            STATUS mandatory
            DESCRIPTION
                "This table contains the SPP Port configuration
                 parameters."
        ::= { cdx6500PCTPortProtocolGroup 30 }

        cdx6500PPCTSPPPortEntry OBJECT-TYPE
            SYNTAX Cdx6500PPCTSPPPortEntry
            ACCESS not-accessible
            STATUS mandatory
            DESCRIPTION
                "Entries in the SPP Port Configuration Table."
            INDEX { cdx6500SPPPCfgPortNum }
        ::= { cdx6500PPCTSPPPortTable 1 }

        Cdx6500PPCTSPPPortEntry ::=
            SEQUENCE {
                cdx6500SPPPCfgPortNum
                    INTEGER,
                cdx6500SPPPCfgPortType
                    INTEGER,
                cdx6500SPPPCfgPortSpeed
                    INTEGER,
                cdx6500SPPPCfgInterchTimeout
                    INTEGER,
                cdx6500SPPPCfgSLCNum
                    INTEGER,
                cdx6500SPPPCfgSLCLineNum
                    INTEGER,
                cdx6500SPPPCfgStnIDList
                    DisplayString,
                cdx6500SPPPCfgProtocolID
                    DisplayString,
                cdx6500SPPPCfgQueueSize
                    INTEGER,
                cdx6500SPPPCfgBlockingThresh
                    INTEGER,
                cdx6500SPPPCfgUnblockThresh
                    INTEGER,
                cdx6500SPPPCfgElectricalInterfaceType
                    INTEGER,
                cdx6500SPPPCfgV24ElectricalInterfaceOption
                    INTEGER,
                cdx6500SPPPCfgHighSpeedElectricalInterfaceOption
                    INTEGER
                }

        cdx6500SPPPCfgPortNum OBJECT-TYPE
            SYNTAX INTEGER (1..54)
            ACCESS read-only
            STATUS mandatory
            DESCRIPTION
                "Port Number of this port."
        ::= { cdx6500PPCTSPPPortEntry 1 }

        cdx6500SPPPCfgPortType OBJECT-TYPE
            SYNTAX INTEGER {
                    spp (52)
                    }
            ACCESS read-only
            STATUS mandatory
            DESCRIPTION
                "Port Type of the port."
        ::= { cdx6500PPCTSPPPortEntry 2 }

        cdx6500SPPPCfgPortSpeed OBJECT-TYPE
            SYNTAX INTEGER {
                    speed300   (2),
                    speed1200  (3),
                    speed600   (4),
                    speed1800  (7),
                    speed2400  (12),
                    speed4800  (13),
                    speed9600  (14),
                    speed19200 (15),
                    speed7200  (98)
                    }
            ACCESS read-only
            STATUS mandatory
            DESCRIPTION
                "This is the speed of the port in bits per second.
                 speed300   : 300  bits per second
                 speed600   : 600  bits per second
                 speed1200  : 1200 bits per second
                 speed1800  : 1800 bits per second
                 speed2400  : 2400 bits per second
                 speed4800  : 4800 bits per second
                 speed7200  : 7200 bits per second
                 speed9600  : 9600 bits per second
                 speed19200 : 19200 bits per second."
        ::= { cdx6500PPCTSPPPortEntry 3 }

        cdx6500SPPPCfgInterchTimeout OBJECT-TYPE
            SYNTAX INTEGER {
                    time50  (51),
                    time100 (100),
                    time150 (150),
                    time200 (200),
                    time250 (250)
                    }
            ACCESS read-only
            STATUS mandatory
            DESCRIPTION
                "This indicates the maximum time period allowed between
                 received characters.
                 time50     :  maximum time period allowed 50 seconds.
                 time100    :  maximum time period allowed 100 seconds.
                 time150    :  maximum time period allowed 150 seconds.
                 time200    :  maximum time period allowed 200 seconds.
                 time250    :  maximum time period allowed 250 seconds."
        ::= { cdx6500PPCTSPPPortEntry 4 }

        cdx6500SPPPCfgSLCNum OBJECT-TYPE
            SYNTAX INTEGER (0..99)
            ACCESS read-only
            STATUS mandatory
            DESCRIPTION
                "This specifies the SLC (Smart Line Controller) the port
                 is connected to."
        ::= { cdx6500PPCTSPPPortEntry 5 }

        cdx6500SPPPCfgSLCLineNum OBJECT-TYPE
            SYNTAX INTEGER (0..31)
            ACCESS read-only
            STATUS mandatory
            DESCRIPTION
                "This specifies the line on the SLC (Smart Line Controller)
                 the port is connected to."
        ::= { cdx6500PPCTSPPPortEntry 6 }

        cdx6500SPPPCfgStnIDList OBJECT-TYPE
            SYNTAX DisplayString
            ACCESS read-only
            STATUS mandatory
            DESCRIPTION
                "List of station identifiers the port will support. A 
                 range of station numbers can be entered, for example :
                 1, 6, 8-12, 250-255 indicates 1, 6, 8, 9, 10, 11, 12, 
                 250, 251, 252, 253, 254, 255 ."
        ::= { cdx6500PPCTSPPPortEntry 7 }

        cdx6500SPPPCfgProtocolID OBJECT-TYPE
            SYNTAX DisplayString (SIZE(0..8))
            ACCESS read-only
            STATUS mandatory
            DESCRIPTION
                "The Protocol Identifier is the first four bytes of
                 the call user data. The default is: 0x11, 0x9F, 0xA7, 0x46."
        ::= { cdx6500PPCTSPPPortEntry 8 }

        cdx6500SPPPCfgQueueSize OBJECT-TYPE
            SYNTAX INTEGER (1..2000)
            ACCESS read-only
            STATUS mandatory
            DESCRIPTION
                "This specifies the size of the queue which will be used 
                 to store the packets to be forwarded to SLC (Smart Line
                 Controller)."
        ::= { cdx6500PPCTSPPPortEntry 9 }

        cdx6500SPPPCfgBlockingThresh OBJECT-TYPE
            SYNTAX INTEGER (1..2000)
            ACCESS read-only
            STATUS mandatory
            DESCRIPTION
                "This specifies the blocking threshold for the queue
                 being used by the SPP."
        ::= { cdx6500PPCTSPPPortEntry 10 }

        cdx6500SPPPCfgUnblockThresh OBJECT-TYPE
            SYNTAX INTEGER (1..2000)
            ACCESS read-only
            STATUS mandatory
            DESCRIPTION
                "This specifies the unblocking threshold for the queue
                 being used by the SPP."
        ::= { cdx6500PPCTSPPPortEntry 11 }

        cdx6500SPPPCfgElectricalInterfaceType OBJECT-TYPE
            SYNTAX INTEGER {
                    v24       (1),
                    v35       (2),
                    v36       (3),
                    x21       (4),
                    none      (5)
                    }
            ACCESS read-only
            STATUS mandatory
            DESCRIPTION
                 "Specify the Electrical Interface Type:
                   V.24  - V.24 Electrical Interface Type
                   V.35  - V.35 Electrical Interface Type
                   V.36  - V.36 Electrical Interface Type
                   X.21  - X.21 Electrical Interface Type
                   NONE  - Electrically disabled"
        ::= { cdx6500PPCTSPPPortEntry 12 }

        cdx6500SPPPCfgV24ElectricalInterfaceOption OBJECT-TYPE
            SYNTAX INTEGER {
                    ri        (1),
                    tm        (2)
                    }
            ACCESS read-only
            STATUS mandatory
            DESCRIPTION
                 "Specify the Pin 22 option:
                  RI    - V.24 uses Pin 22 for Ring Indicator output signal
                  TM    - V.24 uses Pin 22 for Test Mode input signal"
        ::= { cdx6500PPCTSPPPortEntry 13 }

        cdx6500SPPPCfgHighSpeedElectricalInterfaceOption OBJECT-TYPE
            SYNTAX INTEGER {
                    none      (1),
                    xover     (2)
                    }
            ACCESS read-only
            STATUS mandatory
            DESCRIPTION
                 "Specify the cable type:
                  NONE  - V.35/V.36/X.21 DCE with straight through cable
                  XOVER - V.35/V.36/X.21 DCE with crossover adapter cable"
        ::= { cdx6500PPCTSPPPortEntry 14 }

        -- SPP Port Statistics

        cdx6500PPSTSPPPStatsTable OBJECT-TYPE
            SYNTAX SEQUENCE OF Cdx6500PPSTSPPPStatEntry
            ACCESS not-accessible
            STATUS mandatory
            DESCRIPTION
                "This table contains the SPP Port Statistics Parameters."
        ::= { cdx6500PSTPortProtocolGroup 31 }

        cdx6500PPSTSPPPStatEntry OBJECT-TYPE
            SYNTAX Cdx6500PPSTSPPPStatEntry
            ACCESS not-accessible
            STATUS mandatory
            DESCRIPTION
                "Entries in the SPP Port Statistics Table."
            INDEX { cdx6500SPPPStatPortNum }
        ::= { cdx6500PPSTSPPPStatsTable 1 }

        Cdx6500PPSTSPPPStatEntry ::=
            SEQUENCE {
                cdx6500SPPPStatPortNum
                    INTEGER,
                cdx6500SPPPStatPortStatus
                    INTEGER,
                cdx6500SPPPStatPortType
                    INTEGER,
                cdx6500SPPPStatPortSpeed
                    INTEGER,
                cdx6500SPPPStatPortUtilIn
                    INTEGER,
                cdx6500SPPPStatPortUtilOut
                    INTEGER,
                cdx6500SPPPStatSLCNum
                    INTEGER,
                cdx6500SPPPStatSLCLineNum
                    INTEGER,
                cdx6500SPPPStatFlowCntrlState
                    INTEGER,
                cdx6500SPPPStatLastStatsReset
                    DisplayString,
                cdx6500SPPPStatChrsIn
                    Counter,
                cdx6500SPPPStatChrsOut
                    Counter,
                cdx6500SPPPStatFramesIn
                    Counter,
                cdx6500SPPPStatFramesOut
                    Counter,
                cdx6500SPPPStatChrsInPerSec
                    INTEGER,
                cdx6500SPPPStatChrsOutPerSec
                    INTEGER,
                cdx6500SPPPStatFramesInPerSec
                    INTEGER,
                cdx6500SPPPStatFramesOutPerSec
                    INTEGER,
                cdx6500SPPPStatNoOfErrorFrames
                    INTEGER,
                cdx6500SPPPStatNoOfStns
                    INTEGER
                }

        cdx6500SPPPStatPortNum OBJECT-TYPE
            SYNTAX INTEGER (1..54)
            ACCESS read-only
            STATUS mandatory
            DESCRIPTION
                "Port Number of this port."
        ::= { cdx6500PPSTSPPPStatEntry 1 }

        cdx6500SPPPStatPortStatus OBJECT-TYPE
            SYNTAX INTEGER {
                  disabled       (0),
                  enabled        (1),
                  busyOut        (2),
                  up             (3),
                  down           (4),
                  newvalDisabled (50)
                  }
            ACCESS read-only
            STATUS mandatory
            DESCRIPTION
                "This indicates the operational status of the port.
                 disabled : port is disabled
                 enabled  : port is enabled
                 busyOut  : busy out the port
                 up       : port is up
                 down     : port is down.
                 newvalDisabled : same functionality as 'disabled', new
                            enumeration added for RFC1155 compatibility."
        ::= { cdx6500PPSTSPPPStatEntry 2 }

        cdx6500SPPPStatPortType OBJECT-TYPE
            SYNTAX INTEGER {
                    spp (52)
                    }
            ACCESS read-only
            STATUS mandatory
            DESCRIPTION
                "This indicates the type of access protocol for this port."
        ::= { cdx6500PPSTSPPPStatEntry 3 }

        cdx6500SPPPStatPortSpeed OBJECT-TYPE
            SYNTAX INTEGER {
                  speed300   (2),
                  speed1200  (3),
                  speed600   (4),
                  speed1800  (7),
                  speed2400  (12),
                  speed4800  (13),
                  speed9600  (14),
                  speed19200 (15),
                  speed7200  (98)
                  }
            ACCESS read-only
            STATUS mandatory
            DESCRIPTION
                "This indicates the port speed in bits per second.
                 speed300   : 300  bits per second
                 speed600   : 600  bits per second
                 speed1200  : 1200 bits per second
                 speed1800  : 1800 bits per second
                 speed2400  : 2400 bits per second
                 speed4800  : 4800 bits per second
                 speed7200  : 7200 bits per second
                 speed9600  : 9600 bits per second
                 speed19200 : 19200 bits per second."
        ::= { cdx6500PPSTSPPPStatEntry 4 }

        cdx6500SPPPStatPortUtilIn OBJECT-TYPE
            SYNTAX INTEGER
            ACCESS read-only
            STATUS mandatory
            DESCRIPTION
                "This indicates the port utilization for the line to
                 port direction."
        ::= { cdx6500PPSTSPPPStatEntry 5 }

        cdx6500SPPPStatPortUtilOut OBJECT-TYPE
            SYNTAX INTEGER
            ACCESS read-only
            STATUS mandatory
            DESCRIPTION
                "This indicates the port utilization for the port to
                 line direction."
        ::= { cdx6500PPSTSPPPStatEntry 6 }

        cdx6500SPPPStatSLCNum OBJECT-TYPE
            SYNTAX INTEGER
            ACCESS read-only
            STATUS mandatory
            DESCRIPTION
                "This indicates the number of the SLC to which the port
                 is connected."
        ::= { cdx6500PPSTSPPPStatEntry 7 }

        cdx6500SPPPStatSLCLineNum OBJECT-TYPE
            SYNTAX INTEGER
            ACCESS read-only
            STATUS mandatory
            DESCRIPTION
                "This indicates the line number of the SLC to which the
                 port is connected."
        ::= { cdx6500PPSTSPPPStatEntry 8 }

        cdx6500SPPPStatFlowCntrlState OBJECT-TYPE
            SYNTAX INTEGER {
                    blocked   (1),
                    unblocked (2)
                    }
            ACCESS read-only
            STATUS mandatory
            DESCRIPTION
                "This indicates whether the port is blocked by SLC or not."
        ::= { cdx6500PPSTSPPPStatEntry 9 }

        cdx6500SPPPStatLastStatsReset OBJECT-TYPE
            SYNTAX DisplayString
            ACCESS read-only
            STATUS mandatory
            DESCRIPTION
                "This specifies the time stamp of the last statistics reset."
        ::= { cdx6500PPSTSPPPStatEntry 10 }

        cdx6500SPPPStatChrsIn OBJECT-TYPE
            SYNTAX Counter
            ACCESS read-only
            STATUS mandatory
            DESCRIPTION
                "This indicates the number of characters that have been 
                 received by the port."
        ::= { cdx6500PPSTSPPPStatEntry 11 }

        cdx6500SPPPStatChrsOut OBJECT-TYPE
            SYNTAX Counter
            ACCESS read-only
            STATUS mandatory
            DESCRIPTION
                "This indicates the number of characters that have been
                 transmitted by the port."
        ::= { cdx6500PPSTSPPPStatEntry 12 }

        cdx6500SPPPStatFramesIn OBJECT-TYPE
            SYNTAX Counter
            ACCESS read-only
            STATUS mandatory
            DESCRIPTION
                "This indicates the number of frames that have been 
                 received by the port."
        ::= { cdx6500PPSTSPPPStatEntry 13 }

        cdx6500SPPPStatFramesOut OBJECT-TYPE
            SYNTAX Counter
            ACCESS read-only
            STATUS mandatory
            DESCRIPTION
                "This indicates the number of frames that have been
                 transmitted by the port."
        ::= { cdx6500PPSTSPPPStatEntry 14 }

        cdx6500SPPPStatChrsInPerSec OBJECT-TYPE
            SYNTAX INTEGER
            ACCESS read-only
            STATUS mandatory
            DESCRIPTION
                "This indicates the rate at which characters have been
                 received by the port."
        ::= { cdx6500PPSTSPPPStatEntry 15 }

        cdx6500SPPPStatChrsOutPerSec OBJECT-TYPE
            SYNTAX INTEGER
            ACCESS read-only
            STATUS mandatory
            DESCRIPTION
                "This indicates the rate at which characters have been
                 transmitted by the port."
        ::= { cdx6500PPSTSPPPStatEntry 16 }

        cdx6500SPPPStatFramesInPerSec OBJECT-TYPE
            SYNTAX INTEGER
            ACCESS read-only
            STATUS mandatory
            DESCRIPTION
                "This indicates the rate at which frames have been
                 received by the port."
        ::= { cdx6500PPSTSPPPStatEntry 17 }

        cdx6500SPPPStatFramesOutPerSec OBJECT-TYPE
            SYNTAX INTEGER
            ACCESS read-only
            STATUS mandatory
            DESCRIPTION
                "This indicates the rate at which frames have been
                 transmitted by the port."
        ::= { cdx6500PPSTSPPPStatEntry 18 }

        cdx6500SPPPStatNoOfErrorFrames OBJECT-TYPE
            SYNTAX INTEGER
            ACCESS read-only
            STATUS mandatory
            DESCRIPTION
                "This indicates the number of erroneous frames received
                 by the port."
        ::= { cdx6500PPSTSPPPStatEntry 19 }

        cdx6500SPPPStatNoOfStns OBJECT-TYPE
            SYNTAX INTEGER
            ACCESS read-only
            STATUS mandatory
            DESCRIPTION
                "This indicates the number of stations on this SLC line."
        ::= { cdx6500PPSTSPPPStatEntry 20 }


        -- SPP Station Statistics 

        cdx6500SPSTSPPStnStatTable OBJECT-TYPE
            SYNTAX SEQUENCE OF Cdx6500SPSTSPPSStatEntry
            ACCESS not-accessible
            STATUS mandatory
            DESCRIPTION
                "This table contains SPP Station statistics parameters."
        ::= { cdx6500PSTStationProtocolGroup 9 }

        cdx6500SPSTSPPSStatEntry OBJECT-TYPE
            SYNTAX Cdx6500SPSTSPPSStatEntry
            ACCESS not-accessible
            STATUS mandatory
            DESCRIPTION
                "Entries in the SPP Station Statistics Table."
            INDEX { cdx6500SPPSStatPortNum, cdx6500SPPSStatStnId }
        ::= { cdx6500SPSTSPPStnStatTable 1 }

        Cdx6500SPSTSPPSStatEntry ::=
            SEQUENCE {
                cdx6500SPPSStatPortNum
                    INTEGER,
                cdx6500SPPSStatStnId
                    INTEGER,
                cdx6500SPPSStatStnStatus
                    INTEGER,
                cdx6500SPPSStatSLCNum
                    INTEGER,
                cdx6500SPPSStatSLCLineNum
                    INTEGER,
                cdx6500SPPSStatAdjChanState
                    INTEGER,
                cdx6500SPPSStatCurrCallSummStatus
                    INTEGER,
                cdx6500SPPSStatLastClrCauseCode
                    DisplayString,
                cdx6500SPPSStatLastClrDiagCode
                    DisplayString,
                cdx6500SPPSStatLastInCalledAddress
                    DisplayString,
                cdx6500SPPSStatLastInCallingAddress
                    DisplayString,
                cdx6500SPPSStatLastInCallFacilities
                    DisplayString,
                cdx6500SPPSStatLastInCallCUD
                    DisplayString,
                cdx6500SPPSStatLastOutCalledAddress
                    DisplayString,
                cdx6500SPPSStatLastOutCallingAddress
                    DisplayString,
                cdx6500SPPSStatLastOutCallFacilities
                    DisplayString,
                cdx6500SPPSStatLastOutCallCUD
                    DisplayString,
                cdx6500SPPSStatChrsIn
                    Counter,
                cdx6500SPPSStatChrsOut
                    Counter,
                cdx6500SPPSStatFramesIn
                    Counter,
                cdx6500SPPSStatFramesOut
                    Counter,
                cdx6500SPPSStatChrsInPerSec
                    INTEGER,
                cdx6500SPPSStatChrsOutPerSec
                    INTEGER,
                cdx6500SPPSStatFramesInPerSec
                    INTEGER,
                cdx6500SPPSStatFramesOutPerSec
                    INTEGER,
                cdx6500SPPSStatNoOfErrorFrames
                    INTEGER,
                cdx6500SPPSStatStnState
                    DisplayString,
                cdx6500SPPSStatLastStatsReset
                    DisplayString
                }

        cdx6500SPPSStatPortNum OBJECT-TYPE
            SYNTAX INTEGER (1..54)
            ACCESS read-only
            STATUS mandatory
            DESCRIPTION
                "Port Number of this port."
        ::= { cdx6500SPSTSPPSStatEntry 1 }

        cdx6500SPPSStatStnId OBJECT-TYPE
            SYNTAX INTEGER
            ACCESS read-only
            STATUS mandatory
            DESCRIPTION
                "This specifies the entry number of this station."
        ::= { cdx6500SPSTSPPSStatEntry 2 }

        cdx6500SPPSStatStnStatus OBJECT-TYPE
            SYNTAX INTEGER {
            --      disabled       (0),
                    enabled        (1),
                    busyOut        (2),
                    up             (3),
                    down           (4),
                    newvalDisabled (50)
                    }
            ACCESS read-only
            STATUS mandatory
            DESCRIPTION
                "This indicates the state of the station.
                 disabled : Station is disabled
                 enabled  : Station is enabled
                 busyOut  : busy out the station
                 up       : Station is enabled
                 down     : Station is down.
                 newvalDisabled : same functionality as 'disabled', new
                            enumeration added for RFC1155 compatibility."
        ::= { cdx6500SPSTSPPSStatEntry 3 }

        cdx6500SPPSStatSLCNum OBJECT-TYPE
            SYNTAX INTEGER
            ACCESS read-only
            STATUS mandatory
            DESCRIPTION
                "This indicates the number of the SLC to which the port
                 is connected."
        ::= { cdx6500SPSTSPPSStatEntry 4 }

        cdx6500SPPSStatSLCLineNum OBJECT-TYPE
            SYNTAX INTEGER
            ACCESS read-only
            STATUS mandatory
            DESCRIPTION
                "This indicates the line number of the SLC to which the
                 port is connected."
        ::= { cdx6500SPSTSPPSStatEntry 5 }

        cdx6500SPPSStatAdjChanState OBJECT-TYPE
            SYNTAX INTEGER {
                    blocked   (1),
                    unblocked (2)
                    }
            ACCESS read-only
            STATUS mandatory
            DESCRIPTION
                "This indicates whether the port is blocked by the adjacent
                 channel or not."
        ::= { cdx6500SPSTSPPSStatEntry 6 }

        cdx6500SPPSStatCurrCallSummStatus OBJECT-TYPE
              SYNTAX INTEGER {
                      inhibited    (1),
                      disconnected (2),
                      calling      (3),
                      called       (4),
                      connected    (5),
                      notDefined   (6)
                     }
            ACCESS read-only
            STATUS mandatory
            DESCRIPTION
                "This indicates the current status of the SPP station.
                 calling    : when it is awaiting call accept from Host
                 connected  : when the connection to the Host has been
                              established."
        ::= { cdx6500SPSTSPPSStatEntry 7 }

        cdx6500SPPSStatLastClrCauseCode OBJECT-TYPE
            SYNTAX DisplayString
            ACCESS read-only
            STATUS mandatory
            DESCRIPTION
                "This indicates the cause code received in the last clear
                 packet."
        ::= { cdx6500SPSTSPPSStatEntry 8 }

        cdx6500SPPSStatLastClrDiagCode OBJECT-TYPE
            SYNTAX DisplayString
            ACCESS read-only
            STATUS mandatory
            DESCRIPTION
                "This indicates the diagnostic code received in the last
                 clear packet."
        ::= { cdx6500SPSTSPPSStatEntry 9 }

        cdx6500SPPSStatLastInCalledAddress OBJECT-TYPE
            SYNTAX DisplayString
            ACCESS read-only
            STATUS mandatory
            DESCRIPTION
                "This indicates the called address in the last inbound 
                 call packet."
        ::= { cdx6500SPSTSPPSStatEntry 10 }

        cdx6500SPPSStatLastInCallingAddress OBJECT-TYPE
            SYNTAX DisplayString
            ACCESS read-only
            STATUS mandatory
            DESCRIPTION
                "This indicates the calling address in the last inbound
                 call packet."
        ::= { cdx6500SPSTSPPSStatEntry 11 }

        cdx6500SPPSStatLastInCallFacilities OBJECT-TYPE
            SYNTAX DisplayString
            ACCESS read-only
            STATUS mandatory
            DESCRIPTION
                "This indicates the facilities in the last inbound call
                 request packet."
        ::= { cdx6500SPSTSPPSStatEntry 12 }

        cdx6500SPPSStatLastInCallCUD OBJECT-TYPE
            SYNTAX DisplayString
            ACCESS read-only
            STATUS mandatory
            DESCRIPTION
                "This indicates the data in the Call User Data field in the
                 last inbound call request packet."
        ::= { cdx6500SPSTSPPSStatEntry 13 }

        cdx6500SPPSStatLastOutCalledAddress OBJECT-TYPE
            SYNTAX DisplayString
            ACCESS read-only
            STATUS mandatory
            DESCRIPTION
                "This indicates the called address in the last outbound 
                 call packet."
        ::= { cdx6500SPSTSPPSStatEntry 14 }

        cdx6500SPPSStatLastOutCallingAddress OBJECT-TYPE
            SYNTAX DisplayString
            ACCESS read-only
            STATUS mandatory
            DESCRIPTION
                "This indicates the calling address in the last outbound
                 call packet."
        ::= { cdx6500SPSTSPPSStatEntry 15 }

        cdx6500SPPSStatLastOutCallFacilities OBJECT-TYPE
            SYNTAX DisplayString
            ACCESS read-only
            STATUS mandatory
            DESCRIPTION
                "This indicates the facilities in the last outbound call
                 request packet."
        ::= { cdx6500SPSTSPPSStatEntry 16 }

        cdx6500SPPSStatLastOutCallCUD OBJECT-TYPE
            SYNTAX DisplayString
            ACCESS read-only
            STATUS mandatory
            DESCRIPTION
                "This indicates the data in the Call User Data field in the
                 last outbound call request packet."
        ::= { cdx6500SPSTSPPSStatEntry 17 }

        cdx6500SPPSStatChrsIn OBJECT-TYPE
            SYNTAX Counter
            ACCESS read-only
            STATUS mandatory
            DESCRIPTION
                "This indicates the number of characters received by the
                 PAD from SLC for this station."
        ::= { cdx6500SPSTSPPSStatEntry 18 }

        cdx6500SPPSStatChrsOut OBJECT-TYPE
            SYNTAX Counter
            ACCESS read-only
            STATUS mandatory
            DESCRIPTION
                "This indicates the number of characters sent by the
                 PAD to SLC for this station."
        ::= { cdx6500SPSTSPPSStatEntry 19 }

        cdx6500SPPSStatFramesIn OBJECT-TYPE
            SYNTAX Counter
            ACCESS read-only
            STATUS mandatory
            DESCRIPTION
                "This indicates the number of frames received by the
                 PAD from SLC for this station."
        ::= { cdx6500SPSTSPPSStatEntry 20 }

        cdx6500SPPSStatFramesOut OBJECT-TYPE
            SYNTAX Counter
            ACCESS read-only
            STATUS mandatory
            DESCRIPTION
                "This indicates the number of frames sent by the
                 PAD to SLC for this station."
        ::= { cdx6500SPSTSPPSStatEntry 21 }

        cdx6500SPPSStatChrsInPerSec OBJECT-TYPE
            SYNTAX INTEGER
            ACCESS read-only
            STATUS mandatory
            DESCRIPTION
                "This indicates the rate at which characters were received
                 by the PAD from SLC for this station."
        ::= { cdx6500SPSTSPPSStatEntry 22 }

        cdx6500SPPSStatChrsOutPerSec OBJECT-TYPE
            SYNTAX INTEGER
            ACCESS read-only
            STATUS mandatory
            DESCRIPTION
                "This indicates the rate at which characters were sent
                 by the PAD to SLC for this station."
        ::= { cdx6500SPSTSPPSStatEntry 23 }

        cdx6500SPPSStatFramesInPerSec OBJECT-TYPE
            SYNTAX INTEGER
            ACCESS read-only
            STATUS mandatory
            DESCRIPTION
                "This indicates the rate at which frames were received
                 by the PAD from SLC for this station."
        ::= { cdx6500SPSTSPPSStatEntry 24 }

        cdx6500SPPSStatFramesOutPerSec OBJECT-TYPE
            SYNTAX INTEGER
            ACCESS read-only
            STATUS mandatory
            DESCRIPTION
                "This indicates the rate at which frames were sent
                 by the PAD to SLC for this station."
        ::= { cdx6500SPSTSPPSStatEntry 25 }

        cdx6500SPPSStatNoOfErrorFrames OBJECT-TYPE
            SYNTAX INTEGER
            ACCESS read-only
            STATUS mandatory
            DESCRIPTION
                "This indicates the number of erroneous frames received."
        ::= { cdx6500SPSTSPPSStatEntry 26 }

        cdx6500SPPSStatStnState OBJECT-TYPE
            SYNTAX DisplayString
            ACCESS read-only
            STATUS mandatory
            DESCRIPTION
                "This indicates the current status of the configured station.
                 up    : station is up
                 dsbl : station is disabled."
        ::= { cdx6500SPSTSPPSStatEntry 27 }

        cdx6500SPPSStatLastStatsReset OBJECT-TYPE
            SYNTAX DisplayString
            ACCESS read-only
            STATUS mandatory
            DESCRIPTION
                "This specifies the time stamp of the last statistics reset."
        ::= { cdx6500SPSTSPPSStatEntry 28 }

        -- The SPP Control Objects

        cdx6500ContSPPTable OBJECT IDENTIFIER
            ::= { cdx6500Controls 13 }

        -- The SPP Port Control Table
        -- This table contains the port control parameters specified for SPP

        cdx6500ContSPPPortTable OBJECT-TYPE
            SYNTAX SEQUENCE OF Cdx6500ContSPPPortEntry
            ACCESS not-accessible
            STATUS mandatory
            DESCRIPTION
                "This table contains the SPP Port Control parameters."
        ::= { cdx6500ContSPPTable 1 }

        cdx6500ContSPPPortEntry OBJECT-TYPE
            SYNTAX Cdx6500ContSPPPortEntry
            ACCESS not-accessible
            STATUS mandatory
            DESCRIPTION
                "Entries in the SPP Port Control Table."
            INDEX { cdx6500ContSPPPortNum }
        ::= { cdx6500ContSPPPortTable 1 }

        Cdx6500ContSPPPortEntry ::=
            SEQUENCE {
                cdx6500ContSPPPortNum
                    INTEGER,
                cdx6500ContSPPPortBoot
                    INTEGER,
                cdx6500ContSPPPortEnable
                    INTEGER,
                cdx6500ContSPPPortDisable
                    INTEGER,
                cdx6500ContSPPPortResetStats
                    INTEGER
                }

        cdx6500ContSPPPortNum OBJECT-TYPE
            SYNTAX INTEGER (1..54)
            ACCESS not-accessible
            STATUS mandatory
            DESCRIPTION
                "Port Number of this port."
        ::= { cdx6500ContSPPPortEntry 1 }

        cdx6500ContSPPPortBoot OBJECT-TYPE
            SYNTAX INTEGER {
                    boot   (1)
                    }
            ACCESS write-only
            STATUS mandatory
            DESCRIPTION
                "Boots the specified SPP Port
                 boot   : Boot the port."
        ::= { cdx6500ContSPPPortEntry 2 }

        cdx6500ContSPPPortEnable OBJECT-TYPE
            SYNTAX INTEGER {
                    enable   (1)
                    }
            ACCESS write-only
            STATUS mandatory
            DESCRIPTION
                "Enables the specified SPP Port.
                 enable   : Enable the Port."
        ::= { cdx6500ContSPPPortEntry 3 }

        cdx6500ContSPPPortDisable OBJECT-TYPE
            SYNTAX INTEGER {
                    disable   (1)
                    }
            ACCESS write-only
            STATUS mandatory
            DESCRIPTION
                "Disables the specified SPP Port.
                 disable   : Disable Port."
        ::= { cdx6500ContSPPPortEntry 4 }

        cdx6500ContSPPPortResetStats OBJECT-TYPE
            SYNTAX INTEGER {
                    reset   (1)
                    }
            ACCESS write-only
            STATUS mandatory
            DESCRIPTION
                "Reset statistics for the specified SPP Port.
                 reset   : Reset port statistics."
        ::= { cdx6500ContSPPPortEntry 5 }

        -- The SPP Station Control Table
        -- This table contains the station control parameters for SPP station

        cdx6500ContSPPStnTable OBJECT-TYPE
            SYNTAX SEQUENCE OF Cdx6500ContSPPStnEntry
            ACCESS not-accessible
            STATUS mandatory
            DESCRIPTION
                "This table contains the SPP Station Control parameters."
        ::= { cdx6500ContSPPTable 2 }

        cdx6500ContSPPStnEntry OBJECT-TYPE
            SYNTAX Cdx6500ContSPPStnEntry
            ACCESS not-accessible
            STATUS mandatory
            DESCRIPTION
                "Entries in the SPP Station Control Table."
            INDEX { cdx6500ContSPPPortNum, cdx6500ContSPPStnId }
        ::= { cdx6500ContSPPStnTable 1 }

        Cdx6500ContSPPStnEntry ::=
            SEQUENCE {
                cdx6500SContSPPPortNum
                    INTEGER,
                cdx6500ContSPPStnId
                    INTEGER,
                cdx6500ContSPPStnBoot
                    INTEGER,
                cdx6500ContSPPStnEnable
                    INTEGER,
                cdx6500ContSPPStnDisable
                    INTEGER,
                cdx6500ContSPPStnResetStats
                    INTEGER
                }

        cdx6500SContSPPPortNum OBJECT-TYPE
            SYNTAX INTEGER (1..54)
            ACCESS not-accessible
            STATUS mandatory
            DESCRIPTION
                "Port Number of this port."
        ::= { cdx6500ContSPPStnEntry 1 }

        cdx6500ContSPPStnId OBJECT-TYPE
            SYNTAX INTEGER
            ACCESS not-accessible
            STATUS mandatory
            DESCRIPTION
                "SPP station number."
        ::= { cdx6500ContSPPStnEntry 2 }

        cdx6500ContSPPStnBoot OBJECT-TYPE
            SYNTAX INTEGER {
                    boot   (1)
                    }
            ACCESS not-accessible
            STATUS mandatory
            DESCRIPTION
                "Boots the secified SPP station
                 boot   : Boot the station."
        ::= { cdx6500ContSPPStnEntry 3 }

        cdx6500ContSPPStnEnable OBJECT-TYPE
            SYNTAX INTEGER {
                    enable   (1)
                    }
            ACCESS write-only
            STATUS mandatory
            DESCRIPTION
                "Enables the specified SPP station.
                 enable   : Enable station."
        ::= { cdx6500ContSPPStnEntry 4 }

        cdx6500ContSPPStnDisable OBJECT-TYPE
            SYNTAX INTEGER {
                    disable   (1)
                    }
            ACCESS write-only
            STATUS mandatory
            DESCRIPTION
                "Disables the specified SPP station.
                 disable   : Disable Station."
        ::= { cdx6500ContSPPStnEntry 5 }

        cdx6500ContSPPStnResetStats OBJECT-TYPE
            SYNTAX INTEGER {
                    reset   (1)
                    }
            ACCESS write-only
            STATUS mandatory
            DESCRIPTION
                "Reset statistics for the specified SPP station.
                 reset   : Reset station statistics."
        ::= { cdx6500ContSPPStnEntry 6 }

        END
