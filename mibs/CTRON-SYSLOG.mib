CTRON-SYSLOG DEFINITIONS ::= BEGIN

--  ctsyslog-mib.txt
--  Revision: 01.00.00
--  Part Number:  
--  Date: February 3, 1999
              
--  Cabletron Systems, Inc.
--  35 Industrial Way, P.O. Box 5005
--  Rochester, NH 03867-0505
--  (603) 332-9400i
--  support@ctron.com
  
--  Cabletron Systems reserves the right to make changes in
--  specification and other information contained in this document
--  without prior notice.  The reader should consult Cabletron Systems
--  to determine whether any such changes have been made.
--
--  In no event shall Cabletron Systems be liable for any incidental,
--  indirect, special, or consequential damages whatsoever (including
--  but not limited to lost profits) arising out of or related to this
--  document or the information contained in it, even if Cabletron
--  Systems has been advised of, known, or should have known, the
--  possibility of such damages.
--
--  Cabletron grants vendors, end-users, and other interested parties
--  a non-exclusive license to use this Specification in connection
--  with the management of Cabletron products.
--  Copyright October 93 Cabletron Systems
--

IMPORTS
		DisplayString				FROM RFC1213-MIB
		cabletron 				FROM CTRON-OIDS
                TimeTicks     				FROM RFC1155-SMI
                OBJECT-TYPE                     	FROM RFC-1212;
		ctSSA 	OBJECT IDENTIFIER ::= { cabletron 4497 }
		aapsLog		OBJECT IDENTIFIER ::= { ctSSA 9 } 



logWindow	OBJECT IDENTIFIER ::= { aapsLog 1 } 

logWindowTable	OBJECT-TYPE
	SYNTAX	   SEQUENCE OF LogWindowEntry
	ACCESS	   not-accessible
	STATUS     mandatory
	DESCRIPTION
	        "Table of log entries"
	::= { logWindow 1 }

logWindowEntry	OBJECT-TYPE
	SYNTAX	   LogWindowEntry
	ACCESS	   not-accessible
	STATUS     mandatory
	DESCRIPTION
	        "Entry of logWindow Table"
	INDEX	   { ltIndex }
	::= { logWindowTable 1 }

LogWindowEntry	::=
	SEQUENCE {
	   ltIndex		INTEGER, 
	   ltLogString		DisplayString(80)
	}

ltIndex	OBJECT-TYPE
	SYNTAX	   INTEGER
	ACCESS	   read-only
	STATUS	   mandatory
	DESCRIPTION
		"Index (window position) of the entry in the current Log Snapshot."
	::= { logWindowEntry 1 }
ltLogString		OBJECT-TYPE
	SYNTAX	   DisplayString(SIZE(80))
	ACCESS	   read-only
	STATUS	   mandatory
	DESCRIPTION
		"String describing the event in the format: Time(DD:HH:MM:SS) + 
		 Log Level(FREEZE/ERROR/CRITICAL/STATUS/INFO/DEBUG) + Log Client Name 
		 + Event String.  Time is expressed as time since reset (not realtime).
		 This will change to realtime in the next iteration of this MIB."
	::= { logWindowEntry 2 }


ltWindowOperation		OBJECT-TYPE
	SYNTAX	   INTEGER { refresh(2), pageUp(3),  pageDown(4)}
	ACCESS	   read-write
	STATUS	   mandatory
	DESCRIPTION
		"refresh(2) redisplays the contents of the current window table. pageUp(3) 
	  	 moves the window one page up. pageDown(4) moves the window one page down."
	::= { logWindow 2 }

ltWindowReset		OBJECT-TYPE
	SYNTAX	   INTEGER { toLogStart(2), toLogEnd(3) }
	ACCESS	   read-write
	STATUS	   mandatory
	DESCRIPTION
		"By setting this object to one of the two available values moves the 
		 beginning of the next window to log start or end"
	::= { logWindow 3 }

ltClientMatchString		OBJECT-TYPE
	SYNTAX	   DisplayString(SIZE(20))
	ACCESS	   read-write
	STATUS	   mandatory
	DESCRIPTION
		"Setting this object to a string value will filter out those clients that
		do not contain that string as a prefix (case sensitive)."
	::= { logWindow 4 }


ltEventMatchString		OBJECT-TYPE
	SYNTAX	   DisplayString(SIZE(20))
	ACCESS	   read-write
	STATUS	   mandatory
	DESCRIPTION
		"Setting this object to a string value will filter out those logged events that
		do not contain that string within the log entry (case sensitive)."
	::= { logWindow 5 }





serverConfig	OBJECT IDENTIFIER ::= { aapsLog 2 } 



scAutoFreeze		OBJECT-TYPE
	SYNTAX	   INTEGER { disabled(2), enabled(3) }
	ACCESS	   read-write
	STATUS	   mandatory
	DESCRIPTION
		"After this value is enabled, the act of logging a FREEZE level message will prevent 
		any additional messages from being logged. The logging process can continue when 
		scAdminStatus is set to enableLogging(3)."
	::= { serverConfig 1 }


scAdminStatus		OBJECT-TYPE
        SYNTAX          INTEGER 
{
	                      	disableLogging(2),
                            	enableLogging(3),
                            	reset(5)
}

	ACCESS	   read-write
	STATUS	   mandatory
	DESCRIPTION
		"This object controls the status of the message logging system and the log itself. 
		Setting this object to disableLogging(2) will prevent any clients from appending 
		messages to the log. EnableLogging(3) starts/resumes logging. Reset(5) initializes 
		the log."
	::= { serverConfig 2 }

scLastChange		OBJECT-TYPE
        SYNTAX     TimeTicks
	ACCESS	   read-only
	STATUS	   mandatory
	DESCRIPTION
		"The value of sysUpTime at the last change to scAdminStatus or scAutoFreeze." 
	::= { serverConfig 3 }



clientConfigTable	OBJECT-TYPE
	SYNTAX	   SEQUENCE OF ClientConfigEntry
	ACCESS	   not-accessible
	STATUS     mandatory
	DESCRIPTION
	        "This table provides the ability to configure which messages will be logged and
		which will be displayed on a per client basis."
	::= { aapsLog 3 }

clientConfigEntry	OBJECT-TYPE
	SYNTAX	   ClientConfigEntry
	ACCESS	   not-accessible
	STATUS     mandatory
	DESCRIPTION
	        "Entry of the client table"
	INDEX	   { ccClientID }
	::= { clientConfigTable 1 }


ClientConfigEntry	::=
	SEQUENCE {
	   ccClientID			INTEGER, 
	   ccClientName			DisplayString(32),
 	   ccClientPersistent 		INTEGER,
 	   ccClientLogStatus 		INTEGER,
 	   ccClientDisplayStatus 	INTEGER,
 	   ccClientFreezeLogStatus 	INTEGER,
 	   ccClientFreezeDisplayStatus 	INTEGER,
 	   ccClientErrorLogStatus 	INTEGER,
 	   ccClientErrorDisplayStatus 	INTEGER,
 	   ccClientCriticalLogStatus 	INTEGER,
 	   ccClientCriticalDisplayStatus INTEGER,
 	   ccClientStatusLogStatus 	INTEGER,
 	   ccClientStatusDisplayStatus 	INTEGER,
 	   ccClientInfoLogStatus 	INTEGER,
 	   ccClientInfoDisplayStatus 	INTEGER,
 	   ccClientDebugLogStatus 	INTEGER,
 	   ccClientDebugDisplayStatus 	INTEGER
	}


ccClientID		OBJECT-TYPE
	SYNTAX	   INTEGER
	ACCESS	   read-only
	STATUS	   mandatory
	DESCRIPTION
		"Unique ID of the client entry"
	::= { clientConfigEntry 1 }

ccClientName		OBJECT-TYPE
	SYNTAX	   DisplayString(SIZE(32))
	ACCESS	   read-only
	STATUS	   mandatory
	DESCRIPTION
		"Name of the client"
	::= { clientConfigEntry 2 }

ccClientPersistent		OBJECT-TYPE
        SYNTAX          INTEGER { disabled(2), enabled(3) } 
	ACCESS	   read-write
	STATUS	   mandatory
	DESCRIPTION
		"When enabled, client settings in this table are persistent across resets."
	::= { clientConfigEntry 3 }

ccClientLogStatus		OBJECT-TYPE
        SYNTAX          INTEGER { disabled(2), enabled(3) } 
	ACCESS	   read-write
	STATUS	   mandatory
	DESCRIPTION
		"When disabled, this client does not append messages to the log."
	::= { clientConfigEntry 4 }

ccClientDisplayStatus		OBJECT-TYPE
        SYNTAX          INTEGER { disabled(2), enabled(3) } 
	ACCESS	   read-write
	STATUS	   mandatory
	DESCRIPTION
		"When disabled, this client's messages are not displayed in the log window.
		This does not prevent them from being logged."
	::= { clientConfigEntry 5 }

ccClientFreezeLogStatus		OBJECT-TYPE
        SYNTAX          INTEGER { disabled(2), enabled(3) } 
	ACCESS	   read-write
	STATUS	   mandatory
	DESCRIPTION
		"When disabled, client's messages with this log level do not get appended to the log."
	::= { clientConfigEntry 6 }

ccClientFreezeDisplayStatus		OBJECT-TYPE
        SYNTAX          INTEGER { disabled(2), enabled(3) } 
	ACCESS	   read-write
	STATUS	   mandatory
	DESCRIPTION
		"When disabled, client's messages with this log level do not get displayed in the log window."
	::= { clientConfigEntry 7 }

ccClientErrorLogStatus		OBJECT-TYPE
        SYNTAX          INTEGER { disabled(2), enabled(3) } 
	ACCESS	   read-write
	STATUS	   mandatory
	DESCRIPTION
		"When disabled, client's messages with this log level do not get appended to the log."
	::= { clientConfigEntry 8 }

ccClientErrorDisplayStatus		OBJECT-TYPE
        SYNTAX          INTEGER { disabled(2), enabled(3) } 
	ACCESS	   read-write
	STATUS	   mandatory
	DESCRIPTION
		"When disabled, client's messages with this log level do not get displayed in the log window."
	::= { clientConfigEntry 9 }

ccClientCriticalLogStatus		OBJECT-TYPE
        SYNTAX          INTEGER { disabled(2), enabled(3) } 
	ACCESS	   read-write
	STATUS	   mandatory
	DESCRIPTION
		"When disabled, client's messages with this log level do not get appended to the log."
	::= { clientConfigEntry 10 }

ccClientCriticalDisplayStatus		OBJECT-TYPE
        SYNTAX          INTEGER { disabled(2), enabled(3) } 
	ACCESS	   read-write
	STATUS	   mandatory
	DESCRIPTION
		"When disabled, client's messages with this log level do not get displayed in the log window."
	::= { clientConfigEntry 11 }

ccClientStatusLogStatus		OBJECT-TYPE
        SYNTAX          INTEGER { disabled(2), enabled(3) } 
	ACCESS	   read-write
	STATUS	   mandatory
	DESCRIPTION
		"When disabled, client's messages with this log level do not get appended to the log."
	::= { clientConfigEntry 12 }

ccClientStatusDisplayStatus		OBJECT-TYPE
        SYNTAX          INTEGER { disabled(2), enabled(3) } 
	ACCESS	   read-write
	STATUS	   mandatory
	DESCRIPTION
		"When disabled, client's messages with this log level do not get displayed in the log window."
	::= { clientConfigEntry 13 }


ccClientInfoLogStatus		OBJECT-TYPE
        SYNTAX          INTEGER { disabled(2), enabled(3) } 
	ACCESS	   read-write
	STATUS	   mandatory
	DESCRIPTION
		"When disabled, client's messages with this log level do not get appended to the log."
	::= { clientConfigEntry 14 }

ccClientInfoDisplayStatus		OBJECT-TYPE
        SYNTAX          INTEGER { disabled(2), enabled(3) } 
	ACCESS	   read-write
	STATUS	   mandatory
	DESCRIPTION
		"When disabled, client's messages with this log level do not get displayed in the log window."
	::= { clientConfigEntry 15 }

ccClientDebugLogStatus		OBJECT-TYPE
        SYNTAX          INTEGER { disabled(2), enabled(3) } 
	ACCESS	   read-write
	STATUS	   mandatory
	DESCRIPTION
		"When disabled, client's messages with this log level do not get appended to the log."

	::= { clientConfigEntry 16 }

ccClientDebugDisplayStatus		OBJECT-TYPE
        SYNTAX          INTEGER { disabled(2), enabled(3) } 
	ACCESS	   read-write
	STATUS	   mandatory
	DESCRIPTION
		"When disabled, client's messages with this log level do not get displayed in the log window."
	::= { clientConfigEntry 17 }


recoveredLogTable	OBJECT-TYPE
	SYNTAX	   SEQUENCE OF RecoveredLogTableEntry
	ACCESS	   not-accessible
	STATUS     mandatory
	DESCRIPTION
	        "Table that contains a the last 100 entries in the log recorded before the last 
		system shutdown, reset or a power failure."
	::= { aapsLog 4 }

recoveredLogTableEntry	OBJECT-TYPE
	SYNTAX	   RecoveredLogTableEntry
	ACCESS	   not-accessible
	STATUS     mandatory
	DESCRIPTION
	        "Entry of the recovered log table"
	INDEX	   { rlIndex }
	::= { recoveredLogTable 1 }


RecoveredLogTableEntry	::=
	SEQUENCE {
	   rlIndex			INTEGER, 
	   rlLogString			DisplayString(200)
	}
rlIndex		OBJECT-TYPE
	SYNTAX	   INTEGER
	ACCESS	   read-only
	STATUS	   mandatory
	DESCRIPTION
		"Unique index of the recovered log entry. Entry with index 1 is the oldest entry in the log."
	::= { recoveredLogTableEntry 1 }

rlLogString		OBJECT-TYPE
	SYNTAX	   DisplayString(SIZE(200))
	ACCESS	   read-only
	STATUS	   mandatory
	DESCRIPTION
		"Event string of this entry."
	::= { recoveredLogTableEntry 2 }

END
