-- This file is corresponding to Release 6.1.2.100 from 2001/09/26 00:00:00
-- (C)opyright 1991-2000 BinTec Communications AG, All Rights Reserved
--  $RCSfile: mibqos,v $ 
-- $Revision: 1.5 $ 

BIANCA-BRICK-QOS-MIB DEFINITIONS ::= BEGIN
        IMPORTS
            Counter, TimeTicks
                FROM RFC1155-SMI
 
            OBJECT-TYPE
                FROM RFC-1212;

    org		OBJECT IDENTIFIER ::= { iso 3 }
    dod		OBJECT IDENTIFIER ::= { org 6 }
    internet	OBJECT IDENTIFIER ::= { dod 1 }
    private	OBJECT IDENTIFIER ::= { internet 4 }
    enterprises	OBJECT IDENTIFIER ::= { private 1 }
    bintec 	OBJECT IDENTIFIER ::= { enterprises 272 }
    bibo	OBJECT IDENTIFIER ::= { bintec 4 }
    qos		OBJECT IDENTIFIER
	::= { bibo 27 }


    -- QoS Group

    -- Management Information for the QoS Subsystem of the BIANCA/BRICK


    -- qosIfTable

	qosIfTable OBJECT-TYPE
	    SYNTAX  SEQUENCE OF QosIfEntry
	    ACCESS  not-accessible
	    STATUS  mandatory
	    DESCRIPTION
		"The qosIfTable enables QoS policies on the interface
		 specified by qosIfIndex (interface index).

                 Creating entries: Entries are created by assigning a
                 value to the qosIfIndex object.

                 Deleting entries: Entries are removed by setting an
                 entry's qosIfType object to 'delete'."
	::= { qos 1 }

	qosIfEntry OBJECT-TYPE
	    SYNTAX  QosIfEntry
	    ACCESS  not-accessible
	    STATUS  mandatory
	    DESCRIPTION
		""
	    INDEX   { qosIfIndex }
	::= { qosIfTable 1 }

	QosIfEntry ::=
	    SEQUENCE {
		qosIfIndex				INTEGER,
		qosIfType				INTEGER,
		qosIfMaxTxRate				INTEGER
	    }

	qosIfIndex OBJECT-TYPE
	    SYNTAX  INTEGER
	    ACCESS  read-write
	    STATUS  mandatory

	    DESCRIPTION
                "Unique interface index"
	::= { qosIfEntry 1 }

	qosIfType OBJECT-TYPE
	    SYNTAX  INTEGER { 
		pq(1),
		wrr(2),
		wfq(3),
    --		diff-serv(4),
		disabled(8),
		delete(9)
	    } 
            ACCESS  read-write
            STATUS  mandatory

            DESCRIPTION
                "This object defines the queueing and scheduling algorithm
		 used on the related interface, possible values:
		 pq(1)		= priority queueing
		 wrr(2)		= weighted round-robin scheduling
		 wfq(3)		= weighted fair queuing scheduling
		 disable(8)	= disable this entry
		 delete(9)	= delete this entry."
	::= { qosIfEntry 2 }

	qosIfMaxTxRate OBJECT-TYPE
	    SYNTAX  INTEGER
            ACCESS  read-write
            STATUS  mandatory

            DESCRIPTION
                "This object enables traffic shaping on the related interface,
		 if set to zero (0) there is no shaping active. Otherwise this
		 variable defines the maximum amount of bits per second to
		 be transmitted."
	::= { qosIfEntry 3 }


    -- qosIfStatTable

	qosIfStatTable OBJECT-TYPE
	    SYNTAX  SEQUENCE OF QosIfStatEntry
	    ACCESS  not-accessible
	    STATUS  mandatory
	    DESCRIPTION
		"The qosIfStatTable contains statistical QoS-specific
		 information for the interface specified by qosIfStatIndex
		 (interface index). Only the system can add or delete
                 entries to this table."
	::= { qos 2 }

	qosIfStatEntry OBJECT-TYPE
	    SYNTAX  QosIfStatEntry
	    ACCESS  not-accessible
	    STATUS  mandatory
	    DESCRIPTION
		""
	    INDEX   { qosIfStatIndex }
	::= { qosIfStatTable 1 }

	QosIfStatEntry ::=
	    SEQUENCE {
		qosIfStatIndex				INTEGER,
		qosIfStatOutPkts			Counter,
		qosIfStatOutOctets			Counter,
  --		qosIfStatInPkts				Counter,
  --		qosIfStatInOctets			Counter,
		qosIfStatPktsQueued			Counter,
		qosIfStatOctetsQueued			Counter,
		qosIfStatPktsDropped			Counter,
		qosIfStatOctetsDropped			Counter
	    }

	qosIfStatIndex OBJECT-TYPE
	    SYNTAX  INTEGER
	    ACCESS  read-only
	    STATUS  mandatory

	    DESCRIPTION
                "The unique interface index."
	::= { qosIfStatEntry 1 }


	qosIfStatOutPkts OBJECT-TYPE
	    SYNTAX  Counter
	    ACCESS  read-only
	    STATUS  mandatory

	    DESCRIPTION
                "The number of packets transmitted on the related interface
		 since its last change to the 'up' state."
	::= { qosIfStatEntry 2 }

	qosIfStatOutOctets OBJECT-TYPE
	    SYNTAX  Counter
	    ACCESS  read-only
	    STATUS  mandatory

	    DESCRIPTION
                "The number of octets transmitted on the related interface
		 since its last change to the 'up' state."
	::= { qosIfStatEntry 3 }

  --	qosIfStatInPkts OBJECT-TYPE
  --	    SYNTAX  Counter
  --	    ACCESS  read-only
  --	    STATUS  mandatory

  --	    DESCRIPTION
  --            "The number of packets received via the related interface
  --		 since its last change to the 'up' state."
  --	::= { qosIfStatEntry 4 }
  --
  --	qosIfStatInOctets OBJECT-TYPE
  --	    SYNTAX  Counter
  --	    ACCESS  read-only
  --	    STATUS  mandatory
  --
  --	    DESCRIPTION
  --            "The number of octets received via the related interface
  --		 since its last change to the 'up' state."
  --	::= { qosIfStatEntry 5 }
  --

	qosIfStatPktsQueued OBJECT-TYPE
	    SYNTAX  Counter
	    ACCESS  read-only
	    STATUS  mandatory

	    DESCRIPTION
                "The number of data packets enqueued and waiting to be sent
		 across the related interface."
	::= { qosIfStatEntry 6 }

	qosIfStatOctetsQueued OBJECT-TYPE
	    SYNTAX  Counter
	    ACCESS  read-only
	    STATUS  mandatory

	    DESCRIPTION
                "The amount of data (in octets) enqueued waiting to be sent
		 across the related interface."
	::= { qosIfStatEntry 7 }

	qosIfStatPktsDropped OBJECT-TYPE
	    SYNTAX  Counter
	    ACCESS  read-only
	    STATUS  mandatory

	    DESCRIPTION
                "The number of data packets dropped during congestion."
	::= { qosIfStatEntry 8 }

	qosIfStatOctetsDropped OBJECT-TYPE
	    SYNTAX  Counter
	    ACCESS  read-only
	    STATUS  mandatory

	    DESCRIPTION
                "The representation of qosIfStatPktsDropped in octets."
	::= { qosIfStatEntry 9 }


    -- qosPolicyTable

	qosPolicyTable OBJECT-TYPE
	    SYNTAX  SEQUENCE OF QosPolicyEntry
	    ACCESS  not-accessible
	    STATUS  mandatory
	    DESCRIPTION
		"The qosPolicyTable enables QoS policies for the packet
		 class specified by qosPolicyIfIndex (interface index),
		 qosPolicyType and qosPolicyClassId.

                 Creating entries: Entries are created by assigning a
                 value to the qosPolicyIfIndex object.

                 Deleting entries: Entries are removed by setting an
                 entry's qosPolicyType object to 'delete'."
	::= { qos 3 }

	qosPolicyEntry OBJECT-TYPE
	    SYNTAX  QosPolicyEntry
	    ACCESS  not-accessible
	    STATUS  mandatory
	    DESCRIPTION
		""
	    INDEX   { qosPolicyIfIndex }
	::= { qosPolicyTable 1 }

	QosPolicyEntry ::=
	    SEQUENCE {
		qosPolicyIfIndex			INTEGER,
		qosPolicyType				INTEGER,
		qosPolicyClassId			INTEGER,
		qosPolicyPriority			INTEGER,
		qosPolicyWeight				INTEGER,
    		qosPolicyShaper				INTEGER,
		qosPolicyCongestionAvoidance		INTEGER,
  --		qosPolicyExceedAction			INTEGER,
		qosPolicyDropAlgorithm			INTEGER,
  --		qosPolicyTxMinRate			INTEGER,
		qosPolicyTxRate				INTEGER,
		qosPolicyTxRateLimitation		INTEGER,
		qosPolicyTxBurstSize			INTEGER,
		qosPolicyLowerThreshold			INTEGER,
		qosPolicyUpperThreshold			INTEGER	
	    }

	qosPolicyIfIndex OBJECT-TYPE
	    SYNTAX  INTEGER
	    ACCESS  read-write
	    STATUS  mandatory

	    DESCRIPTION
                "The unique interface index"
	::= { qosPolicyEntry 1 }

	qosPolicyType OBJECT-TYPE
	    SYNTAX  INTEGER { 
		class-based(1),
		high-priority(2),
    		default(3),
		delete(4)
	    } 
            ACCESS  read-write
            STATUS  mandatory

            DESCRIPTION
                "This objects defines in conjunction with ipQoSClassId and
		 qosPolicyClassId the related type of packet classes for
		 this QoS policy, possible values:
		 class-based(1) 	= policy for non-high-priority packets
		 high-priority(2)	= policy for high-priority packets
		 default(3)		= policy for packets not matching
		 			  otherwise."
	::= { qosPolicyEntry 2 }

	qosPolicyClassId OBJECT-TYPE
	    SYNTAX  INTEGER  (1..255)
            ACCESS  read-write
            STATUS  mandatory

            DESCRIPTION
                "Defines in conjunction with ipQoSClassId and qosPolicyType
		 the QoS policy to be applied on the classified IP traffic."
	::= { qosPolicyEntry 3 }

	qosPolicyPriority OBJECT-TYPE
	    SYNTAX  INTEGER  (0..255)
            ACCESS  read-write
            STATUS  mandatory

            DESCRIPTION
                "The relative priority for this packet class to be used for
		 the packet scheduling as described via qosIfType."
	::= { qosPolicyEntry 4 }

	qosPolicyWeight OBJECT-TYPE
	    SYNTAX  INTEGER  (0..255)
            ACCESS  read-write
            STATUS  mandatory

            DESCRIPTION
                "The relative weight for this packet class to be used for
		 the packet scheduling as described via qosIfType."
	::= { qosPolicyEntry 5 }

	qosPolicyShaper OBJECT-TYPE
	    SYNTAX  INTEGER {
		none(1),
		token-bucket(2)
  --		leaky-bucket(3)
	    } 
	    ACCESS  read-write
	    STATUS  mandatory

	    DESCRIPTION
	        "This objects describes the traffic-shaping algorithm to be
		 used in order to limit the bandwidth for the related packet
		 class, possible values:
		 none(1) 		= no shaping defined
		 token-bucket(2) 	= token-bucket traffic shaper."
	::= { qosPolicyEntry 6 }

	qosPolicyCongestionAvoidance OBJECT-TYPE
	    SYNTAX  INTEGER { 
		none(1),
    		weighted-random(2)
	    } 
            ACCESS  read-write
            STATUS  mandatory

            DESCRIPTION
                "This objects defines a packet dropping algorithm to use if
		 more than qosPolicyLowerThreshold octets are enqueued."
	::= { qosPolicyEntry 7 }

  --	qosPolicyExceedAction OBJECT-TYPE
  --	    SYNTAX  INTEGER { 
  --		none(1),
  --  		remark-tos(2)
  --	    } 
  --        ACCESS  read-write
  --        STATUS  mandatory
  --
  --        DESCRIPTION
  --            "."
  --	::= { qosPolicyEntry 8 }
  --

	qosPolicyDropAlgorithm OBJECT-TYPE
	    SYNTAX  INTEGER { 
    		tail-drop(1),
    		head-drop(2),
    		random-drop(3)
	    } 
            ACCESS  read-write
            STATUS  mandatory

            DESCRIPTION
                "This objects defines the packet dropping algorithm to apply
		 if more than qosPolicyUpperThreshold octets are currently
		 enqueued, possible values:
		 tail-drop(1) 	= drop all newly arriving packets
		 head-drop(2)   = drop packets at the queue head
			 	  enqueue newly arriving packets
		 random-drop(3) = drop arriving or enqueued packets
				  randomly."
	::= { qosPolicyEntry 9 }

  --	qosPolicyTxMinRate OBJECT-TYPE
  --	    SYNTAX  INTEGER
  --        ACCESS  read-write
  --        STATUS  mandatory
  --
  --        DESCRIPTION
  --            "This object defines the minimum transmission rate in octets
  --		 per second allocated for this packet class."
  --	::= { qosPolicyEntry 16 }
  --

	qosPolicyTxRate OBJECT-TYPE
	    SYNTAX  INTEGER
            ACCESS  read-write
            STATUS  mandatory

            DESCRIPTION
                "This object enables bandwidth limitation for the related
		 class, if set to zero (0) there is no limitation policy.
		 Otherwise this variable defines the maximum amount of bits
		 per second to be send."
	::= { qosPolicyEntry 17 }

	qosPolicyTxRateLimitation OBJECT-TYPE
	    SYNTAX  INTEGER {
    		not-bounded(1),
    		bounded(2)
	    } 
            ACCESS  read-write
            STATUS  mandatory

            DESCRIPTION
                "This objects determines the policy for the related class if
		 the transmission rate limit defined by qosPolicyTxRate is
		 reached. When set to not-bounded(1) allocation of remaining
		 bandwidth not consumed by other classes is allowed. When set
		 to bounded(2), qosPolicyTxRate is strict limitation for the
		 long-term bandwidth consumption."
	::= { qosPolicyEntry 18 }

	qosPolicyTxBurstSize OBJECT-TYPE
	    SYNTAX  INTEGER
            ACCESS  read-write
            STATUS  mandatory

            DESCRIPTION
                "The maximum number of octets in a single transmission burst."
	::= { qosPolicyEntry 19 }

	qosPolicyLowerThreshold OBJECT-TYPE
	    SYNTAX  INTEGER  (0..262143)
            ACCESS  read-write
            STATUS  mandatory

            DESCRIPTION
                "This variable defines the lower or minimum queue depth
		 threshold for packet dropping algorithm used for congestion
		 avoidance (see qosPolicyCongestionAvoidance)."
	::= { qosPolicyEntry 20 }

	qosPolicyUpperThreshold OBJECT-TYPE
	    SYNTAX  INTEGER  (0..262143)
            ACCESS  read-write
            STATUS  mandatory

            DESCRIPTION
                "This variable defines the upper or maximum queue depth
		 threshold at which - depending on qosPolicyDropAlgorithm -
		 all newly arriving or packets enqueued former will be
		 dropped."
	::= { qosPolicyEntry 21 }


    -- qosPolicyStatTable

	qosPolicyStatTable OBJECT-TYPE
	    SYNTAX  SEQUENCE OF QosPolicyStatEntry
	    ACCESS  not-accessible
	    STATUS  mandatory
	    DESCRIPTION
		"The qosPolicyStatTable contains statistical QoS-specific
		 information for the policy specified by qosPolicyStatIfIndex
		 (interface index), qosPolicyStatType and qosPolicyStatClassId.
		 Only the system can add or delete entries to this table."
	::= { qos 4 }

	qosPolicyStatEntry OBJECT-TYPE
	    SYNTAX  QosPolicyStatEntry
	    ACCESS  not-accessible
	    STATUS  mandatory
	    DESCRIPTION
		""
	    INDEX   { qosPolicyStatIfIndex }
	::= { qosPolicyStatTable 1 }

	QosPolicyStatEntry ::=
	    SEQUENCE {
		qosPolicyStatIfIndex			INTEGER,
		qosPolicyStatType			INTEGER,
		qosPolicyStatClassId			INTEGER,
		qosPolicyStatOutPkts			Counter,
		qosPolicyStatOutOctets			Counter,
  --		qosPolicyStatInPkts			Counter,
  --		qosPolicyStatInOctets			Counter,
		qosPolicyStatPktsQueued			Counter,
		qosPolicyStatOctetsQueued		Counter,
		qosPolicyStatPktsDropped		Counter,
		qosPolicyStatOctetsDropped		Counter
  --		qosPolicyStatQlen			INTEGER,
  --		qosPolicyStatMaxQlen			INTEGER,
  --		qosPolicyStatAvgdQlen			INTEGER
	    }

	qosPolicyStatIfIndex OBJECT-TYPE
	    SYNTAX  INTEGER
	    ACCESS  read-only
	    STATUS  mandatory

	    DESCRIPTION
                "The unique interface index"
	::= { qosPolicyStatEntry 1 }

	qosPolicyStatType OBJECT-TYPE
	    SYNTAX  INTEGER { 
		class-based(1),
		high-priority(2),
    		default(3)
	    } 
            ACCESS  read-only
            STATUS  mandatory

            DESCRIPTION
                "The related type of packet classes for this QoS policy
		 (see qosPolicyType for further explanation)."
	::= { qosPolicyStatEntry 2 }

	qosPolicyStatClassId OBJECT-TYPE
	    SYNTAX  INTEGER
	    ACCESS  read-only
	    STATUS  mandatory

	    DESCRIPTION
                "Unique packet class ID"
	::= { qosPolicyStatEntry 3 }

	qosPolicyStatOutPkts OBJECT-TYPE
	    SYNTAX  Counter
	    ACCESS  read-only
	    STATUS  mandatory

	    DESCRIPTION
                "The number of packets sent belonging to the related
		 packet class."
	::= { qosPolicyStatEntry 4 }

	qosPolicyStatOutOctets OBJECT-TYPE
	    SYNTAX  Counter
	    ACCESS  read-only
	    STATUS  mandatory

	    DESCRIPTION
                "The representation of qosPolicyStatOutPkts in octets."
	::= { qosPolicyStatEntry 5 }

  --	qosPolicyStatInPkts OBJECT-TYPE
  --	    SYNTAX  Counter
  --	    ACCESS  read-only
  --	    STATUS  mandatory
  --
  --	    DESCRIPTION
  --            "The number of packets received belonging to the related
  --		 packet class."
  --	::= { qosPolicyStatEntry 6 }
  --
  --	qosPolicyStatInOctets OBJECT-TYPE
  --	    SYNTAX  Counter
  --	    ACCESS  read-only
  --	    STATUS  mandatory
  --
  --	    DESCRIPTION
  --            "The representation of qosPolicyStatInPkts in octets."
  --	::= { qosPolicyStatEntry 7 }
  --


	qosPolicyStatPktsQueued OBJECT-TYPE
	    SYNTAX  Counter
	    ACCESS  read-only
	    STATUS  mandatory

	    DESCRIPTION
                "The number of data packets of the related class enqueued
		 and waiting to be sent."
	::= { qosPolicyStatEntry 8 }

	qosPolicyStatOctetsQueued OBJECT-TYPE
	    SYNTAX  Counter
	    ACCESS  read-only
	    STATUS  mandatory

	    DESCRIPTION
                "The representation of qosPolicyStatPktsQueued in octets."
	::= { qosPolicyStatEntry 9 }

	qosPolicyStatPktsDropped OBJECT-TYPE
	    SYNTAX  Counter
	    ACCESS  read-only
	    STATUS  mandatory

	    DESCRIPTION
                "The number of data packets of the related class dropped
		 during congestion."
	::= { qosPolicyStatEntry 10 }

	qosPolicyStatOctetsDropped OBJECT-TYPE
	    SYNTAX  Counter
	    ACCESS  read-only
	    STATUS  mandatory

	    DESCRIPTION
                "The representation of qosPolicyStatPktsDropped in octets"
	::= { qosPolicyStatEntry 11 }

  --	qosPolicyStatQlen OBJECT-TYPE
  --	    SYNTAX  Counter
  --	    ACCESS  read-only
  --	    STATUS  mandatory
  --
  --	    DESCRIPTION
  --            ""
  --	::= { qosPolicyStatEntry 12 }
  --
  --	qosPolicyStatMaxQlen OBJECT-TYPE
  --	    SYNTAX  Counter
  --	    ACCESS  read-only
  --	    STATUS  mandatory
  --
  --	    DESCRIPTION
  --            ""
  --	::= { qosPolicyStatEntry 13 }
  --
  --	qosPolicyStatAvgdQlen OBJECT-TYPE
  --	    SYNTAX  Counter
  --	    ACCESS  read-only
  --	    STATUS  mandatory
  --
  --	    DESCRIPTION
  --            ""
  --	::= { qosPolicyStatEntry 14 }
  --


END             -- of BIANCA-BRICK-QOS definitions
