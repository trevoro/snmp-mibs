-- *****************************************************************************
-- Unisphere-Data-DNS-MIB
--
-- Unisphere Networks Inc. Enterprise MIB
-- DNS MIB
--
-- Copyright (c) 2001 Unisphere Networks, Inc.  All Rights Reserved.
-- *****************************************************************************

Unisphere-Data-DNS-MIB DEFINITIONS ::= BEGIN

IMPORTS
    MODULE-IDENTITY,
    OBJECT-TYPE,
    IpAddress,
    Integer32
        FROM SNMPv2-SMI

    RowStatus,
    TEXTUAL-CONVENTION
        FROM SNMPv2-TC

    MODULE-COMPLIANCE,
    OBJECT-GROUP
        FROM SNMPv2-CONF

    UsdEnable
        FROM Unisphere-Data-TC

    usDataMibs
        FROM Unisphere-Data-MIBs;


usdDnsMIB  MODULE-IDENTITY
    LAST-UPDATED "200103221929Z"  -- 22-Mar-01 02:29 PM EST
    ORGANIZATION "Unisphere Networks, Inc."
    CONTACT-INFO
        "       Unisphere Networks, Inc.
        Postal: 10 Technology Park Drive
                Westford, MA  01886
                USA
        Tel:    +1 978 589 5800
        Email:  mib@UnisphereNetworks.com"
    DESCRIPTION
        "The DNS MIB for the Unisphere Networks, Inc. enterprise."
    -- Revision History
    REVISION    "200103221929Z"  -- 22-Mar-01 02:29 PM EST  - RX 3.0
    DESCRIPTION
        "Initial version of this MIB module."
    ::= { usDataMibs 47 }


-- ++++++++++++++++++++++++++++++++++++++++++++++++++++++++++++++++++++++
-- Textual conventions
-- ++++++++++++++++++++++++++++++++++++++++++++++++++++++++++++++++++++++

-- Type definitions

UsdNextServerListIndex ::= TEXTUAL-CONVENTION
    STATUS      current
    DESCRIPTION
        "Coordinate index value allocation for entries in an associated table,
        by first reading an index value from this object, then creating an
        entry, having that index value, in the associated table.

        The DESCRIPTION clause for an object of this type must identify the
        associated table.

        A GET of this object returns the next available index value to be used
        to create an entry in the associated table; or zero, if no valid index
        value is available.  This object also returns a value of zero when it is
        the lexicographic successor of a varbind presented in an SNMP GETNEXT or
        GETBULK request, for which circumstance it is assumed that index
        allocation is unintended.

        Successive GETs will typically return different values, thus avoiding
        collisions among cooperating management clients seeking to create table
        entries simultaneously.

        Unless specified otherwise by its MAX-ACCESS and DESCRIPTION clauses, an
        object of this type is read-only, and a SET of such an object returns a
        notWritable error."
    SYNTAX      Integer32 (0..2147483647)

ServerListIndex ::= TEXTUAL-CONVENTION
    DISPLAY-HINT "d"
    STATUS       current
    DESCRIPTION
        "A unique value, greater than zero, for each DNS server in the managed
        system."
    SYNTAX       Integer32 (1..2147483647)

UsdNextLocalDomainNameListIndex ::= TEXTUAL-CONVENTION
    STATUS      current
    DESCRIPTION
        "Coordinate index value allocation for entries in an associated table,
        by first reading an index value from this object, then creating an
        entry, having that index value, in the associated table.

        The DESCRIPTION clause for an object of this type must identify the
        associated table.

        A GET of this object returns the next available index value to be used
        to create an entry in the associated table; or zero, if no valid index
        value is available.  This object also returns a value of zero when it is
        the lexicographic successor of a varbind presented in an SNMP GETNEXT or
        GETBULK request, for which circumstance it is assumed that index
        allocation is unintended.

        Successive GETs will typically return different values, thus avoiding
        collisions among cooperating management clients seeking to create table
        entries simultaneously.

        Unless specified otherwise by its MAX-ACCESS and DESCRIPTION clauses, an
        object of this type is read-only, and a SET of such an object returns a
        notWritable error."
    SYNTAX      Integer32 (0..2147483647)

LocalDomainNameListIndex ::= TEXTUAL-CONVENTION
    DISPLAY-HINT "d"
    STATUS       current
    DESCRIPTION
        "A unique value, greater than zero, for each recognized domain name in
        the managed system."
    SYNTAX       Integer32 (1..2147483647)

LocalDomainName ::= TEXTUAL-CONVENTION
    DISPLAY-HINT "32a"
    STATUS       current
    DESCRIPTION
        "Local domain name.  Represents textual information taken from the NVT
        ASCII character set."
    REFERENCE
        "RFC 854: NVT ASCII character set.  See SNMPv2-TC.DisplayString
        DESCRIPTION for a summary."
    SYNTAX      OCTET STRING (SIZE (0..32))


-- ++++++++++++++++++++++++++++++++++++++++++++++++++++++++++++++++++++++
-- Managed objects
-- ++++++++++++++++++++++++++++++++++++++++++++++++++++++++++++++++++++++

usdDnsObjects              OBJECT IDENTIFIER ::= { usdDnsMIB 1 }
usdDnsGeneral              OBJECT IDENTIFIER ::= { usdDnsObjects 1 }
usdDnsServerList           OBJECT IDENTIFIER ::= { usdDnsObjects 2 }
usdDnsLocalDomainNameList  OBJECT IDENTIFIER ::= { usdDnsObjects 3 }

--
-- General DNS Control Objects
--

usdDnsEnable OBJECT-TYPE
    SYNTAX      UsdEnable
    MAX-ACCESS  read-write
    STATUS      current
    DESCRIPTION
        "Exerts administrative control to enable/disable DNS capability."
    ::= { usdDnsGeneral 1 }

--
-- The DNS Server List
--

usdDnsServerListNextIndex OBJECT-TYPE
    SYNTAX      UsdNextServerListIndex
    MAX-ACCESS  read-only
    STATUS      current
    DESCRIPTION
        "Coordinate usdDnsServerListIndex value allocation for entries in
        usdDnsServerListTable.

        A GET of this object returns the next available index value to be used
        to create an entry in the associated table; or zero, if no valid index
        value is available.  This object also returns a value of zero when it is
        the lexicographic successor of a varbind presented in an SNMP GETNEXT or
        GETBULK request, for which circumstance it is assumed that index
        allocation is unintended.

        Successive GETs will typically return different values, thus avoiding
        collisions among cooperating management clients seeking to create table
        entries simultaneously."
    ::= { usdDnsServerList 1 }

usdDnsServerListTable OBJECT-TYPE
    SYNTAX      SEQUENCE OF UsdDnsServerListEntry
    MAX-ACCESS  not-accessible
    STATUS      current
    DESCRIPTION
        "This table contains an entry for each DNS server."
    ::= { usdDnsServerList 2 }

usdDnsServerListEntry OBJECT-TYPE
    SYNTAX      UsdDnsServerListEntry
    MAX-ACCESS  not-accessible
    STATUS      current
    DESCRIPTION
        "Each entry corresponds to an associated DNS server."
    INDEX   { usdDnsServerListIndex }
    ::= { usdDnsServerListTable 1 }

UsdDnsServerListEntry ::= SEQUENCE {
    usdDnsServerListIndex
        ServerListIndex,        
    usdDnsServerListAddress
        IpAddress,
    usdDnsServerListRowStatus
        RowStatus
    }

usdDnsServerListIndex OBJECT-TYPE
    SYNTAX      ServerListIndex
    MAX-ACCESS  not-accessible
    STATUS      current
    DESCRIPTION
        "The index of the DNS server.  When creating entries in this table,
        suitable values for this object are determined by reading
        usdDnsServerListNextIndex."
    ::= { usdDnsServerListEntry 1 }

usdDnsServerListAddress OBJECT-TYPE
    SYNTAX      IpAddress
    MAX-ACCESS  read-create
    STATUS      current
    DESCRIPTION
        "The IP address of the DNS server."
    ::= { usdDnsServerListEntry 2 }

usdDnsServerListRowStatus OBJECT-TYPE
    SYNTAX      RowStatus
    MAX-ACCESS  read-create
    STATUS      current
    DESCRIPTION
        "Controls creation/deletion of entries in this table according to the
        RowStatus textual convention, constrained to support the following
        values only:

            createAndGo
            destroy"
    ::= { usdDnsServerListEntry 3 }

--
-- The DNS Local Domain Name List
--

usdDnsLocalDomainNameListNextIndex OBJECT-TYPE
    SYNTAX      UsdNextLocalDomainNameListIndex
    MAX-ACCESS  read-only
    STATUS      current
    DESCRIPTION
        "Coordinate usdDnsLocalDomainNameListIndex value allocation for entries
        in usdDnsLocalDomainNameListTable.

        A GET of this object returns the next available index value to be used
        to create an entry in the associated table; or zero, if no valid index
        value is available.  This object also returns a value of zero when it is
        the lexicographic successor of a varbind presented in an SNMP GETNEXT or
        GETBULK request, for which circumstance it is assumed that index
        allocation is unintended.

        Successive GETs will typically return different values, thus avoiding
        collisions among cooperating management clients seeking to create table
        entries simultaneously."
    ::= { usdDnsLocalDomainNameList 1 }

usdDnsLocalDomainNameListTable OBJECT-TYPE
    SYNTAX      SEQUENCE OF UsdDnsLocalDomainNameListEntry
    MAX-ACCESS  not-accessible
    STATUS      current
    DESCRIPTION
        "This table contains an entry for each recognized local domain name."
    ::= { usdDnsLocalDomainNameList 2 }

usdDnsLocalDomainNameListEntry OBJECT-TYPE
    SYNTAX      UsdDnsLocalDomainNameListEntry
    MAX-ACCESS  not-accessible
    STATUS      current
    DESCRIPTION
        "Each entry corresponds to a recognized local domain name."
    INDEX   { usdDnsLocalDomainNameListIndex }
    ::= { usdDnsLocalDomainNameListTable 1 }

UsdDnsLocalDomainNameListEntry ::= SEQUENCE {
    usdDnsLocalDomainNameListIndex
        LocalDomainNameListIndex,        
    usdDnsLocalDomainNameListName
        LocalDomainName,
    usdDnsLocalDomainNameListRowStatus
        RowStatus
    }

usdDnsLocalDomainNameListIndex OBJECT-TYPE
    SYNTAX      LocalDomainNameListIndex
    MAX-ACCESS  not-accessible
    STATUS      current
    DESCRIPTION
        "The index of the domain name.  When creating entries in this table,
        suitable values for this object are determined by reading
        usdDnsLocalDomainNameListNextIndex."
    ::= { usdDnsLocalDomainNameListEntry 1 }

usdDnsLocalDomainNameListName OBJECT-TYPE
    SYNTAX      LocalDomainName
    MAX-ACCESS  read-create
    STATUS      current
    DESCRIPTION
        "A recognized local domain name."
    ::= { usdDnsLocalDomainNameListEntry 2 }

usdDnsLocalDomainNameListRowStatus OBJECT-TYPE
    SYNTAX      RowStatus
    MAX-ACCESS  read-create
    STATUS      current
    DESCRIPTION
        "Controls creation/deletion of entries in this table according to the
        RowStatus textual convention, constrained to support the following
        values only:

            createAndGo
            destroy"
    ::= { usdDnsLocalDomainNameListEntry 3 }

-- ++++++++++++++++++++++++++++++++++++++++++++++++++++++++++++++++++++++
-- Conformance information
-- ++++++++++++++++++++++++++++++++++++++++++++++++++++++++++++++++++++++

usdDnsConformance     OBJECT IDENTIFIER ::= { usdDnsMIB 2 }
usdDnsCompliances     OBJECT IDENTIFIER ::= { usdDnsConformance 1 }
usdDnsGroups          OBJECT IDENTIFIER ::= { usdDnsConformance 2 }

-- compliance statements

usdDnsCompliance MODULE-COMPLIANCE
    STATUS  current
    DESCRIPTION
        "The compliance statement for entities which implement the Unisphere DNS
        MIB."
    MODULE  -- this module
        MANDATORY-GROUPS {
            usdDnsEnableGroup,
            usdDnsServerListGroup,
            usdDnsLocalDomainNameListGroup }
    ::= { usdDnsCompliances 1 }                                        -- RX 3.0

-- units of conformance

usdDnsEnableGroup OBJECT-GROUP
    OBJECTS {
        usdDnsEnable
    }
    STATUS  current
    DESCRIPTION
        "A collection of objects for enabling/disabling DNS capabilities in a
        Unisphere product."
    ::= { usdDnsGroups 1 }

usdDnsServerListGroup OBJECT-GROUP
    OBJECTS {
        usdDnsServerListNextIndex,

        usdDnsServerListAddress,
        usdDnsServerListRowStatus
    }
    STATUS  current
    DESCRIPTION
        "A collection of objects for managing DNS server list capabilities in a
        Unisphere product."
    ::= { usdDnsGroups 2 }

usdDnsLocalDomainNameListGroup OBJECT-GROUP
    OBJECTS {
        usdDnsLocalDomainNameListNextIndex,

        usdDnsLocalDomainNameListName,
        usdDnsLocalDomainNameListRowStatus
    }
    STATUS  current
    DESCRIPTION
        "A collection of objects for managing DNS local domain name list
        capabilities in a Unisphere product."
    ::= { usdDnsGroups 3 }

END
