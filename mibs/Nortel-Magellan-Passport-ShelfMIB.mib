Nortel-Magellan-Passport-ShelfMIB
DEFINITIONS ::= BEGIN



IMPORTS

      OBJECT-TYPE
   FROM RFC-1212

      components,
      passportMIBs
   FROM Nortel-Magellan-Passport-UsefulDefinitionsMIB

      RowPointer,
      DisplayString,
      StorageType,
      RowStatus,
      Gauge32,
      Integer32,
      Unsigned32
   FROM Nortel-Magellan-Passport-StandardTextualConventionsMIB

      AsciiString,
      Hex,
      NonReplicated,
      Link,
      ExtendedAsciiString
   FROM Nortel-Magellan-Passport-TextualConventionsMIB;




-- LAST-UPDATED   "9906090000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     Shelf Enterprise MIB."

shelfMIB OBJECT IDENTIFIER ::= { passportMIBs 12 }










-- Shelf
-- There is one Shelf component per module. It is the parent 
-- component of the hardware components (which include Card and 
-- Bus components).

shelf OBJECT IDENTIFIER ::= { components 13 }



shelfRowStatusTable OBJECT-TYPE
   SYNTAX     SEQUENCE OF ShelfRowStatusEntry
   ACCESS     not-accessible
   STATUS     mandatory
   DESCRIPTION
     "This entry controls the addition and deletion of 
      shelf components."
::= { shelf 1 }

shelfRowStatusEntry OBJECT-TYPE
   SYNTAX     ShelfRowStatusEntry
   ACCESS     not-accessible
   STATUS     mandatory
   DESCRIPTION
     "A single entry in the table represents a single 
      shelf component."
   INDEX {
      shelfIndex }
::= { shelfRowStatusTable 1 }

ShelfRowStatusEntry ::= SEQUENCE {
   shelfRowStatus
      RowStatus,
   shelfComponentName
      DisplayString,
   shelfStorageType
      StorageType,
   shelfIndex
      NonReplicated }

shelfRowStatus OBJECT-TYPE
   SYNTAX     RowStatus 
   ACCESS     read-only
   STATUS     mandatory
   DESCRIPTION
     "This variable is used as the basis for SNMP naming of
      shelf components.
      These components cannot be added nor deleted."
::= { shelfRowStatusEntry 1 }

shelfComponentName OBJECT-TYPE
   SYNTAX     DisplayString 
   ACCESS     read-only
   STATUS     mandatory
   DESCRIPTION
     "This variable provides the component's string name for
      use with the ASCII Console Interface"
::= { shelfRowStatusEntry 2 }

shelfStorageType OBJECT-TYPE
   SYNTAX     StorageType 
   ACCESS     read-only
   STATUS     mandatory
   DESCRIPTION
     "This variable represents the storage type value for the
      shelf tables."
::= { shelfRowStatusEntry 4 }

shelfIndex OBJECT-TYPE
   SYNTAX     NonReplicated 
   ACCESS     not-accessible
   STATUS     mandatory
   DESCRIPTION
     "This variable represents the index for the shelf tables."
::= { shelfRowStatusEntry 10 }

shelfProvTable OBJECT-TYPE
   SYNTAX     SEQUENCE OF ShelfProvEntry
   ACCESS     not-accessible
   STATUS     mandatory
   DESCRIPTION
     "This group contains the provisionable attributes for the Shelf 
      component."
::= { shelf 10 }

shelfProvEntry OBJECT-TYPE
   SYNTAX     ShelfProvEntry
   ACCESS     not-accessible
   STATUS     mandatory
   DESCRIPTION
     "An entry in the shelfProvTable."
   INDEX {
      shelfIndex }
::= { shelfProvTable 1 }

ShelfProvEntry ::= SEQUENCE {
   shelfCommentText
      AsciiString }

shelfCommentText OBJECT-TYPE
   SYNTAX     AsciiString (SIZE (0..80))
   ACCESS     read-write
   STATUS     mandatory
   DESCRIPTION
     "This is an arbitrary string that can be used to specify the location of 
      the module. It is not used by the system."
   DEFVAL     { ''H }  -- ""
::= { shelfProvEntry 1 }

shelfOperTable OBJECT-TYPE
   SYNTAX     SEQUENCE OF ShelfOperEntry
   ACCESS     not-accessible
   STATUS     mandatory
   DESCRIPTION
     "This group contains the operational attributes for the Shelf 
      component."
::= { shelf 11 }

shelfOperEntry OBJECT-TYPE
   SYNTAX     ShelfOperEntry
   ACCESS     not-accessible
   STATUS     mandatory
   DESCRIPTION
     "An entry in the shelfOperTable."
   INDEX {
      shelfIndex }
::= { shelfOperTable 1 }

ShelfOperEntry ::= SEQUENCE {
   shelfBusOperatingMode
      INTEGER,
   shelfHardwareFailures
      OCTET STRING,
   shelfNumberOfSlots
      Unsigned32 }

shelfBusOperatingMode OBJECT-TYPE
   SYNTAX     INTEGER  {
                 noBus(0),
                 singleBusX(1),
                 singleBusY(2),
                 dualBus(3) }
   ACCESS     read-only
   STATUS     mandatory
   DESCRIPTION
     "This attribute indicates the current backplane bus operating mode:
      noBus            No bus is in service now.
      singleBusX     The shelf is running on bus X only.
      singleBusY     The shelf is running on bus Y only.
      dualBus         The shelf is running on bus X and bus Y."
::= { shelfOperEntry 1 }

shelfHardwareFailures OBJECT-TYPE
   SYNTAX     OCTET STRING (SIZE (1))
   ACCESS     read-only
   STATUS     mandatory
   DESCRIPTION
     "The hardware's fault detection system can report four kinds of 
      component failures: card, power converter, cooling unit or 
      terminator card failures. This attribute is a set that specifies which 
      type of components have failed.

      Description of bits:
      card(0)
      powerConverter(1)
      coolingUnit(2)
      terminatorCard(3)"
::= { shelfOperEntry 2 }

shelfNumberOfSlots OBJECT-TYPE
   SYNTAX     Unsigned32 (1..16)
   ACCESS     read-only
   STATUS     mandatory
   DESCRIPTION
     "This attribute specifies the number of slots for this shelf."
::= { shelfOperEntry 3 }


-- Shelf Card/n
-- The Card component is a subcomponent of the Shelf component. 
-- There are a maximum of 16 Card components defined, one 
-- corresponding to each phsyical card slot. This is necessary in order 
-- to be able to reflect which processor card is present in each slot at 
-- any time.  
-- For a Passport Model-50 it is possible to have Card components not 
-- defined for instances 5 through 15.  This is can be accomplished via 
-- the Start-Up initial provisioning system.   It is, however,  possible to 
-- add a Card component since it may be desireable to move a CP 
-- from a Passport Model-50 to a Passport Model-160.  This move of 
-- the CP would result in  adding the provisioning information 
-- associated with the other processor cards instead of starting from 
-- scratch.  
-- It is however not possible to delete a Card component per se, but its 
-- type can be changed to "None".

shelfCard OBJECT IDENTIFIER ::= { shelf 2 }



shelfCardRowStatusTable OBJECT-TYPE
   SYNTAX     SEQUENCE OF ShelfCardRowStatusEntry
   ACCESS     not-accessible
   STATUS     mandatory
   DESCRIPTION
     "This entry controls the addition and deletion of 
      shelfCard components."
::= { shelfCard 1 }

shelfCardRowStatusEntry OBJECT-TYPE
   SYNTAX     ShelfCardRowStatusEntry
   ACCESS     not-accessible
   STATUS     mandatory
   DESCRIPTION
     "A single entry in the table represents a single 
      shelfCard component."
   INDEX {
      shelfIndex,
      shelfCardIndex }
::= { shelfCardRowStatusTable 1 }

ShelfCardRowStatusEntry ::= SEQUENCE {
   shelfCardRowStatus
      RowStatus,
   shelfCardComponentName
      DisplayString,
   shelfCardStorageType
      StorageType,
   shelfCardIndex
      Integer32 }

shelfCardRowStatus OBJECT-TYPE
   SYNTAX     RowStatus 
   ACCESS     read-write
   STATUS     mandatory
   DESCRIPTION
     "This variable is used as the basis for SNMP naming of
      shelfCard components.
      These components can be added."
::= { shelfCardRowStatusEntry 1 }

shelfCardComponentName OBJECT-TYPE
   SYNTAX     DisplayString 
   ACCESS     read-only
   STATUS     mandatory
   DESCRIPTION
     "This variable provides the component's string name for
      use with the ASCII Console Interface"
::= { shelfCardRowStatusEntry 2 }

shelfCardStorageType OBJECT-TYPE
   SYNTAX     StorageType 
   ACCESS     read-only
   STATUS     mandatory
   DESCRIPTION
     "This variable represents the storage type value for the
      shelfCard tables."
::= { shelfCardRowStatusEntry 4 }

shelfCardIndex OBJECT-TYPE
   SYNTAX     Integer32 (0..15)
   ACCESS     not-accessible
   STATUS     mandatory
   DESCRIPTION
     "This variable represents the index for the shelfCard tables."
::= { shelfCardRowStatusEntry 10 }

shelfCardProvTable OBJECT-TYPE
   SYNTAX     SEQUENCE OF ShelfCardProvEntry
   ACCESS     not-accessible
   STATUS     mandatory
   DESCRIPTION
     "This group contains the provisionable attributes for the Card 
      component."
::= { shelfCard 10 }

shelfCardProvEntry OBJECT-TYPE
   SYNTAX     ShelfCardProvEntry
   ACCESS     not-accessible
   STATUS     mandatory
   DESCRIPTION
     "An entry in the shelfCardProvTable."
   INDEX {
      shelfIndex,
      shelfCardIndex }
::= { shelfCardProvTable 1 }

ShelfCardProvEntry ::= SEQUENCE {
   shelfCardCardType
      INTEGER,
   shelfCardSparingConnection
      INTEGER,
   shelfCardCommentText
      AsciiString }

shelfCardCardType OBJECT-TYPE
   SYNTAX     INTEGER  {
                 cP(0),
                 v11(1),
                 v35(2),
                 dS1(3),
                 dS1V(4),
                 dS3(5),
                 e1(6),
                 e1V(7),
                 e3(8),
                 none(9),
                 n1pFddiMultiMode(10),
                 n4pTokenRing(11),
                 n6pEth10BaseT(12),
                 dS1C(13),
                 e1C(14),
                 n3pE3Atm(15),
                 n3pDS3Atm(16),
                 n3pOC3MmAtm(17),
                 n3pOC3SmAtm(19),
                 n3pE1Atm(20),
                 n3pDS1Atm(21),
                 j2MV(22),
                 n4pEthAui(23),
                 n1pFddiSingleMode(24),
                 n1pDS1V(25),
                 n1pE1V(26),
                 n2pJ6MAtm(27),
                 hSSI(33),
                 n8pDS1(34),
                 cFP1(35),
                 dEV1(36),
                 cFP2(37),
                 dEV2(38),
                 n4pDS1Aal1(39),
                 n4pE1Aal1(40),
                 n1pDS3C(41),
                 ilsForwarder(42),
                 n8pDS1Atm(43),
                 n8pE1Atm(44),
                 n1pE1Mvp(45),
                 n1pDS1Mvp(46),
                 n1pTTC2mMvp(47),
                 n1pDS3cAal(51),
                 n2pDS3cAal(52),
                 n12mVspAal(53),
                 n2pEth100BaseT(54),
                 n2pOC3MmAtm2(55),
                 n2pOC3SmAtm2(56),
                 n3pDS3Atm2(57),
                 n3pE3Atm2(58),
                 cPeD(59),
                 cPeE(60),
                 n4pOC3SmIrAtm(61),
                 n4pOC3MmAtm(62),
                 n12pDS3Atm(63),
                 n12pE3Atm(64),
                 n1pOC12SmLrAtm(65),
                 n1pE1Mvpe(66),
                 n1pDS1Mvpe(67),
                 n1pTTC2mMvpe(68),
                 msa32(69),
                 msa32mt(70),
                 msa32mtp(71),
                 msa32st(72),
                 msa32stp(73),
                 n32pE1Aal(74),
                 n12mPcusp(82) }
   ACCESS     read-write
   STATUS     mandatory
   DESCRIPTION
     "This is the type of card expected in this slot. Specifying a card type 
      here has the effect of configuring a card to run in this slot. A value 
      of none means that no card is configured to run in this slot."
   DEFVAL     { none }
::= { shelfCardProvEntry 1 }

shelfCardSparingConnection OBJECT-TYPE
   SYNTAX     INTEGER  {
                 notApplicable(0),
                 mainA(1),
                 mainB(2),
                 mainC(3),
                 mainD(4),
                 spare(16) }
   ACCESS     read-write
   STATUS     mandatory
   DESCRIPTION
     "This attribute contains the identification of the 1 for N sparing panel 
      group of connectors to which the card is connected. This 
      identification should coincide with the label located on the sparing 
      panel."
   DEFVAL     { notApplicable }
::= { shelfCardProvEntry 2 }

shelfCardCommentText OBJECT-TYPE
   SYNTAX     AsciiString (SIZE (0..80))
   ACCESS     read-write
   STATUS     mandatory
   DESCRIPTION
     "This is an arbitrary string that can be used to specify the location of 
      the sparing panel."
   DEFVAL     { ''H }  -- ""
::= { shelfCardProvEntry 4 }

shelfCardStateTable OBJECT-TYPE
   SYNTAX     SEQUENCE OF ShelfCardStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { shelfCard 11 }

shelfCardStateEntry OBJECT-TYPE
   SYNTAX     ShelfCardStateEntry
   ACCESS     not-accessible
   STATUS     mandatory
   DESCRIPTION
     "An entry in the shelfCardStateTable."
   INDEX {
      shelfIndex,
      shelfCardIndex }
::= { shelfCardStateTable 1 }

ShelfCardStateEntry ::= SEQUENCE {
   shelfCardAdminState
      INTEGER,
   shelfCardOperationalState
      INTEGER,
   shelfCardUsageState
      INTEGER,
   shelfCardAvailabilityStatus
      OCTET STRING,
   shelfCardProceduralStatus
      OCTET STRING,
   shelfCardControlStatus
      OCTET STRING,
   shelfCardAlarmStatus
      OCTET STRING,
   shelfCardStandbyStatus
      INTEGER,
   shelfCardUnknownStatus
      INTEGER }

shelfCardAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { shelfCardStateEntry 1 }

shelfCardOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { shelfCardStateEntry 2 }

shelfCardUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { shelfCardStateEntry 3 }

shelfCardAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { shelfCardStateEntry 4 }

shelfCardProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { shelfCardStateEntry 5 }

shelfCardControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { shelfCardStateEntry 6 }

shelfCardAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { shelfCardStateEntry 7 }

shelfCardStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { shelfCardStateEntry 8 }

shelfCardUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { shelfCardStateEntry 9 }

shelfCardOperTable OBJECT-TYPE
   SYNTAX     SEQUENCE OF ShelfCardOperEntry
   ACCESS     not-accessible
   STATUS     mandatory
   DESCRIPTION
     "This group contains the operational attributes that reflect the current 
      status of the card."
::= { shelfCard 12 }

shelfCardOperEntry OBJECT-TYPE
   SYNTAX     ShelfCardOperEntry
   ACCESS     not-accessible
   STATUS     mandatory
   DESCRIPTION
     "An entry in the shelfCardOperTable."
   INDEX {
      shelfIndex,
      shelfCardIndex }
::= { shelfCardOperTable 1 }

ShelfCardOperEntry ::= SEQUENCE {
   shelfCardCurrentLP
      RowPointer,
   shelfCardFailureCause
      INTEGER,
   shelfCardSelfTestFault
      INTEGER,
   shelfCardSparingConnectionStatus
      INTEGER }

shelfCardCurrentLP OBJECT-TYPE
   SYNTAX     RowPointer 
   ACCESS     read-only
   STATUS     obsolete
   DESCRIPTION
     "This is the component name of the LP currently running on this 
      card."
::= { shelfCardOperEntry 1 }

shelfCardFailureCause OBJECT-TYPE
   SYNTAX     INTEGER  {
                 none(0),
                 wrongCardType(1),
                 notConfigured(2),
                 cannotLoadSoftware(3),
                 failedSelfTests(4),
                 notResponding(5),
                 busConnectivityProblem(6) }
   ACCESS     read-only
   STATUS     mandatory
   DESCRIPTION
     "This attribute specifies why the card has failed. This attribute is 
      meaningful when the OSI AvailabilityStatus attribute is set to 
      failed."
::= { shelfCardOperEntry 2 }

shelfCardSelfTestFault OBJECT-TYPE
   SYNTAX     INTEGER  {
                 none(0) }
   ACCESS     read-only
   STATUS     mandatory
   DESCRIPTION
     "This attribute indicates the result of the processor card's self-tests 
      that were performed when it initially came up."
::= { shelfCardOperEntry 3 }

shelfCardSparingConnectionStatus OBJECT-TYPE
   SYNTAX     INTEGER  {
                 notApplicable(0),
                 n1for1Ok(1),
                 n1forNOk(2),
                 unconfirmed(3),
                 notConnected(4),
                 incorrectlyConnected(5),
                 inconsistentlyConnected(6) }
   ACCESS     read-only
   STATUS     mandatory
   DESCRIPTION
     "This attribute indicates if the control signal received from a 1forN 
      sparing panel or a 1for1 sparing panel is properly terminated.
      notApplicable - The card is not provisioned as part of a 
      sparing configuration, and is not connected to any sparing panel.
      1for1Ok -The card is provisioned correctly for 1for1 sparing and is 
      connected to the active relay of a 1for1 sparing panel.
      1forNOk -The card is provisioned correctly for either 1for1 or 
      1forN sparing and is connected to either the standby or active relay 
      of a 1forN sparing panel.
      unconfirmed -The card is provisioned as part of a sparing 
      configuration, but  its connection status cannot be determined.
      To determine if the card is connected to a sparing panel, perform a 
      switchover of the LP to see if the card will grab a relay when it is 
      active. If the card has grabbed the relay, the sparing connection 
      status should change from, unconfirmed, to 1for1Ok and the LED 
      on the sparing panel corresponfing to that relay should be 
      illuminated.
      Please note: Performing the switchover will disrupt traffic on the 
      other card and this test should be conducted when no traffic is 
      running on the active card.
      notConnected - The card is provisioned as part of a sparing 
      configuration, but is not connected to a sparing panel.
      Remedial Action: Check the cable connectivity between the card 
      and the sparing panel.
      incorrectlyConnected - The card is provisioned as part of a sparing 
      configuration, but is connected to the wrong port on a 1forN panel, 
      or is connected to a 1for1 sparing panel while configured for 1forN.
      Remedial Action: Connect the cable to the port that was specified 
      by the sparingConnection attribute.
      inconsistentlyConnected - The card is provisioned as part of a 
      1forN sparing configuration, but is connected to a sparing panel 
      which is not the same as the other cards sharing the same spare 
      card.
      Remedial Action: Ensure all cards that share the same spare card 
      are connected to the same sparing panel.
      This value is also used to indicate that two sparing panels with the 
      same sparing panel IDs are being used by cards on the same shelf.
      Remedial Action: Replace one of the sparing panels with another 
      panel that has a different sparing panel ID. Sparing panel IDs are 
      assigned at the time of manufacture and cannot be changed by the 
      user."
::= { shelfCardOperEntry 4 }

shelfCardPropTable OBJECT-TYPE
   SYNTAX     SEQUENCE OF ShelfCardPropEntry
   ACCESS     not-accessible
   STATUS     mandatory
   DESCRIPTION
     "This group contains the operational attributes that specify the fixed 
      characteristics of the card."
::= { shelfCard 13 }

shelfCardPropEntry OBJECT-TYPE
   SYNTAX     ShelfCardPropEntry
   ACCESS     not-accessible
   STATUS     mandatory
   DESCRIPTION
     "An entry in the shelfCardPropTable."
   INDEX {
      shelfIndex,
      shelfCardIndex }
::= { shelfCardPropTable 1 }

ShelfCardPropEntry ::= SEQUENCE {
   shelfCardInsertedCardType
      INTEGER,
   shelfCardPmRevisionCode
      AsciiString,
   shelfCardImRevisionCode
      AsciiString,
   shelfCardSerialNumber
      AsciiString,
   shelfCardActiveFirmwareVersion
      AsciiString,
   shelfCardInactiveFirmwareVersion
      AsciiString,
   shelfCardProductCode
      AsciiString }

shelfCardInsertedCardType OBJECT-TYPE
   SYNTAX     INTEGER  {
                 cP(0),
                 v11(1),
                 v35(2),
                 dS1(3),
                 dS1V(4),
                 dS3(5),
                 e1(6),
                 e1V(7),
                 e3(8),
                 none(9),
                 n1pFddiMultiMode(10),
                 n4pTokenRing(11),
                 n6pEth10BaseT(12),
                 dS1C(13),
                 e1C(14),
                 n3pE3Atm(15),
                 n3pDS3Atm(16),
                 n3pOC3MmAtm(17),
                 n1pOC3MmAtm(18),
                 n3pOC3SmAtm(19),
                 n3pE1Atm(20),
                 n3pDS1Atm(21),
                 j2MV(22),
                 n4pEthAui(23),
                 n1pFddiSingleMode(24),
                 n1pDS1V(25),
                 n1pE1V(26),
                 n2pJ6MAtm(27),
                 hSSI(33),
                 n8pDS1(34),
                 cFP1(35),
                 dEV1(36),
                 cFP2(37),
                 dEV2(38),
                 n4pDS1Aal1(39),
                 n4pE1Aal1(40),
                 n1pDS3C(41),
                 ilsForwarder(42),
                 n8pDS1Atm(43),
                 n8pE1Atm(44),
                 n1pE1Mvp(45),
                 n1pDS1Mvp(46),
                 n1pTTC2mMvp(47),
                 n1pDS3cAal(51),
                 n2pDS3cAal(52),
                 n12mVspAal(53),
                 n2pEth100BaseT(54),
                 n2pOC3MmAtm2(55),
                 n2pOC3SmAtm2(56),
                 n3pDS3Atm2(57),
                 n3pE3Atm2(58),
                 cPeD(59),
                 cPeE(60),
                 n4pOC3SmIrAtm(61),
                 n4pOC3MmAtm(62),
                 n12pDS3Atm(63),
                 n12pE3Atm(64),
                 n1pOC12SmLrAtm(65),
                 n1pE1Mvpe(66),
                 n1pDS1Mvpe(67),
                 n1pTTC2mMvpe(68),
                 msa32(69),
                 msa32mt(70),
                 msa32mtp(71),
                 msa32st(72),
                 msa32stp(73),
                 n32pE1Aal(74),
                 n12mPcusp(82) }
   ACCESS     read-only
   STATUS     mandatory
   DESCRIPTION
     "This attribute indicates the type of card that is currently inserted in 
      this slot."
::= { shelfCardPropEntry 1 }

shelfCardPmRevisionCode OBJECT-TYPE
   SYNTAX     AsciiString (SIZE (0..16))
   ACCESS     read-only
   STATUS     mandatory
   DESCRIPTION
     "This attribute indicates the hardware revision level of the Processor 
      Module (PM)."
::= { shelfCardPropEntry 2 }

shelfCardImRevisionCode OBJECT-TYPE
   SYNTAX     AsciiString (SIZE (0..16))
   ACCESS     read-only
   STATUS     mandatory
   DESCRIPTION
     "This attribute indicates the hardware revision level of the Interface 
      Module (IM)."
::= { shelfCardPropEntry 3 }

shelfCardSerialNumber OBJECT-TYPE
   SYNTAX     AsciiString (SIZE (0..16))
   ACCESS     read-only
   STATUS     mandatory
   DESCRIPTION
     "This attribute indicates the processor card's serial number."
::= { shelfCardPropEntry 4 }

shelfCardActiveFirmwareVersion OBJECT-TYPE
   SYNTAX     AsciiString (SIZE (0..16))
   ACCESS     read-only
   STATUS     mandatory
   DESCRIPTION
     "This attribute indicates the firmware version of the currently active 
      flash memory bank."
::= { shelfCardPropEntry 5 }

shelfCardInactiveFirmwareVersion OBJECT-TYPE
   SYNTAX     AsciiString (SIZE (0..16))
   ACCESS     read-only
   STATUS     mandatory
   DESCRIPTION
     "This attribute indicates the firmware version of the currently 
      inactive flash memory bank."
::= { shelfCardPropEntry 6 }

shelfCardProductCode OBJECT-TYPE
   SYNTAX     AsciiString (SIZE (0..12))
   ACCESS     read-only
   STATUS     mandatory
   DESCRIPTION
     "This attribute indicates the product ordering code and release of the 
      card."
::= { shelfCardPropEntry 7 }

shelfCardUtilTable OBJECT-TYPE
   SYNTAX     SEQUENCE OF ShelfCardUtilEntry
   ACCESS     not-accessible
   STATUS     mandatory
   DESCRIPTION
     "This group contains the operational attributes that specify the 
      processor's utilization levels. When this group exists for an LP 
      component, the attributes are representative of the active card."
::= { shelfCard 14 }

shelfCardUtilEntry OBJECT-TYPE
   SYNTAX     ShelfCardUtilEntry
   ACCESS     not-accessible
   STATUS     mandatory
   DESCRIPTION
     "An entry in the shelfCardUtilTable."
   INDEX {
      shelfIndex,
      shelfCardIndex }
::= { shelfCardUtilTable 1 }

ShelfCardUtilEntry ::= SEQUENCE {
   shelfCardTimeInterval
      Unsigned32,
   shelfCardCpuUtil
      Gauge32,
   shelfCardCpuUtilAvg
      Gauge32,
   shelfCardCpuUtilAvgMin
      Gauge32,
   shelfCardCpuUtilAvgMax
      Gauge32,
   shelfCardMsgBlockUsage
      Gauge32,
   shelfCardMsgBlockUsageAvg
      Gauge32,
   shelfCardMsgBlockUsageAvgMin
      Gauge32,
   shelfCardMsgBlockUsageAvgMax
      Gauge32,
   shelfCardLocalMsgBlockUsage
      Gauge32,
   shelfCardLocalMsgBlockUsageAvg
      Gauge32,
   shelfCardLocalMsgBlockUsageMin
      Gauge32,
   shelfCardLocalMsgBlockUsageMax
      Gauge32 }

shelfCardTimeInterval OBJECT-TYPE
   SYNTAX     Unsigned32 (0..15)
   ACCESS     read-only
   STATUS     mandatory
   DESCRIPTION
     "This attribute indicates the time period (in minutes) for which the 
      average, minimum and maximum utilization values are calculated.  
      This attribute is reset to 0 every 15 minutes."
::= { shelfCardUtilEntry 1 }

shelfCardCpuUtil OBJECT-TYPE
   SYNTAX     Gauge32 (0..100)
   ACCESS     read-only
   STATUS     mandatory
   DESCRIPTION
     "This attribute indicates an approximation of the current processor 
      utilization level (expressed as a percentage)."
::= { shelfCardUtilEntry 2 }

shelfCardCpuUtilAvg OBJECT-TYPE
   SYNTAX     Gauge32 (0..100)
   ACCESS     read-only
   STATUS     mandatory
   DESCRIPTION
     "This attribute indicates an average processor utilization level over 
      the specified time period, timeInterval. This average is calculated 
      based on one minute CPU utilization averages."
::= { shelfCardUtilEntry 3 }

shelfCardCpuUtilAvgMin OBJECT-TYPE
   SYNTAX     Gauge32 (0..100)
   ACCESS     read-only
   STATUS     mandatory
   DESCRIPTION
     "This attribute indicates the minimum processor utilization level over 
      a specified time period, timeInterval. This is based on one minute 
      CPU utilization averages."
::= { shelfCardUtilEntry 4 }

shelfCardCpuUtilAvgMax OBJECT-TYPE
   SYNTAX     Gauge32 (0..100)
   ACCESS     read-only
   STATUS     mandatory
   DESCRIPTION
     "This attribute indicates the maximum processor utilization level 
      over a specified time period, timeInterval. This is based on one 
      minute CPU utilization averages."
::= { shelfCardUtilEntry 5 }

shelfCardMsgBlockUsage OBJECT-TYPE
   SYNTAX     Gauge32 (0..2147483647)
   ACCESS     read-only
   STATUS     mandatory
   DESCRIPTION
     "This attribute indicates the processor's current shared message 
      block memory utilization (in kilobytes).
      If there is no shared memory on the card, this attribute indicates 0."
::= { shelfCardUtilEntry 6 }

shelfCardMsgBlockUsageAvg OBJECT-TYPE
   SYNTAX     Gauge32 (0..2147483647)
   ACCESS     read-only
   STATUS     mandatory
   DESCRIPTION
     "This attribute indicates the processor's average memory utilization 
      (in kilobytes) of shared message blocks, calculated over a specified 
      time period, timeInterval.  This utilization value is calculated using 
      15 second samples.  At the start of each timeInterval, this average 
      memory utilization is reset to the current usage, 
      sharedMsgBlockUsage.
      If there is no shared memory on the card, this attribute indicates 0."
::= { shelfCardUtilEntry 7 }

shelfCardMsgBlockUsageAvgMin OBJECT-TYPE
   SYNTAX     Gauge32 (0..2147483647)
   ACCESS     read-only
   STATUS     mandatory
   DESCRIPTION
     "This attribute indicates the processor's minimum memory 
      utilization (in kilobytes) of shared message blocks, calculated over a 
      specified time period, timeInterval.  This utilization value is 
      calculated using 15 second samples.  At the start of each 
      timeInterval, this minimum memory utilization is reset to the 
      current usage, sharedMsgBlockUsage.
      If there is no shared memory on the card, this attribute indicates 0."
::= { shelfCardUtilEntry 8 }

shelfCardMsgBlockUsageAvgMax OBJECT-TYPE
   SYNTAX     Gauge32 (0..2147483647)
   ACCESS     read-only
   STATUS     mandatory
   DESCRIPTION
     "This attribute indicates the processor's maximum memory 
      utilization (in kilobytes) of shared message blocks, calculated over a 
      specified time period, timeInterval.  This utilization value is 
      calculated using 15 second samples.  At the start of each 
      timeInterval, this maximum memory utilization is reset to the 
      current usage, sharedMsgBlockUsage.
      If there is no shared memory on the card, this attribute indicates 0."
::= { shelfCardUtilEntry 9 }

shelfCardLocalMsgBlockUsage OBJECT-TYPE
   SYNTAX     Gauge32 (0..2147483647)
   ACCESS     read-only
   STATUS     mandatory
   DESCRIPTION
     "This attribute indicates the processor's current memory utilization 
      (in kilobytes) of message blocks which are used for local messaging 
      on the card."
::= { shelfCardUtilEntry 10 }

shelfCardLocalMsgBlockUsageAvg OBJECT-TYPE
   SYNTAX     Gauge32 (0..2147483647)
   ACCESS     read-only
   STATUS     mandatory
   DESCRIPTION
     "This attribute indicates the processor's average memory utilization 
      (in kilobytes) of message blocks used for local messaging on the 
      card, calculated over a specified time period, timeInterval.  This 
      utilization value is calculated using 15 second samples.  At the start 
      of each timeInterval, this average memory utilization is reset to the 
      current usage, localMsgBlockUsage."
::= { shelfCardUtilEntry 11 }

shelfCardLocalMsgBlockUsageMin OBJECT-TYPE
   SYNTAX     Gauge32 (0..2147483647)
   ACCESS     read-only
   STATUS     mandatory
   DESCRIPTION
     "This attribute indicates the processor's minimum memory 
      utilization (in kilobytes) of message blocks used for local 
      messaging on the card, calculated over a specified time period, 
      timeInterval.  This utilization value is updated at 15 second 
      intervals.  At the start of each timeInterval, this minimum memory 
      utilization is reset to the current usage, localMsgBlockUsage."
::= { shelfCardUtilEntry 12 }

shelfCardLocalMsgBlockUsageMax OBJECT-TYPE
   SYNTAX     Gauge32 (0..2147483647)
   ACCESS     read-only
   STATUS     mandatory
   DESCRIPTION
     "This attribute indicates the processor's maximum memory 
      utilization (in kilobytes) of message blocks used for local 
      messaging on the card, calculated over a specified time period, 
      timeInterval.  This utilization value is updated at 15 second 
      intervals.  At the start of each timeInterval, this maximum memory 
      utilization is reset to the current usage, localMsgBlockUsage."
::= { shelfCardUtilEntry 13 }

shelfCardCapTable OBJECT-TYPE
   SYNTAX     SEQUENCE OF ShelfCardCapEntry
   ACCESS     not-accessible
   STATUS     mandatory
   DESCRIPTION
     "This group contains the operational attributes that specify the 
      processor's capacity levels. When this group exists for an LP 
      component, the attributes are representative of the active Card."
::= { shelfCard 15 }

shelfCardCapEntry OBJECT-TYPE
   SYNTAX     ShelfCardCapEntry
   ACCESS     not-accessible
   STATUS     mandatory
   DESCRIPTION
     "An entry in the shelfCardCapTable."
   INDEX {
      shelfIndex,
      shelfCardIndex }
::= { shelfCardCapTable 1 }

ShelfCardCapEntry ::= SEQUENCE {
   shelfCardMsgBlockCapacity
      Unsigned32,
   shelfCardLocalMsgBlockCapacity
      Unsigned32 }

shelfCardMsgBlockCapacity OBJECT-TYPE
   SYNTAX     Unsigned32 (0..2147483647)
   ACCESS     read-only
   STATUS     mandatory
   DESCRIPTION
     "This attribute indicates the processor card's shared message block 
      memory capacity (in kilobytes)."
::= { shelfCardCapEntry 1 }

shelfCardLocalMsgBlockCapacity OBJECT-TYPE
   SYNTAX     Unsigned32 (0..2147483647)
   ACCESS     read-only
   STATUS     mandatory
   DESCRIPTION
     "This attribute indicates the processor card's local message block 
      memory capacity (in kilobytes).  These message blocks are used for 
      local messaging on the card."
::= { shelfCardCapEntry 2 }

shelfCardConfiguredLPsTable OBJECT-TYPE
   SYNTAX     SEQUENCE OF ShelfCardConfiguredLPsEntry
   ACCESS     not-accessible
   STATUS     mandatory
   DESCRIPTION
     "This is a read-only attribute that shows which LPs are currently 
      configured to run on this card (it is the opposite side of the LP 
      component's mainCard and spareCard link attributes). Note that 
      there is only one case where more than one LP can be configured to 
      run on a card. This is when the card is configured as an N+1 spare. 
      If this is not the case, the card is configured as a main card or as a 
      1for1 spare, only one LP can appear in this list."
::= { shelfCard 243 }

shelfCardConfiguredLPsEntry OBJECT-TYPE
   SYNTAX     ShelfCardConfiguredLPsEntry
   ACCESS     not-accessible
   STATUS     mandatory
   DESCRIPTION
     "An entry in the shelfCardConfiguredLPsTable."
   INDEX {
      shelfIndex,
      shelfCardIndex,
      shelfCardConfiguredLPsValue }
::= { shelfCardConfiguredLPsTable 1 }

ShelfCardConfiguredLPsEntry ::= SEQUENCE {
   shelfCardConfiguredLPsValue
      Link }

shelfCardConfiguredLPsValue OBJECT-TYPE
   SYNTAX     Link 
   ACCESS     read-only
   STATUS     mandatory
   DESCRIPTION
     "This variable represents both the value and the index for the
      shelfCardConfiguredLPsTable."
::= { shelfCardConfiguredLPsEntry 1 }

shelfCardMemoryCapacityTable OBJECT-TYPE
   SYNTAX     SEQUENCE OF ShelfCardMemoryCapacityEntry
   ACCESS     not-accessible
   STATUS     mandatory
   DESCRIPTION
     "This attribute indicates the processor card's memory capacity (in 
      kilobytes) for each type of memory."
::= { shelfCard 244 }

shelfCardMemoryCapacityEntry OBJECT-TYPE
   SYNTAX     ShelfCardMemoryCapacityEntry
   ACCESS     not-accessible
   STATUS     mandatory
   DESCRIPTION
     "An entry in the shelfCardMemoryCapacityTable."
   INDEX {
      shelfIndex,
      shelfCardIndex,
      shelfCardMemoryCapacityIndex }
::= { shelfCardMemoryCapacityTable 1 }

ShelfCardMemoryCapacityEntry ::= SEQUENCE {
   shelfCardMemoryCapacityIndex
      INTEGER,
   shelfCardMemoryCapacityValue
      Unsigned32 }

shelfCardMemoryCapacityIndex OBJECT-TYPE
   SYNTAX     INTEGER  {
                 fastRam(0),
                 normalRam(1),
                 sharedRam(2) }
   ACCESS     not-accessible
   STATUS     mandatory
   DESCRIPTION
     "This variable represents the shelfCardMemoryCapacityTable
      specific index for the shelfCardMemoryCapacityTable."
::= { shelfCardMemoryCapacityEntry 1 }

shelfCardMemoryCapacityValue OBJECT-TYPE
   SYNTAX     Unsigned32 (0..2147483647)
   ACCESS     read-only
   STATUS     mandatory
   DESCRIPTION
     "This variable represents an individual value for the
      shelfCardMemoryCapacityTable."
::= { shelfCardMemoryCapacityEntry 2 }

shelfCardMemoryUsageTable OBJECT-TYPE
   SYNTAX     SEQUENCE OF ShelfCardMemoryUsageEntry
   ACCESS     not-accessible
   STATUS     mandatory
   DESCRIPTION
     "This attribute indicates the processor's current memory utilization 
      (in kilobytes) for each type of memory."
::= { shelfCard 245 }

shelfCardMemoryUsageEntry OBJECT-TYPE
   SYNTAX     ShelfCardMemoryUsageEntry
   ACCESS     not-accessible
   STATUS     mandatory
   DESCRIPTION
     "An entry in the shelfCardMemoryUsageTable."
   INDEX {
      shelfIndex,
      shelfCardIndex,
      shelfCardMemoryUsageIndex }
::= { shelfCardMemoryUsageTable 1 }

ShelfCardMemoryUsageEntry ::= SEQUENCE {
   shelfCardMemoryUsageIndex
      INTEGER,
   shelfCardMemoryUsageValue
      Gauge32 }

shelfCardMemoryUsageIndex OBJECT-TYPE
   SYNTAX     INTEGER  {
                 fastRam(0),
                 normalRam(1),
                 sharedRam(2) }
   ACCESS     not-accessible
   STATUS     mandatory
   DESCRIPTION
     "This variable represents the shelfCardMemoryUsageTable
      specific index for the shelfCardMemoryUsageTable."
::= { shelfCardMemoryUsageEntry 1 }

shelfCardMemoryUsageValue OBJECT-TYPE
   SYNTAX     Gauge32 (0..2147483647)
   ACCESS     read-only
   STATUS     mandatory
   DESCRIPTION
     "This variable represents an individual value for the
      shelfCardMemoryUsageTable."
::= { shelfCardMemoryUsageEntry 2 }

shelfCardMemoryUsageAvgTable OBJECT-TYPE
   SYNTAX     SEQUENCE OF ShelfCardMemoryUsageAvgEntry
   ACCESS     not-accessible
   STATUS     mandatory
   DESCRIPTION
     "This attribute indicates the processor's average memory utilization 
      (in kilobytes) for each type of memory in the specified time period, 
      timeInterval. This value is calculated using 15 second samples."
::= { shelfCard 276 }

shelfCardMemoryUsageAvgEntry OBJECT-TYPE
   SYNTAX     ShelfCardMemoryUsageAvgEntry
   ACCESS     not-accessible
   STATUS     mandatory
   DESCRIPTION
     "An entry in the shelfCardMemoryUsageAvgTable."
   INDEX {
      shelfIndex,
      shelfCardIndex,
      shelfCardMemoryUsageAvgIndex }
::= { shelfCardMemoryUsageAvgTable 1 }

ShelfCardMemoryUsageAvgEntry ::= SEQUENCE {
   shelfCardMemoryUsageAvgIndex
      INTEGER,
   shelfCardMemoryUsageAvgValue
      Gauge32 }

shelfCardMemoryUsageAvgIndex OBJECT-TYPE
   SYNTAX     INTEGER  {
                 fastRam(0),
                 normalRam(1),
                 sharedRam(2) }
   ACCESS     not-accessible
   STATUS     mandatory
   DESCRIPTION
     "This variable represents the shelfCardMemoryUsageAvgTable
      specific index for the shelfCardMemoryUsageAvgTable."
::= { shelfCardMemoryUsageAvgEntry 1 }

shelfCardMemoryUsageAvgValue OBJECT-TYPE
   SYNTAX     Gauge32 (0..2147483647)
   ACCESS     read-only
   STATUS     mandatory
   DESCRIPTION
     "This variable represents an individual value for the
      shelfCardMemoryUsageAvgTable."
::= { shelfCardMemoryUsageAvgEntry 2 }

shelfCardMemoryUsageAvgMinTable OBJECT-TYPE
   SYNTAX     SEQUENCE OF ShelfCardMemoryUsageAvgMinEntry
   ACCESS     not-accessible
   STATUS     mandatory
   DESCRIPTION
     "This attribute indicates the processor's minimum memory 
      utilization (in kilobytes) for each type of memory in the specified 
      time period, timeInterval. This value is calculated using 15 second 
      samples."
::= { shelfCard 277 }

shelfCardMemoryUsageAvgMinEntry OBJECT-TYPE
   SYNTAX     ShelfCardMemoryUsageAvgMinEntry
   ACCESS     not-accessible
   STATUS     mandatory
   DESCRIPTION
     "An entry in the shelfCardMemoryUsageAvgMinTable."
   INDEX {
      shelfIndex,
      shelfCardIndex,
      shelfCardMemoryUsageAvgMinIndex }
::= { shelfCardMemoryUsageAvgMinTable 1 }

ShelfCardMemoryUsageAvgMinEntry ::= SEQUENCE {
   shelfCardMemoryUsageAvgMinIndex
      INTEGER,
   shelfCardMemoryUsageAvgMinValue
      Gauge32 }

shelfCardMemoryUsageAvgMinIndex OBJECT-TYPE
   SYNTAX     INTEGER  {
                 fastRam(0),
                 normalRam(1),
                 sharedRam(2) }
   ACCESS     not-accessible
   STATUS     mandatory
   DESCRIPTION
     "This variable represents the shelfCardMemoryUsageAvgMinTable
      specific index for the shelfCardMemoryUsageAvgMinTable."
::= { shelfCardMemoryUsageAvgMinEntry 1 }

shelfCardMemoryUsageAvgMinValue OBJECT-TYPE
   SYNTAX     Gauge32 (0..2147483647)
   ACCESS     read-only
   STATUS     mandatory
   DESCRIPTION
     "This variable represents an individual value for the
      shelfCardMemoryUsageAvgMinTable."
::= { shelfCardMemoryUsageAvgMinEntry 2 }

shelfCardMemoryUsageAvgMaxTable OBJECT-TYPE
   SYNTAX     SEQUENCE OF ShelfCardMemoryUsageAvgMaxEntry
   ACCESS     not-accessible
   STATUS     mandatory
   DESCRIPTION
     "This attribute indicates the processor's maximum memory 
      utilization (in kilobytes) for each type of memory in the specified 
      time period, timeInterval. This value is calculated using 15 second 
      samples."
::= { shelfCard 278 }

shelfCardMemoryUsageAvgMaxEntry OBJECT-TYPE
   SYNTAX     ShelfCardMemoryUsageAvgMaxEntry
   ACCESS     not-accessible
   STATUS     mandatory
   DESCRIPTION
     "An entry in the shelfCardMemoryUsageAvgMaxTable."
   INDEX {
      shelfIndex,
      shelfCardIndex,
      shelfCardMemoryUsageAvgMaxIndex }
::= { shelfCardMemoryUsageAvgMaxTable 1 }

ShelfCardMemoryUsageAvgMaxEntry ::= SEQUENCE {
   shelfCardMemoryUsageAvgMaxIndex
      INTEGER,
   shelfCardMemoryUsageAvgMaxValue
      Gauge32 }

shelfCardMemoryUsageAvgMaxIndex OBJECT-TYPE
   SYNTAX     INTEGER  {
                 fastRam(0),
                 normalRam(1),
                 sharedRam(2) }
   ACCESS     not-accessible
   STATUS     mandatory
   DESCRIPTION
     "This variable represents the shelfCardMemoryUsageAvgMaxTable
      specific index for the shelfCardMemoryUsageAvgMaxTable."
::= { shelfCardMemoryUsageAvgMaxEntry 1 }

shelfCardMemoryUsageAvgMaxValue OBJECT-TYPE
   SYNTAX     Gauge32 (0..2147483647)
   ACCESS     read-only
   STATUS     mandatory
   DESCRIPTION
     "This variable represents an individual value for the
      shelfCardMemoryUsageAvgMaxTable."
::= { shelfCardMemoryUsageAvgMaxEntry 2 }

shelfCardCurrentLpTable OBJECT-TYPE
   SYNTAX     SEQUENCE OF ShelfCardCurrentLpEntry
   ACCESS     not-accessible
   STATUS     mandatory
   DESCRIPTION
     "This attribute indicates which LPs are currently associated with this 
      card.  A card configured as a 1forN spare may be associated with 
      more than one LP."
::= { shelfCard 406 }

shelfCardCurrentLpEntry OBJECT-TYPE
   SYNTAX     ShelfCardCurrentLpEntry
   ACCESS     not-accessible
   STATUS     mandatory
   DESCRIPTION
     "An entry in the shelfCardCurrentLpTable."
   INDEX {
      shelfIndex,
      shelfCardIndex,
      shelfCardCurrentLpValue }
::= { shelfCardCurrentLpTable 1 }

ShelfCardCurrentLpEntry ::= SEQUENCE {
   shelfCardCurrentLpValue
      RowPointer }

shelfCardCurrentLpValue OBJECT-TYPE
   SYNTAX     RowPointer 
   ACCESS     read-only
   STATUS     mandatory
   DESCRIPTION
     "This variable represents both the value and the index for the
      shelfCardCurrentLpTable."
::= { shelfCardCurrentLpEntry 1 }


-- Shelf Card/n BusTap/b
-- A BusTap component represents a physical bus tap on a card. A bus 
-- tap is a card's interface to a bus; it provides a pathway for the card 
-- to send cells over the bus to the other cards in the module, and to 
-- receive cells sent to it over the bus by the other cards in the module.
-- A card's BusTap components are created automatically whenver the 
-- card begins acting as an active or standby LP, and remain in 
-- existence as long as the card remains operational; BusTap 
-- components cannot be added or deleted.

shelfCardBusTap OBJECT IDENTIFIER ::= { shelfCard 2 }



shelfCardBusTapRowStatusTable OBJECT-TYPE
   SYNTAX     SEQUENCE OF ShelfCardBusTapRowStatusEntry
   ACCESS     not-accessible
   STATUS     mandatory
   DESCRIPTION
     "This entry controls the addition and deletion of 
      shelfCardBusTap components."
::= { shelfCardBusTap 1 }

shelfCardBusTapRowStatusEntry OBJECT-TYPE
   SYNTAX     ShelfCardBusTapRowStatusEntry
   ACCESS     not-accessible
   STATUS     mandatory
   DESCRIPTION
     "A single entry in the table represents a single 
      shelfCardBusTap component."
   INDEX {
      shelfIndex,
      shelfCardIndex,
      shelfCardBusTapIndex }
::= { shelfCardBusTapRowStatusTable 1 }

ShelfCardBusTapRowStatusEntry ::= SEQUENCE {
   shelfCardBusTapRowStatus
      RowStatus,
   shelfCardBusTapComponentName
      DisplayString,
   shelfCardBusTapStorageType
      StorageType,
   shelfCardBusTapIndex
      INTEGER }

shelfCardBusTapRowStatus OBJECT-TYPE
   SYNTAX     RowStatus 
   ACCESS     read-only
   STATUS     mandatory
   DESCRIPTION
     "This variable is used as the basis for SNMP naming of
      shelfCardBusTap components.
      These components cannot be added nor deleted."
::= { shelfCardBusTapRowStatusEntry 1 }

shelfCardBusTapComponentName OBJECT-TYPE
   SYNTAX     DisplayString 
   ACCESS     read-only
   STATUS     mandatory
   DESCRIPTION
     "This variable provides the component's string name for
      use with the ASCII Console Interface"
::= { shelfCardBusTapRowStatusEntry 2 }

shelfCardBusTapStorageType OBJECT-TYPE
   SYNTAX     StorageType 
   ACCESS     read-only
   STATUS     mandatory
   DESCRIPTION
     "This variable represents the storage type value for the
      shelfCardBusTap tables."
::= { shelfCardBusTapRowStatusEntry 4 }

shelfCardBusTapIndex OBJECT-TYPE
   SYNTAX     INTEGER  {
                 x(0),
                 y(1) }
   ACCESS     not-accessible
   STATUS     mandatory
   DESCRIPTION
     "This variable represents the index for the shelfCardBusTap tables."
::= { shelfCardBusTapRowStatusEntry 10 }

shelfCardBusTapStateTable OBJECT-TYPE
   SYNTAX     SEQUENCE OF ShelfCardBusTapStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { shelfCardBusTap 10 }

shelfCardBusTapStateEntry OBJECT-TYPE
   SYNTAX     ShelfCardBusTapStateEntry
   ACCESS     not-accessible
   STATUS     mandatory
   DESCRIPTION
     "An entry in the shelfCardBusTapStateTable."
   INDEX {
      shelfIndex,
      shelfCardIndex,
      shelfCardBusTapIndex }
::= { shelfCardBusTapStateTable 1 }

ShelfCardBusTapStateEntry ::= SEQUENCE {
   shelfCardBusTapAdminState
      INTEGER,
   shelfCardBusTapOperationalState
      INTEGER,
   shelfCardBusTapUsageState
      INTEGER,
   shelfCardBusTapAvailabilityStatus
      OCTET STRING,
   shelfCardBusTapProceduralStatus
      OCTET STRING,
   shelfCardBusTapControlStatus
      OCTET STRING,
   shelfCardBusTapAlarmStatus
      OCTET STRING,
   shelfCardBusTapStandbyStatus
      INTEGER,
   shelfCardBusTapUnknownStatus
      INTEGER }

shelfCardBusTapAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { shelfCardBusTapStateEntry 1 }

shelfCardBusTapOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { shelfCardBusTapStateEntry 2 }

shelfCardBusTapUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { shelfCardBusTapStateEntry 3 }

shelfCardBusTapAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { shelfCardBusTapStateEntry 4 }

shelfCardBusTapProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { shelfCardBusTapStateEntry 5 }

shelfCardBusTapControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { shelfCardBusTapStateEntry 6 }

shelfCardBusTapAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { shelfCardBusTapStateEntry 7 }

shelfCardBusTapStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { shelfCardBusTapStateEntry 8 }

shelfCardBusTapUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { shelfCardBusTapStateEntry 9 }

shelfCardBusTapOperTable OBJECT-TYPE
   SYNTAX     SEQUENCE OF ShelfCardBusTapOperEntry
   ACCESS     not-accessible
   STATUS     mandatory
   DESCRIPTION
     "This attribute group contains operational attributes of a bus tap. This 
      information outlines what the bus tap is doing and why it is doing it, 
      and is primarily intended for use in diagnosing the cause of a bus-
      related problem reported by the module."
::= { shelfCardBusTap 11 }

shelfCardBusTapOperEntry OBJECT-TYPE
   SYNTAX     ShelfCardBusTapOperEntry
   ACCESS     not-accessible
   STATUS     mandatory
   DESCRIPTION
     "An entry in the shelfCardBusTapOperTable."
   INDEX {
      shelfIndex,
      shelfCardIndex,
      shelfCardBusTapIndex }
::= { shelfCardBusTapOperTable 1 }

ShelfCardBusTapOperEntry ::= SEQUENCE {
   shelfCardBusTapFailuresInEffect
      OCTET STRING,
   shelfCardBusTapDependenciesInEffect
      OCTET STRING,
   shelfCardBusTapCardsAvailable
      OCTET STRING,
   shelfCardBusTapCardsTxTo
      OCTET STRING }

shelfCardBusTapFailuresInEffect OBJECT-TYPE
   SYNTAX     OCTET STRING (SIZE (1))
   ACCESS     read-only
   STATUS     mandatory
   DESCRIPTION
     "This attribute records the hardware problems that prevent the bus 
      tap from using the associated bus. It may contain any combination 
      of the following values.
      selfTest: the bus tap has failed its self-test
      clockSignal: the bus tap is not receiving clock signals from the bus
      parityError: the bus tap has detected too many parity errors on the 
      bus

      Description of bits:
      selfTest(0)
      clockSignal(1)
      parityError(2)"
::= { shelfCardBusTapOperEntry 1 }

shelfCardBusTapDependenciesInEffect OBJECT-TYPE
   SYNTAX     OCTET STRING (SIZE (1))
   ACCESS     read-only
   STATUS     mandatory
   DESCRIPTION
     "This attribute records the non-hardware problems that prevent the 
      bus tap from using the associated bus. It may contain any 
      combination of the following values.
      busLocked: the bus is locked
      busDisabled: the bus is disabled

      Description of bits:
      busLocked(0)
      busDisabled(1)"
::= { shelfCardBusTapOperEntry 2 }

shelfCardBusTapCardsAvailable OBJECT-TYPE
   SYNTAX     OCTET STRING (SIZE (2))
   ACCESS     read-only
   STATUS     mandatory
   DESCRIPTION
     "This attribute records the slot numbers of the cards that the bus tap 
      considers available on the busthat is, the cards that have an 
      operational bus tap connected to the bus. The value of this attribute 
      is determined automatically by the bus tap by monitoring signals 
      generated by each bus tap on the bus; it cannot be changed by the 
      operator. Normally, every card in the module signals its availability 
      on both buses; if a card does not signal its availability on a bus this 
      indicates that the card is not present or that its bus tap has failed. By 
      examining this attribute for both of a card's BusTap components, it 
      is possible to determine which cards are present in the module and 
      which buses each can use.
      Note: If failuresInEffect contains either selfTest or clockSignal the 
      bus tap is unable to monitor the availability of the bus taps on the 
      bus; cardsAvailable will indicate that no bus taps are available on 
      the bus.

      Description of bits:
      n0(0)
      n1(1)
      n2(2)
      n3(3)
      n4(4)
      n5(5)
      n6(6)
      n7(7)
      n8(8)
      n9(9)
      n10(10)
      n11(11)
      n12(12)
      n13(13)
      n14(14)
      n15(15)"
::= { shelfCardBusTapOperEntry 3 }

shelfCardBusTapCardsTxTo OBJECT-TYPE
   SYNTAX     OCTET STRING (SIZE (2))
   ACCESS     read-only
   STATUS     mandatory
   DESCRIPTION
     "This attribute records the slot numbers of the cards which the bus 
      tap is currently configured to transmit cells to. This configuration is 
      managed automatically, and cannot be changed by the operator. By 
      examining this attribute for both of a card's BusTap components, it 
      is possible to determine which bus (if any) the card uses when it 
      needs to transmits cells to a specific card in the module.

      Description of bits:
      n0(0)
      n1(1)
      n2(2)
      n3(3)
      n4(4)
      n5(5)
      n6(6)
      n7(7)
      n8(8)
      n9(9)
      n10(10)
      n11(11)
      n12(12)
      n13(13)
      n14(14)
      n15(15)"
::= { shelfCardBusTapOperEntry 4 }

shelfCardBusTapErrorsTable OBJECT-TYPE
   SYNTAX     SEQUENCE OF ShelfCardBusTapErrorsEntry
   ACCESS     not-accessible
   STATUS     mandatory
   DESCRIPTION
     "This attribute group records errors that the bus tap has detected 
      since the card was last rebooted. This information is intended for 
      use in detecting and diagnosing bus-related problems within a 
      module."
::= { shelfCardBusTap 12 }

shelfCardBusTapErrorsEntry OBJECT-TYPE
   SYNTAX     ShelfCardBusTapErrorsEntry
   ACCESS     not-accessible
   STATUS     mandatory
   DESCRIPTION
     "An entry in the shelfCardBusTapErrorsTable."
   INDEX {
      shelfIndex,
      shelfCardIndex,
      shelfCardBusTapIndex }
::= { shelfCardBusTapErrorsTable 1 }

ShelfCardBusTapErrorsEntry ::= SEQUENCE {
   shelfCardBusTapSelfTestErrorCode
      Unsigned32,
   shelfCardBusTapClockErrors
      Unsigned32,
   shelfCardBusTapEndOfCellErrors
      Unsigned32,
   shelfCardBusTapParityErrors
      Unsigned32,
   shelfCardBusTapFrmCongestionErrors
      Unsigned32,
   shelfCardBusTapFrmCollisionErrors
      Unsigned32,
   shelfCardBusTapFrmTimeoutErrors
      Unsigned32,
   shelfCardBusTapFrmDeliveryErrors
      Unsigned32,
   shelfCardBusTapFrmSizeErrors
      Unsigned32 }

shelfCardBusTapSelfTestErrorCode OBJECT-TYPE
   SYNTAX     Unsigned32 (0..4294967295)
   ACCESS     read-only
   STATUS     mandatory
   DESCRIPTION
     "This attribute records the error code generated by the most recent 
      self-test of the bus tap. The value zero indicates that the self-test 
      was successful. A non-zero value indicates that the self-test failed, 
      and is used by the service technician when a defective card is 
      returned for repair."
::= { shelfCardBusTapErrorsEntry 1 }

shelfCardBusTapClockErrors OBJECT-TYPE
   SYNTAX     Unsigned32 (0..4294967295)
   ACCESS     read-only
   STATUS     mandatory
   DESCRIPTION
     "This attribute records the number of times that the bus tap has 
      detected a loss of the fundamental clock signal used by the bus. 
      Each occurrence may result in the loss of one or more cells or 
      frames. This type of event may occur during normal operation of 
      the module, for example when switching from one of the bus's 
      clock sources to the other; it may also be caused by a hardware 
      fault.
      The attribute's value wraps around to zero when it exceeds the 
      maximum permitted value."
::= { shelfCardBusTapErrorsEntry 2 }

shelfCardBusTapEndOfCellErrors OBJECT-TYPE
   SYNTAX     Unsigned32 (0..4294967295)
   ACCESS     read-only
   STATUS     mandatory
   DESCRIPTION
     "This attribute records the number of times that the bus tap has 
      detected a loss of the end-of-cell timing signal used by the bus. 
      Each occurrence may result in the loss of one or more cells or 
      frames. This type of event may occur during normal operation of 
      the module, for example switching the bus's clock source from one 
      card to another; it may also be caused by a hardware fault.
      The attribute's value wraps around to zero when it exceeds the 
      maximum permitted value."
::= { shelfCardBusTapErrorsEntry 3 }

shelfCardBusTapParityErrors OBJECT-TYPE
   SYNTAX     Unsigned32 (0..4294967295)
   ACCESS     read-only
   STATUS     mandatory
   DESCRIPTION
     "This attribute records the number of times that the bus tap has 
      detected a cell with invalid parity on the bus. Each occurrence may 
      result in the loss of one or more cells or frames. This type of event 
      may occur during normal operation of the module, for example 
      when a card is inserted, removed, or reboots; it may also be caused 
      by a hardware fault.
      The attribute's value wraps around to zero when it exceeds the 
      maximum permitted value."
::= { shelfCardBusTapErrorsEntry 4 }

shelfCardBusTapFrmCongestionErrors OBJECT-TYPE
   SYNTAX     Unsigned32 (0..4294967295)
   ACCESS     read-only
   STATUS     mandatory
   DESCRIPTION
     "This attribute records the number of times that the bus tap was 
      unable to receive a frame from the bus because all of its bus receive 
      channels were in use. Each occurrence results in the loss of the 
      frame. This type of event may occur during normal operation of the 
      module, for example when the module is operating in single bus 
      mode; it may also be caused by a hardware fault.
      The attribute's value wraps around to zero when it exceeds the 
      maximum permitted value."
::= { shelfCardBusTapErrorsEntry 5 }

shelfCardBusTapFrmCollisionErrors OBJECT-TYPE
   SYNTAX     Unsigned32 (0..4294967295)
   ACCESS     read-only
   STATUS     mandatory
   DESCRIPTION
     "This attribute records the number of times that the bus tap was 
      unable to receive a frame from the bus because it did not receive the 
      last cell of the frame before the first cell of the following frame 
      from the same source. Each occurrence results in the loss of both 
      frames. This type of event may occur during normal operation of 
      the module, for example when a card reboots; it may also be caused 
      by a hardware fault.
      The attribute's value wraps around to zero when it exceeds the 
      maximum permitted value."
::= { shelfCardBusTapErrorsEntry 6 }

shelfCardBusTapFrmTimeoutErrors OBJECT-TYPE
   SYNTAX     Unsigned32 (0..4294967295)
   ACCESS     read-only
   STATUS     mandatory
   DESCRIPTION
     "This attribute records the number of times that the bus tap was 
      unable to receive a frame from the bus because the delay between 
      two successive cells in that frame exceeded the maximum allowable 
      duration. Each occurrence results in the loss of the frame. This type 
      of event may occur during normal operation of the module, for 
      example when the module changes bus mode; it may also be caused 
      by a hardware fault.
      The attribute's value wraps around to zero when it exceeds the 
      maximum permitted value."
::= { shelfCardBusTapErrorsEntry 7 }

shelfCardBusTapFrmDeliveryErrors OBJECT-TYPE
   SYNTAX     Unsigned32 (0..4294967295)
   ACCESS     read-only
   STATUS     mandatory
   DESCRIPTION
     "This attribute records the number of times that the bus tap was 
      unable to receive a frame from the bus because it was destined for a 
      bus transmit queue; that is, the frame would have been immediately 
      retransmitted over a bus. Each occurrence results in the loss of the 
      frame. This type of event should never occur during normal 
      operation of the module and indicates the occurrence of a hardware 
      or software fault.
      The attribute's value wraps around to zero when it exceeds the 
      maximum permitted value."
::= { shelfCardBusTapErrorsEntry 8 }

shelfCardBusTapFrmSizeErrors OBJECT-TYPE
   SYNTAX     Unsigned32 (0..4294967295)
   ACCESS     read-only
   STATUS     mandatory
   DESCRIPTION
     "This attribute records the number of times that the bus tap was 
      unable to receive a frame from the bus because it required more 
      than 255 blocks of shared memory. Each occurrence results in the 
      loss of the frame. This type of event should never occur during 
      normal operation of the module and indicates improper 
      configuration of the card or the occurrence of a hardware or 
      software fault.
      The attribute's value wraps around to zero when it exceeds the 
      maximum permitted value."
::= { shelfCardBusTapErrorsEntry 9 }


-- Shelf Card/n Test
-- The Test component is used to verify the operation of a module's 
-- cards. A card test may be run when new hardware or services are 
-- commissioned, as part of a routine maintenance program, or to 
-- diagnose the cause of card- or bus-related problems. The Test 
-- component is created automatically for each card that is running as 
-- an active or standby LP; Test components cannot be added or 
-- deleted.
-- 
-- A card test allows the operator to stress test new or existing cards 
-- under controlled conditions. The test circulates frames over the 
-- Passport bus between the card under test and a distinct "target 
-- card", thereby exercising both cards and consuming bus bandwidth. 
-- The test frames follow the same route to their destination as normal 
-- frames. If the Passport node is in dual bus mode, each card test that 
-- is activated consumes bandwidth from both backplane buses in 
-- equal amounts; if the module is in single bus mode, only the bus in 
-- service is utilized.
-- 
-- The test frames generated by the card imder test are grouped into 
-- two independent streams.
-- 1) The loading frame stream circulates a set of "loading frames" 
-- between the card under test and the target card as rapidly as 
-- possible. The intent of this stream is to verify the operation of the 
-- cards and the backplane buses under a controlled load.
-- 2) The verification stream transmits a series of "verification frames" 
-- from the card under test to the the target card; as each frame is 
-- returned, its contents are verified and the next verification frame in 
-- the series is transmitted. The intent of this stream is to verify that 
-- frames are not being corrupted during transfer from card to card.
-- The card test can be configured to send frames from either or both 
-- streams. The priority, size, and content of the test frames can also be 
-- controlled.
-- 
-- Each card in Passport can run the card test independently. The 
-- operator can run the card test on any subset of the cards 
-- simultaneously and can specify different test frame configurations 
-- for each test. It is also possible for a card to act as the target card for 
-- more than one card under test, and for a card to act as a target card 
-- while it is itself under test. The flexibility provided by the card test 
-- allows the operator to tailor a set of card tests according to the 
-- testing to be performed.

shelfCardTest OBJECT IDENTIFIER ::= { shelfCard 3 }



shelfCardTestRowStatusTable OBJECT-TYPE
   SYNTAX     SEQUENCE OF ShelfCardTestRowStatusEntry
   ACCESS     not-accessible
   STATUS     mandatory
   DESCRIPTION
     "This entry controls the addition and deletion of 
      shelfCardTest components."
::= { shelfCardTest 1 }

shelfCardTestRowStatusEntry OBJECT-TYPE
   SYNTAX     ShelfCardTestRowStatusEntry
   ACCESS     not-accessible
   STATUS     mandatory
   DESCRIPTION
     "A single entry in the table represents a single 
      shelfCardTest component."
   INDEX {
      shelfIndex,
      shelfCardIndex,
      shelfCardTestIndex }
::= { shelfCardTestRowStatusTable 1 }

ShelfCardTestRowStatusEntry ::= SEQUENCE {
   shelfCardTestRowStatus
      RowStatus,
   shelfCardTestComponentName
      DisplayString,
   shelfCardTestStorageType
      StorageType,
   shelfCardTestIndex
      NonReplicated }

shelfCardTestRowStatus OBJECT-TYPE
   SYNTAX     RowStatus 
   ACCESS     read-only
   STATUS     mandatory
   DESCRIPTION
     "This variable is used as the basis for SNMP naming of
      shelfCardTest components.
      These components cannot be added nor deleted."
::= { shelfCardTestRowStatusEntry 1 }

shelfCardTestComponentName OBJECT-TYPE
   SYNTAX     DisplayString 
   ACCESS     read-only
   STATUS     mandatory
   DESCRIPTION
     "This variable provides the component's string name for
      use with the ASCII Console Interface"
::= { shelfCardTestRowStatusEntry 2 }

shelfCardTestStorageType OBJECT-TYPE
   SYNTAX     StorageType 
   ACCESS     read-only
   STATUS     mandatory
   DESCRIPTION
     "This variable represents the storage type value for the
      shelfCardTest tables."
::= { shelfCardTestRowStatusEntry 4 }

shelfCardTestIndex OBJECT-TYPE
   SYNTAX     NonReplicated 
   ACCESS     not-accessible
   STATUS     mandatory
   DESCRIPTION
     "This variable represents the index for the shelfCardTest tables."
::= { shelfCardTestRowStatusEntry 10 }

shelfCardTestStateTable OBJECT-TYPE
   SYNTAX     SEQUENCE OF ShelfCardTestStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { shelfCardTest 10 }

shelfCardTestStateEntry OBJECT-TYPE
   SYNTAX     ShelfCardTestStateEntry
   ACCESS     not-accessible
   STATUS     mandatory
   DESCRIPTION
     "An entry in the shelfCardTestStateTable."
   INDEX {
      shelfIndex,
      shelfCardIndex,
      shelfCardTestIndex }
::= { shelfCardTestStateTable 1 }

ShelfCardTestStateEntry ::= SEQUENCE {
   shelfCardTestAdminState
      INTEGER,
   shelfCardTestOperationalState
      INTEGER,
   shelfCardTestUsageState
      INTEGER }

shelfCardTestAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { shelfCardTestStateEntry 1 }

shelfCardTestOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { shelfCardTestStateEntry 2 }

shelfCardTestUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { shelfCardTestStateEntry 3 }

shelfCardTestSetupTable OBJECT-TYPE
   SYNTAX     SEQUENCE OF ShelfCardTestSetupEntry
   ACCESS     not-accessible
   STATUS     mandatory
   DESCRIPTION
     "This attribute group contains the attributes that govern the operation 
      of a card test. These attributes cannot be changed while a card test 
      is running."
::= { shelfCardTest 11 }

shelfCardTestSetupEntry OBJECT-TYPE
   SYNTAX     ShelfCardTestSetupEntry
   ACCESS     not-accessible
   STATUS     mandatory
   DESCRIPTION
     "An entry in the shelfCardTestSetupTable."
   INDEX {
      shelfIndex,
      shelfCardIndex,
      shelfCardTestIndex }
::= { shelfCardTestSetupTable 1 }

ShelfCardTestSetupEntry ::= SEQUENCE {
   shelfCardTestTargetCard
      Unsigned32,
   shelfCardTestFrmTypes
      OCTET STRING,
   shelfCardTestFrmPriorities
      OCTET STRING,
   shelfCardTestFrmPatternType
      INTEGER,
   shelfCardTestCustomizedPattern
      Hex,
   shelfCardTestDuration
      Unsigned32 }

shelfCardTestTargetCard OBJECT-TYPE
   SYNTAX     Unsigned32 (0..15)
   ACCESS     read-write
   STATUS     mandatory
   DESCRIPTION
     "This attribute specifies the slot number of the card to which frames 
      are sent during the card test. There is no single default value for this 
      attributeit defaults to the slot number of the Test component's 
      own card and must be changed to a different value before the test 
      can be started."
::= { shelfCardTestSetupEntry 1 }

shelfCardTestFrmTypes OBJECT-TYPE
   SYNTAX     OCTET STRING (SIZE (1))
   ACCESS     read-write
   STATUS     mandatory
   DESCRIPTION
     "This attribute specifies the types of frames that are sent during the 
      card test. It must contain at least one of the following values.
      loading: A set of 'loading frames' is circulated between the Test 
      component and the Test component on the target card as rapidly as 
      possible. This frame type should be selected when the test is 
      intended to verify the operation of the cards and the backplane 
      buses under a specified load.
      verification: A single 'verification frame' is transmitted to the Test 
      component on the target card; when the frame is returned, its 
      contents are verified and the next verification frame in the series is 
      transmitted. This frame type should be selected when the test is 
      intended to verify that frames are not being corrupted as they pass 
      from card to card.

      Description of bits:
      loading(0)
      verification(1)"
   DEFVAL     { 'c0'H }
::= { shelfCardTestSetupEntry 2 }

shelfCardTestFrmPriorities OBJECT-TYPE
   SYNTAX     OCTET STRING (SIZE (1))
   ACCESS     read-write
   STATUS     mandatory
   DESCRIPTION
     "This attribute specifies the priorities of the frames that are sent 
      during the card test. It must contain at least one of the following 
      values.
      low: Low priority frames are sent.
      high: High priority frames are sent.

      Description of bits:
      lowPriority(0)
      highPriority(1)"
   DEFVAL     { '80'H }
::= { shelfCardTestSetupEntry 3 }

shelfCardTestFrmPatternType OBJECT-TYPE
   SYNTAX     INTEGER  {
                 ccitt32kBitPattern(0),
                 ccitt8MBitPattern(1),
                 customizedPattern(2) }
   ACCESS     read-write
   STATUS     mandatory
   DESCRIPTION
     "This attribute specifies the bit sequence used to fill the frames used 
      in the card test. It must contain one of the following values.
      ccitt32kBitPattern: a pseudo-random sequence of 32 Kbit is used
      ccitt8MBitPattern: a pseudo-random sequence of 8 Mbit is used
      customizedPattern: the pattern defined by the customizedPattern 
      attribute is used"
   DEFVAL     { ccitt32kBitPattern }
::= { shelfCardTestSetupEntry 4 }

shelfCardTestCustomizedPattern OBJECT-TYPE
   SYNTAX     Hex (0..4294967295)
   ACCESS     read-write
   STATUS     mandatory
   DESCRIPTION
     "This attribute specifies a 32 bit sequence used to fill frames when 
      the framePatternType attribute has value customizedPattern. The 
      default value gives a pattern of alternating 0 and 1 bits."
   DEFVAL     { 1431655765 }
::= { shelfCardTestSetupEntry 5 }

shelfCardTestDuration OBJECT-TYPE
   SYNTAX     Unsigned32 (1..43200)
   ACCESS     read-write
   STATUS     mandatory
   DESCRIPTION
     "This attribute specifies the maximum length of time that the card 
      test is allowed to run. The value is expressed in minutes. The 
      maximum allowed value permits the card test to be run for up to 30 
      days."
   DEFVAL     { 60 }
::= { shelfCardTestSetupEntry 6 }

shelfCardTestResultsTable OBJECT-TYPE
   SYNTAX     SEQUENCE OF ShelfCardTestResultsEntry
   ACCESS     not-accessible
   STATUS     mandatory
   DESCRIPTION
     "This attribute group contains the results of the card test that is 
      currently running; if no test is running, the attribute group contains 
      the results of the most recently completed card test. The attributes 
      of the Results group are reset to their inital values whenever a card 
      test is started or any attribute of the Setup group is set."
::= { shelfCardTest 12 }

shelfCardTestResultsEntry OBJECT-TYPE
   SYNTAX     ShelfCardTestResultsEntry
   ACCESS     not-accessible
   STATUS     mandatory
   DESCRIPTION
     "An entry in the shelfCardTestResultsTable."
   INDEX {
      shelfIndex,
      shelfCardIndex,
      shelfCardTestIndex }
::= { shelfCardTestResultsTable 1 }

ShelfCardTestResultsEntry ::= SEQUENCE {
   shelfCardTestElapsedTime
      Unsigned32,
   shelfCardTestTimeRemaining
      Unsigned32,
   shelfCardTestCauseOfTermination
      INTEGER }

shelfCardTestElapsedTime OBJECT-TYPE
   SYNTAX     Unsigned32 (0..43200)
   ACCESS     read-only
   STATUS     mandatory
   DESCRIPTION
     "This attribute records the length of time (in minutes) that the card 
      test has been running."
::= { shelfCardTestResultsEntry 1 }

shelfCardTestTimeRemaining OBJECT-TYPE
   SYNTAX     Unsigned32 (0..43200)
   ACCESS     read-only
   STATUS     mandatory
   DESCRIPTION
     "This attribute records the maximum length of time (in minutes) that 
      the card test will continue to run before stopping."
::= { shelfCardTestResultsEntry 2 }

shelfCardTestCauseOfTermination OBJECT-TYPE
   SYNTAX     INTEGER  {
                 neverStarted(0),
                 testRunning(1),
                 testTimeExpired(2),
                 stoppedByOperator(3),
                 targetFailed(4),
                 becameActive(5) }
   ACCESS     read-only
   STATUS     mandatory
   DESCRIPTION
     "This attribute records the reason the card test ended. It contains one 
      of the following values.
      neverStarted: the card test has not been started
      testRunning: the card test is currently running
      testTimeExpired: the card test ran for the specified duration
      stoppedByOperator: a STOP command was issued
      targetFailed: the target card became non-operational
      becameActive: the source card became the active card for some LP"
::= { shelfCardTestResultsEntry 3 }

shelfCardTestSizeTable OBJECT-TYPE
   SYNTAX     SEQUENCE OF ShelfCardTestSizeEntry
   ACCESS     not-accessible
   STATUS     mandatory
   DESCRIPTION
     "This attribute specifies for each priority level the number of data 
      bytes in each frame sent during the card test. (The value specified 
      does not include the 4-byte header that is automatically added to a 
      frame when it is transmitted over the backplane.)"
::= { shelfCardTest 253 }

shelfCardTestSizeEntry OBJECT-TYPE
   SYNTAX     ShelfCardTestSizeEntry
   ACCESS     not-accessible
   STATUS     mandatory
   DESCRIPTION
     "An entry in the shelfCardTestSizeTable."
   INDEX {
      shelfIndex,
      shelfCardIndex,
      shelfCardTestIndex,
      shelfCardTestSizeIndex }
::= { shelfCardTestSizeTable 1 }

ShelfCardTestSizeEntry ::= SEQUENCE {
   shelfCardTestSizeIndex
      INTEGER,
   shelfCardTestSizeValue
      Unsigned32 }

shelfCardTestSizeIndex OBJECT-TYPE
   SYNTAX     INTEGER  {
                 lowPriority(0),
                 highPriority(1) }
   ACCESS     not-accessible
   STATUS     mandatory
   DESCRIPTION
     "This variable represents the shelfCardTestSizeTable
      specific index for the shelfCardTestSizeTable."
::= { shelfCardTestSizeEntry 1 }

shelfCardTestSizeValue OBJECT-TYPE
   SYNTAX     Unsigned32 (16..16000)
   ACCESS     read-write
   STATUS     mandatory
   DESCRIPTION
     "This variable represents an individual value for the
      shelfCardTestSizeTable."
::= { shelfCardTestSizeEntry 2 }

shelfCardTestLoadingFrmDataTable OBJECT-TYPE
   SYNTAX     SEQUENCE OF ShelfCardTestLoadingFrmDataEntry
   ACCESS     not-accessible
   STATUS     mandatory
   DESCRIPTION
     "This attribute records information about the loading frames that 
      have been transmitted to the Test component on the target card. The 
      following data is shown for each priority level:
      the number of frames that have been transmitted,
      the number of frames that were not returned successfully.
      The attribute's values wrap around to zero when they exceed the 
      maximum permitted value.
      
      Note: A loading frame is considered to have been successfully 
      returned even if it contains bit errors. Frame error statistics are 
      recorded in the verificationFrmData attribute."
::= { shelfCardTest 254 }

shelfCardTestLoadingFrmDataEntry OBJECT-TYPE
   SYNTAX     ShelfCardTestLoadingFrmDataEntry
   ACCESS     not-accessible
   STATUS     mandatory
   DESCRIPTION
     "An entry in the shelfCardTestLoadingFrmDataTable."
   INDEX {
      shelfIndex,
      shelfCardIndex,
      shelfCardTestIndex,
      shelfCardTestLoadingFrmDataResultsIndex,
      shelfCardTestLoadingFrmDataPriorityIndex }
::= { shelfCardTestLoadingFrmDataTable 1 }

ShelfCardTestLoadingFrmDataEntry ::= SEQUENCE {
   shelfCardTestLoadingFrmDataResultsIndex
      INTEGER,
   shelfCardTestLoadingFrmDataPriorityIndex
      INTEGER,
   shelfCardTestLoadingFrmDataValue
      Unsigned32 }

shelfCardTestLoadingFrmDataResultsIndex OBJECT-TYPE
   SYNTAX     INTEGER  {
                 framesSent(0),
                 framesLost(1) }
   ACCESS     not-accessible
   STATUS     mandatory
   DESCRIPTION
     "This variable represents the next to last index for the 
      shelfCardTestLoadingFrmDataTable."
::= { shelfCardTestLoadingFrmDataEntry 1 }

shelfCardTestLoadingFrmDataPriorityIndex OBJECT-TYPE
   SYNTAX     INTEGER  {
                 low(0),
                 high(1) }
   ACCESS     not-accessible
   STATUS     mandatory
   DESCRIPTION
     "This variable represents the final index for the 
      shelfCardTestLoadingFrmDataTable."
::= { shelfCardTestLoadingFrmDataEntry 2 }

shelfCardTestLoadingFrmDataValue OBJECT-TYPE
   SYNTAX     Unsigned32 (0..4294967295)
   ACCESS     read-only
   STATUS     mandatory
   DESCRIPTION
     "This variable represents an individual value for the
      shelfCardTestLoadingFrmDataTable."
::= { shelfCardTestLoadingFrmDataEntry 3 }

shelfCardTestVerificationFrmDataTable OBJECT-TYPE
   SYNTAX     SEQUENCE OF ShelfCardTestVerificationFrmDataEntry
   ACCESS     not-accessible
   STATUS     mandatory
   DESCRIPTION
     "This attribute records information about the verification frames that 
      have been transmitted to the Test component on the target card. The 
      following data is shown for each priority level:
      the number of frames that have been tested,
      the number of frames that had incorrect bits when returned. 
      The attribute's values wrap around to zero when they exceed the 
      maximum permitted value.
      
      Note: Verification frames that are not returned at all, or are returned 
      too late, are considered 'lost' and are not counted in either of the 
      above values. Frame loss statistics are recorded in the 
      loadingFrmData attribute."
::= { shelfCardTest 255 }

shelfCardTestVerificationFrmDataEntry OBJECT-TYPE
   SYNTAX     ShelfCardTestVerificationFrmDataEntry
   ACCESS     not-accessible
   STATUS     mandatory
   DESCRIPTION
     "An entry in the shelfCardTestVerificationFrmDataTable."
   INDEX {
      shelfIndex,
      shelfCardIndex,
      shelfCardTestIndex,
      shelfCardTestVerificationFrmDataResultsIndex,
      shelfCardTestVerificationFrmDataPriorityIndex }
::= { shelfCardTestVerificationFrmDataTable 1 }

ShelfCardTestVerificationFrmDataEntry ::= SEQUENCE {
   shelfCardTestVerificationFrmDataResultsIndex
      INTEGER,
   shelfCardTestVerificationFrmDataPriorityIndex
      INTEGER,
   shelfCardTestVerificationFrmDataValue
      Unsigned32 }

shelfCardTestVerificationFrmDataResultsIndex OBJECT-TYPE
   SYNTAX     INTEGER  {
                 framesTested(0),
                 framesBad(1) }
   ACCESS     not-accessible
   STATUS     mandatory
   DESCRIPTION
     "This variable represents the next to last index for the 
      shelfCardTestVerificationFrmDataTable."
::= { shelfCardTestVerificationFrmDataEntry 1 }

shelfCardTestVerificationFrmDataPriorityIndex OBJECT-TYPE
   SYNTAX     INTEGER  {
                 low(0),
                 high(1) }
   ACCESS     not-accessible
   STATUS     mandatory
   DESCRIPTION
     "This variable represents the final index for the 
      shelfCardTestVerificationFrmDataTable."
::= { shelfCardTestVerificationFrmDataEntry 2 }

shelfCardTestVerificationFrmDataValue OBJECT-TYPE
   SYNTAX     Unsigned32 (0..4294967295)
   ACCESS     read-only
   STATUS     mandatory
   DESCRIPTION
     "This variable represents an individual value for the
      shelfCardTestVerificationFrmDataTable."
::= { shelfCardTestVerificationFrmDataEntry 3 }


-- Shelf Card/n Diagnostics		 
-- This component manages all diagnostic information for a specific 
-- Card. The diagnostic information under this component are 
-- intended to be used by Nortel technical support. 

shelfCardDiag OBJECT IDENTIFIER ::= { shelfCard 4 }



shelfCardDiagRowStatusTable OBJECT-TYPE
   SYNTAX     SEQUENCE OF ShelfCardDiagRowStatusEntry
   ACCESS     not-accessible
   STATUS     mandatory
   DESCRIPTION
     "This entry controls the addition and deletion of 
      shelfCardDiag components."
::= { shelfCardDiag 1 }

shelfCardDiagRowStatusEntry OBJECT-TYPE
   SYNTAX     ShelfCardDiagRowStatusEntry
   ACCESS     not-accessible
   STATUS     mandatory
   DESCRIPTION
     "A single entry in the table represents a single 
      shelfCardDiag component."
   INDEX {
      shelfIndex,
      shelfCardIndex,
      shelfCardDiagIndex }
::= { shelfCardDiagRowStatusTable 1 }

ShelfCardDiagRowStatusEntry ::= SEQUENCE {
   shelfCardDiagRowStatus
      RowStatus,
   shelfCardDiagComponentName
      DisplayString,
   shelfCardDiagStorageType
      StorageType,
   shelfCardDiagIndex
      NonReplicated }

shelfCardDiagRowStatus OBJECT-TYPE
   SYNTAX     RowStatus 
   ACCESS     read-only
   STATUS     mandatory
   DESCRIPTION
     "This variable is used as the basis for SNMP naming of
      shelfCardDiag components.
      These components cannot be added nor deleted."
::= { shelfCardDiagRowStatusEntry 1 }

shelfCardDiagComponentName OBJECT-TYPE
   SYNTAX     DisplayString 
   ACCESS     read-only
   STATUS     mandatory
   DESCRIPTION
     "This variable provides the component's string name for
      use with the ASCII Console Interface"
::= { shelfCardDiagRowStatusEntry 2 }

shelfCardDiagStorageType OBJECT-TYPE
   SYNTAX     StorageType 
   ACCESS     read-only
   STATUS     mandatory
   DESCRIPTION
     "This variable represents the storage type value for the
      shelfCardDiag tables."
::= { shelfCardDiagRowStatusEntry 4 }

shelfCardDiagIndex OBJECT-TYPE
   SYNTAX     NonReplicated 
   ACCESS     not-accessible
   STATUS     mandatory
   DESCRIPTION
     "This variable represents the index for the shelfCardDiag tables."
::= { shelfCardDiagRowStatusEntry 10 }


-- Shelf Card/n Diag TrapData
-- On Passport control and function processors, hardware or software 
-- detected critical faults are preserved on the card until the power is 
-- lost. These critical faults lead to the reboot of the card and the 
-- captured trap data survives the rebooting of the card.
-- This component manages trap data stored in the persistent memory 
-- on the card. The trap data can be retrieved from the card to 
-- determine the cause of the fault.

shelfCardDiagTrapData OBJECT IDENTIFIER ::= { shelfCardDiag 2 }



shelfCardDiagTrapDataRowStatusTable OBJECT-TYPE
   SYNTAX     SEQUENCE OF ShelfCardDiagTrapDataRowStatusEntry
   ACCESS     not-accessible
   STATUS     mandatory
   DESCRIPTION
     "This entry controls the addition and deletion of 
      shelfCardDiagTrapData components."
::= { shelfCardDiagTrapData 1 }

shelfCardDiagTrapDataRowStatusEntry OBJECT-TYPE
   SYNTAX     ShelfCardDiagTrapDataRowStatusEntry
   ACCESS     not-accessible
   STATUS     mandatory
   DESCRIPTION
     "A single entry in the table represents a single 
      shelfCardDiagTrapData component."
   INDEX {
      shelfIndex,
      shelfCardIndex,
      shelfCardDiagIndex,
      shelfCardDiagTrapDataIndex }
::= { shelfCardDiagTrapDataRowStatusTable 1 }

ShelfCardDiagTrapDataRowStatusEntry ::= SEQUENCE {
   shelfCardDiagTrapDataRowStatus
      RowStatus,
   shelfCardDiagTrapDataComponentName
      DisplayString,
   shelfCardDiagTrapDataStorageType
      StorageType,
   shelfCardDiagTrapDataIndex
      NonReplicated }

shelfCardDiagTrapDataRowStatus OBJECT-TYPE
   SYNTAX     RowStatus 
   ACCESS     read-only
   STATUS     mandatory
   DESCRIPTION
     "This variable is used as the basis for SNMP naming of
      shelfCardDiagTrapData components.
      These components cannot be added nor deleted."
::= { shelfCardDiagTrapDataRowStatusEntry 1 }

shelfCardDiagTrapDataComponentName OBJECT-TYPE
   SYNTAX     DisplayString 
   ACCESS     read-only
   STATUS     mandatory
   DESCRIPTION
     "This variable provides the component's string name for
      use with the ASCII Console Interface"
::= { shelfCardDiagTrapDataRowStatusEntry 2 }

shelfCardDiagTrapDataStorageType OBJECT-TYPE
   SYNTAX     StorageType 
   ACCESS     read-only
   STATUS     mandatory
   DESCRIPTION
     "This variable represents the storage type value for the
      shelfCardDiagTrapData tables."
::= { shelfCardDiagTrapDataRowStatusEntry 4 }

shelfCardDiagTrapDataIndex OBJECT-TYPE
   SYNTAX     NonReplicated 
   ACCESS     not-accessible
   STATUS     mandatory
   DESCRIPTION
     "This variable represents the index for the shelfCardDiagTrapData tables."
::= { shelfCardDiagTrapDataRowStatusEntry 10 }

-- 
-- *** THIS SUBTREE CURRENTLY NOT IMPLEMENTED ***
-- 

-- Shelf Card/m Diag TrapData Line/n		
-- This component represents one line of trap data report.

shelfCardDiagTrapDataLine OBJECT IDENTIFIER ::= { shelfCardDiagTrapData 2 }



shelfCardDiagTrapDataLineRowStatusTable OBJECT-TYPE
   SYNTAX     SEQUENCE OF ShelfCardDiagTrapDataLineRowStatusEntry
   ACCESS     not-accessible
   STATUS     mandatory
   DESCRIPTION
     "*** THIS TABLE CURRENTLY NOT IMPLEMENTED ***

      This entry controls the addition and deletion of 
      shelfCardDiagTrapDataLine components."
::= { shelfCardDiagTrapDataLine 1 }

shelfCardDiagTrapDataLineRowStatusEntry OBJECT-TYPE
   SYNTAX     ShelfCardDiagTrapDataLineRowStatusEntry
   ACCESS     not-accessible
   STATUS     mandatory
   DESCRIPTION
     "A single entry in the table represents a single 
      shelfCardDiagTrapDataLine component."
   INDEX {
      shelfIndex,
      shelfCardIndex,
      shelfCardDiagIndex,
      shelfCardDiagTrapDataIndex,
      shelfCardDiagTrapDataLineIndex }
::= { shelfCardDiagTrapDataLineRowStatusTable 1 }

ShelfCardDiagTrapDataLineRowStatusEntry ::= SEQUENCE {
   shelfCardDiagTrapDataLineRowStatus
      RowStatus,
   shelfCardDiagTrapDataLineComponentName
      DisplayString,
   shelfCardDiagTrapDataLineStorageType
      StorageType,
   shelfCardDiagTrapDataLineIndex
      Integer32 }

shelfCardDiagTrapDataLineRowStatus OBJECT-TYPE
   SYNTAX     RowStatus 
   ACCESS     read-only
   STATUS     mandatory
   DESCRIPTION
     "This variable is used as the basis for SNMP naming of
      shelfCardDiagTrapDataLine components.
      These components cannot be added nor deleted."
::= { shelfCardDiagTrapDataLineRowStatusEntry 1 }

shelfCardDiagTrapDataLineComponentName OBJECT-TYPE
   SYNTAX     DisplayString 
   ACCESS     read-only
   STATUS     mandatory
   DESCRIPTION
     "This variable provides the component's string name for
      use with the ASCII Console Interface"
::= { shelfCardDiagTrapDataLineRowStatusEntry 2 }

shelfCardDiagTrapDataLineStorageType OBJECT-TYPE
   SYNTAX     StorageType 
   ACCESS     read-only
   STATUS     mandatory
   DESCRIPTION
     "This variable represents the storage type value for the
      shelfCardDiagTrapDataLine tables."
::= { shelfCardDiagTrapDataLineRowStatusEntry 4 }

shelfCardDiagTrapDataLineIndex OBJECT-TYPE
   SYNTAX     Integer32 (1..500)
   ACCESS     not-accessible
   STATUS     mandatory
   DESCRIPTION
     "This variable represents the index for the shelfCardDiagTrapDataLine tables."
::= { shelfCardDiagTrapDataLineRowStatusEntry 10 }

shelfCardDiagTrapDataLineOperTable OBJECT-TYPE
   SYNTAX     SEQUENCE OF ShelfCardDiagTrapDataLineOperEntry
   ACCESS     not-accessible
   STATUS     mandatory
   DESCRIPTION
     "*** THIS TABLE CURRENTLY NOT IMPLEMENTED ***

      This attribute group contains operational attributes for one line of 
      trap data or recoverable error report."
::= { shelfCardDiagTrapDataLine 10 }

shelfCardDiagTrapDataLineOperEntry OBJECT-TYPE
   SYNTAX     ShelfCardDiagTrapDataLineOperEntry
   ACCESS     not-accessible
   STATUS     mandatory
   DESCRIPTION
     "An entry in the shelfCardDiagTrapDataLineOperTable."
   INDEX {
      shelfIndex,
      shelfCardIndex,
      shelfCardDiagIndex,
      shelfCardDiagTrapDataIndex,
      shelfCardDiagTrapDataLineIndex }
::= { shelfCardDiagTrapDataLineOperTable 1 }

ShelfCardDiagTrapDataLineOperEntry ::= SEQUENCE {
   shelfCardDiagTrapDataLineData
      ExtendedAsciiString }

shelfCardDiagTrapDataLineData OBJECT-TYPE
   SYNTAX     ExtendedAsciiString (SIZE (0..512))
   ACCESS     read-only
   STATUS     mandatory
   DESCRIPTION
     "This attribute contains one line of trap data or recoverable error 
      report."
::= { shelfCardDiagTrapDataLineOperEntry 1 }


-- Shelf Card/n Diag RecoverableError
-- This component manages recoverable errors stored in the persistent 
-- memory which are preserved on the card until the power is lost. 
-- Recoverable errors do not cause the reboot of a card. Information 
-- about the errors can be retrieved from the card to determine the 
-- cause of the fault.

shelfCardDiagRecErr OBJECT IDENTIFIER ::= { shelfCardDiag 3 }



shelfCardDiagRecErrRowStatusTable OBJECT-TYPE
   SYNTAX     SEQUENCE OF ShelfCardDiagRecErrRowStatusEntry
   ACCESS     not-accessible
   STATUS     mandatory
   DESCRIPTION
     "This entry controls the addition and deletion of 
      shelfCardDiagRecErr components."
::= { shelfCardDiagRecErr 1 }

shelfCardDiagRecErrRowStatusEntry OBJECT-TYPE
   SYNTAX     ShelfCardDiagRecErrRowStatusEntry
   ACCESS     not-accessible
   STATUS     mandatory
   DESCRIPTION
     "A single entry in the table represents a single 
      shelfCardDiagRecErr component."
   INDEX {
      shelfIndex,
      shelfCardIndex,
      shelfCardDiagIndex,
      shelfCardDiagRecErrIndex }
::= { shelfCardDiagRecErrRowStatusTable 1 }

ShelfCardDiagRecErrRowStatusEntry ::= SEQUENCE {
   shelfCardDiagRecErrRowStatus
      RowStatus,
   shelfCardDiagRecErrComponentName
      DisplayString,
   shelfCardDiagRecErrStorageType
      StorageType,
   shelfCardDiagRecErrIndex
      NonReplicated }

shelfCardDiagRecErrRowStatus OBJECT-TYPE
   SYNTAX     RowStatus 
   ACCESS     read-only
   STATUS     mandatory
   DESCRIPTION
     "This variable is used as the basis for SNMP naming of
      shelfCardDiagRecErr components.
      These components cannot be added nor deleted."
::= { shelfCardDiagRecErrRowStatusEntry 1 }

shelfCardDiagRecErrComponentName OBJECT-TYPE
   SYNTAX     DisplayString 
   ACCESS     read-only
   STATUS     mandatory
   DESCRIPTION
     "This variable provides the component's string name for
      use with the ASCII Console Interface"
::= { shelfCardDiagRecErrRowStatusEntry 2 }

shelfCardDiagRecErrStorageType OBJECT-TYPE
   SYNTAX     StorageType 
   ACCESS     read-only
   STATUS     mandatory
   DESCRIPTION
     "This variable represents the storage type value for the
      shelfCardDiagRecErr tables."
::= { shelfCardDiagRecErrRowStatusEntry 4 }

shelfCardDiagRecErrIndex OBJECT-TYPE
   SYNTAX     NonReplicated 
   ACCESS     not-accessible
   STATUS     mandatory
   DESCRIPTION
     "This variable represents the index for the shelfCardDiagRecErr tables."
::= { shelfCardDiagRecErrRowStatusEntry 10 }

-- 
-- *** THIS SUBTREE CURRENTLY NOT IMPLEMENTED ***
-- 

-- Shelf Card/m Diag RecErr Line/n		
-- This component represents one line of recoverable error report.

shelfCardDiagRecErrLine OBJECT IDENTIFIER ::= { shelfCardDiagRecErr 2 }



shelfCardDiagRecErrLineRowStatusTable OBJECT-TYPE
   SYNTAX     SEQUENCE OF ShelfCardDiagRecErrLineRowStatusEntry
   ACCESS     not-accessible
   STATUS     mandatory
   DESCRIPTION
     "*** THIS TABLE CURRENTLY NOT IMPLEMENTED ***

      This entry controls the addition and deletion of 
      shelfCardDiagRecErrLine components."
::= { shelfCardDiagRecErrLine 1 }

shelfCardDiagRecErrLineRowStatusEntry OBJECT-TYPE
   SYNTAX     ShelfCardDiagRecErrLineRowStatusEntry
   ACCESS     not-accessible
   STATUS     mandatory
   DESCRIPTION
     "A single entry in the table represents a single 
      shelfCardDiagRecErrLine component."
   INDEX {
      shelfIndex,
      shelfCardIndex,
      shelfCardDiagIndex,
      shelfCardDiagRecErrIndex,
      shelfCardDiagRecErrLineIndex }
::= { shelfCardDiagRecErrLineRowStatusTable 1 }

ShelfCardDiagRecErrLineRowStatusEntry ::= SEQUENCE {
   shelfCardDiagRecErrLineRowStatus
      RowStatus,
   shelfCardDiagRecErrLineComponentName
      DisplayString,
   shelfCardDiagRecErrLineStorageType
      StorageType,
   shelfCardDiagRecErrLineIndex
      Integer32 }

shelfCardDiagRecErrLineRowStatus OBJECT-TYPE
   SYNTAX     RowStatus 
   ACCESS     read-only
   STATUS     mandatory
   DESCRIPTION
     "This variable is used as the basis for SNMP naming of
      shelfCardDiagRecErrLine components.
      These components cannot be added nor deleted."
::= { shelfCardDiagRecErrLineRowStatusEntry 1 }

shelfCardDiagRecErrLineComponentName OBJECT-TYPE
   SYNTAX     DisplayString 
   ACCESS     read-only
   STATUS     mandatory
   DESCRIPTION
     "This variable provides the component's string name for
      use with the ASCII Console Interface"
::= { shelfCardDiagRecErrLineRowStatusEntry 2 }

shelfCardDiagRecErrLineStorageType OBJECT-TYPE
   SYNTAX     StorageType 
   ACCESS     read-only
   STATUS     mandatory
   DESCRIPTION
     "This variable represents the storage type value for the
      shelfCardDiagRecErrLine tables."
::= { shelfCardDiagRecErrLineRowStatusEntry 4 }

shelfCardDiagRecErrLineIndex OBJECT-TYPE
   SYNTAX     Integer32 (1..500)
   ACCESS     not-accessible
   STATUS     mandatory
   DESCRIPTION
     "This variable represents the index for the shelfCardDiagRecErrLine tables."
::= { shelfCardDiagRecErrLineRowStatusEntry 10 }

shelfCardDiagRecErrLineOperTable OBJECT-TYPE
   SYNTAX     SEQUENCE OF ShelfCardDiagRecErrLineOperEntry
   ACCESS     not-accessible
   STATUS     mandatory
   DESCRIPTION
     "*** THIS TABLE CURRENTLY NOT IMPLEMENTED ***

      This attribute group contains operational attributes for one line of 
      trap data or recoverable error report."
::= { shelfCardDiagRecErrLine 10 }

shelfCardDiagRecErrLineOperEntry OBJECT-TYPE
   SYNTAX     ShelfCardDiagRecErrLineOperEntry
   ACCESS     not-accessible
   STATUS     mandatory
   DESCRIPTION
     "An entry in the shelfCardDiagRecErrLineOperTable."
   INDEX {
      shelfIndex,
      shelfCardIndex,
      shelfCardDiagIndex,
      shelfCardDiagRecErrIndex,
      shelfCardDiagRecErrLineIndex }
::= { shelfCardDiagRecErrLineOperTable 1 }

ShelfCardDiagRecErrLineOperEntry ::= SEQUENCE {
   shelfCardDiagRecErrLineData
      ExtendedAsciiString }

shelfCardDiagRecErrLineData OBJECT-TYPE
   SYNTAX     ExtendedAsciiString (SIZE (0..512))
   ACCESS     read-only
   STATUS     mandatory
   DESCRIPTION
     "This attribute contains one line of trap data or recoverable error 
      report."
::= { shelfCardDiagRecErrLineOperEntry 1 }

-- 
-- *** THIS SUBTREE CURRENTLY NOT IMPLEMENTED ***
-- 

-- DaughterCard/n
-- The DaughterCard component contains the information of a 
-- daughter card located on a card. The instance value of the 
-- daughterCard indicates the physical location of its socket on the 
-- card.

shelfCardDcard OBJECT IDENTIFIER ::= { shelfCard 16 }



shelfCardDcardRowStatusTable OBJECT-TYPE
   SYNTAX     SEQUENCE OF ShelfCardDcardRowStatusEntry
   ACCESS     not-accessible
   STATUS     mandatory
   DESCRIPTION
     "*** THIS TABLE CURRENTLY NOT IMPLEMENTED ***

      This entry controls the addition and deletion of 
      shelfCardDcard components."
::= { shelfCardDcard 1 }

shelfCardDcardRowStatusEntry OBJECT-TYPE
   SYNTAX     ShelfCardDcardRowStatusEntry
   ACCESS     not-accessible
   STATUS     mandatory
   DESCRIPTION
     "A single entry in the table represents a single 
      shelfCardDcard component."
   INDEX {
      shelfIndex,
      shelfCardIndex,
      shelfCardDcardIndex }
::= { shelfCardDcardRowStatusTable 1 }

ShelfCardDcardRowStatusEntry ::= SEQUENCE {
   shelfCardDcardRowStatus
      RowStatus,
   shelfCardDcardComponentName
      DisplayString,
   shelfCardDcardStorageType
      StorageType,
   shelfCardDcardIndex
      Integer32 }

shelfCardDcardRowStatus OBJECT-TYPE
   SYNTAX     RowStatus 
   ACCESS     read-only
   STATUS     mandatory
   DESCRIPTION
     "This variable is used as the basis for SNMP naming of
      shelfCardDcard components.
      These components cannot be added nor deleted."
::= { shelfCardDcardRowStatusEntry 1 }

shelfCardDcardComponentName OBJECT-TYPE
   SYNTAX     DisplayString 
   ACCESS     read-only
   STATUS     mandatory
   DESCRIPTION
     "This variable provides the component's string name for
      use with the ASCII Console Interface"
::= { shelfCardDcardRowStatusEntry 2 }

shelfCardDcardStorageType OBJECT-TYPE
   SYNTAX     StorageType 
   ACCESS     read-only
   STATUS     mandatory
   DESCRIPTION
     "This variable represents the storage type value for the
      shelfCardDcard tables."
::= { shelfCardDcardRowStatusEntry 4 }

shelfCardDcardIndex OBJECT-TYPE
   SYNTAX     Integer32 (1..15)
   ACCESS     not-accessible
   STATUS     mandatory
   DESCRIPTION
     "This variable represents the index for the shelfCardDcard tables."
::= { shelfCardDcardRowStatusEntry 10 }

shelfCardDcardDcardOperTable OBJECT-TYPE
   SYNTAX     SEQUENCE OF ShelfCardDcardDcardOperEntry
   ACCESS     not-accessible
   STATUS     mandatory
   DESCRIPTION
     "*** THIS TABLE CURRENTLY NOT IMPLEMENTED ***

      This group contains the operational attributes of the DaughterCard 
      component."
::= { shelfCardDcard 17 }

shelfCardDcardDcardOperEntry OBJECT-TYPE
   SYNTAX     ShelfCardDcardDcardOperEntry
   ACCESS     not-accessible
   STATUS     mandatory
   DESCRIPTION
     "An entry in the shelfCardDcardDcardOperTable."
   INDEX {
      shelfIndex,
      shelfCardIndex,
      shelfCardDcardIndex }
::= { shelfCardDcardDcardOperTable 1 }

ShelfCardDcardDcardOperEntry ::= SEQUENCE {
   shelfCardDcardType
      INTEGER,
   shelfCardDcardMemorySize
      Unsigned32,
   shelfCardDcardProductCode
      AsciiString }

shelfCardDcardType OBJECT-TYPE
   SYNTAX     INTEGER  {
                 unknown(0),
                 ram(1),
                 aqm(2),
                 pqc(3) }
   ACCESS     read-only
   STATUS     mandatory
   DESCRIPTION
     "This attributes indicates the type of a daugher card."
::= { shelfCardDcardDcardOperEntry 1 }

shelfCardDcardMemorySize OBJECT-TYPE
   SYNTAX     Unsigned32 (0..2147483647)
   ACCESS     read-only
   STATUS     mandatory
   DESCRIPTION
     "This attribute indicates the memory size in megabytes of the 
      daughter card."
::= { shelfCardDcardDcardOperEntry 2 }

shelfCardDcardProductCode OBJECT-TYPE
   SYNTAX     AsciiString (SIZE (0..12))
   ACCESS     read-only
   STATUS     mandatory
   DESCRIPTION
     "This attribute indicates the product equipment code of the daughter 
      card."
::= { shelfCardDcardDcardOperEntry 3 }


-- Shelf Bus/b
-- A Bus component respresents a hardware resource within a module 
-- that cards can use to communicate with each other. Each frame (or 
-- other data) to be transferred between cards is broken up into one or 
-- more cells by the sending card, placed on the bus, and reassembled 
-- by the receiving card(s).
-- A module's Bus components are created automatically, and cannot 
-- be added or deleted.

shelfBus OBJECT IDENTIFIER ::= { shelf 3 }



shelfBusRowStatusTable OBJECT-TYPE
   SYNTAX     SEQUENCE OF ShelfBusRowStatusEntry
   ACCESS     not-accessible
   STATUS     mandatory
   DESCRIPTION
     "This entry controls the addition and deletion of 
      shelfBus components."
::= { shelfBus 1 }

shelfBusRowStatusEntry OBJECT-TYPE
   SYNTAX     ShelfBusRowStatusEntry
   ACCESS     not-accessible
   STATUS     mandatory
   DESCRIPTION
     "A single entry in the table represents a single 
      shelfBus component."
   INDEX {
      shelfIndex,
      shelfBusIndex }
::= { shelfBusRowStatusTable 1 }

ShelfBusRowStatusEntry ::= SEQUENCE {
   shelfBusRowStatus
      RowStatus,
   shelfBusComponentName
      DisplayString,
   shelfBusStorageType
      StorageType,
   shelfBusIndex
      INTEGER }

shelfBusRowStatus OBJECT-TYPE
   SYNTAX     RowStatus 
   ACCESS     read-only
   STATUS     mandatory
   DESCRIPTION
     "This variable is used as the basis for SNMP naming of
      shelfBus components.
      These components cannot be added nor deleted."
::= { shelfBusRowStatusEntry 1 }

shelfBusComponentName OBJECT-TYPE
   SYNTAX     DisplayString 
   ACCESS     read-only
   STATUS     mandatory
   DESCRIPTION
     "This variable provides the component's string name for
      use with the ASCII Console Interface"
::= { shelfBusRowStatusEntry 2 }

shelfBusStorageType OBJECT-TYPE
   SYNTAX     StorageType 
   ACCESS     read-only
   STATUS     mandatory
   DESCRIPTION
     "This variable represents the storage type value for the
      shelfBus tables."
::= { shelfBusRowStatusEntry 4 }

shelfBusIndex OBJECT-TYPE
   SYNTAX     INTEGER  {
                 x(0),
                 y(1) }
   ACCESS     not-accessible
   STATUS     mandatory
   DESCRIPTION
     "This variable represents the index for the shelfBus tables."
::= { shelfBusRowStatusEntry 10 }

shelfBusStateTable OBJECT-TYPE
   SYNTAX     SEQUENCE OF ShelfBusStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { shelfBus 10 }

shelfBusStateEntry OBJECT-TYPE
   SYNTAX     ShelfBusStateEntry
   ACCESS     not-accessible
   STATUS     mandatory
   DESCRIPTION
     "An entry in the shelfBusStateTable."
   INDEX {
      shelfIndex,
      shelfBusIndex }
::= { shelfBusStateTable 1 }

ShelfBusStateEntry ::= SEQUENCE {
   shelfBusAdminState
      INTEGER,
   shelfBusOperationalState
      INTEGER,
   shelfBusUsageState
      INTEGER,
   shelfBusAvailabilityStatus
      OCTET STRING,
   shelfBusProceduralStatus
      OCTET STRING,
   shelfBusControlStatus
      OCTET STRING,
   shelfBusAlarmStatus
      OCTET STRING,
   shelfBusStandbyStatus
      INTEGER,
   shelfBusUnknownStatus
      INTEGER }

shelfBusAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { shelfBusStateEntry 1 }

shelfBusOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { shelfBusStateEntry 2 }

shelfBusUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { shelfBusStateEntry 3 }

shelfBusAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { shelfBusStateEntry 4 }

shelfBusProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { shelfBusStateEntry 5 }

shelfBusControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { shelfBusStateEntry 6 }

shelfBusAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { shelfBusStateEntry 7 }

shelfBusStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { shelfBusStateEntry 8 }

shelfBusUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { shelfBusStateEntry 9 }

shelfBusOperTable OBJECT-TYPE
   SYNTAX     SEQUENCE OF ShelfBusOperEntry
   ACCESS     not-accessible
   STATUS     mandatory
   DESCRIPTION
     "This attribute group contains operational attributes of a bus."
::= { shelfBus 11 }

shelfBusOperEntry OBJECT-TYPE
   SYNTAX     ShelfBusOperEntry
   ACCESS     not-accessible
   STATUS     mandatory
   DESCRIPTION
     "An entry in the shelfBusOperTable."
   INDEX {
      shelfIndex,
      shelfBusIndex }
::= { shelfBusOperTable 1 }

ShelfBusOperEntry ::= SEQUENCE {
   shelfBusClockSource
      INTEGER,
   shelfBusUtilization
      Unsigned32 }

shelfBusClockSource OBJECT-TYPE
   SYNTAX     INTEGER  {
                 activeCP(0),
                 alternate(1) }
   ACCESS     read-only
   STATUS     mandatory
   DESCRIPTION
     "This attribute records the source of the fundamental clock signal 
      and end-of-cell synchronization signal used by the bus. It contains 
      one of the following values.
      activeCP: the card which is the active control processor (CP) is 
      providing clock signals
      alternate: the card at the opposite end of the module from the active 
      CP is providing clock signals"
::= { shelfBusOperEntry 1 }

shelfBusUtilization OBJECT-TYPE
   SYNTAX     Unsigned32 (0..100)
   ACCESS     read-only
   STATUS     mandatory
   DESCRIPTION
     "This attribute records how much of the available bus bandwidth was 
      actually used during the most recently sampled 1 second interval. 
      The value is expressed as a percentage."
::= { shelfBusOperEntry 2 }

shelfBusBusTapStatusTable OBJECT-TYPE
   SYNTAX     SEQUENCE OF ShelfBusBusTapStatusEntry
   ACCESS     not-accessible
   STATUS     mandatory
   DESCRIPTION
     "This attribute records the operability of each bus tap on the bus, as 
      reported by the associated BusTap component; the entries are 
      indexed by slot number of the card. Each entry contains one of the 
      following values.
      ok: the bus tap is operational
      failed: the bus tap has failed
      none: the bus tap status is not availablethe associated BusTap 
      component does not currently exist"
::= { shelfBus 246 }

shelfBusBusTapStatusEntry OBJECT-TYPE
   SYNTAX     ShelfBusBusTapStatusEntry
   ACCESS     not-accessible
   STATUS     mandatory
   DESCRIPTION
     "An entry in the shelfBusBusTapStatusTable."
   INDEX {
      shelfIndex,
      shelfBusIndex,
      shelfBusBusTapStatusIndex }
::= { shelfBusBusTapStatusTable 1 }

ShelfBusBusTapStatusEntry ::= SEQUENCE {
   shelfBusBusTapStatusIndex
      Integer32,
   shelfBusBusTapStatusValue
      INTEGER }

shelfBusBusTapStatusIndex OBJECT-TYPE
   SYNTAX     Integer32 (0..15)
   ACCESS     not-accessible
   STATUS     mandatory
   DESCRIPTION
     "This variable represents the shelfBusBusTapStatusTable
      specific index for the shelfBusBusTapStatusTable."
::= { shelfBusBusTapStatusEntry 1 }

shelfBusBusTapStatusValue OBJECT-TYPE
   SYNTAX     INTEGER  {
                 ok(0),
                 failed(1),
                 none(2) }
   ACCESS     read-only
   STATUS     mandatory
   DESCRIPTION
     "This variable represents an individual value for the
      shelfBusBusTapStatusTable."
::= { shelfBusBusTapStatusEntry 2 }

shelfBusClockSourceStatusTable OBJECT-TYPE
   SYNTAX     SEQUENCE OF ShelfBusClockSourceStatusEntry
   ACCESS     not-accessible
   STATUS     mandatory
   DESCRIPTION
     "This vector attribute, indexed with activeCP or alternate, represents 
      the state of the bus clock sources. It can be set to one of the 
      following values:
      ok: all operational cards can receive signals from the clock source.
      failed: at least one operational card is unable to receive signals from 
      the clock source.
      unknown: status of a clock source is unknown. To determine the 
      status of the clock source, a test must be run.
      testInProgress: the clock source is currently being tested.
      notApplicable: the LP state of the clock source's card is down or 
      not provisioned."
::= { shelfBus 247 }

shelfBusClockSourceStatusEntry OBJECT-TYPE
   SYNTAX     ShelfBusClockSourceStatusEntry
   ACCESS     not-accessible
   STATUS     mandatory
   DESCRIPTION
     "An entry in the shelfBusClockSourceStatusTable."
   INDEX {
      shelfIndex,
      shelfBusIndex,
      shelfBusClockSourceStatusIndex }
::= { shelfBusClockSourceStatusTable 1 }

ShelfBusClockSourceStatusEntry ::= SEQUENCE {
   shelfBusClockSourceStatusIndex
      INTEGER,
   shelfBusClockSourceStatusValue
      INTEGER }

shelfBusClockSourceStatusIndex OBJECT-TYPE
   SYNTAX     INTEGER  {
                 activeCP(0),
                 alternate(1) }
   ACCESS     not-accessible
   STATUS     mandatory
   DESCRIPTION
     "This variable represents the shelfBusClockSourceStatusTable
      specific index for the shelfBusClockSourceStatusTable."
::= { shelfBusClockSourceStatusEntry 1 }

shelfBusClockSourceStatusValue OBJECT-TYPE
   SYNTAX     INTEGER  {
                 ok(0),
                 failed(1),
                 unknown(2),
                 testInProgress(3),
                 notApplicable(4) }
   ACCESS     read-only
   STATUS     mandatory
   DESCRIPTION
     "This variable represents an individual value for the
      shelfBusClockSourceStatusTable."
::= { shelfBusClockSourceStatusEntry 2 }


-- Shelf Bus/b Test
-- The Test component is used to verify the operation of a bus. A bus 
-- test may be run as part of a regular maintenance program, or to 
-- diagnose the cause of a bus-related problem. The Test component is 
-- created automatically, and cannot be added or deleted.
-- 
-- The bus test ensures that the bus taps on a specific bus are 
-- functioning properly at minimal utilization rates. The bus to be 
-- tested must be locked while testing is in progress. The test only 
-- involves bus taps on operational cards (active and standby LPs). If 
-- an operational card becomes non-operational or fails to respond 
-- during the test, it is dropped from the test and is not allowed to 
-- rejoin; however, the results of any tests on its bus tap up to that 
-- point are preserved. The results of the test can help to determine 
-- which portions of the bus system are faulty, if any.
-- 
-- A bus test is composed of several different tests. The tests are 
-- performed in the following order.
-- 1) Bus tap self-test: Each bus tap executes its self-test.
-- 2) Clock source test: Each bus tap ensures that it can receive clock 
-- signals from the active control processor clock source and the 
-- alternate clock source (if present).
-- 3) Broadcast test: Each bus tap ensures that it can receive a 
-- broadcast frame over the backplane from every operational card 
-- (including itself).
-- 4) Ping test: Each bus tap ensures that it can receive a low priority 
-- non-broadcast frame over the backplane from every operational 
-- card (including itself).
-- Once all of the tests have been performed, the ping test is repeated 
-- continuously until the bus test is terminated; this repetition helps to 
-- detect transient bus faults. The bus test stops automatically after a 
-- specified time interval, or if it detects a bus tap self-test failure, an 
-- active control processor clock source test failure, or a broadcast test 
-- failure.

shelfBusTest OBJECT IDENTIFIER ::= { shelfBus 2 }



shelfBusTestRowStatusTable OBJECT-TYPE
   SYNTAX     SEQUENCE OF ShelfBusTestRowStatusEntry
   ACCESS     not-accessible
   STATUS     mandatory
   DESCRIPTION
     "This entry controls the addition and deletion of 
      shelfBusTest components."
::= { shelfBusTest 1 }

shelfBusTestRowStatusEntry OBJECT-TYPE
   SYNTAX     ShelfBusTestRowStatusEntry
   ACCESS     not-accessible
   STATUS     mandatory
   DESCRIPTION
     "A single entry in the table represents a single 
      shelfBusTest component."
   INDEX {
      shelfIndex,
      shelfBusIndex,
      shelfBusTestIndex }
::= { shelfBusTestRowStatusTable 1 }

ShelfBusTestRowStatusEntry ::= SEQUENCE {
   shelfBusTestRowStatus
      RowStatus,
   shelfBusTestComponentName
      DisplayString,
   shelfBusTestStorageType
      StorageType,
   shelfBusTestIndex
      NonReplicated }

shelfBusTestRowStatus OBJECT-TYPE
   SYNTAX     RowStatus 
   ACCESS     read-only
   STATUS     mandatory
   DESCRIPTION
     "This variable is used as the basis for SNMP naming of
      shelfBusTest components.
      These components cannot be added nor deleted."
::= { shelfBusTestRowStatusEntry 1 }

shelfBusTestComponentName OBJECT-TYPE
   SYNTAX     DisplayString 
   ACCESS     read-only
   STATUS     mandatory
   DESCRIPTION
     "This variable provides the component's string name for
      use with the ASCII Console Interface"
::= { shelfBusTestRowStatusEntry 2 }

shelfBusTestStorageType OBJECT-TYPE
   SYNTAX     StorageType 
   ACCESS     read-only
   STATUS     mandatory
   DESCRIPTION
     "This variable represents the storage type value for the
      shelfBusTest tables."
::= { shelfBusTestRowStatusEntry 4 }

shelfBusTestIndex OBJECT-TYPE
   SYNTAX     NonReplicated 
   ACCESS     not-accessible
   STATUS     mandatory
   DESCRIPTION
     "This variable represents the index for the shelfBusTest tables."
::= { shelfBusTestRowStatusEntry 10 }

shelfBusTestStateTable OBJECT-TYPE
   SYNTAX     SEQUENCE OF ShelfBusTestStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { shelfBusTest 10 }

shelfBusTestStateEntry OBJECT-TYPE
   SYNTAX     ShelfBusTestStateEntry
   ACCESS     not-accessible
   STATUS     mandatory
   DESCRIPTION
     "An entry in the shelfBusTestStateTable."
   INDEX {
      shelfIndex,
      shelfBusIndex,
      shelfBusTestIndex }
::= { shelfBusTestStateTable 1 }

ShelfBusTestStateEntry ::= SEQUENCE {
   shelfBusTestAdminState
      INTEGER,
   shelfBusTestOperationalState
      INTEGER,
   shelfBusTestUsageState
      INTEGER }

shelfBusTestAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { shelfBusTestStateEntry 1 }

shelfBusTestOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { shelfBusTestStateEntry 2 }

shelfBusTestUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { shelfBusTestStateEntry 3 }

shelfBusTestSetupTable OBJECT-TYPE
   SYNTAX     SEQUENCE OF ShelfBusTestSetupEntry
   ACCESS     not-accessible
   STATUS     mandatory
   DESCRIPTION
     "This attribute group contains the attributes that govern the operation 
      of a bus test. These attributes cannot be changed while the bus test 
      is running."
::= { shelfBusTest 11 }

shelfBusTestSetupEntry OBJECT-TYPE
   SYNTAX     ShelfBusTestSetupEntry
   ACCESS     not-accessible
   STATUS     mandatory
   DESCRIPTION
     "An entry in the shelfBusTestSetupTable."
   INDEX {
      shelfIndex,
      shelfBusIndex,
      shelfBusTestIndex }
::= { shelfBusTestSetupTable 1 }

ShelfBusTestSetupEntry ::= SEQUENCE {
   shelfBusTestDuration
      Unsigned32 }

shelfBusTestDuration OBJECT-TYPE
   SYNTAX     Unsigned32 (1..43200)
   ACCESS     read-write
   STATUS     mandatory
   DESCRIPTION
     "This attribute specifies the maximum length of time that the bus test 
      is allowed to run. The value is expressed in minutes. The maximum 
      allowed value permits the bus test to be run for up to 30 days."
   DEFVAL     { 1 }
::= { shelfBusTestSetupEntry 1 }

shelfBusTestResultsTable OBJECT-TYPE
   SYNTAX     SEQUENCE OF ShelfBusTestResultsEntry
   ACCESS     not-accessible
   STATUS     mandatory
   DESCRIPTION
     "This attribute group contains the results of the bus test that is 
      currently running; if no bus test is running, the attribute group 
      contains the results of the most recently completed bus test. The 
      attributes of the Results group are reset to their initial values 
      whenever a bus test is started or any attribute in the Setup group is 
      set."
::= { shelfBusTest 12 }

shelfBusTestResultsEntry OBJECT-TYPE
   SYNTAX     ShelfBusTestResultsEntry
   ACCESS     not-accessible
   STATUS     mandatory
   DESCRIPTION
     "An entry in the shelfBusTestResultsTable."
   INDEX {
      shelfIndex,
      shelfBusIndex,
      shelfBusTestIndex }
::= { shelfBusTestResultsTable 1 }

ShelfBusTestResultsEntry ::= SEQUENCE {
   shelfBusTestElapsedTime
      Unsigned32,
   shelfBusTestTimeRemaining
      Unsigned32,
   shelfBusTestCauseOfTermination
      INTEGER,
   shelfBusTestTestsDone
      OCTET STRING }

shelfBusTestElapsedTime OBJECT-TYPE
   SYNTAX     Unsigned32 (0..43200)
   ACCESS     read-only
   STATUS     mandatory
   DESCRIPTION
     "This attribute records the length of time (in minutes) that the bus 
      test has been running."
::= { shelfBusTestResultsEntry 1 }

shelfBusTestTimeRemaining OBJECT-TYPE
   SYNTAX     Unsigned32 (0..43200)
   ACCESS     read-only
   STATUS     mandatory
   DESCRIPTION
     "This attribute records the maximum length of time (in minutes) that 
      the bus test will continue to run before stopping."
::= { shelfBusTestResultsEntry 2 }

shelfBusTestCauseOfTermination OBJECT-TYPE
   SYNTAX     INTEGER  {
                 neverStarted(0),
                 testRunning(1),
                 testTimeExpired(2),
                 stoppedByOperator(3),
                 selfTestFailure(4),
                 clockSourceFailure(5),
                 broadcastFailure(6) }
   ACCESS     read-only
   STATUS     mandatory
   DESCRIPTION
     "This attribute records the reason the bus test ended. It contains one 
      of the following values.
      neverStarted: the bus test has not been started
      testRunning: the bus test is currently running
      testTimeExpired: the bus test ran for the specified duration
      stoppedByOperator: a STOP command was issued
      selfTestFailure: a failure was detected during the bus tap self-test
      clockSourceFailure: a failure was detected during the test of the 
      active control processor (CP) clock source
      broadcastFailure: a failure was detected during the broadcast test"
::= { shelfBusTestResultsEntry 3 }

shelfBusTestTestsDone OBJECT-TYPE
   SYNTAX     OCTET STRING (SIZE (1))
   ACCESS     read-only
   STATUS     mandatory
   DESCRIPTION
     "This attribute records the tests that have been performed during the 
      bus test. It may contain zero or more of the following values.
      selfTest: the bus tap self-test has been performed
      clockSourceTest: the clock source test has been performed
      broadcastTest: the broadcast test has been performed
      pingTest: at least one ping test has been performed

      Description of bits:
      selfTest(0)
      clockSourceTest(1)
      broadcastTest(2)
      pingTest(3)"
::= { shelfBusTestResultsEntry 4 }

shelfBusTestSelfTestResultsTable OBJECT-TYPE
   SYNTAX     SEQUENCE OF ShelfBusTestSelfTestResultsEntry
   ACCESS     not-accessible
   STATUS     mandatory
   DESCRIPTION
     "This attribute records the results of the bus tap self-test, indexed by 
      the slot number of the card containing the bus tap tested. Each entry 
      contains one of the following values.
      +: the bus tap passed its self-test
      X: the bus tap failed its self-test
      .: the bus tap was not tested
      The bus test terminates automatically if a failure is detected."
::= { shelfBusTest 248 }

shelfBusTestSelfTestResultsEntry OBJECT-TYPE
   SYNTAX     ShelfBusTestSelfTestResultsEntry
   ACCESS     not-accessible
   STATUS     mandatory
   DESCRIPTION
     "An entry in the shelfBusTestSelfTestResultsTable."
   INDEX {
      shelfIndex,
      shelfBusIndex,
      shelfBusTestIndex,
      shelfBusTestSelfTestResultsIndex }
::= { shelfBusTestSelfTestResultsTable 1 }

ShelfBusTestSelfTestResultsEntry ::= SEQUENCE {
   shelfBusTestSelfTestResultsIndex
      Integer32,
   shelfBusTestSelfTestResultsValue
      INTEGER }

shelfBusTestSelfTestResultsIndex OBJECT-TYPE
   SYNTAX     Integer32 (0..15)
   ACCESS     not-accessible
   STATUS     mandatory
   DESCRIPTION
     "This variable represents the shelfBusTestSelfTestResultsTable
      specific index for the shelfBusTestSelfTestResultsTable."
::= { shelfBusTestSelfTestResultsEntry 1 }

shelfBusTestSelfTestResultsValue OBJECT-TYPE
   SYNTAX     INTEGER  {
                 x(0),
                 n1(1),
                 n2(2) }
   ACCESS     read-only
   STATUS     mandatory
   DESCRIPTION
     "This variable represents an individual value for the
      shelfBusTestSelfTestResultsTable."
::= { shelfBusTestSelfTestResultsEntry 2 }

shelfBusTestClockSourceTestResultsTable OBJECT-TYPE
   SYNTAX     SEQUENCE OF ShelfBusTestClockSourceTestResultsEntry
   ACCESS     not-accessible
   STATUS     mandatory
   DESCRIPTION
     "This attribute records the results of the clock source test, indexed by 
      the clock source and the slot number of the card containing the bus 
      tap tested. Each entry contains one of the following values.
      +: the bus tap was able to receive clock signals from the clock 
      source
      X: the bus tap was unable to receive clock signals from the clock 
      source
      .: the bus tap was not tested against the clock source
      The bus test terminates automatically if a failure is detected 
      involving the active control processor (CP) clock source."
::= { shelfBusTest 249 }

shelfBusTestClockSourceTestResultsEntry OBJECT-TYPE
   SYNTAX     ShelfBusTestClockSourceTestResultsEntry
   ACCESS     not-accessible
   STATUS     mandatory
   DESCRIPTION
     "An entry in the shelfBusTestClockSourceTestResultsTable."
   INDEX {
      shelfIndex,
      shelfBusIndex,
      shelfBusTestIndex,
      shelfBusTestClockSourceTestResultsSourceIndex,
      shelfBusTestClockSourceTestResultsCardIndex }
::= { shelfBusTestClockSourceTestResultsTable 1 }

ShelfBusTestClockSourceTestResultsEntry ::= SEQUENCE {
   shelfBusTestClockSourceTestResultsSourceIndex
      INTEGER,
   shelfBusTestClockSourceTestResultsCardIndex
      Integer32,
   shelfBusTestClockSourceTestResultsValue
      INTEGER }

shelfBusTestClockSourceTestResultsSourceIndex OBJECT-TYPE
   SYNTAX     INTEGER  {
                 activeCP(0),
                 alternate(1) }
   ACCESS     not-accessible
   STATUS     mandatory
   DESCRIPTION
     "This variable represents the next to last index for the 
      shelfBusTestClockSourceTestResultsTable."
::= { shelfBusTestClockSourceTestResultsEntry 1 }

shelfBusTestClockSourceTestResultsCardIndex OBJECT-TYPE
   SYNTAX     Integer32 (0..15)
   ACCESS     not-accessible
   STATUS     mandatory
   DESCRIPTION
     "This variable represents the final index for the 
      shelfBusTestClockSourceTestResultsTable."
::= { shelfBusTestClockSourceTestResultsEntry 2 }

shelfBusTestClockSourceTestResultsValue OBJECT-TYPE
   SYNTAX     INTEGER  {
                 x(0),
                 n1(1),
                 n2(2) }
   ACCESS     read-only
   STATUS     mandatory
   DESCRIPTION
     "This variable represents an individual value for the
      shelfBusTestClockSourceTestResultsTable."
::= { shelfBusTestClockSourceTestResultsEntry 3 }

shelfBusTestBroadcastTestResultsTable OBJECT-TYPE
   SYNTAX     SEQUENCE OF ShelfBusTestBroadcastTestResultsEntry
   ACCESS     not-accessible
   STATUS     mandatory
   DESCRIPTION
     "This attribute records the results of the broadcast test, indexed by 
      the slot numbers of the cards containing the bus taps tested. Each 
      entry contains one of the following values.
      +: a broadcast message was successfully sent from the transmitting 
      bus tap to the receiving bus tap 
      X: a broadcast message was not successfully sent from the 
      transmitting bus tap to the receiving bus tap
      .: the associated pair of bus taps was not tested 
      The bus test terminates automatically if a failure is detected."
::= { shelfBusTest 250 }

shelfBusTestBroadcastTestResultsEntry OBJECT-TYPE
   SYNTAX     ShelfBusTestBroadcastTestResultsEntry
   ACCESS     not-accessible
   STATUS     mandatory
   DESCRIPTION
     "An entry in the shelfBusTestBroadcastTestResultsTable."
   INDEX {
      shelfIndex,
      shelfBusIndex,
      shelfBusTestIndex,
      shelfBusTestBroadcastTestResultsTxCardIndex,
      shelfBusTestBroadcastTestResultsRxCardIndex }
::= { shelfBusTestBroadcastTestResultsTable 1 }

ShelfBusTestBroadcastTestResultsEntry ::= SEQUENCE {
   shelfBusTestBroadcastTestResultsTxCardIndex
      Integer32,
   shelfBusTestBroadcastTestResultsRxCardIndex
      Integer32,
   shelfBusTestBroadcastTestResultsValue
      INTEGER }

shelfBusTestBroadcastTestResultsTxCardIndex OBJECT-TYPE
   SYNTAX     Integer32 (0..15)
   ACCESS     not-accessible
   STATUS     mandatory
   DESCRIPTION
     "This variable represents the next to last index for the 
      shelfBusTestBroadcastTestResultsTable."
::= { shelfBusTestBroadcastTestResultsEntry 1 }

shelfBusTestBroadcastTestResultsRxCardIndex OBJECT-TYPE
   SYNTAX     Integer32 (0..15)
   ACCESS     not-accessible
   STATUS     mandatory
   DESCRIPTION
     "This variable represents the final index for the 
      shelfBusTestBroadcastTestResultsTable."
::= { shelfBusTestBroadcastTestResultsEntry 2 }

shelfBusTestBroadcastTestResultsValue OBJECT-TYPE
   SYNTAX     INTEGER  {
                 x(0),
                 n1(1),
                 n2(2) }
   ACCESS     read-only
   STATUS     mandatory
   DESCRIPTION
     "This variable represents an individual value for the
      shelfBusTestBroadcastTestResultsTable."
::= { shelfBusTestBroadcastTestResultsEntry 3 }

shelfBusTestPingTestsTable OBJECT-TYPE
   SYNTAX     SEQUENCE OF ShelfBusTestPingTestsEntry
   ACCESS     not-accessible
   STATUS     mandatory
   DESCRIPTION
     "This attribute records the number of ping tests performed, indexed 
      by the slot numbers of the cards containing the bus taps involved. 
      Each test attempts to transmit a single low-priority frame from the 
      transmitting bus tap to the receiving bus tap."
::= { shelfBusTest 251 }

shelfBusTestPingTestsEntry OBJECT-TYPE
   SYNTAX     ShelfBusTestPingTestsEntry
   ACCESS     not-accessible
   STATUS     mandatory
   DESCRIPTION
     "An entry in the shelfBusTestPingTestsTable."
   INDEX {
      shelfIndex,
      shelfBusIndex,
      shelfBusTestIndex,
      shelfBusTestPingTestsTxCardIndex,
      shelfBusTestPingTestsRxCardIndex }
::= { shelfBusTestPingTestsTable 1 }

ShelfBusTestPingTestsEntry ::= SEQUENCE {
   shelfBusTestPingTestsTxCardIndex
      Integer32,
   shelfBusTestPingTestsRxCardIndex
      Integer32,
   shelfBusTestPingTestsValue
      Unsigned32 }

shelfBusTestPingTestsTxCardIndex OBJECT-TYPE
   SYNTAX     Integer32 (0..15)
   ACCESS     not-accessible
   STATUS     mandatory
   DESCRIPTION
     "This variable represents the next to last index for the 
      shelfBusTestPingTestsTable."
::= { shelfBusTestPingTestsEntry 1 }

shelfBusTestPingTestsRxCardIndex OBJECT-TYPE
   SYNTAX     Integer32 (0..15)
   ACCESS     not-accessible
   STATUS     mandatory
   DESCRIPTION
     "This variable represents the final index for the 
      shelfBusTestPingTestsTable."
::= { shelfBusTestPingTestsEntry 2 }

shelfBusTestPingTestsValue OBJECT-TYPE
   SYNTAX     Unsigned32 (0..4294967295)
   ACCESS     read-only
   STATUS     mandatory
   DESCRIPTION
     "This variable represents an individual value for the
      shelfBusTestPingTestsTable."
::= { shelfBusTestPingTestsEntry 3 }

shelfBusTestPingFailuresTable OBJECT-TYPE
   SYNTAX     SEQUENCE OF ShelfBusTestPingFailuresEntry
   ACCESS     not-accessible
   STATUS     mandatory
   DESCRIPTION
     "This attribute records the number of ping test failures detected, 
      indexed by the slot numbers of the cards containing the bus taps 
      involved. Each failure represents a single low-priority frame that 
      was not successfully transmitted from the transmitting bus tap to the 
      receiving bus tap. The bus test does not terminate automatically if a 
      failure is detected."
::= { shelfBusTest 252 }

shelfBusTestPingFailuresEntry OBJECT-TYPE
   SYNTAX     ShelfBusTestPingFailuresEntry
   ACCESS     not-accessible
   STATUS     mandatory
   DESCRIPTION
     "An entry in the shelfBusTestPingFailuresTable."
   INDEX {
      shelfIndex,
      shelfBusIndex,
      shelfBusTestIndex,
      shelfBusTestPingFailuresTxCardIndex,
      shelfBusTestPingFailuresRxCardIndex }
::= { shelfBusTestPingFailuresTable 1 }

ShelfBusTestPingFailuresEntry ::= SEQUENCE {
   shelfBusTestPingFailuresTxCardIndex
      Integer32,
   shelfBusTestPingFailuresRxCardIndex
      Integer32,
   shelfBusTestPingFailuresValue
      Unsigned32 }

shelfBusTestPingFailuresTxCardIndex OBJECT-TYPE
   SYNTAX     Integer32 (0..15)
   ACCESS     not-accessible
   STATUS     mandatory
   DESCRIPTION
     "This variable represents the next to last index for the 
      shelfBusTestPingFailuresTable."
::= { shelfBusTestPingFailuresEntry 1 }

shelfBusTestPingFailuresRxCardIndex OBJECT-TYPE
   SYNTAX     Integer32 (0..15)
   ACCESS     not-accessible
   STATUS     mandatory
   DESCRIPTION
     "This variable represents the final index for the 
      shelfBusTestPingFailuresTable."
::= { shelfBusTestPingFailuresEntry 2 }

shelfBusTestPingFailuresValue OBJECT-TYPE
   SYNTAX     Unsigned32 (0..4294967295)
   ACCESS     read-only
   STATUS     mandatory
   DESCRIPTION
     "This variable represents an individual value for the
      shelfBusTestPingFailuresTable."
::= { shelfBusTestPingFailuresEntry 3 }


-- PcsTest
-- The PcsTest component allows automated tests of the Shelf to be 
-- controlled for regular execution.

shelfTest OBJECT IDENTIFIER ::= { shelf 4 }



shelfTestRowStatusTable OBJECT-TYPE
   SYNTAX     SEQUENCE OF ShelfTestRowStatusEntry
   ACCESS     not-accessible
   STATUS     mandatory
   DESCRIPTION
     "This entry controls the addition and deletion of 
      shelfTest components."
::= { shelfTest 1 }

shelfTestRowStatusEntry OBJECT-TYPE
   SYNTAX     ShelfTestRowStatusEntry
   ACCESS     not-accessible
   STATUS     mandatory
   DESCRIPTION
     "A single entry in the table represents a single 
      shelfTest component."
   INDEX {
      shelfIndex,
      shelfTestIndex }
::= { shelfTestRowStatusTable 1 }

ShelfTestRowStatusEntry ::= SEQUENCE {
   shelfTestRowStatus
      RowStatus,
   shelfTestComponentName
      DisplayString,
   shelfTestStorageType
      StorageType,
   shelfTestIndex
      NonReplicated }

shelfTestRowStatus OBJECT-TYPE
   SYNTAX     RowStatus 
   ACCESS     read-only
   STATUS     mandatory
   DESCRIPTION
     "This variable is used as the basis for SNMP naming of
      shelfTest components.
      These components cannot be added nor deleted."
::= { shelfTestRowStatusEntry 1 }

shelfTestComponentName OBJECT-TYPE
   SYNTAX     DisplayString 
   ACCESS     read-only
   STATUS     mandatory
   DESCRIPTION
     "This variable provides the component's string name for
      use with the ASCII Console Interface"
::= { shelfTestRowStatusEntry 2 }

shelfTestStorageType OBJECT-TYPE
   SYNTAX     StorageType 
   ACCESS     read-only
   STATUS     mandatory
   DESCRIPTION
     "This variable represents the storage type value for the
      shelfTest tables."
::= { shelfTestRowStatusEntry 4 }

shelfTestIndex OBJECT-TYPE
   SYNTAX     NonReplicated 
   ACCESS     not-accessible
   STATUS     mandatory
   DESCRIPTION
     "This variable represents the index for the shelfTest tables."
::= { shelfTestRowStatusEntry 10 }

shelfTestProvTable OBJECT-TYPE
   SYNTAX     SEQUENCE OF ShelfTestProvEntry
   ACCESS     not-accessible
   STATUS     mandatory
   DESCRIPTION
     "This group contains provisionable attributes of the Test component."
::= { shelfTest 10 }

shelfTestProvEntry OBJECT-TYPE
   SYNTAX     ShelfTestProvEntry
   ACCESS     not-accessible
   STATUS     mandatory
   DESCRIPTION
     "An entry in the shelfTestProvTable."
   INDEX {
      shelfIndex,
      shelfTestIndex }
::= { shelfTestProvTable 1 }

ShelfTestProvEntry ::= SEQUENCE {
   shelfTestAutomaticBusClockTest
      INTEGER }

shelfTestAutomaticBusClockTest OBJECT-TYPE
   SYNTAX     INTEGER  {
                 enabled(0),
                 disabled(1) }
   ACCESS     read-write
   STATUS     mandatory
   DESCRIPTION
     "This attribute specifies whether or not a bus clock source test is 
      automatically executed after a clock source's LP state changes, and 
      after failure or recovery of the active CP bus clock source. Since 
      tests of an alternate bus clock source may cause a minor loss of 
      traffic, the attribute is set to disabled by default.
      If set to enabled, a bus clock source test is automatically executed. 
      If the status of the corresponding Shelf Bus clockSourceStatus is 
      changed after the test, an alarm is issued if the status is one of the 
      following: ok, failed, or unknown.
      If set to disabled, no bus clock source test is automatically 
      executed. However, a test can be executed by the RUN command. If 
      the status is changed after the test, an alarm is issued if the status is 
      one of the following: ok, or failed."
   DEFVAL     { disabled }
::= { shelfTestProvEntry 1 }

shelfTestSetupTable OBJECT-TYPE
   SYNTAX     SEQUENCE OF ShelfTestSetupEntry
   ACCESS     not-accessible
   STATUS     mandatory
   DESCRIPTION
     "This attribute group contains the attributes that govern the operation 
      of a shelf test."
::= { shelfTest 11 }

shelfTestSetupEntry OBJECT-TYPE
   SYNTAX     ShelfTestSetupEntry
   ACCESS     not-accessible
   STATUS     mandatory
   DESCRIPTION
     "An entry in the shelfTestSetupTable."
   INDEX {
      shelfIndex,
      shelfTestIndex }
::= { shelfTestSetupTable 1 }

ShelfTestSetupEntry ::= SEQUENCE {
   shelfTestType
      INTEGER }

shelfTestType OBJECT-TYPE
   SYNTAX     INTEGER  {
                 busClock(0) }
   ACCESS     read-write
   STATUS     mandatory
   DESCRIPTION
     "type
      The attribute determines the test to be executed when the RUN
      command is applied to the component. Note that running a 
      busClock test may cause a minor loss of traffic."
   DEFVAL     { busClock }
::= { shelfTestSetupEntry 1 }

shelfTestResultsTable OBJECT-TYPE
   SYNTAX     SEQUENCE OF ShelfTestResultsEntry
   ACCESS     not-accessible
   STATUS     mandatory
   DESCRIPTION
     "This attribute group contains the results of the Shelf Test that is 
      currently running; if no test is running, the attribute group contains 
      the results of the most recently completed Shelf Test. The attributes 
      of the Results group are reset to their initial values whenever a 
      corresponding Shelf Test is run or the corresponding attribute of the 
      Setup group is set."
::= { shelfTest 12 }

shelfTestResultsEntry OBJECT-TYPE
   SYNTAX     ShelfTestResultsEntry
   ACCESS     not-accessible
   STATUS     mandatory
   DESCRIPTION
     "An entry in the shelfTestResultsTable."
   INDEX {
      shelfIndex,
      shelfTestIndex }
::= { shelfTestResultsTable 1 }

ShelfTestResultsEntry ::= SEQUENCE {
   shelfTestBusClockTestResult
      INTEGER }

shelfTestBusClockTestResult OBJECT-TYPE
   SYNTAX     INTEGER  {
                 noTest(0),
                 fail(1),
                 pass(2) }
   ACCESS     read-only
   STATUS     mandatory
   DESCRIPTION
     "busClockTestResult
      This attribute records the result of the bus clock manual test. The 
      result can be one of the following values.
      pass     : the test passed
      fail       : the test failed
      noTest  : the test was not executed when RUN command is issued, 
      because the shelf was in single bus mode."
::= { shelfTestResultsEntry 1 }


-- Module wide provisioning data is used to define a number of 
-- attributes used by various systems within the module.

mod OBJECT IDENTIFIER ::= { components 16 }



modRowStatusTable OBJECT-TYPE
   SYNTAX     SEQUENCE OF ModRowStatusEntry
   ACCESS     not-accessible
   STATUS     mandatory
   DESCRIPTION
     "This entry controls the addition and deletion of 
      mod components."
::= { mod 1 }

modRowStatusEntry OBJECT-TYPE
   SYNTAX     ModRowStatusEntry
   ACCESS     not-accessible
   STATUS     mandatory
   DESCRIPTION
     "A single entry in the table represents a single 
      mod component."
   INDEX {
      modIndex }
::= { modRowStatusTable 1 }

ModRowStatusEntry ::= SEQUENCE {
   modRowStatus
      RowStatus,
   modComponentName
      DisplayString,
   modStorageType
      StorageType,
   modIndex
      NonReplicated }

modRowStatus OBJECT-TYPE
   SYNTAX     RowStatus 
   ACCESS     read-only
   STATUS     mandatory
   DESCRIPTION
     "This variable is used as the basis for SNMP naming of
      mod components.
      These components cannot be added nor deleted."
::= { modRowStatusEntry 1 }

modComponentName OBJECT-TYPE
   SYNTAX     DisplayString 
   ACCESS     read-only
   STATUS     mandatory
   DESCRIPTION
     "This variable provides the component's string name for
      use with the ASCII Console Interface"
::= { modRowStatusEntry 2 }

modStorageType OBJECT-TYPE
   SYNTAX     StorageType 
   ACCESS     read-only
   STATUS     mandatory
   DESCRIPTION
     "This variable represents the storage type value for the
      mod tables."
::= { modRowStatusEntry 4 }

modIndex OBJECT-TYPE
   SYNTAX     NonReplicated 
   ACCESS     not-accessible
   STATUS     mandatory
   DESCRIPTION
     "This variable represents the index for the mod tables."
::= { modRowStatusEntry 10 }

modProvTable OBJECT-TYPE
   SYNTAX     SEQUENCE OF ModProvEntry
   ACCESS     not-accessible
   STATUS     mandatory
   DESCRIPTION
     "Mod Provisionable
      This group provides attributes that are used by internal and external 
      systems to identify the module."
::= { mod 10 }

modProvEntry OBJECT-TYPE
   SYNTAX     ModProvEntry
   ACCESS     not-accessible
   STATUS     mandatory
   DESCRIPTION
     "An entry in the modProvTable."
   INDEX {
      modIndex }
::= { modProvTable 1 }

ModProvEntry ::= SEQUENCE {
   modNodeId
      Unsigned32,
   modNodeName
      AsciiString,
   modNamsId
      Unsigned32,
   modRegionId
      Unsigned32,
   modNodePrefix
      AsciiString }

modNodeId OBJECT-TYPE
   SYNTAX     Unsigned32 (1..4095)
   ACCESS     read-write
   STATUS     mandatory
   DESCRIPTION
     "The nodeId is a number that uniquely identifies a Magellan Passport 
      module in a Passport network.
      
      Changing the value of the nodeId will cause the node to restart."
::= { modProvEntry 1 }

modNodeName OBJECT-TYPE
   SYNTAX     AsciiString (SIZE (1..12))
   ACCESS     read-write
   STATUS     mandatory
   DESCRIPTION
     "The nodeName is a 12 character ASCII string that is unique to every 
      Passport module in a Passport network. This name is the component 
      instance value of EM - the root of the Passport component 
      hierarchy. It has, therefore, the same restriction and behaviour as 
      any ascii string instance value, e.g., it is converted to upper case.
      
      Note that the EM component is typically suppressed on output.
      
      Changing the value of the nodeName will cause the node to restart."
   DEFVAL     { '4e4f4e414d45'H }  -- "NONAME"
::= { modProvEntry 2 }

modNamsId OBJECT-TYPE
   SYNTAX     Unsigned32 (256..49151)
   ACCESS     read-write
   STATUS     mandatory
   DESCRIPTION
     "This attribute stores the Network Administration (Nams) Identifier 
      associated with the Passport node. It must be unique across the 
      entire network of Passport nodes supporting the transport of DPN 
      traffic as well as all RMs and AMs in the network.
      
      The namsId must be set when a DpnAddressPlan component is 
      configured on an Passport node.
      
      The namsId is used in the accounting record, statistics record and in 
      time change accounting record and identifies nodes in these records.
      
      The Nams Id is to be assigned by the network administrator.
      Value 49151 indicates that no Nams Id was assigned to the module.
      
      Changing the value of the namsId will cause the node to restart."
   DEFVAL     { 49151 }
::= { modProvEntry 3 }

modRegionId OBJECT-TYPE
   SYNTAX     Unsigned32 (0..126)
   ACCESS     read-write
   STATUS     mandatory
   DESCRIPTION
     "This attribute identifies the Topology Region to which the node 
      belongs. Nodes will only exchange topological information with 
      connected nodes in the same region.
      
      The default value of 0 indicates that no regionId has been assigned 
      to the module. A module using the default regionId belongs to the 
      same region as the first neighbour which stages with it using a non-
      zero regionId. If another neighbour tries to stage using a different 
      non-zero regionId, the trunk will not be allowed to come up. 
      
      Changing the value of the regionId will cause the node to restart."
   DEFVAL     { 0 }
::= { modProvEntry 4 }

modNodePrefix OBJECT-TYPE
   SYNTAX     AsciiString (SIZE (0..26))
   ACCESS     read-write
   STATUS     mandatory
   DESCRIPTION
     "This attribute specifies an NSAP prefix which is distributed to all 
      other Passport nodes within a Topology region and by which this 
      node can be identified. This prefix is used by PORS, PNNI routing, 
      and Data Shunts.
      
      PORS calls that use NSAP addressing (for example, CES) will look 
      for the node with the longest NSAP prefix that matches the called 
      party address. The NSAP prefixes that PORS matches against are 
      the nodePrefix and the alternatePorsPrefixes. 
      
      PNNI forms the default value of the nodeAddressPrefix under the 
      AtmPnni component with this NSAP prefix followed by a unique 
      MAC address. 
      
      Data Shunts uses the nodePrefix to form an NSAP address that is 
      registered with the Networking API. This NSAP address is used to 
      identify this node when establishing a Data Shunt.
      
      The value entered must be 26 characters long. All characters must 
      be hexadecimal with the following restrictions:
      - the first two characters must be either '39', '45', or '47'
      - if the first two characters are '45', the 18th character must be an 
      'f' or an 'F'"
   DEFVAL     { ''H }  -- ""
::= { modProvEntry 5 }

modNodePrefixesTable OBJECT-TYPE
   SYNTAX     SEQUENCE OF ModNodePrefixesEntry
   ACCESS     not-accessible
   STATUS     obsolete
   DESCRIPTION
     "This attribute specifies five different NSAP prefixes which are 
      distributed to all other Passport nodes within a Topology region and 
      by which this node can be identified. PORS calls that use NSAP 
      addressing (for example, CES) will look for the node with the 
      longest NSAP prefix that matches the called party address. The 
      default value of the nodeAddressPrefix under the AtmPnni 
      component is formed by the first NSAP prefix followed by a unique 
      MAC address. Each NSAP prefix may contain 40 hexadecimal 
      characters with the exception of the first prefix which has a 
      maximum length of 26 chracacters.
      
      This attribute was never deployed and will be removed prior to Gate 
      2.."
::= { mod 338 }

modNodePrefixesEntry OBJECT-TYPE
   SYNTAX     ModNodePrefixesEntry
   ACCESS     not-accessible
   STATUS     obsolete
   DESCRIPTION
     "An entry in the modNodePrefixesTable."
   INDEX {
      modIndex,
      modNodePrefixesIndex }
::= { modNodePrefixesTable 1 }

ModNodePrefixesEntry ::= SEQUENCE {
   modNodePrefixesIndex
      Integer32,
   modNodePrefixesValue
      AsciiString }

modNodePrefixesIndex OBJECT-TYPE
   SYNTAX     Integer32 (0..4)
   ACCESS     not-accessible
   STATUS     obsolete
   DESCRIPTION
     "This variable represents the modNodePrefixesTable
      specific index for the modNodePrefixesTable."
::= { modNodePrefixesEntry 1 }

modNodePrefixesValue OBJECT-TYPE
   SYNTAX     AsciiString (SIZE (0..40))
   ACCESS     read-write
   STATUS     obsolete
   DESCRIPTION
     "This variable represents an individual value for the
      modNodePrefixesTable."
::= { modNodePrefixesEntry 2 }

modAlternatePorsPrefixesTable OBJECT-TYPE
   SYNTAX     SEQUENCE OF ModAlternatePorsPrefixesEntry
   ACCESS     not-accessible
   STATUS     mandatory
   DESCRIPTION
     "This attribute specifies four NSAP prefixes which are distributed to 
      all other Passport nodes within a Topology region and by which this 
      node can be identified. These prefixes are used by PORS. 
      
      PORS calls that use NSAP addressing (for example, CES) will look 
      for the node with the longest NSAP prefix that matches the called 
      party address. The NSAP prefixes that PORS matches against are 
      the alternatePorsPrefixes and the nodePrefix. 
      
      These prefixes may contain up to 40 hexadecimal characters."
::= { mod 405 }

modAlternatePorsPrefixesEntry OBJECT-TYPE
   SYNTAX     ModAlternatePorsPrefixesEntry
   ACCESS     not-accessible
   STATUS     mandatory
   DESCRIPTION
     "An entry in the modAlternatePorsPrefixesTable."
   INDEX {
      modIndex,
      modAlternatePorsPrefixesIndex }
::= { modAlternatePorsPrefixesTable 1 }

ModAlternatePorsPrefixesEntry ::= SEQUENCE {
   modAlternatePorsPrefixesIndex
      Integer32,
   modAlternatePorsPrefixesValue
      AsciiString }

modAlternatePorsPrefixesIndex OBJECT-TYPE
   SYNTAX     Integer32 (0..3)
   ACCESS     not-accessible
   STATUS     mandatory
   DESCRIPTION
     "This variable represents the modAlternatePorsPrefixesTable
      specific index for the modAlternatePorsPrefixesTable."
::= { modAlternatePorsPrefixesEntry 1 }

modAlternatePorsPrefixesValue OBJECT-TYPE
   SYNTAX     AsciiString (SIZE (0..40))
   ACCESS     read-write
   STATUS     mandatory
   DESCRIPTION
     "This variable represents an individual value for the
      modAlternatePorsPrefixesTable."
::= { modAlternatePorsPrefixesEntry 2 }




-- 
-- Version and Compliance statements
-- 



-- Object-Group Statement:
-- A list of all current accessible leaf objects.

-- OBJECTS { shelfCommentText,
--           shelfBusOperationalState,
--           shelfBusTestClockSourceTestResultsValue,
--           modComponentName,
--           shelfCardMemoryCapacityValue,
--           modRowStatus,
--           shelfBusTestAdminState,
--           shelfCardMemoryUsageAvgValue,
--           shelfCardBusTapOperationalState,
--           shelfCardCommentText,
--           shelfStorageType,
--           shelfCardActiveFirmwareVersion,
--           shelfCardSparingConnectionStatus,
--           shelfBusTestRowStatus,
--           shelfBusTestElapsedTime,
--           modRegionId,
--           shelfTestBusClockTestResult,
--           shelfCardTestCustomizedPattern,
--           shelfCardTestFrmPriorities,
--           shelfCardUnknownStatus,
--           shelfCardStandbyStatus,
--           shelfCardBusTapSelfTestErrorCode,
--           shelfCardDiagTrapDataLineData,
--           shelfCardMemoryUsageAvgMinValue,
--           shelfCardDcardMemorySize,
--           shelfCardStorageType,
--           shelfCardProductCode,
--           shelfCardTestTargetCard,
--           shelfCardCpuUtilAvgMax,
--           shelfCardDcardStorageType,
--           shelfCardDcardProductCode,
--           shelfTestType,
--           modNamsId,
--           shelfCardBusTapAvailabilityStatus,
--           shelfComponentName,
--           shelfCardTestSizeValue,
--           shelfRowStatus,
--           shelfBusRowStatus,
--           shelfCardBusTapAlarmStatus,
--           shelfCardControlStatus,
--           shelfCardAdminState,
--           shelfBusTestOperationalState,
--           shelfCardDiagRecErrRowStatus,
--           shelfTestAutomaticBusClockTest,
--           shelfCardDiagRecErrStorageType,
--           shelfCardTestFrmTypes,
--           shelfCardRowStatus,
--           shelfCardTestDuration,
--           shelfCardMsgBlockUsageAvgMax,
--           modNodeName,
--           shelfCardDiagTrapDataComponentName,
--           shelfCardCpuUtilAvg,
--           shelfCardDiagComponentName,
--           shelfCardBusTapCardsTxTo,
--           shelfTestStorageType,
--           shelfCardDiagTrapDataLineComponentName,
--           shelfBusTestComponentName,
--           shelfBusAvailabilityStatus,
--           shelfCardComponentName,
--           shelfCardUsageState,
--           shelfCardMsgBlockUsageAvg,
--           shelfCardBusTapFrmCongestionErrors,
--           shelfCardDiagRecErrLineStorageType,
--           shelfCardCpuUtilAvgMin,
--           shelfCardBusTapClockErrors,
--           shelfBusProceduralStatus,
--           shelfCardTestStorageType,
--           modNodePrefix,
--           shelfCardLocalMsgBlockUsageAvg,
--           shelfCardBusTapFrmDeliveryErrors,
--           shelfCardOperationalState,
--           shelfCardBusTapProceduralStatus,
--           shelfCardSerialNumber,
--           shelfCardBusTapFailuresInEffect,
--           shelfBusClockSourceStatusValue,
--           shelfCardBusTapEndOfCellErrors,
--           shelfTestRowStatus,
--           shelfCardBusTapFrmSizeErrors,
--           shelfCardDcardComponentName,
--           shelfBusTestCauseOfTermination,
--           shelfCardTestAdminState,
--           shelfBusTestTestsDone,
--           shelfNumberOfSlots,
--           shelfCardDcardType,
--           shelfCardBusTapComponentName,
--           shelfCardTestElapsedTime,
--           shelfCardConfiguredLPsValue,
--           shelfCardBusTapFrmCollisionErrors,
--           shelfCardTestRowStatus,
--           shelfTestComponentName,
--           shelfCardSelfTestFault,
--           shelfCardMemoryUsageValue,
--           modStorageType,
--           shelfCardBusTapDependenciesInEffect,
--           shelfCardAvailabilityStatus,
--           shelfBusClockSource,
--           shelfBusTestSelfTestResultsValue,
--           shelfCardDiagTrapDataStorageType,
--           shelfCardDiagStorageType,
--           shelfCardAlarmStatus,
--           shelfCardTestUsageState,
--           shelfBusTestTimeRemaining,
--           shelfBusBusTapStatusValue,
--           shelfCardDiagTrapDataLineStorageType,
--           shelfBusTestPingFailuresValue,
--           shelfCardTimeInterval,
--           shelfCardFailureCause,
--           shelfCardMsgBlockUsageAvgMin,
--           shelfBusStorageType,
--           shelfCardDiagRecErrLineComponentName,
--           shelfBusTestUsageState,
--           shelfCardCurrentLpValue,
--           shelfBusStandbyStatus,
--           shelfCardDiagRecErrLineData,
--           shelfCardTestOperationalState,
--           shelfBusUnknownStatus,
--           shelfCardTestComponentName,
--           shelfCardBusTapCardsAvailable,
--           shelfCardDiagTrapDataRowStatus,
--           shelfCardPmRevisionCode,
--           shelfBusTestBroadcastTestResultsValue,
--           shelfCardDiagRowStatus,
--           shelfCardInactiveFirmwareVersion,
--           shelfCardImRevisionCode,
--           shelfCardMsgBlockCapacity,
--           shelfCardTestFrmPatternType,
--           shelfCardDiagTrapDataLineRowStatus,
--           modAlternatePorsPrefixesValue,
--           shelfCardBusTapUnknownStatus,
--           shelfCardBusTapStandbyStatus,
--           shelfBusUtilization,
--           shelfBusControlStatus,
--           shelfBusAdminState,
--           shelfCardCardType,
--           shelfCardCpuUtil,
--           shelfCardLocalMsgBlockCapacity,
--           shelfCardProceduralStatus,
--           shelfCardTestLoadingFrmDataValue,
--           shelfCardDcardRowStatus,
--           shelfBusTestPingTestsValue,
--           shelfCardLocalMsgBlockUsageMax,
--           shelfBusAlarmStatus,
--           shelfCardBusTapParityErrors,
--           shelfCardMsgBlockUsage,
--           shelfCardDiagRecErrComponentName,
--           shelfBusTestDuration,
--           modNodeId,
--           shelfCardSparingConnection,
--           shelfCardBusTapControlStatus,
--           shelfCardBusTapAdminState,
--           shelfBusOperatingMode,
--           shelfCardInsertedCardType,
--           shelfBusComponentName,
--           shelfCardLocalMsgBlockUsage,
--           shelfHardwareFailures,
--           shelfBusUsageState,
--           shelfCardBusTapRowStatus,
--           shelfCardTestCauseOfTermination,
--           shelfCardTestVerificationFrmDataValue,
--           shelfCardBusTapStorageType,
--           shelfCardTestTimeRemaining,
--           shelfCardBusTapFrmTimeoutErrors,
--           shelfBusTestStorageType,
--           shelfCardLocalMsgBlockUsageMin,
--           shelfCardDiagRecErrLineRowStatus,
--           shelfCardBusTapUsageState,
--           shelfCardMemoryUsageAvgMaxValue }
-- STATUS  mandatory
-- DESCRIPTION
--   "A list of all current accessible leaf objects."

shelfGroup OBJECT IDENTIFIER ::= { shelfMIB 1 }
shelfGroupBE OBJECT IDENTIFIER ::= { shelfGroup 5 }
shelfGroupBE01 OBJECT IDENTIFIER ::= { shelfGroupBE 2 }
shelfGroupBE01A OBJECT IDENTIFIER ::= { shelfGroupBE01 2 }



-- Agent-Capabilities Statement:

-- PRODUCT-RELEASE "Passport Release 7.0 Shelf."
-- STATUS          mandatory
-- DESCRIPTION     "Shelf MIB: MIB Version BE01A,
--                  Software Version BG00S4C."
-- SUPPORTS        Nortel-Magellan-Passport-ShelfMIB
--    INCLUDES     { shelfGroupBE01A }

shelfCapabilities OBJECT IDENTIFIER ::= { shelfMIB 3 }
shelfCapabilitiesBE OBJECT IDENTIFIER ::= { shelfCapabilities 5 }
shelfCapabilitiesBE01 OBJECT IDENTIFIER ::= { shelfCapabilitiesBE 2 }
shelfCapabilitiesBE01A OBJECT IDENTIFIER ::= { shelfCapabilitiesBE01 2 }





END
