USR-PPPLINK-MIB DEFINITIONS ::= BEGIN
          IMPORTS
               OBJECT-TYPE, MODULE-IDENTITY, Integer32, Counter32
                    FROM SNMPv2-SMI
					DisplayString FROM SNMPv2-TC
               common
                    FROM USR-DEFINITIONS-MIB
               usrPPPBundleInstance
                    FROM USR-PPPML-MIB;
    usrPPP  MODULE-IDENTITY
            LAST-UPDATED "200208231425Z"
            ORGANIZATION "CommWorks Corporation, a 3Com Company"
            CONTACT-INFO "Customer Support"
            DESCRIPTION
                "The commWorks enterprise defined MIB objects  for PPP Link."
--          REVISION "200208231425Z"
--          DESCRIPTION "Converted to SNMPv2 and modified usrPPPLinkInterfaceName."
            ::= { common 11 }
          usrPPPLk OBJECT IDENTIFIER ::= { usrPPP 3 }
          --
          -- The PPP Link Group.
          --
          -- The following objects reflect the values of the option
          -- parameters used over the PPP Link
          --   usrPPPLinkInstance
          --   usrPPPLinkOperStatus
          --   usrPPPLinkPhysicalIndex
          --   usrPPPLinkLocalMRU
          --   usrPPPLinkRemoteMRU
          --   usrPPPLinkLocalToPeerACCMap
          --   usrPPPLinkPeerToLocalACCMap
          --   usrPPPLinkLocalToRemoteProtocolCompression
          --   usrPPPLinkRemoteToLocalProtocolCompression
          --   usrPPPLinkLocalToRemoteACCompression
          --   usrPPPLinkRemoteToLocalACCompression
          --   usrPPPLinkTxTotalFrames
          --   usrPPPLinkTxTotalBytes
          --   usrPPPLinkRxPacketTooLongs
          --   usrPPPLinkRxTotalFrames
          --   usrPPPLinkRxTotalBytes
          --
          -- These values are not available until after the PPP Option
          -- negotiation has completed, which is indicated by the link
          -- reaching the open state (i.e., ifOperStatus is set to
          -- up).
          --
          -- Therefore, when ifOperStatus is not up
          -- the contents of these objects is undefined. The value
          -- returned when accessing the objects is an implementation
          -- dependent issue.
          usrPPPLinkTable   OBJECT-TYPE
               SYNTAX       SEQUENCE OF UsrPPPLinkEntry
               MAX-ACCESS   not-accessible
               STATUS       current
               DESCRIPTION
                         "Table containing the Link parameters and
                         statistics for a local PPP entity."
               ::= { usrPPPLk 1 }
          usrPPPLinkEntry   OBJECT-TYPE
               SYNTAX       UsrPPPLinkEntry
               MAX-ACCESS   not-accessible
               STATUS       current
               DESCRIPTION
                         "Status information for a PPP link."
               INDEX     { usrPPPBundleInstance, usrPPPLinkInstance }
               ::= { usrPPPLinkTable 1 }
          UsrPPPLinkEntry ::= SEQUENCE {
               usrPPPLinkInstance
                    Integer32,
               usrPPPLinkOperStatus
                    INTEGER,
               usrPPPLinkPhysicalIndex
                    Integer32,
               usrPPPLinkInterfaceName
                    DisplayString,
               usrPPPLinkLocalMRU
                    Integer32,
               usrPPPLinkRemoteMRU
                    Integer32,
               usrPPPLinkLocalToPeerACCMap
                    OCTET STRING,
               usrPPPLinkPeerToLocalACCMap
                    OCTET STRING,
               usrPPPLinkLocalToRemoteProtocolCompression
                    INTEGER,
               usrPPPLinkRemoteToLocalProtocolCompression
                    INTEGER,
               usrPPPLinkLocalToRemoteACCompression
                    INTEGER,
               usrPPPLinkRemoteToLocalACCompression
                    INTEGER,
               usrPPPLinkTxTotalFrames
                    Counter32,
               usrPPPLinkTxTotalBytes
                    Counter32,
               usrPPPLinkRxPacketTooLongs
                    Counter32,
               usrPPPLinkRxTotalFrames
                    Counter32,
               usrPPPLinkRxTotalBytes
                    Counter32
          }
          usrPPPLinkInstance   OBJECT-TYPE
               SYNTAX    Integer32
               MAX-ACCESS    read-only
               STATUS    current
               DESCRIPTION
                         "The unique identifier of the instance of PPP
                         link to which this entry corresponds."
               ::= { usrPPPLinkEntry 1 }
          usrPPPLinkOperStatus   OBJECT-TYPE
               SYNTAX    INTEGER {opened(1), not-opened(2)}
               MAX-ACCESS    read-only
               STATUS    current
               DESCRIPTION
                         "The operational status of the Link control
                         protocol. If the value of this object is up
                         then the finite state machine for the Link
                         control protocol has reached the Opened state."
               ::= { usrPPPLinkEntry 2 }
          usrPPPLinkPhysicalIndex   OBJECT-TYPE
               SYNTAX    Integer32(0..2147483647)
               MAX-ACCESS    read-only
               STATUS    current
               DESCRIPTION
                         "The value of ifIndex that identifies the
                         lower-level interface over which this PPP Link
                         is operating. This interface would usually be
                         an HDLC or RS-232 type of interface. If there
                         is no lower-layer interface element, or there
                         is no ifEntry for the element, or the element
                         can not be identified, then the value of this
                         object is 0."
               ::= { usrPPPLinkEntry 3 }
          usrPPPLinkInterfaceName   OBJECT-TYPE
               SYNTAX    DisplayString (SIZE(0..32))
               MAX-ACCESS    read-only
               STATUS    current
               DESCRIPTION
                         "The value of the Name that identifies the
                         lower-level interface over which this PPP Link
                         is operating. This interface would usually be
                         an HDLC or RS-232 type of interface. If there
                         is no lower-layer interface element, or there
                         is no ifEntry for the element, or the element
                         can not be identified, then the value of this
                         object is NULL."
               ::= { usrPPPLinkEntry 4 }
          usrPPPLinkLocalMRU   OBJECT-TYPE
               SYNTAX    Integer32(1..2147483647)
               MAX-ACCESS    read-only
               STATUS    current
               DESCRIPTION
                         "The current value of the MRU for the local PPP
                         Entity. This value is the MRU that the remote
                         entity is using when sending packets to the
                         local PPP entity. The value of this object is
                         meaningful only when the link has reached the
                         open state (usrPPPLinkOperStatus is up)."
               ::= { usrPPPLinkEntry 5 }
          usrPPPLinkRemoteMRU   OBJECT-TYPE
               SYNTAX    Integer32(1..2147483647)
               MAX-ACCESS    read-only
               STATUS    current
               DESCRIPTION
                         "The current value of the MRU for the remote
                         PPP Entity. This value is the MRU that the
                         local entity is using when sending packets to
                         the remote PPP entity. The value of this object
                         is meaningful only when the link has reached
                         the open state (usrPPPLinkOperStatus is up)."
               ::= { usrPPPLinkEntry 6 }
          usrPPPLinkLocalToPeerACCMap   OBJECT-TYPE
               SYNTAX    OCTET STRING (SIZE (4))
               MAX-ACCESS    read-only
               STATUS    current
               DESCRIPTION
                         "The current value of the ACC Map used for
                         sending packets from the local PPP entity to
                         the remote PPP entity. The value of this object
                         is meaningful only when the link has reached
                         the open state (usrPPPLinkOperStatus is up)."
               ::= { usrPPPLinkEntry 7 }
          usrPPPLinkPeerToLocalACCMap   OBJECT-TYPE
               SYNTAX    OCTET STRING (SIZE (4))
               MAX-ACCESS    read-only
               STATUS    current
               DESCRIPTION
                         "The ACC Map used by the remote PPP entity when
                         transmitting packets to the local PPP entity.
                         The value of this object is meaningful only
                         when the link has reached the open state
                         (usrPPPLinkOperStatus is up)."
               ::= { usrPPPLinkEntry 8 }
          usrPPPLinkLocalToRemoteProtocolCompression
               OBJECT-TYPE
               SYNTAX    INTEGER {
                         enabled(1),
                         disabled(2)
                    }
               MAX-ACCESS    read-only
               STATUS    current
               DESCRIPTION
                         "Indicates whether the local PPP entity will
                         use Protocol Compression when transmitting
                         packets to the remote PPP entity. The value of
                         this object is meaningful only when the link
                         has reached the open state (usrPPPLinkOperStatus
                         is up)."
               ::= { usrPPPLinkEntry 9 }
          usrPPPLinkRemoteToLocalProtocolCompression
               OBJECT-TYPE
               SYNTAX    INTEGER {
                         enabled(1),
                         disabled(2)
                    }
               MAX-ACCESS    read-only
               STATUS    current
               DESCRIPTION
                         "Indicates whether the remote PPP entity will
                         use Protocol Compression when transmitting
                         packets to the local PPP entity. The value of
                         this object is meaningful only when the link
                         has reached the open state (usrPPPLinkOperStatus
                         is up)."
               ::= { usrPPPLinkEntry 10 }
          usrPPPLinkLocalToRemoteACCompression   OBJECT-TYPE
               SYNTAX    INTEGER {
                         enabled(1),
                         disabled(2)
                    }
               MAX-ACCESS    read-only
               STATUS    current
               DESCRIPTION
                         "Indicates whether the local PPP entity will
                         use Address and Control Compression when
                         transmitting packets to the remote PPP entity.
                         The value of this object is meaningful only
                         when the link has reached the open state
                         (usrPPPLinkOperStatus is up)."
               ::= { usrPPPLinkEntry 11 }
          usrPPPLinkRemoteToLocalACCompression   OBJECT-TYPE
               SYNTAX    INTEGER {
                         enabled(1),
                         disabled(2)
                    }
               MAX-ACCESS    read-only
               STATUS    current
               DESCRIPTION
                         "Indicates whether the remote PPP entity will
                         use Address and Control Compression when
                         transmitting packets to the local PPP entity.
                         The value of this object is meaningful only
                         when the link has reached the open state
                         (usrPPPLinkOperStatus is up)."
               ::= { usrPPPLinkEntry 12 }
          usrPPPLinkTxTotalFrames   OBJECT-TYPE
               SYNTAX    Counter32
               MAX-ACCESS    read-only
               STATUS    current
               DESCRIPTION
                         "The total number of frames received from the PPP
                         application for transmission over this link.
                         The value of this object is meaningful only when the
                         link has reached the open state
                         (usrPPPLinkOperStatus is up)."
               ::= { usrPPPLinkEntry 13 }
          usrPPPLinkTxTotalBytes   OBJECT-TYPE
               SYNTAX    Counter32
               MAX-ACCESS    read-only
               STATUS    current
               DESCRIPTION
                         "The total number of bytes received from the PPP
                         application for transmission over this link. The
                         value of this object is meaningful only when the
                         link has reached the open state
                         (usrPPPLinkOperStatus is up)."
               ::= { usrPPPLinkEntry 14 }
          usrPPPLinkRxPacketTooLongs   OBJECT-TYPE
               SYNTAX    Counter32
               MAX-ACCESS    read-only
               STATUS    current
               DESCRIPTION
                         "The number of received packets that have been
                         discarded because their length exceeded the
                         MRU. NOTE, packets which are longer than the
                         MRU but which are successfully received and
                         processed are NOT included in this count."
               ::= { usrPPPLinkEntry 15 }
          usrPPPLinkRxTotalFrames   OBJECT-TYPE
               SYNTAX    Counter32
               MAX-ACCESS    read-only
               STATUS    current
               DESCRIPTION
                         "The total number of frames received from a lower
                         layer application over this link. The value of
                         this object is meaningful only when the link has
                         reached the open state (usrPPPLinkOperStatus is up)."
               ::= { usrPPPLinkEntry 16 }
          usrPPPLinkRxTotalBytes   OBJECT-TYPE
               SYNTAX    Counter32
               MAX-ACCESS    read-only
               STATUS    current
               DESCRIPTION
                         "The total number of bytes received from a lower
                         layer application over this link. The value of
                         this object is meaningful only when the link has
                         reached the open state (usrPPPLinkOperStatus is
                         up)."
               ::= { usrPPPLinkEntry 17 }
          --
          -- The PPP Authentication Group.
          --
          -- The following objects reflect the values of the option
          -- parameters used in the PPP Authentication Control Protocol
          --   usrPPPAuthOperStatus
          --   usrPPPAuthLclToRemProtocol
          --   usrPPPAuthRemToLclProtocol
          usrPPPAuthTable   OBJECT-TYPE
               SYNTAX    SEQUENCE OF UsrPPPAuthEntry
               MAX-ACCESS    not-accessible
               STATUS    current
               DESCRIPTION
                         "Table containing the Authentication status
                         information for a local PPP entity."
               ::= { usrPPPLk 2 }
          usrPPPAuthEntry   OBJECT-TYPE
               SYNTAX    UsrPPPAuthEntry
               MAX-ACCESS    not-accessible
               STATUS    current
               DESCRIPTION
                         "Authentication status information for a PPP link."
               INDEX     { usrPPPBundleInstance, usrPPPLinkInstance }
               ::= { usrPPPAuthTable 1 }
          UsrPPPAuthEntry ::= SEQUENCE {
               usrPPPAuthOperStatus
                    INTEGER,
               usrPPPAuthLclToRemProtocol
                    INTEGER,
               usrPPPAuthRemToLclProtocol
                    INTEGER
          }
          usrPPPAuthOperStatus   OBJECT-TYPE
               SYNTAX    INTEGER {
                         opened(1),
                         not-opened(2)
                    }
               MAX-ACCESS    read-only
               STATUS    current
               DESCRIPTION
                         "The operational status of the Authentication control
                         protocol. If the value of this object is up
                         then the finite state machine for the Authentication
                         control protocol has reached the Opened state."
               ::= { usrPPPAuthEntry 1 }
          usrPPPAuthLclToRemProtocol OBJECT-TYPE
               SYNTAX    INTEGER {
                        none(1),
                        pap(2),
                        chap(3),
                        any(4),
                        eapMD5(5),
                        msChap(6),
                        encryptedOnly(7),
                        radiusEapProxy(8)
                    }
               MAX-ACCESS    read-only
               STATUS    current
               DESCRIPTION
                         "This is the authentication protocol that was used
                         by the local PPP entity when it authenticated the
                         local PPP entity to the remote PPP entity. The
                         value of this object is meaningful only when the
                         authentication has reached the open state
                         (usrPPPAuthOperStatus is up)."
               ::= { usrPPPAuthEntry 2 }
          usrPPPAuthRemToLclProtocol OBJECT-TYPE
               SYNTAX    INTEGER {
                        none(1),
                        pap(2),
                        chap(3),
                        any(4),
                        eapMD5(5),
                        msChap(6),
                        encryptedOnly(7),
                        radiusEapProxy(8)
                    }
               MAX-ACCESS    read-only
               STATUS    current
               DESCRIPTION
                         "This is the authentication protocol that was used
                         by the remote PPP entity when it authenticated the
                         remote PPP entity to the local PPP entity. The
                         value of this object is meaningful only when the
                         authentication has reached the open state
                         (usrPPPAuthOperStatus is up)."
               ::= { usrPPPAuthEntry 3 }
END     -- End of USR-PPPLINK-MIB DEFINITIONS
-- ************************************************************************
--
--
--	usr_ip.mib
--
-- Author:         Jim Halpin
--
