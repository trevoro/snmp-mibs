-- PairGain IISP MIB Release 0.1
-- Revision Date:  02/11/2000
--
-- Copyright 2000 PairGain Technologies, Inc.  All Rights
-- Reserved.  Reproduction of this document is authorized on
-- condition that the foregoing copyright notice is included.
-- This PairGain SNMP Management Information Base Specification
-- (Specification) embodies PairGain's confidential and
-- proprietary intellectual property.  PairGain retains all
-- title and ownership in the Specification, including any
-- revisions.
--
-- It is PairGain's intent to encourage the widespread use of
-- this Specification in connection with the management of
-- PairGain products. PairGain grants vendors, end-users,
-- and other interested parties a non-exclusive license to
-- use this Specification in connection with the management
-- of PairGain products.
--
-- This Specification is supplied "AS IS," and PairGain makes
-- no warranty, either expressed or implied, as to the use,
-- operation, condition, or performance of the Specification.
--
-- Revision History
--------------------------------------------------------------
-- Date            Ver     Programmer  Description
--------------------------------------------------------------
-- 02/11/2000      0.1     F. Murolo     Initial Version

PAIRGAIN-IISP-MIB DEFINITIONS ::= BEGIN

IMPORTS
	MODULE-IDENTITY, OBJECT-TYPE, OBJECT-IDENTITY,
        Counter32, Gauge32, Integer32, enterprises	FROM SNMPv2-SMI
	TEXTUAL-CONVENTION, RowStatus, DisplayString,
	TimeStamp, TruthValue 				FROM SNMPv2-TC
	InterfaceIndex, ifIndex				FROM IF-MIB
	AtmTrafficDescrParamIndex			FROM ATM-MIB
	AtmAddr						FROM ATM-TC-MIB
	pgIISPMIB					FROM PAIRGAIN-COMMON-HD-MIB
	MODULE-COMPLIANCE, OBJECT-GROUP			FROM SNMPv2-CONF;

pgIISP	 	MODULE-IDENTITY
 			LAST-UPDATED "0002020000Z"
    		ORGANIZATION "Pairgain Technologies Inc."
		  	CONTACT-INFO    "
                    14402 Franklin Avenue
                    Tustin, CA  92780
                    "
       		DESCRIPTION
            	"Initial version of the MIB for monitoring and controlling
             	IISP routing."
        		::= { pgIISPMIB 1 }


pgIISPMIBObjects OBJECT IDENTIFIER ::= { pgIISP 1 }

PgAtmAddrPrefix ::= TEXTUAL-CONVENTION
        STATUS        current
        DESCRIPTION
            "A prefix of one or more ATM End System Addresses.  The
             significant portion of a prefix is padded with zeros on the
             right to fill 20 octets."
        SYNTAX        OCTET STRING (SIZE(20))


PgAtmPrefixLength ::= TEXTUAL-CONVENTION
        STATUS        current
        DESCRIPTION
            "The number of bits that are significant in an ATM address
            ."
        SYNTAX        Integer32 (0..152)

-- Network-Prefixes for an ATM Address use this data type:
NetPrefix ::= OCTET STRING (SIZE (8 | 13))

-- In both the AtmAddress and NetPrefix conventions, Native E.164 addresses
-- are represented as 8 octets.
-- In contrast, an NSAP-encoded address is 20 octets, and an NSAP-encoded
-- network prefix is 13 octets long.

-- Table of routes from nodes to reachable addresses

pgIISPRouteAddrIndexNext  OBJECT-TYPE
          SYNTAX         INTEGER (0..2147483647)
          MAX-ACCESS     read-only
          STATUS         current
          DESCRIPTION
           "This object contains an appropriate value to
            be used for pgIISPRouteAddrIndex when creating
            entries in the pgIISPRouteAddrTable.  The value
            0 indicates that no unassigned entries are
            available. To obtain the atmVcCrossConnectIndex
            value for a new entry, the manager issues a
            management protocol retrieval operation to obtain
            the current value of this object.  After each
            retrieval, the agent should modify the value to
            the next unassigned index.
            After a manager retrieves a value the agent will
            determine through its local policy when this index
            value will be made available for reuse."
          ::= { pgIISPMIBObjects 1 }

pgIISPRouteAddrTable OBJECT-TYPE
        SYNTAX        SEQUENCE OF PgIISPRouteAddrEntry
        MAX-ACCESS    not-accessible
        STATUS        current
        DESCRIPTION
            "A table containing all the attributes necessary to
             determine what the entity believes is reachable in
             terms of ATM End System Addresses and to determine which
             nodes are advertising this reachability.  This table is
             also used to configure static routes to reachable address
             prefixes.  The local node index that received the
             reachability information, reachable address, address prefix
             length, and an index that distinguishes between multiple
             listings of connectivity to a given address prefix from a
             given local node are combined to form an instance ID for
             this object.."
        ::= { pgIISPMIBObjects 2 }

pgIISPRouteAddrEntry OBJECT-TYPE
        SYNTAX        PgIISPRouteAddrEntry
        MAX-ACCESS    not-accessible
        STATUS        current
        DESCRIPTION
            "An entry in the table, containing information about a
             reachable address prefix."
        INDEX         { pgIISPRouteAddrIndex,
			pgIISPRouteAddrAddress,
                        pgIISPRouteAddrPrefixLength
                         }
        ::= { pgIISPRouteAddrTable 1 }

PgIISPRouteAddrEntry ::=
        SEQUENCE {
                pgIISPRouteAddrIndex              Integer32,
                pgIISPRouteAddrRowStatus          RowStatus,
		pgIISPRouteAddrAddress            PgAtmAddrPrefix,
                pgIISPRouteAddrPrefixLength       PgAtmPrefixLength,
                pgIISPRouteAddrIfIndex            InterfaceIndex,
		pgIISPRouteAddrType               INTEGER,
		pgIISPRouteAddrAdminStatus        INTEGER,
		pgIISPRouteAddrOperStatus         INTEGER,
                pgIISPRouteAddrTimeStamp          TimeStamp
                }

pgIISPRouteAddrIndex OBJECT-TYPE
        SYNTAX        Integer32 (1..65535)
        MAX-ACCESS    read-only
        STATUS        current
        DESCRIPTION
            "An index into the set of listings of connectivity to a
             given route."
        ::= { pgIISPRouteAddrEntry 1 }

pgIISPRouteAddrRowStatus OBJECT-TYPE
        SYNTAX        RowStatus
        MAX-ACCESS    read-create
        STATUS        current
        DESCRIPTION
            "To create, delete, activate and de-activate a reachable
             address prefix."
        ::= { pgIISPRouteAddrEntry 2 }

pgIISPRouteAddrAddress OBJECT-TYPE
        SYNTAX        PgAtmAddrPrefix
        MAX-ACCESS    read-only
        STATUS        current
        DESCRIPTION
            "The value of the ATM End System Address prefix."
        ::= { pgIISPRouteAddrEntry 3 }

pgIISPRouteAddrPrefixLength OBJECT-TYPE
        SYNTAX        PgAtmPrefixLength
        MAX-ACCESS    read-only
        STATUS        current
        DESCRIPTION
            "The prefix length to be applied to the ATM End System
             Address prefix."
        ::= { pgIISPRouteAddrEntry 4 }

pgIISPRouteAddrIfIndex OBJECT-TYPE
        SYNTAX        InterfaceIndex
        MAX-ACCESS    read-write
        STATUS        current
        DESCRIPTION
            "The local interface over which the reachable address can be
             reached.  The value zero indicates an unknown interface or
             reachability through a remote node."
	 ::= { pgIISPRouteAddrEntry 5 }


pgIISPRouteAddrType OBJECT-TYPE
        SYNTAX        INTEGER {
                                other(1), -- not specified by this MIB
                                reject(2), -- route which discards
                                           -- traffic
                                internal(3),
                                exterior(4)
        }
        MAX-ACCESS    read-write
        STATUS        current
        DESCRIPTION
            "The type (e.g. internal or exterior) of reachability from
             the advertising node to the address prefix.

             Reject(2) refers to an address prefix which, if matched,
             indicates that the message should be discarded as
             unreachable. This is used in some protocols as a means of
             correctly aggregating routes."
	DEFVAL { exterior }
        ::= { pgIISPRouteAddrEntry 6 }

pgIISPRouteAddrAdminStatus OBJECT-TYPE
        SYNTAX        INTEGER {
                                inactive(1),
                                active(2)
	}
        MAX-ACCESS    read-write
        STATUS        current
        DESCRIPTION
            "Indicates whether the route is configured to be used."
        ::= { pgIISPRouteAddrEntry 7 }


pgIISPRouteAddrOperStatus OBJECT-TYPE
        SYNTAX        INTEGER {
                                inactive(1),
                                active(2),
                                advertised(3)
                                }
        MAX-ACCESS    read-write
        STATUS        current
        DESCRIPTION
            "Indicates whether the reachable address prefix is
             operationally valid and whether it is being advertised by
             this node."
        ::= { pgIISPRouteAddrEntry 8 }

pgIISPRouteAddrTimeStamp OBJECT-TYPE
        SYNTAX        TimeStamp
        MAX-ACCESS    read-write
        STATUS        current
        DESCRIPTION
            "Indicates when the connectivity from the advertising node
             to the reachable address prefix became known to the local
             node."
        ::= { pgIISPRouteAddrEntry 9 }



--                  The NetPrefix Table
--
-- The Network Prefix Table is implemented by the user-side.

pgIISPNetPrefixIndexNext  OBJECT-TYPE
          SYNTAX         INTEGER (0..2147483647)
          MAX-ACCESS     read-only
          STATUS         current
          DESCRIPTION
           "This object contains an appropriate value to
            be used for pgIISPRouteAddrIndex when creating
            entries in the pgIISPRouteAddrTable.  The value
            0 indicates that no unassigned entries are
            available. To obtain the atmVcCrossConnectIndex
            value for a new entry, the manager issues a
            management protocol retrieval operation to obtain
            the current value of this object.  After each
            retrieval, the agent should modify the value to
            the next unassigned index.
            After a manager retrieves a value the agent will
            determine through its local policy when this index
            value will be made available for reuse."
          ::= { pgIISPMIBObjects 3 }

pgIISPNetPrefixTable OBJECT-TYPE
        SYNTAX  SEQUENCE OF PgIISPNetPrefixEntry
        MAX-ACCESS  not-accessible
        STATUS  current
        DESCRIPTION
                "A table implemented by the user-side, containing the
                network-prefix(es) for ATM-layer addresses in effect on
                the user side of the UNI."
        ::= { pgIISPMIBObjects 4 }

pgIISPNetPrefixEntry OBJECT-TYPE
        SYNTAX  PgIISPNetPrefixEntry
        MAX-ACCESS  not-accessible
        STATUS  current
        DESCRIPTION
                "Information about a single network-prefix for
                ATM-layer addresses in effect on the user-side.
                Note that the index variable atmNetPrefixPrefix is a
                variable-length string, and as such the rule for
                variable-length strings in section 4.1.6 of RFC 1212
                applies."

        INDEX   { pgIISPNetPrefixIndex,
		  pgIISPNetPrefixPort,
		  pgIISPNetPrefixPrefix }
        ::= { pgIISPNetPrefixTable 1 }

PgIISPNetPrefixEntry ::=
        SEQUENCE {
	  	pgIISPNetPrefixIndex		Integer32,
                pgIISPNetPrefixRowStatus        RowStatus,
                pgIISPNetPrefixPort  		INTEGER,
                pgIISPNetPrefixPrefix   	NetPrefix,
		pgIISPNetPrefixFormat   	INTEGER,
		pgIISPNetPrefixLength		Integer32,
	        pgIISPNetPrefixStatus   	INTEGER
        }

pgIISPNetPrefixIndex OBJECT-TYPE
        SYNTAX        Integer32 (1..65535)
        MAX-ACCESS    read-only
        STATUS        current
        DESCRIPTION
            "An index into the set of listings of connectivity to a
             given address prefix."
        ::= { pgIISPNetPrefixEntry 1 }

pgIISPNetPrefixRowStatus OBJECT-TYPE
        SYNTAX        RowStatus
        MAX-ACCESS    read-create
        STATUS        current
        DESCRIPTION
            "To create, delete, activate and de-activate a net prefix entry."
        ::= { pgIISPNetPrefixEntry 2 }

pgIISPNetPrefixPort OBJECT-TYPE
        SYNTAX  INTEGER (0..2147483647)
        MAX-ACCESS  read-only
        STATUS  current
        DESCRIPTION
		"A unique value which identifies the UNI port for
                which the network prefix for ATM addresses is in
                effect.  The value of 0 has the special meaning of
                identifying the local UNI."
        ::= { pgIISPNetPrefixEntry 3 }

pgIISPNetPrefixPrefix  OBJECT-TYPE
        SYNTAX  NetPrefix
        MAX-ACCESS  read-only
        STATUS  current
        DESCRIPTION
                "The network prefix for ATM addresses which is in
                effect on the user side of the ATM UNI port."
        ::= { pgIISPNetPrefixEntry 4 }

pgIISPNetPrefixFormat  OBJECT-TYPE
        SYNTAX  INTEGER { dcc(1), icd(2), e164(3) }
        MAX-ACCESS  read-write
        STATUS  current
        DESCRIPTION
                "ATM address format."
	 DEFVAL { dcc }
	 ::= { pgIISPNetPrefixEntry 5 }

pgIISPNetPrefixLength OBJECT-TYPE
        SYNTAX        Integer32 (0..152)
        MAX-ACCESS    read-write
        STATUS        current
        DESCRIPTION
            "The number of bits that are significant in an ATM address
             prefix used."
	 ::= { pgIISPNetPrefixEntry 6 }

pgIISPNetPrefixStatus  OBJECT-TYPE
        SYNTAX  INTEGER { valid(1), invalid(2) }
        MAX-ACCESS  read-write
        STATUS  current
        DESCRIPTION
                "An indication of the validity of the network prefix
                for ATM addresses on the user side of the UNI port.
                To configure a new network prefix in this table, the
                network-side must set the appropriate instance of this
                object to the value valid(1).  To delete an existing
                network prefix in this table, the network-side must
                set the appropriate instance of this object to the
                value invalid(2).

                If circumstances occur on the user-side which cause a
                prefix to become invalid, the user-side modifies the
                value of the appropriate instance of this object to invalid(2).

                Whenever the value of this object for a particular
                prefix becomes invalid(2), the conceptual row for that
                prefix may be removed from the table at any time,
                either immediately or subsequently."
        ::= { pgIISPNetPrefixEntry 7 }

pgIISPAtmAddrPrefix OBJECT-TYPE
	SYNTAX		AtmAddr
	MAX-ACCESS	read-write
	STATUS		current
	DESCRIPTION
           	"The identifier assigned by a service provider.
            	This ATM address prefix is used by more than one line cards
		in the Avidia."
	::= { pgIISPMIBObjects 5 }

END
