BAS-EVENT-MIB DEFINITIONS ::= BEGIN

IMPORTS
    MODULE-IDENTITY, OBJECT-TYPE, IpAddress,
    Integer32                                           FROM SNMPv2-SMI
    DisplayString, RowStatus			        FROM SNMPv2-TC
    basExtEvent                                         FROM BAS-MIB;

basEventMib MODULE-IDENTITY
    LAST-UPDATED "9811171430Z"
    ORGANIZATION "Broadband Access Systems, Inc."
    CONTACT-INFO
        " Tech Support
          Broadband Access Systems, Inc.
          201 Forest Street
          Marlborough, MA 01752
          USA
          508-485-8200
          support@basystems.com"
    DESCRIPTION
        "The MIB module defines the event MIB objects
         for Broadband Access Systems, Inc. interfaces
         extensions."
    ::= { basExtEvent 1 }


basEvent  OBJECT IDENTIFIER ::= { basEventMib 1 }

-- the BAS Trap Recipient table

-- The BAS Trap Recipient table contains BAS proprietary information on
-- the recipient's entity.

basTrapRecipientTable OBJECT-TYPE
    SYNTAX      SEQUENCE OF BasTrapRecipientEntry
    MAX-ACCESS  not-accessible
    STATUS      current
    DESCRIPTION
        "A list of trap recipient entries.  The number of entries
        is given by the value of trapRecipientNumber."
    ::= { basEvent 1 }

basTrapRecipientEntry OBJECT-TYPE
    SYNTAX      BasTrapRecipientEntry
    MAX-ACCESS  not-accessible
    STATUS      current
    DESCRIPTION
        "An entry containing management information applicable
        to a particular recipient."
    INDEX   { basTrapRecipientIndex }
    ::= { basTrapRecipientTable 1 }

BasTrapRecipientEntry ::=
    SEQUENCE {
        basTrapRecipientIndex       	Integer32,
        basTrapRecipientIpAddr     	IpAddress,
        basTrapRecipientUdpPort       	INTEGER,
        basTrapRecipientCommName      	OCTET STRING,
        basTrapRecipientRowStatus	RowStatus,
	basTrapRecipientSnmpVersion	INTEGER
    }

basTrapRecipientIndex OBJECT-TYPE
    SYNTAX      Integer32
    MAX-ACCESS  read-only
    STATUS      current
    DESCRIPTION
        "This object indicates an entry into the Trap Recipient Table. If no entries are present, this object must be zero"
     ::= { basTrapRecipientEntry 1 }

basTrapRecipientIpAddr OBJECT-TYPE
    SYNTAX      IpAddress
    MAX-ACCESS  read-create
    STATUS      current
    DESCRIPTION
        "The Recipient's IP address."
    ::= { basTrapRecipientEntry 2 }

basTrapRecipientUdpPort OBJECT-TYPE
    SYNTAX      INTEGER(0..65535)
    MAX-ACCESS  read-create
    STATUS      current
    DESCRIPTION
        "The Recipient's UDP port."
    ::= { basTrapRecipientEntry 3 }

basTrapRecipientCommName OBJECT-TYPE
    SYNTAX      OCTET STRING (SIZE (0..255))
    MAX-ACCESS  read-create
    STATUS      current
    DESCRIPTION
        "The Recipient's community name."
    ::= { basTrapRecipientEntry 4 }

basTrapRecipientRowStatus OBJECT-TYPE
    SYNTAX      RowStatus
    MAX-ACCESS  read-create
    STATUS      current
    DESCRIPTION
        "This object is used to create and delete rows in the Trap Recipient's table"
    ::= { basTrapRecipientEntry 5 }

basTrapRecipientSnmpVersion OBJECT-TYPE
    SYNTAX      INTEGER(1..2)
    MAX-ACCESS  read-create
    STATUS      current
    DESCRIPTION
        "This object is used to select the SNMP version when sending traps."
    ::= { basTrapRecipientEntry 6 }

-- the BAS Trap Notification table

-- The BAS Trap Notification Table contains Trap OID specifications.

basTrapNotificationTable OBJECT-TYPE
    SYNTAX      SEQUENCE OF BasTrapNotificationEntry
    MAX-ACCESS  not-accessible
    STATUS      current
    DESCRIPTION
        "A list of trap notification entries.  The number of entries
        is given by the value of TrapRecipientNumber."
    ::= { basEvent 2 }

basTrapNotificationEntry OBJECT-TYPE
    SYNTAX      BasTrapNotificationEntry
    MAX-ACCESS  not-accessible
    STATUS      current
    DESCRIPTION
        "An entry containing management information applicable
        to a particular Trap."
    INDEX   { basTrapNotificationId, basTrapNotificationIndex }
    ::= { basTrapNotificationTable 1 }

BasTrapNotificationEntry ::=
    SEQUENCE {
        basTrapNotificationId       	OBJECT IDENTIFIER,
        basTrapNotificationIndex      	Integer32,
        basTrapNotificationRowStatus	RowStatus
    }

basTrapNotificationId OBJECT-TYPE
    SYNTAX      OBJECT IDENTIFIER
    MAX-ACCESS  accessible-for-notify
    STATUS      current
    DESCRIPTION
        "This object indicates an OID entry into the Trap Notification Table."
     ::= { basTrapNotificationEntry 1 }


basTrapNotificationIndex OBJECT-TYPE
    SYNTAX      Integer32
    MAX-ACCESS  read-only
    STATUS      current
    DESCRIPTION
        "The Recipient's Trap Notification Index. The value specified by this object must be represented in the Trap Recipient's list"
    ::= { basTrapNotificationEntry 2 }

basTrapNotificationRowStatus OBJECT-TYPE
    SYNTAX      RowStatus
    MAX-ACCESS  read-create
    STATUS      current
    DESCRIPTION
        "This object is used to create and delete rows in the Trap Notification table."
    ::= { basTrapNotificationEntry 3 }

END
