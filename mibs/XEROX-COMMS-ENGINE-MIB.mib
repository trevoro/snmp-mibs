XEROX-COMMS-ENGINE-MIB DEFINITIONS ::= BEGIN

--  Module: Communications Engine MIB
--  Author: Ira McDonald, Alan Sullivan, Robert Westfall
--  File:   51comms.mib
--  Date:   4 September 1997 - Version 2.32.pub

IMPORTS
    MODULE-IDENTITY, OBJECT-TYPE,
        Integer32, Counter32, Gauge32
            FROM SNMPv2-SMI             -- IETF RFC 1442/1902
    RowStatus, TruthValue, DateAndTime
            FROM SNMPv2-TC              -- IETF RFC 1443/1903
    MODULE-COMPLIANCE, OBJECT-GROUP
            FROM SNMPv2-CONF            -- IETF RFC 1444/1904
    ProductID,
        hrDeviceIndex
            FROM HOST-RESOURCES-MIB     -- IETF RFC 1514
    xeroxCommonMIB
            FROM XEROX-COMMON-MIB
    Ordinal32, Cardinal32,
        XcmFixedLocaleDisplayString,
        XcmGenSNMPv2ErrorStatus,
        xcmGenZeroDotZero
            FROM XEROX-GENERAL-TC
    XcmHrDevTrafficUnit
            FROM XEROX-HOST-RESOURCES-EXT-TC
    XcmCommsEngineGroupSupport,
       XcmCommsMgmtCommandRequest,
        XcmCommsMgmtCommandData,
        XcmCommsMgmtState,
        XcmCommsMgmtConditions,
        XcmCommsStackPosition,
        XcmCommsStackExtPurpose,
        XcmCommsStackExtRole,
        XcmCommsStackExtSuite,
        XcmCommsStackExtSuiteVersion,


        XcmCommsStackExtLayer,
        XcmCommsStackExtProtocol,
        XcmCommsAddressExtForm,
        XcmCommsAddressExtScope,
        XcmCommsAddressExtFanout
            FROM XEROX-COMMS-ENGINE-TC;

xcmCommsEngineMIB MODULE-IDENTITY
    LAST-UPDATED "9709040000Z"
    ORGANIZATION "Xerox Corporation - XCMI Working Group"
    CONTACT-INFO
        "           XCMI Editors
        Email:      xcmieditors@cp10.es.xerox.com

        --
        --
        "
    DESCRIPTION
        "Version:   2.32.pub

        The MIB module for detailed protocol stack graphing, and active
        management of communications protocol stacks, communications end
        system applications, communications intermediate systems, and
        communications gateways for network accessible host systems.

        Usage:  Note that throughout this MIB module, the INDEX clauses
        referring to 'hrDeviceIndex' for the 'hrDeviceTable' (Devices
        Group) of the Host Resources MIB (RFC 1514) shall ALWAYS
        specify host system CPUs (ie, 'hrDeviceProcessor') and shall NOT
        specify ANY other 'hrDeviceType'.

        Usage:  The object 'xcmCommsStackXrefHrCommDevIndex' in  the


        Comms Stack Xref Group of this MIB MAY be used to specify
        (for 'bottom' protocol stack layers) the corresponding value of
        'hrDeviceIndex' for network, modem, serial port, and parallel
        port devices.  And the object 'xcmCommsStackXrefIfIndex' may be
        used to specify the value of 'ifIndex' for the corresponding
        entry in the MIB-II 'ifTable' (ie, 'network interfaces').

        Copyright (C) 1997 Xerox Corporation. All Rights Reserved."
    ::= { xeroxCommonMIB 61 }

--
--          Comms Engine MIB
--
--          Comms Engine Group (Mandatory)
--
--          Implementation of this group is mandatory for all systems.

xcmCommsEngine          OBJECT IDENTIFIER ::= { xcmCommsEngineMIB 3 }

xcmCommsEngineTable OBJECT-TYPE
    SYNTAX      SEQUENCE OF XcmCommsEngineEntry
    MAX-ACCESS  not-accessible
    STATUS      current
    DESCRIPTION
        "A table of the communications engines installed and (possibly)
        running on platforms (ie, CPUs) on this host system."
    ::= { xcmCommsEngine 2 }

xcmCommsEngineEntry OBJECT-TYPE
    SYNTAX      XcmCommsEngineEntry
    MAX-ACCESS  not-accessible
    STATUS      current
    DESCRIPTION
        "An entry for a communications engine installed and (possibly)
        running on a platform (ie, CPU) on this host system.

        Usage:  Note that values of 'hrDeviceIndex' used to reference
        entries in the 'xcmCommsEngineTable' shall ALWAYS reference
        entries in the 'hrDeviceTable' with 'hrDeviceType' equal to
        'hrDeviceProcessor' (representing host system CPUs and therefore
        also having corresponding entries in the 'hrProcessorTable')."
    INDEX       { hrDeviceIndex }
    ::= { xcmCommsEngineTable 1 }

XcmCommsEngineEntry ::= SEQUENCE {
        --  Comms Engine Information
        xcmCommsEngineRowStatus         RowStatus,
        xcmCommsEngineName              XcmFixedLocaleDisplayString,
        xcmCommsEngineStackLast         Cardinal32,
        xcmCommsEngineMuxLast           Cardinal32,
        xcmCommsEngineAddressLast       Cardinal32,
        xcmCommsEngineMgmtLast          Cardinal32,
        xcmCommsEngineGroupSupport      XcmCommsEngineGroupSupport,
        xcmCommsEngineCreateSupport     XcmCommsEngineGroupSupport,


        xcmCommsEngineUpdateSupport     XcmCommsEngineGroupSupport
    }

--
--          Comms Engine Information
--

xcmCommsEngineRowStatus OBJECT-TYPE
    SYNTAX      RowStatus
    MAX-ACCESS  read-only
    STATUS      current
    DESCRIPTION
        "This object is used to create and delete individual conceptual
        rows in the 'xcmCommsEngineTable'."
    ::= { xcmCommsEngineEntry 1 }

xcmCommsEngineName OBJECT-TYPE
    SYNTAX      XcmFixedLocaleDisplayString (SIZE (0..255))
    MAX-ACCESS  read-only
    STATUS      current
    DESCRIPTION
        "Human-readable name, used by system administrators
        and end users to identify this communications engine
        for systems management.

        Usage:  This name should be the one normally used in a
        command shell for control of this communications engine."
    DEFVAL      { ''H }                 -- empty string
    ::= { xcmCommsEngineEntry 2 }

xcmCommsEngineStackLast OBJECT-TYPE
    SYNTAX      Cardinal32
    MAX-ACCESS  read-only
    STATUS      current
    DESCRIPTION
        "The last entry index (regardless of its current state) in
        the 'xcmCommsStackTable' of this communications engine,
        on this host system.

        Usage:  The last entry index explicitly bounds the valid range
        of 'xcmCommsStackIndex'."
    DEFVAL      { 0 }                   -- no entries
    ::= { xcmCommsEngineEntry 3 }

xcmCommsEngineMuxLast OBJECT-TYPE
    SYNTAX      Cardinal32
    MAX-ACCESS  read-only
    STATUS      current
    DESCRIPTION
        "The last entry index (regardless of its current state) in
        the 'xcmCommsMuxTable' of this communications engine,
        on this host system.

        Usage:  The last entry index explicitly bounds the valid range


        of 'xcmCommsMuxIndex'."
    DEFVAL      { 0 }                   -- no entries
    ::= { xcmCommsEngineEntry 4 }

xcmCommsEngineAddressLast OBJECT-TYPE
    SYNTAX      Cardinal32
    MAX-ACCESS  read-only
    STATUS      current
    DESCRIPTION
        "The last entry index (regardless of its current state) in
        the 'xcmCommsAddressTable' of this communications engine,
        on this host system.

        Usage:  The last entry index explicitly bounds the valid range
        of 'xcmCommsAddressIndex'."
    DEFVAL      { 0 }                   -- no entries
    ::= { xcmCommsEngineEntry 6 }

xcmCommsEngineMgmtLast OBJECT-TYPE
    SYNTAX      Cardinal32
    MAX-ACCESS  read-only
    STATUS      current
    DESCRIPTION
        "The last entry index (regardless of its current state) in
        the 'xcmCommsMgmtTable' of this communications engine,
        on this host system.

        Usage:  The last entry index explicitly bounds the valid range
        of 'xcmCommsMgmtIndex'."
    DEFVAL      { 0 }                   -- no entries
    ::= { xcmCommsEngineEntry 7 }

xcmCommsEngineGroupSupport OBJECT-TYPE
    SYNTAX      XcmCommsEngineGroupSupport
    MAX-ACCESS  read-only
    STATUS      current
    DESCRIPTION
        "The terse conformance statement of ALL mandatory, conditionally
        mandatory, and optional XCMI Comms Engine MIB object groups
        supported by this management agent implementation (ie, version)
        on this host system, specified in a bit-mask.

        Usage:  Conforming management agents shall ALWAYS accurately
        report their support for XCMI Comms Engine MIB object groups."
    DEFVAL      { 1 }                   -- mandatory groups
    ::= { xcmCommsEngineEntry 8 }

xcmCommsEngineCreateSupport OBJECT-TYPE
    SYNTAX      XcmCommsEngineGroupSupport
    MAX-ACCESS  read-only
    STATUS      current
    DESCRIPTION
        "The terse conformance statement of ALL mandatory, conditionally
        mandatory, and optional XCMI Comms Engine MIB object groups


        supported for dynamic row creation (via '...RowStatus')
        by this management agent implementation (ie, version)
        on this host system, specified in a bit-mask.

        Usage:  Conforming management agents shall ALWAYS accurately
        report their support for XCMI Comms Engine MIB object groups."
    DEFVAL      { 0 }                   -- no dynamic row create groups
    ::= { xcmCommsEngineEntry 9 }

xcmCommsEngineUpdateSupport OBJECT-TYPE
    SYNTAX      XcmCommsEngineGroupSupport
    MAX-ACCESS  read-only
    STATUS      current
    DESCRIPTION
        "The terse conformance statement of ALL mandatory, conditionally
        mandatory, and optional XCMI Comms Engine MIB object groups
        supported for existing row update (via SNMP Set-Request PDUs)
        by this management agent implementation (ie, version)
        on this host system, specified in a bit-mask.

        Usage:  Conforming management agents shall ALWAYS accurately
        report their support for XCMI Comms Engine MIB object groups."
    DEFVAL      { 0 }                   -- no existing row update groups
    ::= { xcmCommsEngineEntry 10 }

--
--          Comms Engine Ext Group (Optional)
--
--          Implementation of this group is optional for all systems.

xcmCommsEngineExt       OBJECT IDENTIFIER ::= { xcmCommsEngineMIB 4 }

xcmCommsEngineExtTable OBJECT-TYPE
    SYNTAX      SEQUENCE OF XcmCommsEngineExtEntry
    MAX-ACCESS  not-accessible
    STATUS      current
    DESCRIPTION
        "A 'sparse' table which augments 'xcmCommsEngineTable' with
        additional useful information."
    ::= { xcmCommsEngineExt 2 }

xcmCommsEngineExtEntry OBJECT-TYPE
    SYNTAX      XcmCommsEngineExtEntry
    MAX-ACCESS  not-accessible
    STATUS      current
    DESCRIPTION
        "A 'sparse' entry which augments 'xcmCommsEngineEntry' with
        additional useful information."
    INDEX       { hrDeviceIndex }
    ::= { xcmCommsEngineExtTable 1 }

XcmCommsEngineExtEntry ::= SEQUENCE {
        --  Comms Engine Ext Information
        xcmCommsEngineExtRowStatus      RowStatus,


        xcmCommsEngineExtState          XcmCommsMgmtState,
        xcmCommsEngineExtConditions     XcmCommsMgmtConditions,
        xcmCommsEngineExtVersionID      ProductID,
        xcmCommsEngineExtVersionDate    DateAndTime,
        --  Comms Engine Ext Common Cross References
        xcmCommsEngineExtMgmtIndex      Cardinal32,
        --  Comms Engine Ext Owner Cross References
        xcmCommsEngineExtOwnerOID       OBJECT IDENTIFIER
    }

--
--          Comms Engine Ext Information
--

xcmCommsEngineExtRowStatus OBJECT-TYPE
    SYNTAX      RowStatus
    MAX-ACCESS  read-only
    STATUS      current
    DESCRIPTION
        "This object is used to create and delete individual conceptual
        rows in the 'xcmCommsEngineExtTable'."
    ::= { xcmCommsEngineExtEntry 1 }

xcmCommsEngineExtState OBJECT-TYPE
    SYNTAX      XcmCommsMgmtState
    MAX-ACCESS  read-only
    STATUS      current
    DESCRIPTION
        "A relatively generic description of the current state of
        this communications entity."
    DEFVAL      { inoperative }         -- inoperative
    ::= { xcmCommsEngineExtEntry 2 }

xcmCommsEngineExtConditions OBJECT-TYPE
    SYNTAX      XcmCommsMgmtConditions
    MAX-ACCESS  read-only
    STATUS      current
    DESCRIPTION
        "A relatively generic description of the current conditions of
        this communications entity."
    DEFVAL      { 0 }                   -- no conditions
    ::= { xcmCommsEngineExtEntry 4 }

xcmCommsEngineExtVersionID OBJECT-TYPE
    SYNTAX      ProductID
    MAX-ACCESS  read-only
    STATUS      current
    DESCRIPTION
        "The software product ID of the SNMP sub-agent which implements
        the XCMI Comms Engine MIB on this host system.

        Usage:  This object shall specify the software product ID of an
        SNMP sub-agent (possibly also found in a conceptual row in the
        'hrSWRunTable' and/or 'hrSWInstalledTable' in the IETF HR MIB).


        This object shall NOT specify a particular release of the XCMI
        Comms Engine MIB, or the whole host system product.

        Note:   Contrast with 'sysObjectID' for the whole SNMP agent in
        the IETF MIB-II (RFC 1213) and 'hrDeviceID' for the whole device
        (or whole product, in the case of 'xcmHrDevice...') in the IETF
        Host Resources MIB (RFC 1514)."
    REFERENCE
        "See:   'hrSW[Installed|Run]ID' in the Software Installed and
                Software Running groups of the IETF HR MIB (RFC 1514)."
    DEFVAL      { xcmGenZeroDotZero }   -- no sub-agent version ID
    ::= { xcmCommsEngineExtEntry 5 }

xcmCommsEngineExtVersionDate OBJECT-TYPE
    SYNTAX      DateAndTime
    MAX-ACCESS  read-only
    STATUS      current
    DESCRIPTION
        "The software build date of the SNMP sub-agent which implements
        the XCMI Comms Engine MIB on this host system.

        Usage:  This object shall specify the BUILD date of the SNMP
        sub-agent software (not available elsewhere in IETF/XCMI MIBs).
        This object shall NOT specify the INSTALL date of the SNMP
        sub-agent software on this host system, nor the RESET date.

        Note:   Contrast with 'hrSWInstalledDate' in the Software
        Installed group of the IETF Host Resources MIB (RFC 1514), and
        'xcmHrDevInfoResetDate' in the Device Info group of the XCMI
        Host Resources Extensions MIB."
    REFERENCE
        "See:   'hrSW[Installed|Run]ID' in the Software Installed and
                Software Running groups of the IETF HR MIB (RFC 1514)."
    DEFVAL      { '0000000000000000'H } -- no sub-agent version date
    ::= { xcmCommsEngineExtEntry 6 }

--
--          Comms EngineExt Common Cross References
--

xcmCommsEngineExtMgmtIndex OBJECT-TYPE
    SYNTAX      Cardinal32
    MAX-ACCESS  read-only
    STATUS      current
    DESCRIPTION
        "The value of 'xcmCommsMgmtIndex' corresponding to a directly
        associated conceptual row in the 'xcmCommsMgmtTable', or zero
        if this 'managed entity' does NOT require such information."
    DEFVAL      { 0 }                   -- no entry
    ::= { xcmCommsEngineExtEntry 7 }

--
--          Comms EngineExt Owner Cross References
--


xcmCommsEngineExtOwnerOID OBJECT-TYPE
    SYNTAX      OBJECT IDENTIFIER
    MAX-ACCESS  read-only
    STATUS      current
    DESCRIPTION
        "The OID (object identifier) of the conceptual row or simple
        object which represents some 'owner entity' associated with
        this entry in the 'xcmCommsEngineExtTable'."
    DEFVAL      { xcmGenZeroDotZero }   -- no owner
    ::= { xcmCommsEngineExtEntry 8 }

--
--          Comms Stack Group (Cond Mandatory)
--
--          Implementation of this group is conditionally mandatory, ie,
--          mandatory for systems which implement stack layer graphing
--          via SNMP.

xcmCommsStack           OBJECT IDENTIFIER ::= { xcmCommsEngineMIB 5 }

xcmCommsStackTable OBJECT-TYPE
    SYNTAX      SEQUENCE OF XcmCommsStackEntry
    MAX-ACCESS  not-accessible
    STATUS      current
    DESCRIPTION
        "A table containing information on the relationships between
        the multiple stack layers or sublayers (ie, protocol entities)
        comprising the (possibly) running 'protocol stacks' on this host
        system.  In particular, it contains information about which
        stack layer runs 'above' and 'below' which other stack layer."
    ::= { xcmCommsStack 2 }

xcmCommsStackEntry OBJECT-TYPE
    SYNTAX      XcmCommsStackEntry
    MAX-ACCESS  not-accessible
    STATUS      current
    DESCRIPTION
        "An entry for a stack layer in a protocol stack installed
        and (possibly) running on this host system."
    INDEX       { hrDeviceIndex, xcmCommsStackIndex }
    ::= { xcmCommsStackTable 1 }

XcmCommsStackEntry ::= SEQUENCE {
        --  Comms Stack Information
        xcmCommsStackIndex              Ordinal32,
        xcmCommsStackRowStatus          RowStatus,
        xcmCommsStackTypeOID            OBJECT IDENTIFIER,
        xcmCommsStackName               XcmFixedLocaleDisplayString,
        xcmCommsStackPosition           XcmCommsStackPosition,
        --  Comms Stack Common Cross References
        xcmCommsStackLowerStackIndex    Cardinal32,
        xcmCommsStackUpperStackIndex    Cardinal32,
        xcmCommsStackAddressIndex       Cardinal32,


        xcmCommsStackOptionIndex        Cardinal32,
        --  Comms Stack Mux ONLY Cross References
        xcmCommsStackLowerMuxIndex      Cardinal32,
        xcmCommsStackUpperMuxIndex      Cardinal32
    }

--
--          Comms Stack Information
--

xcmCommsStackIndex OBJECT-TYPE
    SYNTAX      Ordinal32
    MAX-ACCESS  not-accessible
    STATUS      current
    DESCRIPTION
        "A unique value used by this host system to identify this
        conceptual row in the 'xcmCommsStackTable'."
    ::= { xcmCommsStackEntry 1 }

xcmCommsStackRowStatus OBJECT-TYPE
    SYNTAX      RowStatus
    MAX-ACCESS  read-only
    STATUS      current
    DESCRIPTION
        "This object is used to create and delete individual conceptual
        rows in the 'xcmCommsStackTable'."
    ::= { xcmCommsStackEntry 2 }

xcmCommsStackTypeOID OBJECT-TYPE
    SYNTAX      OBJECT IDENTIFIER
    MAX-ACCESS  read-only
    STATUS      current
    DESCRIPTION
        "An unambiguous stack layer type,
        used by system administrators and end users to identify
        the type of this stack layer.

        Usage:  Since this unambiguous stack layer type is specified
        as an object identifier, it may be taken from any IETF, Xerox,
        third- party, or product-specific MIB, or it may simply be any
        IETF SMIv2-style 'autonomous type'.

        Usage:  Suitable values for this unambiguous stack layer type
        are specified in the companion XCMI Comms Config TC (eg,
        'xcmCONetwareIPX')."
    DEFVAL      { xcmGenZeroDotZero }   -- no stack layer type
    ::= { xcmCommsStackEntry 3 }

xcmCommsStackName OBJECT-TYPE
    SYNTAX      XcmFixedLocaleDisplayString (SIZE (0..255))
    MAX-ACCESS  read-only
    STATUS      current
    DESCRIPTION
        "Human-readable name, used by system administrators


        and end users to identify this stack layer
        for systems management.

        Usage:  This name should be the one normally used in a
        command shell for control of this stack layer."
    DEFVAL      { ''H }                 -- empty string
    ::= { xcmCommsStackEntry 4 }

xcmCommsStackPosition OBJECT-TYPE
    SYNTAX      XcmCommsStackPosition
    MAX-ACCESS  read-only
    STATUS      current
    DESCRIPTION
        "A relatively generic description of the current position of
        this protocol entity (ie, this layer) in this protocol stack.

        Usage:  A conceptual row in 'xcmCommsStackTable', which occupies
        a 'bottom' position in a protocol stack AND has a corresponding
        row in the 'xcmCommsStackXrefTable', should ALWAYS have valid
        references in 'xcmCommsStackXrefIfIndex' (to IETF MIB-II) and
        'xcmCommsStackXrefHrCommDevIndex' (to IETF Host Resources MIB).

        Usage:  A conceptual row in 'xcmCommsStackTable' which occupies
        a 'lowerMux' and/or an 'upperMux' position in a protocol stack
        shall ALWAYS have one (or two) valid corresponding conceptual
        rows in the 'xcmCommsMuxTable', as the conventionally used
        'xcmCommsStack[Lower|Upper]StackIndex' objects take on zero
        values for multiplexors (thus breaking the graph of the stack
        layers, without the use of the 'xcmCommsMuxTable')."
    DEFVAL      { bottom }              -- bottom layer position
    ::= { xcmCommsStackEntry 5 }

--
--          Comms Stack Common Cross References
--

xcmCommsStackLowerStackIndex OBJECT-TYPE
    SYNTAX      Cardinal32
    MAX-ACCESS  read-only
    STATUS      current
    DESCRIPTION
        "The value of 'xcmCommsStackIndex' corresponding to a next
        lower associated conceptual row in the 'xcmCommsStackTable', or
        zero if this stack layer's position is either 'bottom' or
        'lowerMux'."
    DEFVAL      { 0 }                   -- no entry
    ::= { xcmCommsStackEntry 6 }

xcmCommsStackUpperStackIndex OBJECT-TYPE
    SYNTAX      Cardinal32
    MAX-ACCESS  read-only
    STATUS      current
    DESCRIPTION
        "The value of 'xcmCommsStackIndex' corresponding to a next


        higher associated conceptual row in the 'xcmCommsStackTable', or
        zero if this stack layer's position is either 'upperMux' or
        sometimes 'top' (see usage note below).

        Usage:  Only for protocol entities whose current purpose is
        either 'layerInterWorkingUnit' (ie, relays or gateways) or
        'systemInterWorkingUnit' (ie, application gateways), it is
        permitted that the stack layer whose current position is 'top'
        have an upper layer index pointing to the peer entity (also in a
        'top' position) which comprises the 'other half' of a relay or
        gateway between two different address domains (ie, an active
        protocol conversion relay) - that is the graphed protocol stack
        is an inverted 'U'."
    DEFVAL      { 0 }                   -- no entry
    ::= { xcmCommsStackEntry 7 }

xcmCommsStackAddressIndex OBJECT-TYPE
    SYNTAX      Cardinal32
    MAX-ACCESS  read-only
    STATUS      current
    DESCRIPTION
        "The value of 'xcmCommsAddressIndex' corresponding to the first
        associated conceptual row in the 'xcmCommsAddressTable', or zero
        if this 'owner entity' does NOT require such information."
    DEFVAL      { 0 }                   -- no entry
    ::= { xcmCommsStackEntry 8 }

xcmCommsStackOptionIndex OBJECT-TYPE
    SYNTAX      Cardinal32
    MAX-ACCESS  read-only
    STATUS      current
    DESCRIPTION
        "The value of 'xcmCommsOptionIndex' corresponding to the first
        associated conceptual row in the 'xcmCommsOptionTable', or zero
        if this stack layer does NOT require such information."
    DEFVAL      { 0 }                   -- no entry
    ::= { xcmCommsStackEntry 9 }

--
--          Comms Stack Mux ONLY Cross References
--

xcmCommsStackLowerMuxIndex OBJECT-TYPE
    SYNTAX      Cardinal32
    MAX-ACCESS  read-only
    STATUS      current
    DESCRIPTION
        "The value of 'xcmCommsMuxIndex' corresponding to the first
        associated conceptual row in the 'xcmCommsMuxTable', or zero
        if this stack layer's position is NOT 'lowerMux'."
    DEFVAL      { 0 }                   -- no entry
    ::= { xcmCommsStackEntry 10 }

xcmCommsStackUpperMuxIndex OBJECT-TYPE


    SYNTAX      Cardinal32
    MAX-ACCESS  read-only
    STATUS      current
    DESCRIPTION
        "The value of 'xcmCommsMuxIndex' corresponding to the first
        associated conceptual row in the 'xcmCommsMuxTable', or zero
        if this stack layer's position is NOT 'upperMux'."
    DEFVAL      { 0 }                   -- no entry
    ::= { xcmCommsStackEntry 11 }

--
--          Comms Stack Ext Group (Optional)
--
--          Implementation of this group is optional for all systems.

xcmCommsStackExt        OBJECT IDENTIFIER ::= { xcmCommsEngineMIB 6 }

xcmCommsStackExtTable OBJECT-TYPE
    SYNTAX      SEQUENCE OF XcmCommsStackExtEntry
    MAX-ACCESS  not-accessible
    STATUS      current
    DESCRIPTION
        "A 'sparse' table which augments 'xcmCommsStackTable' with
        additional useful information."
    ::= { xcmCommsStackExt 2 }

xcmCommsStackExtEntry OBJECT-TYPE
    SYNTAX      XcmCommsStackExtEntry
    MAX-ACCESS  not-accessible
    STATUS      current
    DESCRIPTION
        "A 'sparse' entry which augments 'xcmCommsStackEntry' with
        additional useful information."
    INDEX       { hrDeviceIndex, xcmCommsStackIndex }
    ::= { xcmCommsStackExtTable 1 }

XcmCommsStackExtEntry ::= SEQUENCE {
        --  Comms Stack Ext Information
        xcmCommsStackExtRowStatus       RowStatus,
        xcmCommsStackExtState           XcmCommsMgmtState,
        xcmCommsStackExtConditions      XcmCommsMgmtConditions,
        xcmCommsStackExtPurpose         XcmCommsStackExtPurpose,
        xcmCommsStackExtRole            XcmCommsStackExtRole,
        xcmCommsStackExtSuite           XcmCommsStackExtSuite,
        xcmCommsStackExtSuiteVersion    XcmCommsStackExtSuiteVersion,
        xcmCommsStackExtLayer           XcmCommsStackExtLayer,
        xcmCommsStackExtProtocol        XcmCommsStackExtProtocol,
        --  Comms Stack Ext Common Cross References
        xcmCommsStackExtMgmtIndex       Cardinal32,
        --  Comms Stack Ext Owner Cross References
        xcmCommsStackExtOwnerOID        OBJECT IDENTIFIER
    }

--


--          Comms Stack Ext Information
--

xcmCommsStackExtRowStatus OBJECT-TYPE
    SYNTAX      RowStatus
    MAX-ACCESS  read-only
    STATUS      current
    DESCRIPTION
        "This object is used to create and delete individual conceptual
        rows in the 'xcmCommsStackExtTable'."
    ::= { xcmCommsStackExtEntry 1 }

xcmCommsStackExtState OBJECT-TYPE
    SYNTAX      XcmCommsMgmtState
    MAX-ACCESS  read-only
    STATUS      current
    DESCRIPTION
        "A relatively generic description of the current state of
        this communications entity."
    DEFVAL      { inoperative }         -- inoperative
    ::= { xcmCommsStackExtEntry 2 }

xcmCommsStackExtConditions OBJECT-TYPE
    SYNTAX      XcmCommsMgmtConditions
    MAX-ACCESS  read-only
    STATUS      current
    DESCRIPTION
        "A relatively generic description of the current conditions of
        this communications entity."
    DEFVAL      { 0 }                   -- no conditions
    ::= { xcmCommsStackExtEntry 3 }

xcmCommsStackExtPurpose OBJECT-TYPE
    SYNTAX      XcmCommsStackExtPurpose
    MAX-ACCESS  read-only
    STATUS      current
    DESCRIPTION
        "A relatively generic description of the current purpose of
        this stack layer during normal operation."
    DEFVAL      { unknown }             -- unknown
    ::= { xcmCommsStackExtEntry 4 }

xcmCommsStackExtRole OBJECT-TYPE
    SYNTAX      XcmCommsStackExtRole
    MAX-ACCESS  read-only
    STATUS      current
    DESCRIPTION
        "A relatively generic description of the current role of
        this stack layer during normal operation."
    DEFVAL      { unknown }             -- unknown
    ::= { xcmCommsStackExtEntry 5 }

xcmCommsStackExtSuite OBJECT-TYPE
    SYNTAX      XcmCommsStackExtSuite


    MAX-ACCESS  read-only
    STATUS      current
    DESCRIPTION
        "The current protocol suite of this protocol entity
        (stack layer or sublayer)."
    DEFVAL      { unknown }             -- unknown
    ::= { xcmCommsStackExtEntry 6 }

xcmCommsStackExtSuiteVersion OBJECT-TYPE
    SYNTAX      XcmCommsStackExtSuiteVersion
    MAX-ACCESS  read-only
    STATUS      current
    DESCRIPTION
        "The current protocol suite version of this protocol entity
        (stack layer or sublayer)."
    DEFVAL      { unknown }             -- unknown
    ::= { xcmCommsStackExtEntry 7 }

xcmCommsStackExtLayer OBJECT-TYPE
    SYNTAX      XcmCommsStackExtLayer
    MAX-ACCESS  read-only
    STATUS      current
    DESCRIPTION
        "The closest approximate layer in the OSI Reference Model
        (CCITT X.200 | ISO 7498) to the current behavior
        of this stack layer or sublayer."
    DEFVAL      { unknown }             -- unknown
    ::= { xcmCommsStackExtEntry 8 }

xcmCommsStackExtProtocol OBJECT-TYPE
    SYNTAX      XcmCommsStackExtProtocol
    MAX-ACCESS  read-only
    STATUS      current
    DESCRIPTION
        "The specific protocol (within a given protocol suite) currently
        configured for this stack layer or sublayer."
    DEFVAL      { unknown }             -- unknown
    ::= { xcmCommsStackExtEntry 9 }

--
--          Comms Stack Ext Common Cross References
--

xcmCommsStackExtMgmtIndex OBJECT-TYPE
    SYNTAX      Cardinal32
    MAX-ACCESS  read-only
    STATUS      current
    DESCRIPTION
        "The value of 'xcmCommsMgmtIndex' corresponding to the directly
        associated conceptual row in the 'xcmCommsMgmtTable', or zero
        if this 'managed entity' does NOT require such information."
    DEFVAL      { 0 }                   -- no entry
    ::= { xcmCommsStackExtEntry 10 }


--
--          Comms Stack Ext Owner Cross References
--

xcmCommsStackExtOwnerOID OBJECT-TYPE
    SYNTAX      OBJECT IDENTIFIER
    MAX-ACCESS  read-only
    STATUS      current
    DESCRIPTION
        "The OID (object identifier) of the conceptual row or simple
        object which represents some 'owner entity' associated with
        this entry in the 'xcmCommsStackExtTable'.

        Usage:  A Printer Channel, for example, might choose to specify
        the OID of some conceptual row in the 'prtChannelTable'."
    REFERENCE
        "See:   'prtChannelTable' in Printer MIB (RFC 1759)"
    DEFVAL      { xcmGenZeroDotZero }   -- no owner
    ::= { xcmCommsStackExtEntry 11 }

--
--          Comms Stack Xref Group (Optional)
--
--          Implementation of this group is optional for all systems.

xcmCommsStackXref       OBJECT IDENTIFIER ::= { xcmCommsEngineMIB 7 }

xcmCommsStackXrefTable OBJECT-TYPE
    SYNTAX      SEQUENCE OF XcmCommsStackXrefEntry
    MAX-ACCESS  not-accessible
    STATUS      current
    DESCRIPTION
        "A table containing optional cross reference information for
        the multiple stack layers or sublayers (ie, protocol entities)
        comprising the (possibly) running 'protocol stacks' on this host
        system."
    ::= { xcmCommsStackXref 2 }

xcmCommsStackXrefEntry OBJECT-TYPE
    SYNTAX      XcmCommsStackXrefEntry
    MAX-ACCESS  not-accessible
    STATUS      current
    DESCRIPTION
        "An entry for a stack layer in a protocol stack installed
        and (possibly) running on this host system."
    INDEX       { hrDeviceIndex, xcmCommsStackIndex }
    ::= { xcmCommsStackXrefTable 1 }

XcmCommsStackXrefEntry ::= SEQUENCE {
        --  Comms Stack Xref Information
        xcmCommsStackXrefRowStatus      RowStatus,
        --  Comms Stack Xref Special ONLY Cross References
        xcmCommsStackXrefLayerMgmtIndex Cardinal32,


        xcmCommsStackXrefLayerSecIndex  Cardinal32,
        xcmCommsStackXrefLayerIWUIndex  Cardinal32,
        xcmCommsStackXrefHrSWRunIndex   Cardinal32,
        xcmCommsStackXrefHrSWInsIndex   Cardinal32,
        --  Comms Stack Xref Bottom ONLY Cross References
        xcmCommsStackXrefIfIndex        Cardinal32,
        xcmCommsStackXrefHrCommDevIndex Cardinal32
    }

--
--          Comms Stack Xref Information
--

xcmCommsStackXrefRowStatus OBJECT-TYPE
    SYNTAX      RowStatus
    MAX-ACCESS  read-only
    STATUS      current
    DESCRIPTION
        "This object is used to create and delete individual conceptual
        rows in the 'xcmCommsStackXrefTable'."
    ::= { xcmCommsStackXrefEntry 1 }

--
--          Comms Stack Xref Special ONLY Cross References
--

xcmCommsStackXrefLayerMgmtIndex OBJECT-TYPE
    SYNTAX      Cardinal32
    MAX-ACCESS  read-only
    STATUS      current
    DESCRIPTION
        "The value of 'xcmCommsStackIndex' corresponding to the
        one-to-one associated conceptual row in the 'xcmCommsStackTable'
        which has 'xcmCommsStackExtPurpose' of 'layerManagement',
        or zero if this this stack layer has no associated layer
        management entity."
    DEFVAL      { 0 }                   -- no entry
    ::= { xcmCommsStackXrefEntry 2 }

xcmCommsStackXrefLayerSecIndex OBJECT-TYPE
    SYNTAX      Cardinal32
    MAX-ACCESS  read-only
    STATUS      current
    DESCRIPTION
        "The value of 'xcmCommsStackIndex' corresponding to the
        one-to-one associated conceptual row in the 'xcmCommsStackTable'
        which has 'xcmCommsStackExtPurpose' of 'layerSecurity',
        or zero if this this stack layer has no associated layer
        security entity."
    DEFVAL      { 0 }                   -- no entry
    ::= { xcmCommsStackXrefEntry 3 }

xcmCommsStackXrefLayerIWUIndex OBJECT-TYPE
    SYNTAX      Cardinal32


    MAX-ACCESS  read-only
    STATUS      current
    DESCRIPTION
        "The value of 'xcmCommsStackIndex' corresponding to the
        one-to-one associated conceptual row in the 'xcmCommsStackTable'
        which has 'xcmCommsStackExtPurpose' of 'layerInterWorkingUnit',
        or zero if this this stack layer has no associated layer
        relay entity."
    DEFVAL      { 0 }                   -- no entry
    ::= { xcmCommsStackXrefEntry 4 }

xcmCommsStackXrefHrSWRunIndex OBJECT-TYPE
    SYNTAX      Cardinal32
    MAX-ACCESS  read-only
    STATUS      current
    DESCRIPTION
        "The value of 'hrSWRunIndex' corresponding to the directly
        associated conceptual row in the 'hrSWRunTable' of the
        Host Resources MIB (RFC 1514), or zero if 'hrSWRunTable'
        is NOT implemented."
    DEFVAL      { 0 }                   -- no entry
    ::= { xcmCommsStackXrefEntry 5 }

xcmCommsStackXrefHrSWInsIndex OBJECT-TYPE
    SYNTAX      Cardinal32
    MAX-ACCESS  read-only
    STATUS      current
    DESCRIPTION
        "The value of 'hrSWInstalledIndex' corresponding to the directly
        associated conceptual row in the 'hrSWInstalledTable' of the
        Host Resources MIB (RFC 1514), or zero if 'hrSWInstalledTable'
        is NOT implemented."
    DEFVAL      { 0 }                   -- no entry
    ::= { xcmCommsStackXrefEntry 6 }

--
--          Comms Stack Xref Bottom ONLY Cross References
--

xcmCommsStackXrefIfIndex OBJECT-TYPE
    SYNTAX      Cardinal32
    MAX-ACCESS  read-only
    STATUS      current
    DESCRIPTION
        "The value of 'ifIndex' corresponding to the directly
        associated conceptual row in the 'ifTable' (Interfaces Group)
        of the MIB-II (RFC 1213), or zero if the position of this
        stack layer is NOT 'bottom' (ie, this stack layer does NOT
        represent a physical 'network interface').

        Usage:  This is partially a convenience object, since given the
        value of 'hrDeviceIndex' for an 'hrDeviceNetwork' type device,
        the corresponding 'ifIndex' is found in the mandatory entry in
        the 'hrNetworkTable'.  However, note that for 'hrDeviceModem',


        'hrDeviceSerialPort', and 'hrDeviceParallelPort' devices, the
        'xcmCommsStackXrefIfIndex' object is a NECESSITY for support of
        this communications engine MIB."
    REFERENCE
        "See:   'xcmCommsStackPosition' and the 'InterfaceIndex'
        textual convention in Evolution of the Interfaces Group of
        MIB-II (RFC 1573)."
    DEFVAL      { 0 }                   -- no entry
    ::= { xcmCommsStackXrefEntry 7 }

xcmCommsStackXrefHrCommDevIndex OBJECT-TYPE
    SYNTAX      Cardinal32
    MAX-ACCESS  read-only
    STATUS      current
    DESCRIPTION
        "The value of 'hrDeviceIndex' corresponding to the directly
        associated conceptual rows in the 'hrDeviceTable' and (possibly)
        'hrNetworkTable' of the Host Resources MIB (RFC 1514), or zero
        if the position of this stack layer is NOT 'bottom' (ie, this
        stack layer does NOT represent a physical 'network interface').

        Usage:  Note that for 'hrDeviceModem', 'hrDeviceSerialPort', and
        'hrDeviceParallelPort' devices, there is NO corresponding entry
        in the 'hrNetworkTable', a subtle difference between MIB-II (RFC
        1213) and the Host Resources MIB (RFC 1514)."
    REFERENCE
        "See:   'xcmCommsStackPosition' and the 'hrDeviceIndex'
        of the Devices Group of the Host Resources MIB (RFC 1514)."
    DEFVAL      { 0 }                   -- no entry
    ::= { xcmCommsStackXrefEntry 8 }

--
--          Comms Mux Group (Cond Mandatory)
--
--          Implementation of this group is conditionally mandatory, ie,
--          mandatory for systems which implement stack layer graphing
--          via SNMP.

xcmCommsMux             OBJECT IDENTIFIER ::= { xcmCommsEngineMIB 8 }

xcmCommsMuxTable OBJECT-TYPE
    SYNTAX      SEQUENCE OF XcmCommsMuxEntry
    MAX-ACCESS  not-accessible
    STATUS      current
    DESCRIPTION
        "A table containing information on the relationships between
        the multiple stack layers or sublayers (ie, protocol entities)
        participating in a 'upper' or 'lower' multiplexor (ie, the
        simultaneous adjacency of two or more 'upper' or 'lower'
        stack layers with a single instance of a 'base' stack layer),
        eg, IP (a 'base' stack layer) operating below both TCP and UDP
        (the 'adjacent' stack layers)."
    ::= { xcmCommsMux 2 }


xcmCommsMuxEntry OBJECT-TYPE
    SYNTAX      XcmCommsMuxEntry
    MAX-ACCESS  not-accessible
    STATUS      current
    DESCRIPTION
        "An entry for a 'base' stack layer participating in an 'upper'
        or 'lower' multiplexor."
    INDEX       { hrDeviceIndex, xcmCommsMuxIndex }
    ::= { xcmCommsMuxTable 1 }

XcmCommsMuxEntry ::= SEQUENCE {
        --  Comms Mux Information
        xcmCommsMuxIndex                Ordinal32,
        xcmCommsMuxRowStatus            RowStatus,
        --  Comms Mux Common Cross References
        xcmCommsMuxNextIndex            Cardinal32,
        xcmCommsMuxPreviousIndex        Cardinal32,
        xcmCommsMuxOptionIndex          Cardinal32,
        --  Comms Mux Stack Cross References
        xcmCommsMuxBaseStackIndex       Ordinal32,
        xcmCommsMuxAdjacentStackIndex   Ordinal32
    }

--
--          Comms Mux Information
--

xcmCommsMuxIndex OBJECT-TYPE
    SYNTAX      Ordinal32
    MAX-ACCESS  not-accessible
    STATUS      current
    DESCRIPTION
        "A unique value used by this host system to identify this
        conceptual row in the 'xcmCommsMuxTable'."
    ::= { xcmCommsMuxEntry 1 }

xcmCommsMuxRowStatus OBJECT-TYPE
    SYNTAX      RowStatus
    MAX-ACCESS  read-only
    STATUS      current
    DESCRIPTION
        "This object is used to create and delete individual conceptual
        rows in the 'xcmCommsMuxTable'."
    ::= { xcmCommsMuxEntry 2 }

--
--          Comms Mux Common Cross References
--

xcmCommsMuxNextIndex OBJECT-TYPE
    SYNTAX      Cardinal32
    MAX-ACCESS  read-only
    STATUS      current


    DESCRIPTION
        "The value of 'xcmCommsMuxIndex' corresponding to a next
        associated conceptual row in the 'xcmCommsMuxTable', or zero
        if this is the last associated conceptual row in a given set."
    DEFVAL      { 0 }                   -- no entry
    ::= { xcmCommsMuxEntry 3 }

xcmCommsMuxPreviousIndex OBJECT-TYPE
    SYNTAX      Cardinal32
    MAX-ACCESS  read-only
    STATUS      current
    DESCRIPTION
        "The value of 'xcmCommsMuxIndex' corresponding to a previous
        associated conceptual row in the 'xcmCommsMuxTable', or zero
        if this is the first associated conceptual row in a given set."
    DEFVAL      { 0 }                   -- no entry
    ::= { xcmCommsMuxEntry 4 }

xcmCommsMuxOptionIndex OBJECT-TYPE
    SYNTAX      Cardinal32
    MAX-ACCESS  read-only
    STATUS      current
    DESCRIPTION
        "The value of 'xcmCommsOptionIndex' corresponding to the first
        associated conceptual row in the 'xcmCommsOptionTable', or zero
        if this multiplexor entry does NOT require such information."
    DEFVAL      { 0 }                   -- no entry
    ::= { xcmCommsMuxEntry 5 }

--
--          Comms Mux Stack Cross References
--

xcmCommsMuxBaseStackIndex OBJECT-TYPE
    SYNTAX      Ordinal32
    MAX-ACCESS  read-only
    STATUS      current
    DESCRIPTION
        "The value of 'xcmCommsStackIndex' corresponding to the base
        associated conceptual row in the 'xcmCommsStackTable'."
    ::= { xcmCommsMuxEntry 6 }

xcmCommsMuxAdjacentStackIndex OBJECT-TYPE
    SYNTAX      Ordinal32
    MAX-ACCESS  read-only
    STATUS      current
    DESCRIPTION
        "The value of 'xcmCommsStackIndex' corresponding to the adjacent
        associated conceptual row in the 'xcmCommsStackTable'."
    ::= { xcmCommsMuxEntry 7 }


--
--          Comms Mux Ext Group (Optional)
--
--          Implementation of this group is optional for all systems.

xcmCommsMuxExt          OBJECT IDENTIFIER ::= { xcmCommsEngineMIB 9 }

xcmCommsMuxExtTable OBJECT-TYPE
    SYNTAX      SEQUENCE OF XcmCommsMuxExtEntry
    MAX-ACCESS  not-accessible
    STATUS      current
    DESCRIPTION
        "A 'sparse' table which augments 'xcmCommsMuxTable' with
        additional useful information."
    ::= { xcmCommsMuxExt 2 }

xcmCommsMuxExtEntry OBJECT-TYPE
    SYNTAX      XcmCommsMuxExtEntry
    MAX-ACCESS  not-accessible
    STATUS      current
    DESCRIPTION
        "A 'sparse' entry which augments 'xcmCommsMuxEntry' with
        additional useful information."
    INDEX       { hrDeviceIndex, xcmCommsMuxIndex }
    ::= { xcmCommsMuxExtTable 1 }

XcmCommsMuxExtEntry ::= SEQUENCE {
        --  Comms Mux Ext Information
        xcmCommsMuxExtRowStatus         RowStatus,
        xcmCommsMuxExtState             XcmCommsMgmtState,
        xcmCommsMuxExtConditions        XcmCommsMgmtConditions,
        --  Comms Mux Ext Common Cross References
        xcmCommsMuxExtMgmtIndex         Cardinal32,
        xcmCommsMuxExtAddressIndex      Cardinal32,
        --  Comms Mux Ext Owner Cross References
        xcmCommsMuxExtOwnerOID          OBJECT IDENTIFIER
    }

--
--          Comms Mux Ext Information
--

xcmCommsMuxExtRowStatus OBJECT-TYPE
    SYNTAX      RowStatus
    MAX-ACCESS  read-only
    STATUS      current
    DESCRIPTION
        "This object is used to create and delete individual conceptual
        rows in the 'xcmCommsMuxExtTable'."
    ::= { xcmCommsMuxExtEntry 1 }

xcmCommsMuxExtState OBJECT-TYPE
    SYNTAX      XcmCommsMgmtState
    MAX-ACCESS  read-only


    STATUS      current
    DESCRIPTION
        "A relatively generic description of the current state of
        this communications entity."
    DEFVAL      { inoperative }         -- inoperative
    ::= { xcmCommsMuxExtEntry 2 }

xcmCommsMuxExtConditions OBJECT-TYPE
    SYNTAX      XcmCommsMgmtConditions
    MAX-ACCESS  read-only
    STATUS      current
    DESCRIPTION
        "A relatively generic description of the current conditions of
        this communications entity."
    DEFVAL      { 0 }                   -- no conditions
    ::= { xcmCommsMuxExtEntry 3 }

--
--          Comms Mux Ext Common Cross References
--

xcmCommsMuxExtMgmtIndex OBJECT-TYPE
    SYNTAX      Cardinal32
    MAX-ACCESS  read-only
    STATUS      current
    DESCRIPTION
        "The value of 'xcmCommsMgmtIndex' corresponding to the directly
        associated conceptual row in the 'xcmCommsMgmtTable', or zero
        if this 'managed entity' does NOT require such information."
    DEFVAL      { 0 }                   -- no entry
    ::= { xcmCommsMuxExtEntry 4 }

xcmCommsMuxExtAddressIndex OBJECT-TYPE
    SYNTAX      Cardinal32
    MAX-ACCESS  read-only
    STATUS      current
    DESCRIPTION
        "The value of 'xcmCommsAddressIndex' corresponding to the first
        associated conceptual row in the 'xcmCommsAddressTable', or zero
        if this 'owner entity' does NOT require such information."
    DEFVAL      { ''H }                 -- empty string
    ::= { xcmCommsMuxExtEntry 5 }

--
--          Comms Mux Ext Owner Cross References
--

xcmCommsMuxExtOwnerOID OBJECT-TYPE
    SYNTAX      OBJECT IDENTIFIER
    MAX-ACCESS  read-only
    STATUS      current
    DESCRIPTION
        "The OID (object identifier) of the conceptual row or simple
        object which represents some 'owner entity' associated with


        this entry in the 'xcmCommsMuxExtTable'."
    DEFVAL      { xcmGenZeroDotZero }   -- no owner
    ::= { xcmCommsMuxExtEntry 6 }

--
--          Comms Address Group (Cond Mandatory)
--
--          Implementation of this group is conditionally mandatory, ie,
--          mandatory for systems which implement address directories
--          via SNMP.

xcmCommsAddress         OBJECT IDENTIFIER ::= { xcmCommsEngineMIB 10 }

xcmCommsAddressTable OBJECT-TYPE
    SYNTAX      SEQUENCE OF XcmCommsAddressEntry
    MAX-ACCESS  not-accessible
    STATUS      current
    DESCRIPTION
        "A table containing information on unicast, multicast, and
        broadcast addresses (remote/local) known to this host system."
    ::= { xcmCommsAddress 2 }

xcmCommsAddressEntry OBJECT-TYPE
    SYNTAX      XcmCommsAddressEntry
    MAX-ACCESS  not-accessible
    STATUS      current
    DESCRIPTION
        "An entry containing information on one unicast, multicast, or
        broadcast address (remote/local) known to this host system."
    INDEX       { hrDeviceIndex, xcmCommsAddressIndex }
    ::= { xcmCommsAddressTable 1 }

XcmCommsAddressEntry ::= SEQUENCE {
        --  Comms Address Information
        xcmCommsAddressIndex            Ordinal32,
        xcmCommsAddressRowStatus        RowStatus,
        xcmCommsAddressTypeOID          OBJECT IDENTIFIER,
        xcmCommsAddressUserRole         Integer32,
        xcmCommsAddressName             XcmFixedLocaleDisplayString,
        xcmCommsAddressCanonical        OCTET STRING,
        --  Comms Address Common Cross References
        xcmCommsAddressNextIndex        Cardinal32,
        xcmCommsAddressPreviousIndex    Cardinal32,
        xcmCommsAddressOptionIndex      Cardinal32
    }

--
--          Comms Address Information
--

xcmCommsAddressIndex OBJECT-TYPE
    SYNTAX      Ordinal32
    MAX-ACCESS  not-accessible
    STATUS      current


    DESCRIPTION
        "A unique value used by this host system to identify this
        conceptual row in the 'xcmCommsAddressTable'."
    ::= { xcmCommsAddressEntry 1 }

xcmCommsAddressRowStatus OBJECT-TYPE
    SYNTAX      RowStatus
    MAX-ACCESS  read-create
    STATUS      current
    DESCRIPTION
        "This object is used to create and delete individual conceptual
        rows in the 'xcmCommsAddressTable'."
    ::= { xcmCommsAddressEntry 2 }

xcmCommsAddressTypeOID OBJECT-TYPE
    SYNTAX      OBJECT IDENTIFIER
    MAX-ACCESS  read-create
    STATUS      current
    DESCRIPTION
        "An unambiguous address type,
        used by system administrators and end users to identify
        the type of this address.

        Usage:  Since this unambiguous address type is specified
        as an object identifier, it may be taken from any IETF, Xerox,
        third- party, or product-specific MIB, or it may simply be any
        IETF SMIv2-style 'autonomous type'.

        Usage:  Suitable values for this unambiguous address type
        are specified in the companion XCMI Comms Config TC (eg,
        'xcmCONetwareIPX')."
    DEFVAL      { xcmGenZeroDotZero }   -- no address type
    ::= { xcmCommsAddressEntry 3 }

xcmCommsAddressUserRole OBJECT-TYPE
    SYNTAX      Integer32
    MAX-ACCESS  read-create
    STATUS      current
    DESCRIPTION
        "An unambiguous address user role,
        used by system administrators and end users to identify
        the user role of this address.

        Usage:  This unambiguous address user role is specified by a
        value defined in the textual convention 'XcmSecUserRole' in the
        XCMI Security/AAA TC.

        Usage:  This unambiguous address user role is weakly typed here
        to avoid cyclic compilation dependencies between XCMI MIBs.

        Usage:  A chain of 'xcmCommsAddressEntry' objects may be pointed
        to by 'xcmDevHelpCommsAddressIndex' in the Device Help group of
        the XCMI Host Resources Extensions MIB.  In this case, the
        'xcmCommsAddressTypeOID' object may contain values such as


        'xcmCOOsiwanPSTNAddress' (analog phone number),
        'xcmCOOsiwanFaxAddress' (fax phone number), etc,
        taken from the XCMI Comms Config TC.
        In this case, the 'xcmCommsAddressUserRole' object may be used
        to specify the role of the system admin, system operator, etc
        (whose name is specified by 'xcmCommsAddressName',
        address format is specified by 'xcmCommsAddressTypeOID',
        and actual address is specified by 'xcmCommsAddressCanonical')."
    REFERENCE
        "See:   'XcmSecUserRole' in the XCMI Security/AAA TC.
        See:    'xcmDevHelpCommsAddressIndex' in the XCMI Host Resources
        Extensions MIB."
    ::= { xcmCommsAddressEntry 4 }

xcmCommsAddressName OBJECT-TYPE
    SYNTAX      XcmFixedLocaleDisplayString (SIZE (0..255))
    MAX-ACCESS  read-create
    STATUS      current
    DESCRIPTION
        "Human-readable name, used by system administrators
        and end users to identify this protocol entity.

        Usage:  This name should be the one normally used in a
        command shell for control of this protocol entity.

        Usage:  When a chain of 'xcmCommsAddressEntry' objects is
        pointed to by 'xcmHrDevHelpCommsAddressIndex' in the Device Help
        group of the XCMI Host Resources Extensions MIB (see details at
        'xcmCommsAddressUserRole' object above) special semantics apply.
        In this case, the 'xcmCommsAddressName' object may be used
        to specify the name of the system admin, system operator, etc
        (whose role is specified by 'xcmCommsAddressUserRole',
        address format is specified by 'xcmCommsAddressTypeOID',
        and actual address is specified by 'xcmCommsAddressCanonical')."
    DEFVAL      { ''H }                 -- empty string
    ::= { xcmCommsAddressEntry 5 }

xcmCommsAddressCanonical OBJECT-TYPE
    SYNTAX      OCTET STRING (SIZE (0..255))
    MAX-ACCESS  read-create
    STATUS      current
    DESCRIPTION
        "The current canonical address of this protocol entity."
    ::= { xcmCommsAddressEntry 6 }

--
--          Comms Address Common Cross References
--

xcmCommsAddressNextIndex OBJECT-TYPE
    SYNTAX      Cardinal32
    MAX-ACCESS  read-create
    STATUS      current
    DESCRIPTION


        "The value of 'xcmCommsAddressIndex' corresponding to a next
        associated conceptual row in the 'xcmCommsAddressTable', or zero
        if this is the last associated conceptual row in a given set.

        Usage:  A locally administered 'directory' may be searched
        and/or managed via use of the 'xcmCommsAddressNextIndex'
        and the 'xcmCommsAddressPreviousIndex' objects referenced
        from each base protocol entity (ie, stack layer)."
    DEFVAL      { 0 }                   -- no entry
    ::= { xcmCommsAddressEntry 7 }

xcmCommsAddressPreviousIndex OBJECT-TYPE
    SYNTAX      Cardinal32
    MAX-ACCESS  read-create
    STATUS      current
    DESCRIPTION
        "The value of 'xcmCommsAddressIndex' corresponding to a previous
        associated conceptual row in the 'xcmCommsAddressTable', or zero
        if this is the first associated conceptual row in a given set."
    DEFVAL      { 0 }                   -- no entry
    ::= { xcmCommsAddressEntry 8 }

xcmCommsAddressOptionIndex OBJECT-TYPE
    SYNTAX      Cardinal32
    MAX-ACCESS  read-create
    STATUS      current
    DESCRIPTION
        "The value of 'xcmCommsOptionIndex' corresponding to the first
        associated conceptual row in the 'xcmCommsOptionTable', or zero
        if this address entry does NOT require such information."
    DEFVAL      { ''H }                 -- empty string
    ::= { xcmCommsAddressEntry 9 }

--
--          Comms Address Ext Group (Optional)
--
--          Implementation of this group is optional for all systems.

xcmCommsAddressExt      OBJECT IDENTIFIER ::= { xcmCommsEngineMIB 11 }

xcmCommsAddressExtTable OBJECT-TYPE
    SYNTAX      SEQUENCE OF XcmCommsAddressExtEntry
    MAX-ACCESS  not-accessible
    STATUS      current
    DESCRIPTION
        "A 'sparse' table which augments 'xcmCommsAddressTable' with
        additional useful information."
    ::= { xcmCommsAddressExt 2 }

xcmCommsAddressExtEntry OBJECT-TYPE
    SYNTAX      XcmCommsAddressExtEntry
    MAX-ACCESS  not-accessible
    STATUS      current
    DESCRIPTION


        "A 'sparse' entry which augments 'xcmCommsAddressEntry' with
        additional useful information."
    INDEX       { hrDeviceIndex, xcmCommsAddressIndex }
    ::= { xcmCommsAddressExtTable 1 }

XcmCommsAddressExtEntry ::= SEQUENCE {
        --  Comms Address Ext Information
        xcmCommsAddressExtRowStatus     RowStatus,
        xcmCommsAddressExtState         XcmCommsMgmtState,
        xcmCommsAddressExtConditions    XcmCommsMgmtConditions,
        xcmCommsAddressExtForm          XcmCommsAddressExtForm,
        xcmCommsAddressExtScope         XcmCommsAddressExtScope,
        xcmCommsAddressExtFanout        XcmCommsAddressExtFanout,
        --  Comms Address Ext Common Cross References
        xcmCommsAddressExtMgmtIndex     Cardinal32,
        --  Comms Address Ext Owner Cross References
        xcmCommsAddressExtOwnerOID      OBJECT IDENTIFIER
    }

--
--          Comms Address Ext Information
--

xcmCommsAddressExtRowStatus OBJECT-TYPE
    SYNTAX      RowStatus
    MAX-ACCESS  read-create
    STATUS      current
    DESCRIPTION
        "This object is used to create and delete individual conceptual
        rows in the 'xcmCommsAddressExtTable'."
    ::= { xcmCommsAddressExtEntry 1 }

xcmCommsAddressExtState OBJECT-TYPE
    SYNTAX      XcmCommsMgmtState
    MAX-ACCESS  read-only
    STATUS      current
    DESCRIPTION
        "A relatively generic description of the current state of
        this communications entity."
    DEFVAL      { inoperative }         -- inoperative
    ::= { xcmCommsAddressExtEntry 2 }

xcmCommsAddressExtConditions OBJECT-TYPE
    SYNTAX      XcmCommsMgmtConditions
    MAX-ACCESS  read-only
    STATUS      current
    DESCRIPTION
        "A relatively generic description of the current conditions of
        this communications entity."
    DEFVAL      { 0 }                   -- no conditions
    ::= { xcmCommsAddressExtEntry 3 }

xcmCommsAddressExtForm OBJECT-TYPE
    SYNTAX      XcmCommsAddressExtForm


    MAX-ACCESS  read-create
    STATUS      current
    DESCRIPTION
        "The current address form of this protocol entity."
    DEFVAL      { unknown }             -- unknown
    ::= { xcmCommsAddressExtEntry 4 }

xcmCommsAddressExtScope OBJECT-TYPE
    SYNTAX      XcmCommsAddressExtScope
    MAX-ACCESS  read-create
    STATUS      current
    DESCRIPTION
        "The current address scope of this protocol entity."
    DEFVAL      { unknown }             -- unknown
    ::= { xcmCommsAddressExtEntry 5 }

xcmCommsAddressExtFanout OBJECT-TYPE
    SYNTAX      XcmCommsAddressExtFanout
    MAX-ACCESS  read-create
    STATUS      current
    DESCRIPTION
        "The current address fan out of this protocol entity."
    DEFVAL      { unknown }             -- unknown
    ::= { xcmCommsAddressExtEntry 6 }

--
--          Comms Address Ext Common Cross References
--

xcmCommsAddressExtMgmtIndex OBJECT-TYPE
    SYNTAX      Cardinal32
    MAX-ACCESS  read-create
    STATUS      current
    DESCRIPTION
        "The value of 'xcmCommsMgmtIndex' corresponding to the directly
        associated conceptual row in the 'xcmCommsMgmtTable', or zero
        if this 'managed entity' does NOT require such information."
    DEFVAL      { ''H }                 -- empty string
    ::= { xcmCommsAddressExtEntry 7 }

--
--          Comms Address Ext Owner Cross References
--

xcmCommsAddressExtOwnerOID OBJECT-TYPE
    SYNTAX      OBJECT IDENTIFIER
    MAX-ACCESS  read-create
    STATUS      current
    DESCRIPTION
        "The OID (object identifier) of the conceptual row or simple
        object which represents some 'owner entity' associated with
        this entry in the 'xcmCommsAddressExtTable'."
    DEFVAL      { xcmGenZeroDotZero }   -- no owner
    ::= { xcmCommsAddressExtEntry 8 }


--
--          Comms Traffic Group (Optional)
--
--          Implementation of this group is optional for all systems.

xcmCommsTraffic         OBJECT IDENTIFIER ::= { xcmCommsEngineMIB 12 }

xcmCommsTrafficTable OBJECT-TYPE
    SYNTAX      SEQUENCE OF XcmCommsTrafficEntry
    MAX-ACCESS  not-accessible
    STATUS      current
    DESCRIPTION
        "A table containing input and output traffic counters for
        stack layers."
    ::= { xcmCommsTraffic 2 }

xcmCommsTrafficEntry OBJECT-TYPE
    SYNTAX      XcmCommsTrafficEntry
    MAX-ACCESS  not-accessible
    STATUS      current
    DESCRIPTION
        "An entry containing input and output traffic counters for
        this stack layer."
    INDEX       { hrDeviceIndex, xcmCommsStackIndex }
    ::= { xcmCommsTrafficTable 1 }

XcmCommsTrafficEntry ::= SEQUENCE {
        --  Comms Traffic Information
        xcmCommsTrafficRowStatus        RowStatus,
        xcmCommsTrafficInputUnit        XcmHrDevTrafficUnit,
        xcmCommsTrafficOutputUnit       XcmHrDevTrafficUnit,
        xcmCommsTrafficInputCount       Counter32,
        xcmCommsTrafficOutputCount      Counter32,
        xcmCommsTrafficInputErrors      Counter32,
        xcmCommsTrafficOutputErrors     Counter32
    }

--
--          Comms Traffic Information
--

xcmCommsTrafficRowStatus OBJECT-TYPE
    SYNTAX      RowStatus
    MAX-ACCESS  read-only
    STATUS      current
    DESCRIPTION
        "This object is used to create and delete individual conceptual
        rows in the 'xcmCommsTrafficTable'."
    ::= { xcmCommsTrafficEntry 1 }

xcmCommsTrafficInputUnit OBJECT-TYPE
    SYNTAX      XcmHrDevTrafficUnit
    MAX-ACCESS  read-only


    STATUS      current
    DESCRIPTION
        "A layer input unit, used by system administrators
        and end users of this layer for traffic counters."
    DEFVAL      { unknown }             -- unknown
    ::= { xcmCommsTrafficEntry 2 }

xcmCommsTrafficOutputUnit OBJECT-TYPE
    SYNTAX      XcmHrDevTrafficUnit
    MAX-ACCESS  read-only
    STATUS      current
    DESCRIPTION
        "A layer output unit, used by system administrators
        and end users of this layer for traffic counters."
    DEFVAL      { unknown }             -- unknown
    ::= { xcmCommsTrafficEntry 3 }

xcmCommsTrafficInputCount OBJECT-TYPE
    SYNTAX      Counter32
    MAX-ACCESS  read-only
    STATUS      current
    DESCRIPTION
        "A layer input traffic count, used by system administrators
        and end users of this layer.

        Usage:  Although no default value ('DEFVAL' clause) is permitted
        (by IETF SMIv2) for this counter, conforming host systems shall
        ALWAYS zero this counter upon conceptual row creation."
    ::= { xcmCommsTrafficEntry 4 }

xcmCommsTrafficOutputCount OBJECT-TYPE
    SYNTAX      Counter32
    MAX-ACCESS  read-only
    STATUS      current
    DESCRIPTION
        "A layer output traffic count, used by system administrators
        and end users of this layer.

        Usage:  Although no default value ('DEFVAL' clause) is permitted
        (by IETF SMIv2) for this counter, conforming host systems shall
        ALWAYS zero this counter upon conceptual row creation."
    ::= { xcmCommsTrafficEntry 5 }

xcmCommsTrafficInputErrors OBJECT-TYPE
    SYNTAX      Counter32
    MAX-ACCESS  read-only
    STATUS      current
    DESCRIPTION
        "A layer input errors count, used by system administrators
        and end users of this layer.

        Usage:  Although no default value ('DEFVAL' clause) is permitted
        (by IETF SMIv2) for this counter, conforming host systems shall
        ALWAYS zero this counter upon conceptual row creation."


    ::= { xcmCommsTrafficEntry 6 }

xcmCommsTrafficOutputErrors OBJECT-TYPE
    SYNTAX      Counter32
    MAX-ACCESS  read-only
    STATUS      current
    DESCRIPTION
        "A layer output errors count, used by system administrators
        and end users of this layer.

        Usage:  Although no default value ('DEFVAL' clause) is permitted
        (by IETF SMIv2) for this counter, conforming host systems shall
        ALWAYS zero this counter upon conceptual row creation."
    ::= { xcmCommsTrafficEntry 7 }

--
--          Comms Access Group (Optional)
--
--          Implementation of this group is optional for all systems.

xcmCommsAccess          OBJECT IDENTIFIER ::= { xcmCommsEngineMIB 13 }

xcmCommsAccessTable OBJECT-TYPE
    SYNTAX      SEQUENCE OF XcmCommsAccessEntry
    MAX-ACCESS  not-accessible
    STATUS      current
    DESCRIPTION
        "A table containing current, high-water mark, and maximum
        permitted values for both connection (or association) and
        message (or datagram) ports at the upper sides (ie, service
        provider interfaces) of stack layers."
    ::= { xcmCommsAccess 2 }

xcmCommsAccessEntry OBJECT-TYPE
    SYNTAX      XcmCommsAccessEntry
    MAX-ACCESS  not-accessible
    STATUS      current
    DESCRIPTION
        "A table containing current, high-water mark, and maximum
        permitted values for both connection (or association) and
        message (or datagram) ports at the upper side (ie, service
        provider interface) of this stack layer."
    INDEX       { hrDeviceIndex, xcmCommsStackIndex }
    ::= { xcmCommsAccessTable 1 }

XcmCommsAccessEntry ::= SEQUENCE {
        --  Comms Access Information
        xcmCommsAccessRowStatus         RowStatus,
        xcmCommsAccessConnectPorts      Gauge32,
        xcmCommsAccessHighConnectPorts  Gauge32,
        xcmCommsAccessMaxConnectPorts   Cardinal32,
        xcmCommsAccessDatagramPorts     Gauge32,
        xcmCommsAccessHighDatagramPorts Gauge32,
        xcmCommsAccessMaxDatagramPorts  Cardinal32


    }

--
--          Comms Access Information
--

xcmCommsAccessRowStatus OBJECT-TYPE
    SYNTAX      RowStatus
    MAX-ACCESS  read-only
    STATUS      current
    DESCRIPTION
        "This object is used to create and delete individual conceptual
        rows in the 'xcmCommsAccessTable'."
    ::= { xcmCommsAccessEntry 1 }

xcmCommsAccessConnectPorts OBJECT-TYPE
    SYNTAX      Gauge32
    MAX-ACCESS  read-only
    STATUS      current
    DESCRIPTION
        "The current number of connection (or association) ports open at
        the upper side (ie, service provider interface) of this layer."
    DEFVAL      { 0 }                   -- no ports
    ::= { xcmCommsAccessEntry 2 }

xcmCommsAccessHighConnectPorts OBJECT-TYPE
    SYNTAX      Gauge32
    MAX-ACCESS  read-only
    STATUS      current
    DESCRIPTION
        "The highest number of connection (or association) ports open at
        the upper side (ie, service provider interface) of this layer."
    DEFVAL      { 0 }                   -- no ports
    ::= { xcmCommsAccessEntry 3 }

xcmCommsAccessMaxConnectPorts OBJECT-TYPE
    SYNTAX      Cardinal32
    MAX-ACCESS  read-only
    STATUS      current
    DESCRIPTION
        "The maximum number of connection (or association) ports
        permitted at the upper side (ie, service provider interface)
        of this layer."
    DEFVAL      { 0 }                   -- no ports
    ::= { xcmCommsAccessEntry 4 }

xcmCommsAccessDatagramPorts OBJECT-TYPE
    SYNTAX      Gauge32
    MAX-ACCESS  read-only
    STATUS      current
    DESCRIPTION
        "The current number of message (or datagram) ports open at
        the upper side (ie, service provider interface) of this layer."
    DEFVAL      { 0 }                   -- no ports


    ::= { xcmCommsAccessEntry 5 }

xcmCommsAccessHighDatagramPorts OBJECT-TYPE
    SYNTAX      Gauge32
    MAX-ACCESS  read-only
    STATUS      current
    DESCRIPTION
        "The highest number of message (or datagram) ports open at
        the upper side (ie, service provider interface) of this layer."
    DEFVAL      { 0 }                   -- no ports
    ::= { xcmCommsAccessEntry 6 }

xcmCommsAccessMaxDatagramPorts OBJECT-TYPE
    SYNTAX      Cardinal32
    MAX-ACCESS  read-only
    STATUS      current
    DESCRIPTION
        "The maximum number of message (or datagram) ports permitted at
        the upper side (ie, service provider interface) of this layer."
    DEFVAL      { 0 }                   -- no ports
    ::= { xcmCommsAccessEntry 7 }

--
--          Comms Mgmt Group (Optional)
--
--          Implementation of this group is optional for all systems.

xcmCommsMgmt            OBJECT IDENTIFIER ::= { xcmCommsEngineMIB 14 }

xcmCommsMgmtTable OBJECT-TYPE
    SYNTAX      SEQUENCE OF XcmCommsMgmtEntry
    MAX-ACCESS  not-accessible
    STATUS      current
    DESCRIPTION
        "A table containing additional management control objects for
        installed and (possibly) active entities on this host system and
        supporting detailed and extensible 'states' and 'conditions'."
    ::= { xcmCommsMgmt 2 }

xcmCommsMgmtEntry OBJECT-TYPE
    SYNTAX      XcmCommsMgmtEntry
    MAX-ACCESS  not-accessible
    STATUS      current
    DESCRIPTION
        "An entry containing additional management control objects for
        installed and (possibly) active entity on this host system and
        supporting detailed and extensible 'states' and 'conditions'."
    INDEX       { hrDeviceIndex, xcmCommsMgmtIndex }
    ::= { xcmCommsMgmtTable 1 }

XcmCommsMgmtEntry ::= SEQUENCE {
        --  Comms Mgmt Information
        xcmCommsMgmtIndex               Ordinal32,
        xcmCommsMgmtRowStatus           RowStatus,


        xcmCommsMgmtCommandRequest      XcmCommsMgmtCommandRequest,
        xcmCommsMgmtCommandData         XcmCommsMgmtCommandData,
        xcmCommsMgmtCommandStatus       XcmGenSNMPv2ErrorStatus,
        xcmCommsMgmtCommandInProgress   TruthValue
    }

--
--          Comms Mgmt Information
--

xcmCommsMgmtIndex OBJECT-TYPE
    SYNTAX      Ordinal32
    MAX-ACCESS  not-accessible
    STATUS      current
    DESCRIPTION
        "A unique value used by this host system to identify this
        conceptual row in the 'xcmCommsMgmtTable'."
    ::= { xcmCommsMgmtEntry 1 }

xcmCommsMgmtRowStatus OBJECT-TYPE
    SYNTAX      RowStatus
    MAX-ACCESS  read-create
    STATUS      current
    DESCRIPTION
        "This object is used to create and delete individual conceptual
        rows in the 'xcmCommsMgmtTable'."
    ::= { xcmCommsMgmtEntry 2 }

xcmCommsMgmtCommandRequest OBJECT-TYPE
    SYNTAX      XcmCommsMgmtCommandRequest
    MAX-ACCESS  read-create
    STATUS      current
    DESCRIPTION
        "The most recent comms management command request
        specified for this conceptual row in the 'xcmCommsMgmtTable'."
    REFERENCE
        "See:   'xcmCommsMgmtCommand[Data|Status|InProgress]'"
    DEFVAL      { none }                -- no command request
    ::= { xcmCommsMgmtEntry 3 }

xcmCommsMgmtCommandData OBJECT-TYPE
    SYNTAX      XcmCommsMgmtCommandData (SIZE (0..255))
    MAX-ACCESS  read-create
    STATUS      current
    DESCRIPTION
        "The most recent comms management command data (if any)
        specified for this conceptual row in the 'xcmCommsMgmtTable'."
    REFERENCE
        "See:   'xcmCommsMgmtCommand[Request|Status|InProgress]'"
    DEFVAL      { ''H }                 -- no command data
    ::= { xcmCommsMgmtEntry 4 }

xcmCommsMgmtCommandStatus OBJECT-TYPE
    SYNTAX      XcmGenSNMPv2ErrorStatus


    MAX-ACCESS  read-only
    STATUS      current
    DESCRIPTION
        "The simple comms management error status associated with
        this conceptual row in 'xcmCommsMgmtTable'.

        Usage:  Conforming management agents shall ALWAYS set this
        object to the value returned in an SNMP Set-Response PDU when
        a simple comms management operation is 'accepted', ie, when
        'xcmCommsMgmtCommandInProgress' goes from 'false' to 'true'.

        Usage:  Conforming management agents shall ALWAYS set this
        object to the value of the completion status of the (possibly
        deferred) simple comms management operation, when
        'xcmCommsMgmtCommandInProgress' goes from 'true' to 'false'."
    REFERENCE
        "See:   'xcmCommsMgmtCommand[Request|Data|InProgress]'"
    DEFVAL      { noError }             -- no error
    ::= { xcmCommsMgmtEntry 5 }

xcmCommsMgmtCommandInProgress OBJECT-TYPE
    SYNTAX      TruthValue
    MAX-ACCESS  read-only
    STATUS      current
    DESCRIPTION
        "The comms management in progress status associated with
        this conceptual row in 'xcmCommsMgmtTable'."
    REFERENCE
        "See:   'xcmCommsMgmtCommand[Request|Data|Status]'"
    DEFVAL      { false }               -- no command in progress
    ::= { xcmCommsMgmtEntry 6 }

--
--          Comms Engine MIB Conformance Information
--
--          With Mandatory and Optional Conformance Groups

xcmCommsEngineMIBConformance
    OBJECT IDENTIFIER ::= { xcmCommsEngineMIB 2 }
xcmCommsEngineMIBGroups
    OBJECT IDENTIFIER ::= { xcmCommsEngineMIBConformance 2 }

--
--          Basic Compliance Statements
--

xcmCommsEngineMIBCompliance MODULE-COMPLIANCE
    STATUS      current
    DESCRIPTION
        "The compliance statements for SNMP management agents that
        implement the Comms Engine MIB."
    MODULE -- this module
    MANDATORY-GROUPS {
        xcmCommsEngineGroup


    }

    GROUP       xcmCommsEngineExtGroup
    DESCRIPTION
        "Implementation of this group is optional for all systems."

    GROUP       xcmCommsStackGroup
    DESCRIPTION
        "Implementation of this group is conditionally mandatory, ie,
        mandatory for systems which implement stack layer graphing
        via SNMP."

    GROUP       xcmCommsStackExtGroup
    DESCRIPTION
        "Implementation of this group is optional for all systems."

    GROUP       xcmCommsStackXrefGroup
    DESCRIPTION
        "Implementation of this group is optional for all systems."

    GROUP       xcmCommsMuxGroup
    DESCRIPTION
        "Implementation of this group is conditionally mandatory, ie,
        mandatory for systems which implement stack layer graphing
        via SNMP."

    GROUP       xcmCommsMuxExtGroup
    DESCRIPTION
        "Implementation of this group is optional for all systems."

    GROUP       xcmCommsAddressGroup
    DESCRIPTION
        "Implementation of this group is conditionally mandatory, ie,
        mandatory for systems which implement address directories
        via SNMP."

    GROUP       xcmCommsAddressExtGroup
    DESCRIPTION
        "Implementation of this group is optional for all systems."

    GROUP       xcmCommsTrafficGroup
    DESCRIPTION
        "Implementation of this group is optional for all systems."

    GROUP       xcmCommsAccessGroup
    DESCRIPTION
        "Implementation of this group is optional for all systems."

    GROUP       xcmCommsMgmtGroup
    DESCRIPTION
        "Implementation of this group is optional for all systems."

    OBJECT      xcmCommsEngineRowStatus
    SYNTAX      INTEGER { active(1) }   -- subset of RowStatus


    DESCRIPTION
        "It is conformant to implement this object as read-only, and
        only one of the enumerated values for the 'RowStatus' textual
        convention need be supported, specifically:  active(1)."

    OBJECT      xcmCommsEngineName
    SYNTAX      XcmFixedLocaleDisplayString (SIZE (0..32))
    DESCRIPTION
        "It is conformant to implement this object as read-only, and
        only 32 octets maximum string length need be supported."

    OBJECT      xcmCommsEngineExtRowStatus
    SYNTAX      INTEGER { active(1) }   -- subset of RowStatus
    DESCRIPTION
        "It is conformant to implement this object as read-only, and
        only one of the enumerated values for the 'RowStatus' textual
        convention need be supported, specifically:  active(1)."

    OBJECT      xcmCommsStackRowStatus
    SYNTAX      INTEGER { active(1) }   -- subset of RowStatus
    DESCRIPTION
        "It is conformant to implement this object as read-only, and
        only one of the enumerated values for the 'RowStatus' textual
        convention need be supported, specifically:  active(1)."

    OBJECT      xcmCommsStackName
    SYNTAX      XcmFixedLocaleDisplayString (SIZE (0..32))
    DESCRIPTION
        "It is conformant to implement this object as read-only, and
        only 32 octets maximum string length need be supported."

    OBJECT      xcmCommsStackExtRowStatus
    SYNTAX      INTEGER { active(1) }   -- subset of RowStatus
    DESCRIPTION
        "It is conformant to implement this object as read-only, and
        only one of the enumerated values for the 'RowStatus' textual
        convention need be supported, specifically:  active(1)."

    OBJECT      xcmCommsStackXrefRowStatus
    SYNTAX      INTEGER { active(1) }   -- subset of RowStatus
    DESCRIPTION
        "It is conformant to implement this object as read-only, and
        only one of the enumerated values for the 'RowStatus' textual
        convention need be supported, specifically:  active(1)."

    OBJECT      xcmCommsMuxRowStatus
    SYNTAX      INTEGER { active(1) }   -- subset of RowStatus
    DESCRIPTION
        "It is conformant to implement this object as read-only, and
        only one of the enumerated values for the 'RowStatus' textual
        convention need be supported, specifically:  active(1)."

    OBJECT      xcmCommsMuxExtRowStatus
    SYNTAX      INTEGER { active(1) }   -- subset of RowStatus


    DESCRIPTION
        "It is conformant to implement this object as read-only, and
        only one of the enumerated values for the 'RowStatus' textual
        convention need be supported, specifically:  active(1)."

    OBJECT      xcmCommsAddressRowStatus
    SYNTAX      INTEGER { active(1) }   -- subset of RowStatus
    MIN-ACCESS  read-only
    DESCRIPTION
        "It is conformant to implement this object as read-only, and
        only one of the enumerated values for the 'RowStatus' textual
        convention need be supported, specifically:  active(1)."

    OBJECT      xcmCommsAddressTypeOID
    MIN-ACCESS  read-only
    DESCRIPTION
        "It is conformant to implement this object as read-only."

    OBJECT      xcmCommsAddressUserRole
    MIN-ACCESS  read-only
    DESCRIPTION
        "It is conformant to implement this object as read-only."

    OBJECT      xcmCommsAddressName
    SYNTAX      XcmFixedLocaleDisplayString (SIZE (0..32))
    MIN-ACCESS  read-only
    DESCRIPTION
        "It is conformant to implement this object as read-only, and
        only 32 octets maximum string length need be supported."

    OBJECT      xcmCommsAddressCanonical
    SYNTAX      OCTET STRING (SIZE (0..32))
    MIN-ACCESS  read-only
    DESCRIPTION
        "It is conformant to implement this object as read-only, and
        only 32 octets maximum string length need be supported."

    OBJECT      xcmCommsAddressNextIndex
    MIN-ACCESS  read-only
    DESCRIPTION
        "It is conformant to implement this object as read-only."

    OBJECT      xcmCommsAddressPreviousIndex
    MIN-ACCESS  read-only
    DESCRIPTION
        "It is conformant to implement this object as read-only."

    OBJECT      xcmCommsAddressOptionIndex
    MIN-ACCESS  read-only
    DESCRIPTION
        "It is conformant to implement this object as read-only."

    OBJECT      xcmCommsAddressExtRowStatus
    SYNTAX      INTEGER { active(1) }   -- subset of RowStatus


    MIN-ACCESS  read-only
    DESCRIPTION
        "It is conformant to implement this object as read-only, and
        only one of the enumerated values for the 'RowStatus' textual
        convention need be supported, specifically:  active(1)."

    OBJECT      xcmCommsAddressExtForm
    MIN-ACCESS  read-only
    DESCRIPTION
        "It is conformant to implement this object as read-only."

    OBJECT      xcmCommsAddressExtScope
    MIN-ACCESS  read-only
    DESCRIPTION
        "It is conformant to implement this object as read-only."

    OBJECT      xcmCommsAddressExtFanout
    MIN-ACCESS  read-only
    DESCRIPTION
        "It is conformant to implement this object as read-only."

    OBJECT      xcmCommsAddressExtMgmtIndex
    MIN-ACCESS  read-only
    DESCRIPTION
        "It is conformant to implement this object as read-only."

    OBJECT      xcmCommsAddressExtOwnerOID
    MIN-ACCESS  read-only
    DESCRIPTION
        "It is conformant to implement this object as read-only."

    OBJECT      xcmCommsTrafficRowStatus
    SYNTAX      INTEGER { active(1) }   -- subset of RowStatus
    DESCRIPTION
        "It is conformant to implement this object as read-only, and
        only one of the enumerated values for the 'RowStatus' textual
        convention need be supported, specifically:  active(1)."

    OBJECT      xcmCommsAccessRowStatus
    SYNTAX      INTEGER { active(1) }   -- subset of RowStatus
    DESCRIPTION
        "It is conformant to implement this object as read-only, and
        only one of the enumerated values for the 'RowStatus' textual
        convention need be supported, specifically:  active(1)."

    OBJECT      xcmCommsMgmtRowStatus
    SYNTAX      INTEGER { active(1) }   -- subset of RowStatus
    MIN-ACCESS  read-only
    DESCRIPTION
        "It is conformant to implement this object as read-only, and
        only one of the enumerated values for the 'RowStatus' textual
        convention need be supported, specifically:  active(1)."

    OBJECT      xcmCommsMgmtCommandRequest


    MIN-ACCESS  read-only
    DESCRIPTION
        "It is conformant to implement this object as read-only."

    OBJECT      xcmCommsMgmtCommandData
    SYNTAX      XcmCommsMgmtCommandData (SIZE (0..32))
    MIN-ACCESS  read-only
    DESCRIPTION
        "It is conformant to implement this object as read-only, and
        only 32 octets maximum string length need be supported."

    ::= { xcmCommsEngineMIBConformance 3 }

--
--          Help Compliance Statements (used w/ Device Help in HRX MIB)
--

xcmCommsEngineMIBHelpCompliance MODULE-COMPLIANCE
    STATUS      current
    DESCRIPTION
        "The compliance statements for SNMP management agents that
        implement a subset of the Comms Engine MIB, for the sole purpose
        of supporting extended 'contact' information per device, via
        the Device Help group of the XCMI Host Resources Ext MIB.

        Usage:  See 'Usage' paragraphs in the DESCRIPTION sub-clauses of
        the following OBJECT clauses for additional usage details."
    MODULE -- this module
    MANDATORY-GROUPS {
        xcmCommsEngineGroup,
        xcmCommsAddressGroup
    }

    GROUP       xcmCommsAddressExtGroup
    DESCRIPTION
        "Implementation of this group is optional for all systems."

    GROUP       xcmCommsMgmtGroup
    DESCRIPTION
        "Implementation of this group is optional for all systems."

    OBJECT      xcmCommsEngineRowStatus
    SYNTAX      INTEGER { active(1) }   -- subset of RowStatus
    DESCRIPTION
        "It is conformant to implement this object as read-only, and
        only one of the enumerated values for the 'RowStatus' textual
        convention need be supported, specifically:  active(1)."

    OBJECT      xcmCommsEngineName
    SYNTAX      XcmFixedLocaleDisplayString (SIZE (0..32))
    DESCRIPTION
        "It is conformant to implement this object as read-only, and
        only 32 octets maximum string length need be supported."


    OBJECT      xcmCommsAddressRowStatus
    SYNTAX      INTEGER { active(1) }   -- subset of RowStatus
    MIN-ACCESS  read-only
    DESCRIPTION
        "It is conformant to implement this object as read-only, and
        only one of the enumerated values for the 'RowStatus' textual
        convention need be supported, specifically:  active(1)."

    OBJECT      xcmCommsAddressTypeOID
    MIN-ACCESS  read-only
    DESCRIPTION
        "It is conformant to implement this object as read-only.

        Usage:  Suitable values for this unambiguous address type
        are specified in the XCMI Comms Config TC, for use with
        the Device Help group of the XCMI Host Resources Ext MIB (eg,
        'xcmCOOsiwanPSTNAddress' - analog phone number)."

    OBJECT      xcmCommsAddressUserRole
    MIN-ACCESS  read-only
    DESCRIPTION
        "It is conformant to implement this object as read-only.

        Usage:  Suitable values for this unambiguous address user role
        are specified in the XCMI Security TC, in the textual convention
        'XcmSecUserRole' (system/technician/end user), for use with
        the Device Help group of the XCMI Host Resources Ext MIB (eg,
        'systemSuppliesSource' - device supplies contact info)."

    OBJECT      xcmCommsAddressName
    SYNTAX      XcmFixedLocaleDisplayString (SIZE (0..32))
    MIN-ACCESS  read-only
    DESCRIPTION
        "It is conformant to implement this object as read-only, and
        only 32 octets maximum string length need be supported.

        Usage:  This object shall contain the human-readable 'common'
        name of a person (or business entity), eg 'John J Wellingtion',
        and NOT the user 'login' name, eg 'jwellington', for use with
        the Device Help group of the XCMI Host Resources Ext MIB."

    OBJECT      xcmCommsAddressCanonical
    SYNTAX      OCTET STRING (SIZE (0..32))
    MIN-ACCESS  read-only
    DESCRIPTION
        "It is conformant to implement this object as read-only, and
        only 32 octets maximum string length need be supported.

        Usage:  This object shall contain the 'canonical' (standardized)
        form of the electronic (eg, Fax) or hardcopy (eg, postal)
        'address' of the person (or business entity) identified in the
        above 'xcmCommsAddressName' object."


    OBJECT      xcmCommsAddressNextIndex
    MIN-ACCESS  read-only
    DESCRIPTION
        "It is conformant to implement this object as read-only.

        Usage:  This object shall contain the index of the next
        extended 'contact' info row in the 'xcmCommsAddressTable', or
        zero, if this is the last row in the set which is currently
        associated with a given managed device, for use with
        the Device Help group of the XCMI Host Resources Ext MIB."

    OBJECT      xcmCommsAddressPreviousIndex
    MIN-ACCESS  read-only
    DESCRIPTION
        "It is conformant to implement this object as read-only.

        Usage:  This object shall contain the index of the previous
        extended 'contact' info row in the 'xcmCommsAddressTable', or
        zero, if this is the first row in the set which is currently
        associated with a given managed device, for use with
        the Device Help group of the XCMI Host Resources Ext MIB."

    OBJECT      xcmCommsAddressOptionIndex
    MIN-ACCESS  read-only
    DESCRIPTION
        "It is conformant to implement this object as read-only.

        Usage:  This object shall ALWAYS contain zero, for use with
        the Device Help group of the XCMI Host Resources Ext MIB."

    OBJECT      xcmCommsAddressExtRowStatus
    SYNTAX      INTEGER { active(1) }   -- subset of RowStatus
    MIN-ACCESS  read-only
    DESCRIPTION
        "It is conformant to implement this object as read-only, and
        only one of the enumerated values for the 'RowStatus' textual
        convention need be supported, specifically:  active(1)."

    OBJECT      xcmCommsAddressExtForm
    MIN-ACCESS  read-only
    DESCRIPTION
        "It is conformant to implement this object as read-only."

    OBJECT      xcmCommsAddressExtScope
    MIN-ACCESS  read-only
    DESCRIPTION
        "It is conformant to implement this object as read-only."

    OBJECT      xcmCommsAddressExtFanout
    MIN-ACCESS  read-only
    DESCRIPTION
        "It is conformant to implement this object as read-only."


    OBJECT      xcmCommsAddressExtMgmtIndex
    MIN-ACCESS  read-only
    DESCRIPTION
        "It is conformant to implement this object as read-only."

    OBJECT      xcmCommsAddressExtOwnerOID
    MIN-ACCESS  read-only
    DESCRIPTION
        "It is conformant to implement this object as read-only."

    OBJECT      xcmCommsMgmtRowStatus
    SYNTAX      INTEGER { active(1) }   -- subset of RowStatus
    MIN-ACCESS  read-only
    DESCRIPTION
        "It is conformant to implement this object as read-only, and
        only one of the enumerated values for the 'RowStatus' textual
        convention need be supported, specifically:  active(1)."

    OBJECT      xcmCommsMgmtCommandRequest
    MIN-ACCESS  read-only
    DESCRIPTION
        "It is conformant to implement this object as read-only."

    OBJECT      xcmCommsMgmtCommandData
    SYNTAX      XcmCommsMgmtCommandData (SIZE (0..32))
    MIN-ACCESS  read-only
    DESCRIPTION
        "It is conformant to implement this object as read-only, and
        only 32 octets maximum string length need be supported."

    ::= { xcmCommsEngineMIBConformance 4 }

--
--          Conformance Groups
--

xcmCommsEngineGroup OBJECT-GROUP
    OBJECTS {
        --  Comms Engine Information
        xcmCommsEngineRowStatus,
        xcmCommsEngineName,
        xcmCommsEngineStackLast,
        xcmCommsEngineMuxLast,
        xcmCommsEngineAddressLast,
        xcmCommsEngineMgmtLast,
        xcmCommsEngineGroupSupport,
        xcmCommsEngineCreateSupport,
        xcmCommsEngineUpdateSupport
    }
    STATUS      current
    DESCRIPTION
        "Comms Engine Group (Comms Engines)."
    ::= { xcmCommsEngineMIBGroups 3 }


xcmCommsEngineExtGroup OBJECT-GROUP
    OBJECTS {
        --  Comms Engine Ext Information
        xcmCommsEngineExtRowStatus,
        xcmCommsEngineExtState,
        xcmCommsEngineExtConditions,
        xcmCommsEngineExtVersionID,
        xcmCommsEngineExtVersionDate,
        --  Comms Engine Ext Common Cross References
        xcmCommsEngineExtMgmtIndex,
        --  Comms Engine Ext Owner Cross References
        xcmCommsEngineExtOwnerOID
    }
    STATUS      current
    DESCRIPTION
        "Comms Engine Ext Group (Comms Engines)."
    ::= { xcmCommsEngineMIBGroups 4 }

xcmCommsStackGroup OBJECT-GROUP
    OBJECTS {
        --  Comms Stack Information
        xcmCommsStackRowStatus,
        xcmCommsStackTypeOID,
        xcmCommsStackName,
        xcmCommsStackPosition,
        --  Comms Stack Common Cross References
        xcmCommsStackLowerStackIndex,
        xcmCommsStackUpperStackIndex,
        xcmCommsStackAddressIndex,
        xcmCommsStackOptionIndex,
        --  Comms Stack Mux ONLY Cross References
        xcmCommsStackLowerMuxIndex,
        xcmCommsStackUpperMuxIndex
    }
    STATUS      current
    DESCRIPTION
        "Comms Stack Group (Stack Layers)."
    ::= { xcmCommsEngineMIBGroups 5 }

xcmCommsStackExtGroup OBJECT-GROUP
    OBJECTS {
        --  Comms Stack Ext Information
        xcmCommsStackExtRowStatus,
        xcmCommsStackExtState,
        xcmCommsStackExtConditions,
        xcmCommsStackExtPurpose,
        xcmCommsStackExtRole,
        xcmCommsStackExtSuite,
        xcmCommsStackExtSuiteVersion,
        xcmCommsStackExtLayer,
        xcmCommsStackExtProtocol,
        --  Comms Stack Ext Common Cross References
        xcmCommsStackExtMgmtIndex,


        --  Comms Stack Ext Owner Cross References
        xcmCommsStackExtOwnerOID
    }
    STATUS      current
    DESCRIPTION
        "Comms Stack Ext Group (Stack Layers)."
    ::= { xcmCommsEngineMIBGroups 6 }

xcmCommsStackXrefGroup OBJECT-GROUP
    OBJECTS {
        --  Comms Stack Xref Information
        xcmCommsStackXrefRowStatus,
        --  Comms Stack Xref Special ONLY Cross References
        xcmCommsStackXrefLayerMgmtIndex,
        xcmCommsStackXrefLayerSecIndex,
        xcmCommsStackXrefLayerIWUIndex,
        xcmCommsStackXrefHrSWRunIndex,
        xcmCommsStackXrefHrSWInsIndex,
        --  Comms Stack Xref Bottom ONLY Cross References
        xcmCommsStackXrefIfIndex,
        xcmCommsStackXrefHrCommDevIndex
    }
    STATUS      current
    DESCRIPTION
        "Comms Stack Xref Group (Stack Layers)."
    ::= { xcmCommsEngineMIBGroups 7 }

xcmCommsMuxGroup OBJECT-GROUP
    OBJECTS {
        --  Comms Mux Information
        xcmCommsMuxRowStatus,
        --  Comms Mux Common Cross References
        xcmCommsMuxNextIndex,
        xcmCommsMuxPreviousIndex,
        xcmCommsMuxOptionIndex,
        --  Comms Mux Stack Cross References
        xcmCommsMuxBaseStackIndex,
        xcmCommsMuxAdjacentStackIndex
    }
    STATUS      current
    DESCRIPTION
        "Comms Mux Group (Multiplexors)."
    ::= { xcmCommsEngineMIBGroups 8 }

xcmCommsMuxExtGroup OBJECT-GROUP
    OBJECTS {
        --  Comms Mux Ext Information
        xcmCommsMuxExtRowStatus,
        xcmCommsMuxExtState,
        xcmCommsMuxExtConditions,
        --  Comms Mux Ext Common Cross References
        xcmCommsMuxExtMgmtIndex,
        xcmCommsMuxExtAddressIndex,
        --  Comms Mux Ext Owner Cross References


        xcmCommsMuxExtOwnerOID
    }
    STATUS      current
    DESCRIPTION
        "Comms Mux Ext Group (Multiplexors)."
    ::= { xcmCommsEngineMIBGroups 9 }

xcmCommsAddressGroup OBJECT-GROUP
    OBJECTS {
        --  Comms Address Information
        xcmCommsAddressRowStatus,
        xcmCommsAddressTypeOID,
        xcmCommsAddressUserRole,
        xcmCommsAddressName,
        xcmCommsAddressCanonical,
        --  Comms Address Common Cross References
        xcmCommsAddressNextIndex,
        xcmCommsAddressPreviousIndex,
        xcmCommsAddressOptionIndex
    }
    STATUS      current
    DESCRIPTION
        "Comms Address Group (Directories)."
    ::= { xcmCommsEngineMIBGroups 10 }

xcmCommsAddressExtGroup OBJECT-GROUP
    OBJECTS {
        --  Comms Address Ext Information
        xcmCommsAddressExtRowStatus,
        xcmCommsAddressExtState,
        xcmCommsAddressExtConditions,
        xcmCommsAddressExtForm,
        xcmCommsAddressExtScope,
        xcmCommsAddressExtFanout,
        --  Comms Address Ext Common Cross References
        xcmCommsAddressExtMgmtIndex,
        --  Comms Address Ext Owner Cross References
        xcmCommsAddressExtOwnerOID
    }
    STATUS      current
    DESCRIPTION
        "Comms Address Ext Group (Directories)."
    ::= { xcmCommsEngineMIBGroups 11 }

xcmCommsTrafficGroup OBJECT-GROUP
    OBJECTS {
        --  Comms Traffic Information
        xcmCommsTrafficRowStatus,
        xcmCommsTrafficInputUnit,
        xcmCommsTrafficOutputUnit,
        xcmCommsTrafficInputCount,
        xcmCommsTrafficOutputCount,
        xcmCommsTrafficInputErrors,
        xcmCommsTrafficOutputErrors


    }
    STATUS      current
    DESCRIPTION
        "Comms Traffic Group (Stack Layer Traffic Counters)."
    ::= { xcmCommsEngineMIBGroups 12 }

xcmCommsAccessGroup OBJECT-GROUP
    OBJECTS {
        --  Comms Access Information
        xcmCommsAccessRowStatus,
        xcmCommsAccessConnectPorts,
        xcmCommsAccessHighConnectPorts,
        xcmCommsAccessMaxConnectPorts,
        xcmCommsAccessDatagramPorts,
        xcmCommsAccessHighDatagramPorts,
        xcmCommsAccessMaxDatagramPorts
    }
    STATUS      current
    DESCRIPTION
        "Comms Access Group (Stack Layer Access Counters)."
    ::= { xcmCommsEngineMIBGroups 13 }

xcmCommsMgmtGroup OBJECT-GROUP
    OBJECTS {
        --  Comms Mgmt Information
        xcmCommsMgmtRowStatus,
        xcmCommsMgmtCommandRequest,
        xcmCommsMgmtCommandData,
        xcmCommsMgmtCommandStatus,
        xcmCommsMgmtCommandInProgress
    }
    STATUS      current
    DESCRIPTION
        "Comms Mgmt Group (State Management)."
    ::= { xcmCommsEngineMIBGroups 14 }

END
