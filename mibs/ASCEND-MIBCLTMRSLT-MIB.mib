--			Ascend mibcltmrslt MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBCLTMRSLT-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibcltmRslt  OBJECT IDENTIFIER ::= { configuration 68}

	-- The mibcltmRslt table
	--
	-- This table contains parameters for the mibcltmRslt profile
	--

    mibcltmRsltTable	OBJECT-TYPE
	SYNTAX		SEQUENCE OF MibcltmRsltEntry
	ACCESS		not-accessible
	STATUS		mandatory
	DESCRIPTION	"A list of mibcltmRslt profile entries."
	::= { mibcltmRslt 1 }

    mibcltmRsltEntry	OBJECT-TYPE
	SYNTAX		MibcltmRsltEntry
	ACCESS		not-accessible
	STATUS		mandatory
	DESCRIPTION	"A mibcltmRslt entry containing objects that
			 maps to the parameters of mibcltmRslt profile."
	INDEX		{ cltmRslt-Index-o }
	::= { mibcltmRsltTable 1 }

    MibcltmRsltEntry ::=
	SEQUENCE {
	    cltmRslt-Index-o
		INTEGER,
	    cltmRslt-CltmSlot
		INTEGER,
	    cltmRslt-TestResultTimeStamp
		INTEGER,
	    cltmRslt-TestResultSequence
		INTEGER,
	    cltmRslt-TestResultStatus
		INTEGER,
	    cltmRslt-DmmResult
		INTEGER,
	    cltmRslt-LoopResistance
		INTEGER,
	    cltmRslt-LoopResistanceLength1
		INTEGER,
	    cltmRslt-LoopResistanceLength2
		INTEGER,
	    cltmRslt-LoopResistanceLength3
		INTEGER,
	    cltmRslt-CoilDetectionCoilCount
		INTEGER,
	    cltmRslt-ImpulseNoiseReadLowThreshold
		INTEGER,
	    cltmRslt-ImpulseNoiseReadMidThreshold
		INTEGER,
	    cltmRslt-ImpulseNoiseReadHighThreshold
		INTEGER,
	    cltmRslt-RcvToneFrequency
		INTEGER,
	    cltmRslt-RcvToneLevel
		INTEGER,
	    cltmRslt-TdrManualSampleCount
		INTEGER,
	    cltmRslt-TdrAutomaticFaultDistance
		INTEGER,
	    cltmRslt-HardwareRevision
		INTEGER,
	    cltmRslt-SofwareRevision
		INTEGER,
	    cltmRslt-DcDeltaResistanceTR
		INTEGER,
	    cltmRslt-DcDeltaResistanceTS
		INTEGER,
	    cltmRslt-DcDeltaResistanceRS
		INTEGER,
	    cltmRslt-DcDeltaVoltageTS
		INTEGER,
	    cltmRslt-DcDeltaVoltageRS
		INTEGER,
	    cltmRslt-CapEquivalentTR
		INTEGER,
	    cltmRslt-CapEquivalentTS
		INTEGER,
	    cltmRslt-CapEquivalentRS
		INTEGER,
	    cltmRslt-DmmAllTR
		INTEGER,
	    cltmRslt-DmmAllTS
		INTEGER,
	    cltmRslt-DmmAllRS
		INTEGER,
	    cltmRslt-Ringer
		INTEGER,
	    cltmRslt-AtuR
		INTEGER,
	    cltmRslt-BridgeTapNumber
		INTEGER,
	    cltmRslt-BridgeTapLength
		INTEGER,
	    cltmRslt-VoiceDetection
		INTEGER,
	    cltmRslt-FirstCoilLocation
		INTEGER,
	    cltmRslt-ShortLocation
		INTEGER,
	    cltmRslt-Action-o
		INTEGER
	}

    cltmRslt-Index-o	OBJECT-TYPE
	SYNTAX	INTEGER
	ACCESS	read-only
	STATUS	mandatory
	DESCRIPTION	""
	::= { mibcltmRsltEntry 1 }

    cltmRslt-CltmSlot	OBJECT-TYPE
	SYNTAX	INTEGER {
		    anySlot (1),
		    slot1 (2),
		    slot2 (3),
		    slot3 (4),
		    slot4 (5),
		    slot5 (6),
		    slot6 (7),
		    slot7 (8),
		    slot10 (11),
		    slot11 (12),
		    slot12 (13),
		    slot13 (14),
		    slot14 (15),
		    slot15 (16),
		    slot16 (17)
		}
	ACCESS	read-only
	STATUS	mandatory
	DESCRIPTION	"Identify the CLTM slot within the system."
	::= { mibcltmRsltEntry 2 }

    cltmRslt-TestResultTimeStamp	OBJECT-TYPE
	SYNTAX	INTEGER
	ACCESS	read-only
	STATUS	mandatory
	DESCRIPTION	"Value of the sysUpTime when the test result was obtained."
	::= { mibcltmRsltEntry 3 }

    cltmRslt-TestResultSequence	OBJECT-TYPE
	SYNTAX	INTEGER
	ACCESS	read-only
	STATUS	mandatory
	DESCRIPTION	"Sequence of the last test result."
	::= { mibcltmRsltEntry 4 }

    cltmRslt-TestResultStatus	OBJECT-TYPE
	SYNTAX	INTEGER {
		    notReady (1),
		    notValid (2),
		    overRange (3),
		    valid (4)
		}
	ACCESS	read-only
	STATUS	mandatory
	DESCRIPTION	"This parameter indicates whether the test result is valid."
	::= { mibcltmRsltEntry 5 }

    cltmRslt-DmmResult	OBJECT-TYPE
	SYNTAX	INTEGER
	ACCESS	read-only
	STATUS	mandatory
	DESCRIPTION	"DMM Measurement result. The units are Ohm for resistance, dc/av milli Volt for voltage and pico Farad for capacitance."
	::= { mibcltmRsltEntry 6 }

    cltmRslt-LoopResistance	OBJECT-TYPE
	SYNTAX	INTEGER
	ACCESS	read-only
	STATUS	mandatory
	DESCRIPTION	"Resistance in Kohm for Loop Resistance Test."
	::= { mibcltmRsltEntry 7 }

    cltmRslt-LoopResistanceLength1	OBJECT-TYPE
	SYNTAX	INTEGER
	ACCESS	read-only
	STATUS	mandatory
	DESCRIPTION	"Length in feet of 22AWG or meter of 0.644mm for Loop Resistance Test."
	::= { mibcltmRsltEntry 8 }

    cltmRslt-LoopResistanceLength2	OBJECT-TYPE
	SYNTAX	INTEGER
	ACCESS	read-only
	STATUS	mandatory
	DESCRIPTION	"Length in feet of 24AWG or meter of 0.511mm Loop Resistance Test."
	::= { mibcltmRsltEntry 9 }

    cltmRslt-LoopResistanceLength3	OBJECT-TYPE
	SYNTAX	INTEGER
	ACCESS	read-only
	STATUS	mandatory
	DESCRIPTION	"Length in feet of 26AWG or meter of 0.405mm Loop Resistance Test."
	::= { mibcltmRsltEntry 10 }

    cltmRslt-CoilDetectionCoilCount	OBJECT-TYPE
	SYNTAX	INTEGER
	ACCESS	read-only
	STATUS	mandatory
	DESCRIPTION	"Number of coil detected for Coil Detection Test."
	::= { mibcltmRsltEntry 11 }

    cltmRslt-ImpulseNoiseReadLowThreshold	OBJECT-TYPE
	SYNTAX	INTEGER
	ACCESS	read-only
	STATUS	mandatory
	DESCRIPTION	"Impulse Read Counter over low Db threshold."
	::= { mibcltmRsltEntry 12 }

    cltmRslt-ImpulseNoiseReadMidThreshold	OBJECT-TYPE
	SYNTAX	INTEGER
	ACCESS	read-only
	STATUS	mandatory
	DESCRIPTION	"Impulse Read Counter over mid Db threshold."
	::= { mibcltmRsltEntry 13 }

    cltmRslt-ImpulseNoiseReadHighThreshold	OBJECT-TYPE
	SYNTAX	INTEGER
	ACCESS	read-only
	STATUS	mandatory
	DESCRIPTION	"Impulse Read Counter over high Db threshold."
	::= { mibcltmRsltEntry 14 }

    cltmRslt-RcvToneFrequency	OBJECT-TYPE
	SYNTAX	INTEGER
	ACCESS	read-only
	STATUS	mandatory
	DESCRIPTION	"Receive Tone Frequency."
	::= { mibcltmRsltEntry 15 }

    cltmRslt-RcvToneLevel	OBJECT-TYPE
	SYNTAX	INTEGER
	ACCESS	read-only
	STATUS	mandatory
	DESCRIPTION	"Receive Tone Level."
	::= { mibcltmRsltEntry 16 }

    cltmRslt-TdrManualSampleCount	OBJECT-TYPE
	SYNTAX	INTEGER
	ACCESS	read-only
	STATUS	mandatory
	DESCRIPTION	"Number of detectde sample pairs via manual TDR test."
	::= { mibcltmRsltEntry 17 }

    cltmRslt-TdrAutomaticFaultDistance	OBJECT-TYPE
	SYNTAX	INTEGER
	ACCESS	read-only
	STATUS	mandatory
	DESCRIPTION	"Distance of the detected fault via automatic TDR test."
	::= { mibcltmRsltEntry 18 }

    cltmRslt-HardwareRevision	OBJECT-TYPE
	SYNTAX	INTEGER
	ACCESS	read-only
	STATUS	mandatory
	DESCRIPTION	"Hardware revision number."
	::= { mibcltmRsltEntry 19 }

    cltmRslt-SofwareRevision	OBJECT-TYPE
	SYNTAX	INTEGER
	ACCESS	read-only
	STATUS	mandatory
	DESCRIPTION	"Software revision number."
	::= { mibcltmRsltEntry 20 }

    cltmRslt-DcDeltaResistanceTR	OBJECT-TYPE
	SYNTAX	INTEGER
	ACCESS	read-only
	STATUS	mandatory
	DESCRIPTION	"dc delta resistance T-R."
	::= { mibcltmRsltEntry 21 }

    cltmRslt-DcDeltaResistanceTS	OBJECT-TYPE
	SYNTAX	INTEGER
	ACCESS	read-only
	STATUS	mandatory
	DESCRIPTION	"dc delta resistance T-S."
	::= { mibcltmRsltEntry 22 }

    cltmRslt-DcDeltaResistanceRS	OBJECT-TYPE
	SYNTAX	INTEGER
	ACCESS	read-only
	STATUS	mandatory
	DESCRIPTION	"dc delta resistance R-S."
	::= { mibcltmRsltEntry 23 }

    cltmRslt-DcDeltaVoltageTS	OBJECT-TYPE
	SYNTAX	INTEGER
	ACCESS	read-only
	STATUS	mandatory
	DESCRIPTION	"dc delta voltage T-S."
	::= { mibcltmRsltEntry 24 }

    cltmRslt-DcDeltaVoltageRS	OBJECT-TYPE
	SYNTAX	INTEGER
	ACCESS	read-only
	STATUS	mandatory
	DESCRIPTION	"dc delta voltage R-S."
	::= { mibcltmRsltEntry 25 }

    cltmRslt-CapEquivalentTR	OBJECT-TYPE
	SYNTAX	INTEGER
	ACCESS	read-only
	STATUS	mandatory
	DESCRIPTION	"capacitance T-R."
	::= { mibcltmRsltEntry 26 }

    cltmRslt-CapEquivalentTS	OBJECT-TYPE
	SYNTAX	INTEGER
	ACCESS	read-only
	STATUS	mandatory
	DESCRIPTION	"capacitance T-S."
	::= { mibcltmRsltEntry 27 }

    cltmRslt-CapEquivalentRS	OBJECT-TYPE
	SYNTAX	INTEGER
	ACCESS	read-only
	STATUS	mandatory
	DESCRIPTION	"capacitance R-S."
	::= { mibcltmRsltEntry 28 }

    cltmRslt-DmmAllTR	OBJECT-TYPE
	SYNTAX	INTEGER
	ACCESS	read-only
	STATUS	mandatory
	DESCRIPTION	"dmm all T-R."
	::= { mibcltmRsltEntry 29 }

    cltmRslt-DmmAllTS	OBJECT-TYPE
	SYNTAX	INTEGER
	ACCESS	read-only
	STATUS	mandatory
	DESCRIPTION	"dmm all T-S."
	::= { mibcltmRsltEntry 30 }

    cltmRslt-DmmAllRS	OBJECT-TYPE
	SYNTAX	INTEGER
	ACCESS	read-only
	STATUS	mandatory
	DESCRIPTION	"dmm all R-S."
	::= { mibcltmRsltEntry 31 }

    cltmRslt-Ringer	OBJECT-TYPE
	SYNTAX	INTEGER
	ACCESS	read-only
	STATUS	mandatory
	DESCRIPTION	"detect ringer."
	::= { mibcltmRsltEntry 32 }

    cltmRslt-AtuR	OBJECT-TYPE
	SYNTAX	INTEGER
	ACCESS	read-only
	STATUS	mandatory
	DESCRIPTION	"detect ATU-R."
	::= { mibcltmRsltEntry 33 }

    cltmRslt-BridgeTapNumber	OBJECT-TYPE
	SYNTAX	INTEGER
	ACCESS	read-only
	STATUS	mandatory
	DESCRIPTION	"bridge-tap number."
	::= { mibcltmRsltEntry 34 }

    cltmRslt-BridgeTapLength	OBJECT-TYPE
	SYNTAX	INTEGER
	ACCESS	read-only
	STATUS	mandatory
	DESCRIPTION	"bridge-tap-loop-len."
	::= { mibcltmRsltEntry 35 }

    cltmRslt-VoiceDetection	OBJECT-TYPE
	SYNTAX	INTEGER
	ACCESS	read-only
	STATUS	mandatory
	DESCRIPTION	"Voice Detection: 1: Voice signal not detected. 2: Voice signal detected. 3: Steady state - possible data traffic. 4: Interrupted tone detected - 60 or 120 IPM."
	::= { mibcltmRsltEntry 37 }

    cltmRslt-FirstCoilLocation	OBJECT-TYPE
	SYNTAX	INTEGER
	ACCESS	read-only
	STATUS	mandatory
	DESCRIPTION	"First Coil Location in 0.01 feet or cm."
	::= { mibcltmRsltEntry 38 }

    cltmRslt-ShortLocation	OBJECT-TYPE
	SYNTAX	INTEGER
	ACCESS	read-only
	STATUS	mandatory
	DESCRIPTION	"Short Location in 0.01 feet or cm."
	::= { mibcltmRsltEntry 39 }

    cltmRslt-Action-o	OBJECT-TYPE
	SYNTAX	INTEGER {
		    noAction (1),
		    createProfile (2),
		    deleteProfile (3)
		}
	ACCESS	read-write
	STATUS	mandatory
	DESCRIPTION	""
	::= { mibcltmRsltEntry 36 }


	-- The mibcltmRslt__bridge_tap_table table
	--
	-- This table contains parameters for the mibcltmRslt__bridge_tap_table profile
	--

    mibcltmRslt-BridgeTapTableTable	OBJECT-TYPE
	SYNTAX		SEQUENCE OF MibcltmRslt-BridgeTapTableEntry
	ACCESS		not-accessible
	STATUS		mandatory
	DESCRIPTION	"A list of mibcltmRslt__bridge_tap_table profile entries."
	::= { mibcltmRslt 2 }

    mibcltmRslt-BridgeTapTableEntry	OBJECT-TYPE
	SYNTAX		MibcltmRslt-BridgeTapTableEntry
	ACCESS		not-accessible
	STATUS		mandatory
	DESCRIPTION	"A mibcltmRslt__bridge_tap_table entry containing objects that
			 maps to the parameters of mibcltmRslt__bridge_tap_table profile."
	INDEX		{ cltmRslt-BridgeTapTable-Index-o, cltmRslt-BridgeTapTable-Index1-o }
	::= { mibcltmRslt-BridgeTapTableTable 1 }

    MibcltmRslt-BridgeTapTableEntry ::=
	SEQUENCE {
	    cltmRslt-BridgeTapTable-Index-o
		INTEGER,
	    cltmRslt-BridgeTapTable-Index1-o
		INTEGER,
	    cltmRslt-BridgeTapTable-Distance
		INTEGER,
	    cltmRslt-BridgeTapTable-Length
		INTEGER,
	    cltmRslt-BridgeTapTable-Confidence
		INTEGER
	}

    cltmRslt-BridgeTapTable-Index-o	OBJECT-TYPE
	SYNTAX	INTEGER
	ACCESS	read-only
	STATUS	mandatory
	DESCRIPTION	""
	::= { mibcltmRslt-BridgeTapTableEntry 1 }

    cltmRslt-BridgeTapTable-Index1-o	OBJECT-TYPE
	SYNTAX	INTEGER
	ACCESS	read-only
	STATUS	mandatory
	DESCRIPTION	""
	::= { mibcltmRslt-BridgeTapTableEntry 2 }

    cltmRslt-BridgeTapTable-Distance	OBJECT-TYPE
	SYNTAX	INTEGER
	ACCESS	read-only
	STATUS	mandatory
	DESCRIPTION	"Bridge-Tap Distance in Feet or Meter"
	::= { mibcltmRslt-BridgeTapTableEntry 3 }

    cltmRslt-BridgeTapTable-Length	OBJECT-TYPE
	SYNTAX	INTEGER
	ACCESS	read-only
	STATUS	mandatory
	DESCRIPTION	"Bridge-Tap length(in Feet or Meter)"
	::= { mibcltmRslt-BridgeTapTableEntry 4 }

    cltmRslt-BridgeTapTable-Confidence	OBJECT-TYPE
	SYNTAX	INTEGER
	ACCESS	read-only
	STATUS	mandatory
	DESCRIPTION	"confidence Level in percentage(33 or 55)"
	::= { mibcltmRslt-BridgeTapTableEntry 5 }


	-- The mibcltmRslt__tdr_distance_level table
	--
	-- This table contains parameters for the mibcltmRslt__tdr_distance_level profile
	--

    mibcltmRslt-TdrDistanceLevelTable	OBJECT-TYPE
	SYNTAX		SEQUENCE OF MibcltmRslt-TdrDistanceLevelEntry
	ACCESS		not-accessible
	STATUS		mandatory
	DESCRIPTION	"A list of mibcltmRslt__tdr_distance_level profile entries."
	::= { mibcltmRslt 3 }

    mibcltmRslt-TdrDistanceLevelEntry	OBJECT-TYPE
	SYNTAX		MibcltmRslt-TdrDistanceLevelEntry
	ACCESS		not-accessible
	STATUS		mandatory
	DESCRIPTION	"A mibcltmRslt__tdr_distance_level entry containing objects that
			 maps to the parameters of mibcltmRslt__tdr_distance_level profile."
	INDEX		{ cltmRslt-TdrDistanceLevel-Index-o, cltmRslt-TdrDistanceLevel-Index1-o }
	::= { mibcltmRslt-TdrDistanceLevelTable 1 }

    MibcltmRslt-TdrDistanceLevelEntry ::=
	SEQUENCE {
	    cltmRslt-TdrDistanceLevel-Index-o
		INTEGER,
	    cltmRslt-TdrDistanceLevel-Index1-o
		INTEGER,
	    cltmRslt-TdrDistanceLevel-Distance
		INTEGER,
	    cltmRslt-TdrDistanceLevel-Level
		INTEGER
	}

    cltmRslt-TdrDistanceLevel-Index-o	OBJECT-TYPE
	SYNTAX	INTEGER
	ACCESS	read-only
	STATUS	mandatory
	DESCRIPTION	""
	::= { mibcltmRslt-TdrDistanceLevelEntry 1 }

    cltmRslt-TdrDistanceLevel-Index1-o	OBJECT-TYPE
	SYNTAX	INTEGER
	ACCESS	read-only
	STATUS	mandatory
	DESCRIPTION	""
	::= { mibcltmRslt-TdrDistanceLevelEntry 2 }

    cltmRslt-TdrDistanceLevel-Distance	OBJECT-TYPE
	SYNTAX	INTEGER
	ACCESS	read-only
	STATUS	mandatory
	DESCRIPTION	"Distance."
	::= { mibcltmRslt-TdrDistanceLevelEntry 3 }

    cltmRslt-TdrDistanceLevel-Level	OBJECT-TYPE
	SYNTAX	INTEGER
	ACCESS	read-only
	STATUS	mandatory
	DESCRIPTION	"Level."
	::= { mibcltmRslt-TdrDistanceLevelEntry 4 }


	-- The mibcltmRslt__psd_frequency_level table
	--
	-- This table contains parameters for the mibcltmRslt__psd_frequency_level profile
	--

    mibcltmRslt-PsdFrequencyLevelTable	OBJECT-TYPE
	SYNTAX		SEQUENCE OF MibcltmRslt-PsdFrequencyLevelEntry
	ACCESS		not-accessible
	STATUS		mandatory
	DESCRIPTION	"A list of mibcltmRslt__psd_frequency_level profile entries."
	::= { mibcltmRslt 4 }

    mibcltmRslt-PsdFrequencyLevelEntry	OBJECT-TYPE
	SYNTAX		MibcltmRslt-PsdFrequencyLevelEntry
	ACCESS		not-accessible
	STATUS		mandatory
	DESCRIPTION	"A mibcltmRslt__psd_frequency_level entry containing objects that
			 maps to the parameters of mibcltmRslt__psd_frequency_level profile."
	INDEX		{ cltmRslt-PsdFrequencyLevel-Index-o, cltmRslt-PsdFrequencyLevel-Index1-o }
	::= { mibcltmRslt-PsdFrequencyLevelTable 1 }

    MibcltmRslt-PsdFrequencyLevelEntry ::=
	SEQUENCE {
	    cltmRslt-PsdFrequencyLevel-Index-o
		INTEGER,
	    cltmRslt-PsdFrequencyLevel-Index1-o
		INTEGER,
	    cltmRslt-PsdFrequencyLevel-Frequency
		INTEGER,
	    cltmRslt-PsdFrequencyLevel-Level
		INTEGER
	}

    cltmRslt-PsdFrequencyLevel-Index-o	OBJECT-TYPE
	SYNTAX	INTEGER
	ACCESS	read-only
	STATUS	mandatory
	DESCRIPTION	""
	::= { mibcltmRslt-PsdFrequencyLevelEntry 1 }

    cltmRslt-PsdFrequencyLevel-Index1-o	OBJECT-TYPE
	SYNTAX	INTEGER
	ACCESS	read-only
	STATUS	mandatory
	DESCRIPTION	""
	::= { mibcltmRslt-PsdFrequencyLevelEntry 2 }

    cltmRslt-PsdFrequencyLevel-Frequency	OBJECT-TYPE
	SYNTAX	INTEGER
	ACCESS	read-only
	STATUS	mandatory
	DESCRIPTION	"Test frequency."
	::= { mibcltmRslt-PsdFrequencyLevelEntry 3 }

    cltmRslt-PsdFrequencyLevel-Level	OBJECT-TYPE
	SYNTAX	INTEGER
	ACCESS	read-only
	STATUS	mandatory
	DESCRIPTION	"Db Level."
	::= { mibcltmRslt-PsdFrequencyLevelEntry 4 }

END
