Nortel-MsCarrier-MscPassport-AtmCoreMIB
DEFINITIONS ::= BEGIN



IMPORTS

      OBJECT-TYPE
   FROM RFC-1212

      mscPassportMIBs,
      mscComponents
   FROM Nortel-MsCarrier-MscPassport-UsefulDefinitionsMIB

      Counter32,
      DisplayString,
      StorageType,
      RowStatus,
      Gauge32,
      Integer32,
      Unsigned32
   FROM Nortel-MsCarrier-MscPassport-StandardTextualConventionsMIB

      AsciiString,
      Hex,
      NonReplicated,
      PassportCounter64,
      Link,
      FixedPoint9,
      AsciiStringIndex,
      IntegerSequence,
      FixedPoint7
   FROM Nortel-MsCarrier-MscPassport-TextualConventionsMIB;




-- LAST-UPDATED   "0101300000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     AtmCore Enterprise MIB."

atmCoreMIB OBJECT IDENTIFIER ::= { mscPassportMIBs 123 }










-- AtmInterface/n
-- An AtmIf component is provisioned for each ATM interface. It 
-- manages the set of ATM connections that terminate at or traverse 
-- the interface.

mscAtmIf OBJECT IDENTIFIER ::= { mscComponents 114 }



mscAtmIfRowStatusTable OBJECT-TYPE
   SYNTAX     SEQUENCE OF MscAtmIfRowStatusEntry
   ACCESS     not-accessible
   STATUS     mandatory
   DESCRIPTION
     "This entry controls the addition and deletion of 
      mscAtmIf components."
::= { mscAtmIf 1 }

mscAtmIfRowStatusEntry OBJECT-TYPE
   SYNTAX     MscAtmIfRowStatusEntry
   ACCESS     not-accessible
   STATUS     mandatory
   DESCRIPTION
     "A single entry in the table represents a single 
      mscAtmIf component."
   INDEX {
      mscAtmIfIndex }
::= { mscAtmIfRowStatusTable 1 }

MscAtmIfRowStatusEntry ::= SEQUENCE {
   mscAtmIfRowStatus
      RowStatus,
   mscAtmIfComponentName
      DisplayString,
   mscAtmIfStorageType
      StorageType,
   mscAtmIfIndex
      Integer32 }

mscAtmIfRowStatus OBJECT-TYPE
   SYNTAX     RowStatus 
   ACCESS     read-write
   STATUS     mandatory
   DESCRIPTION
     "This variable is used as the basis for SNMP naming of
      mscAtmIf components.
      These components can be added and deleted."
::= { mscAtmIfRowStatusEntry 1 }

mscAtmIfComponentName OBJECT-TYPE
   SYNTAX     DisplayString 
   ACCESS     read-only
   STATUS     mandatory
   DESCRIPTION
     "This variable provides the component's string name for
      use with the ASCII Console Interface"
::= { mscAtmIfRowStatusEntry 2 }

mscAtmIfStorageType OBJECT-TYPE
   SYNTAX     StorageType 
   ACCESS     read-only
   STATUS     mandatory
   DESCRIPTION
     "This variable represents the storage type value for the
      mscAtmIf tables."
::= { mscAtmIfRowStatusEntry 4 }

mscAtmIfIndex OBJECT-TYPE
   SYNTAX     Integer32 (1..4095)
   ACCESS     not-accessible
   STATUS     mandatory
   DESCRIPTION
     "This variable represents the index for the mscAtmIf tables."
::= { mscAtmIfRowStatusEntry 10 }

mscAtmIfCidDataTable OBJECT-TYPE
   SYNTAX     SEQUENCE OF MscAtmIfCidDataEntry
   ACCESS     not-accessible
   STATUS     mandatory
   DESCRIPTION
     "This group contains the attribute for a component's Customer 
      Identifier (CID). Refer to the attribute description for a detailed 
      explanation of CIDs."
::= { mscAtmIf 100 }

mscAtmIfCidDataEntry OBJECT-TYPE
   SYNTAX     MscAtmIfCidDataEntry
   ACCESS     not-accessible
   STATUS     mandatory
   DESCRIPTION
     "An entry in the mscAtmIfCidDataTable."
   INDEX {
      mscAtmIfIndex }
::= { mscAtmIfCidDataTable 1 }

MscAtmIfCidDataEntry ::= SEQUENCE {
   mscAtmIfCustomerIdentifier
      Unsigned32 }

mscAtmIfCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { mscAtmIfCidDataEntry 1 }

mscAtmIfProvTable OBJECT-TYPE
   SYNTAX     SEQUENCE OF MscAtmIfProvEntry
   ACCESS     not-accessible
   STATUS     mandatory
   DESCRIPTION
     "This group contains provisionable attributes for the AtmIf 
      component."
::= { mscAtmIf 110 }

mscAtmIfProvEntry OBJECT-TYPE
   SYNTAX     MscAtmIfProvEntry
   ACCESS     not-accessible
   STATUS     mandatory
   DESCRIPTION
     "An entry in the mscAtmIfProvTable."
   INDEX {
      mscAtmIfIndex }
::= { mscAtmIfProvTable 1 }

MscAtmIfProvEntry ::= SEQUENCE {
   mscAtmIfInterfaceName
      Link,
   mscAtmIfType
      INTEGER,
   mscAtmIfOamSegmentBoundary
      INTEGER,
   mscAtmIfMaxVpcs
      Unsigned32,
   mscAtmIfMaxVccs
      Unsigned32,
   mscAtmIfTrafficShaping
      INTEGER,
   mscAtmIfUnshapedTransmitQueueing
      INTEGER,
   mscAtmIfUsageParameterControl
      INTEGER,
   mscAtmIfMaxVpiBits
      Unsigned32,
   mscAtmIfRemoteAtmInterfaceLabel
      AsciiString,
   mscAtmIfTxCellMemory
      Unsigned32,
   mscAtmIfFaultHoldOffTime
      INTEGER,
   mscAtmIfCtdCalculation
      INTEGER }

mscAtmIfInterfaceName OBJECT-TYPE
   SYNTAX     Link 
   ACCESS     read-write
   STATUS     mandatory
   DESCRIPTION
     "This attribute associates the AtmIf component with a specific 
      interface on a Function Processorfor example, Lp/1 Ds3/0. This 
      implicitly defines the logical processor on which the AtmIf is 
      activated."
::= { mscAtmIfProvEntry 10 }

mscAtmIfType OBJECT-TYPE
   SYNTAX     INTEGER  {
                 uni(0),
                 ppi(1) }
   ACCESS     read-write
   STATUS     obsolete
   DESCRIPTION
     "This attribute indicates the type of AtmIf, either uni or ppi. These 
      types differ only in their handling of OAM cellsall connections 
      passing through a uni interface terminate segment loopback cells; 
      whereas a ppi interface permits these cells to be passed 
      transparently. This is obsoleted. The value is migrated into 
      oamSegmentBoundary.
      
      uni maps to yes. ppi maps to no."
   DEFVAL     { uni }
::= { mscAtmIfProvEntry 20 }

mscAtmIfOamSegmentBoundary OBJECT-TYPE
   SYNTAX     INTEGER  {
                 no(0),
                 yes(1) }
   ACCESS     read-write
   STATUS     mandatory
   DESCRIPTION
     "This attribute specifies whether the interface is on an OAM segment 
      boundary. 
      
      When yes is selected, the interface is on an OAM segment boundary 
      and all connections passing through the interface terminate OAM 
      segment cells. 
      
      When no is selected, the interface is not on an OAM segment 
      boundary and the interface permits the segment cells to be passed 
      transparently."
   DEFVAL     { yes }
::= { mscAtmIfProvEntry 30 }

mscAtmIfMaxVpcs OBJECT-TYPE
   SYNTAX     Unsigned32 (0..255)
   ACCESS     read-write
   STATUS     obsolete
   DESCRIPTION
     "This attribute specifies the maximum number of VPCs that can be 
      configured on this AtmIf. The value must not exceed the total 
      number of usable VPCs supported by this AtmIf (which is equal to 
      256 or (256 - (number of VPIs used for VCCs)), according to the 
      ConnectionMapping component).
      
      Furthermore, if the AtmIf is linked to an LogicalProcessor of 
      cardType other than 3pE3Atm, 3pDS3Atm, 3pOC3MmAtm, 
      3pOC3SmAtm, 3pE1Atm, 3pDS1Atm, 2pJ6MAtm, the sum of 
      (maxVccs + maxVpcs + 1) across all AtmIf linked to that Lp must be 
      less than or equal to the totalConnectionPoolCapacity attribute of 
      the Arc component. If the Arc component doesn't exist, the default 
      value of totalConnectionPoolCapacity is used as the limit.
      
      This attribute has been migrated to the Ca component."
   DEFVAL     { 128 }
::= { mscAtmIfProvEntry 40 }

mscAtmIfMaxVccs OBJECT-TYPE
   SYNTAX     Unsigned32 (0..16384)
   ACCESS     read-write
   STATUS     obsolete
   DESCRIPTION
     "This attribute specifies the maximum number of usable VCCs that 
      can be configured on this AtmIf. The value must not exceed the 
      number of non-reserved VCC identifiers in the Vcc space supported 
      by this AtmIf (which is specified by the ConnectionMapping 
      component).
      
      Furthermore, if the AtmIf is linked to an LogicalProcessor of 
      cardType other than 3pE3Atm, 3pDS3Atm, 3pOC3MmAtm, 
      3pOC3SmAtm, 3pE1Atm, 3pDS1Atm, 2pJ6MAtm, the sum of 
      (maxVccs + maxVpcs + 1) across all AtmIf linked to that Lp must be 
      less than the totalConnectionPoolCapacity attribute of the Arc 
      component. If the Arc component doesn't exist, the default value of 
      totalConnectionPoolCapacity is used as the limit.
      
      This attribute has been migrated to the Ca component."
   DEFVAL     { 255 }
::= { mscAtmIfProvEntry 50 }

mscAtmIfTrafficShaping OBJECT-TYPE
   SYNTAX     INTEGER  {
                 enabled(0),
                 disabled(1) }
   ACCESS     read-write
   STATUS     obsolete
   DESCRIPTION
     "It is migrated in P6.0 to a combination of the trafficShaping 
      attributes and the emissionPriority attributes under each ATM 
      service category component of the AtmIf CA.
      
      This attribute defines whether traffic shaping is enabled or disabled 
      for the entire AtmIf. When this attribute is set to enabled, each 
      provisioned connection under the interface can be individually 
      provisioned to permit or prohibit traffic shaping. When this attribute 
      is set to disabled, no traffic shaping is performed on the transmit 
      path for any of the connections. This attribute may be set to enabled 
      if the interface supports shaping, as defined by the 
      perVcQueueInterfaces attribute in the AtmResourceControl 
      component. If the AtmResourceControl component does not exist, 
      this attribute may not be set to enabled."
   DEFVAL     { disabled }
::= { mscAtmIfProvEntry 60 }

mscAtmIfUnshapedTransmitQueueing OBJECT-TYPE
   SYNTAX     INTEGER  {
                 perVc(0),
                 common(1),
                 autoConfigure(2) }
   ACCESS     read-write
   STATUS     obsolete
   DESCRIPTION
     "It is migrated in P6.0 to the attributes of the same name under each 
      ATM service category component of the AtmIf CA.
      
      This attribute applies only for unshaped VCC and VPC 
      connections. This attribute defines the transmit queueing method for 
      all unshaped connections under this AtmIf. Per-VC queueing means 
      that unshaped connections are treated with the same fairness as 
      shaped queues in the transmit round-robin scheduling. The 
      alternative to per-VC queueing is to use the common queue for a 
      particular service category (medium or low priority). The common 
      queue is only counted as one queue in the transmit round-robin 
      scheduling. Thus, if there are multiple connections which are 
      destined for the common queue, they are not fairly allocated a 
      portion of the transmit bandwidth compared to shaped connections. 
      
      When this attribute is set to perVc, any unshaped connection is 
      allocated its own per-VC queue, and is treated with the same 
      fairness as any shaped connections. Per-VC queues have a 
      maximum rate of 58,962 cell/s (25 Mbit/s) in a multi-port shaping 
      configuration. Per-VC queues also have their own congestion 
      control level. This means that total number of cell/frame blocks 
      allocated for several per-VC queues are higher than would be 
      allowed on the common queue. This can be an advantage in 
      reducing cell loss due to queue congestion. This attribute may only 
      be set to perVc if the interface supports per-VC queueing, (specified 
      by the perVcQueueInterfaces attribute in the AtmResourceControl 
      component).
      
      When this attribute is set to common, any unshaped connection is 
      destined for the common queue. The common queue has one set of 
      congestion control levels for all cells enqueued on it. The common 
      queue is only allocated one queue position when scheduling which 
      queue to transmit from. Due to the possibility of unfairness, this 
      value is only recommended in cases where the configuration cannot 
      otherwise achieve full link utilization. 
      
      When this attribute is set to autoConfigure and the interface 
      support per-VC queueing (specified by the perVcQueueInterfaces 
      attribute in the AtmResourceControl component) per-VC queueing 
      is enabled for all unshaped connections. Otherwise, the common 
      queue is used. The unshapedTransmitQueueingOper attribute 
      indicates whether the transmit queueing is perVc or common."
   DEFVAL     { autoConfigure }
::= { mscAtmIfProvEntry 70 }

mscAtmIfUsageParameterControl OBJECT-TYPE
   SYNTAX     INTEGER  {
                 enabled(0),
                 disabled(1) }
   ACCESS     read-write
   STATUS     obsolete
   DESCRIPTION
     "It is migrated in P6.0 to the attributes of the same name under each 
      ATM service category component of the AtmIf CA.
      
      This attribute defines whether usage parameter control (UPC) is 
      enabled or disabled for receive traffic for Vcc and Vpc connections 
      for this entire AtmIf. When this attribute is set to enabled, each 
      provisioned connection under the interface can be individually 
      provisioned to enforce or ignore UPC. When this attribute is set to 
      disabled, UPC cannot be enabled on the receive path for any of the 
      connections."
   DEFVAL     { disabled }
::= { mscAtmIfProvEntry 80 }

mscAtmIfMaxVpiBits OBJECT-TYPE
   SYNTAX     Unsigned32 (8 | 12)
   ACCESS     read-write
   STATUS     mandatory
   DESCRIPTION
     "This attribute specifies the maximum number of VPI bits that may 
      be active for this AtmIf. These bits start at the least significant bit 
      position and are contiguous. In general, the maximum VPI which 
      may be used on the interface is 2**maxVpiBits - 1. The value of the 
      remaining (inactive) VPI bits is ignored on cells received from the 
      link.
      
      If the AtmIf is linked to a LogicalProcessor of cardType 
      3pOC3MmAtm, 3pOC3SmAtm, 3pE3Atm, 3pDS3Atm, 3pE1Atm, 
      3pDS1Atm, or 2pJ6MAtm, the value of this attribute must be 8. The 
      maximum VPI supported on these card types is 255.
      
      If the AtmIf is linked to a LogicalProcessor of any other cardType, 
      the value of this attribute may be 8 or 12. The maximum VPI 
      supported on these card types is 4095. An exception is that 
      cardType 8pE1Atm and 8pDS1Atm do not support VPI 4095; the 
      maximum VPI on these card types is 4094.
      
      If a Uni or an Iisp component is present directly under the AtmIf, 
      the value of this attribute must be 8."
   DEFVAL     { 8 }
::= { mscAtmIfProvEntry 85 }

mscAtmIfRemoteAtmInterfaceLabel OBJECT-TYPE
   SYNTAX     AsciiString (SIZE (0..60))
   ACCESS     read-write
   STATUS     mandatory
   DESCRIPTION
     "This attribute specifies a unique indication of the remote ATM 
      service or interface component connected to this one. The value of 
      this attribute can be used by network management applications to 
      discover the network's ATM topology from its configuration 
      information.
      
      The syntax of the value, such as component ID, address, or other 
      numerical identifier, must follow the conventions of the network 
      management platform. In absence of such convention or platform, 
      the value should be left empty.
      
      The value is only stored by the module. It is neither validated nor 
      used to perform any form of remote connectivity validation."
   DEFVAL     { ''H }  -- ""
::= { mscAtmIfProvEntry 90 }

mscAtmIfTxCellMemory OBJECT-TYPE
   SYNTAX     Unsigned32 (1..100)
   ACCESS     read-write
   STATUS     mandatory
   DESCRIPTION
     "This attribute specifies the percentage of the Lp/x Eng Arc Aqm/0 
      txCellMemoryThreshold 0 attribute. This attribute only applies to 
      ATM IP FPs. It is ignored on all other card types. 
      
      For ATM IP FPs, the cell memory which is displayed in Lp/x Eng 
      Arc Aqm/0 txCellMemoryThreshold 0 is shared across all interfaces 
      for the card. This attribute allows the allocation of a specific 
      proportion of the transmit cell memory for the use of connections 
      under this AtmIf. 
      
      If the value of this attribute is specified as 100, connections under 
      this AtmIf may use up to 100% of the transmit cell memory. If this 
      attribute is specified as an amount less than 100, then only that 
      percentage of the transmit cell memory may be used by connections 
      under this AtmIf. By specifying values for this attribute under the 
      AtmIf's on a DS3, E3 or MSA32 card, you can limit the transmit 
      cell memory usage for each AtmIf. This is used to guarantee that all 
      cell traffic for an AtmIf will respect the cell loss priority (CLP) bit 
      settings regardless of the atmServiceCategory for the connection."
   DEFVAL     { 100 }
::= { mscAtmIfProvEntry 91 }

mscAtmIfFaultHoldOffTime OBJECT-TYPE
   SYNTAX     INTEGER  {
                 n0(0),
                 infinity(65535) }
   ACCESS     read-write
   STATUS     mandatory
   DESCRIPTION
     "This attribute specifies the delay before faults detected at the VP 
      layer are propagated to the VC layer, and thus to the application 
      using the connection.
      
      If the value is 0 (zero), applications using a VirtualPathTerminator 
      are immediately notified of faults detected by the VP. Using this 
      value allows these applications to be advised of faults without 
      requiring loopbacks on each Vcc. Typically, the application goes out 
      of service when advised of a fault.
      
      If the value is infinity, applications are not notified of VP layer 
      faults. Using this value allows the applications to survive transient 
      VP layer fault conditions.
      
      The value chosen applies only to Vpts and Vccs directly beneath a 
      Vpt."
   DEFVAL     { infinity }
::= { mscAtmIfProvEntry 100 }

mscAtmIfCtdCalculation OBJECT-TYPE
   SYNTAX     INTEGER  {
                 off(0),
                 on(1) }
   ACCESS     read-write
   STATUS     mandatory
   DESCRIPTION
     "This attribute specifies whether cell transfer delay calculation 
      should be performed on loopback cells for each SPVC and SPVP 
      connection under this interface. 
      
      Cell transfer delay is calculated as half of the measured segment 
      round trip delay of a loopback cell.
      
      Cell transfer delay calculation is only supported when segment 
      switch side loopback is enabled on the source segment endpoint. 
      Cell transfer delay calculation is only performed on supported 
      connections when the accountCollection attribute of the AtmIf Uni 
      or AtmIf Iisp component has a non-empty reason. Cell transfer delay 
      calculation is not provided for connections under the Vpt."
   DEFVAL     { off }
::= { mscAtmIfProvEntry 110 }

mscAtmIfLbkTable OBJECT-TYPE
   SYNTAX     SEQUENCE OF MscAtmIfLbkEntry
   ACCESS     not-accessible
   STATUS     mandatory
   DESCRIPTION
     "This group contains the default loopback attribute 
      values for all Vcc, Vpc and Vpt components. Note that these 
      attribute values can be overridden by setting different values in the 
      Vcd component of the provisioned Vcc or the Vpd component of the 
      provisioned Vpc or Vpt.
      
      Certain loopback requests may not be possible on a given 
      connection. In such cases, the corresponding operational loopback 
      attribute in the AtmStatus group of the Vcc, Vpc, or Vpt component 
      is set to notApplicable and the requested loopback is not performed."
::= { mscAtmIf 120 }

mscAtmIfLbkEntry OBJECT-TYPE
   SYNTAX     MscAtmIfLbkEntry
   ACCESS     not-accessible
   STATUS     mandatory
   DESCRIPTION
     "An entry in the mscAtmIfLbkTable."
   INDEX {
      mscAtmIfIndex }
::= { mscAtmIfLbkTable 1 }

MscAtmIfLbkEntry ::= SEQUENCE {
   mscAtmIfSegLinkSideLoopback
      INTEGER,
   mscAtmIfSegSwitchSideLoopback
      INTEGER,
   mscAtmIfEndToEndLoopback
      INTEGER }

mscAtmIfSegLinkSideLoopback OBJECT-TYPE
   SYNTAX     INTEGER  {
                 on(0),
                 off(1) }
   ACCESS     read-write
   STATUS     mandatory
   DESCRIPTION
     "This attribute specifies the default value for link-side segment 
      loopback insertion for all connections under this interface. Link-
      side segment loopback is not possible if the oamSegmentBoundary 
      attribute of the AtmIf component is no."
   DEFVAL     { off }
::= { mscAtmIfLbkEntry 10 }

mscAtmIfSegSwitchSideLoopback OBJECT-TYPE
   SYNTAX     INTEGER  {
                 on(0),
                 off(1) }
   ACCESS     read-write
   STATUS     mandatory
   DESCRIPTION
     "This attribute specifies the default value for switch-side segment 
      loopback insertion for all connections under this interface. Switch-
      side segment loopback is not possible if the oamSegmentBoundary 
      attribute of the AtmIf component is no."
   DEFVAL     { off }
::= { mscAtmIfLbkEntry 20 }

mscAtmIfEndToEndLoopback OBJECT-TYPE
   SYNTAX     INTEGER  {
                 on(0),
                 off(1) }
   ACCESS     read-write
   STATUS     mandatory
   DESCRIPTION
     "This attribute specifies the default value for end-to-end loopback 
      insertion for all connections under this interface. End-to-end 
      loopback insertion is not possible if the connectionPointType 
      attribute of the Vcc or Vpc component is connectingPoint or 
      segmentEndPoint. End-to-end loopback insertion is possible if the 
      connectionPointType attribute of the Vcc or Vpc component is 
      connectionEndPoint. End-to-end loopback insertion is always 
      possible on a Vpt component."
   DEFVAL     { off }
::= { mscAtmIfLbkEntry 30 }

mscAtmIfStateTable OBJECT-TYPE
   SYNTAX     SEQUENCE OF MscAtmIfStateEntry
   ACCESS     not-accessible
   STATUS     mandatory
   DESCRIPTION
     "This group contains the three OSI State attributes and the six OSI 
      Status attributes. The descriptions generically indicate what each 
      attribute implies about the component. Note that not all the values 
      and state combinations described here are supported by every 
      component which reuses this group. For component-specific 
      information and the valid state combinations, refer to the 
      appropriate NTP."
::= { mscAtmIf 130 }

mscAtmIfStateEntry OBJECT-TYPE
   SYNTAX     MscAtmIfStateEntry
   ACCESS     not-accessible
   STATUS     mandatory
   DESCRIPTION
     "An entry in the mscAtmIfStateTable."
   INDEX {
      mscAtmIfIndex }
::= { mscAtmIfStateTable 1 }

MscAtmIfStateEntry ::= SEQUENCE {
   mscAtmIfAdminState
      INTEGER,
   mscAtmIfOperationalState
      INTEGER,
   mscAtmIfUsageState
      INTEGER,
   mscAtmIfAvailabilityStatus
      OCTET STRING,
   mscAtmIfProceduralStatus
      OCTET STRING,
   mscAtmIfControlStatus
      OCTET STRING,
   mscAtmIfAlarmStatus
      OCTET STRING,
   mscAtmIfStandbyStatus
      INTEGER,
   mscAtmIfUnknownStatus
      INTEGER }

mscAtmIfAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock -force or 
      Lock command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mscAtmIfStateEntry 1 }

mscAtmIfOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mscAtmIfStateEntry 2 }

mscAtmIfUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mscAtmIfStateEntry 3 }

mscAtmIfAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below is present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. Usually, the resource remains available for service. The 
      operationalState is almost always enabled. There is one exception 
      where an operationalState of disabled is used in conjunction with 
      degraded for a component which represents a rolled up view of a 
      set of other components.
      
      The value notInstalled indicates the resource is not present. The 
      operationalState is disabled.
      
      The value logFull is not used.
      
      The value migrating indicates that a software migration activation 
      is in progress, making the component unavailable for other 
      activities until the migration is complete.

      Description of bits:
      inTest(0)
      failed(1)
      powerOff(2)
      offLine(3)
      offDuty(4)
      dependency(5)
      degraded(6)
      notInstalled(7)
      logFull(8)
      migrating(9)"
::= { mscAtmIfStateEntry 4 }

mscAtmIfProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below is present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mscAtmIfStateEntry 5 }

mscAtmIfControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below is present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mscAtmIfStateEntry 6 }

mscAtmIfAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below is present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mscAtmIfStateEntry 7 }

mscAtmIfStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below is present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mscAtmIfStateEntry 8 }

mscAtmIfUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mscAtmIfStateEntry 9 }

mscAtmIfOperTable OBJECT-TYPE
   SYNTAX     SEQUENCE OF MscAtmIfOperEntry
   ACCESS     not-accessible
   STATUS     mandatory
   DESCRIPTION
     "This group contains operational attributes which show the status of 
      the AtmIf component."
::= { mscAtmIf 140 }

mscAtmIfOperEntry OBJECT-TYPE
   SYNTAX     MscAtmIfOperEntry
   ACCESS     not-accessible
   STATUS     mandatory
   DESCRIPTION
     "An entry in the mscAtmIfOperTable."
   INDEX {
      mscAtmIfIndex }
::= { mscAtmIfOperTable 1 }

MscAtmIfOperEntry ::= SEQUENCE {
   mscAtmIfTxCellMemoryAvailable
      Gauge32,
   mscAtmIfTxCellMemoryCongestionState
      Gauge32,
   mscAtmIfUnshapedTransmitQueueingOper
      INTEGER }

mscAtmIfTxCellMemoryAvailable OBJECT-TYPE
   SYNTAX     Gauge32 (0..163839)
   ACCESS     read-only
   STATUS     mandatory
   DESCRIPTION
     "This attribute is only valid for AtmIf's on ATM IP FPs. It is not 
      displayed for AtmIf's on other card types. 
      
      This attribute indicates the current amount of transmit cells 
      available for this AtmIf. Transmit cell memory is the memory 
      available for storing ATM cells to be transmitted by connections 
      under this AtmIf."
::= { mscAtmIfOperEntry 1 }

mscAtmIfTxCellMemoryCongestionState OBJECT-TYPE
   SYNTAX     Gauge32 (0..3)
   ACCESS     read-only
   STATUS     mandatory
   DESCRIPTION
     "This attribute is only valid for AtmIf's on ATM IP FPs. It is not 
      displayed for AtmIf's on other card types. 
      
      This attribute indicates the congestion state of the transmit  cell 
      memory for this AtmIf. It indicates which txCellMemoryThreshold 
      corresponds to the current value of txCellMemoryAvailable. 
      
      The congestion state of memory is indicated by a numeric value 
      ranging from 0 to 3. When memory is in a congested state 'x', only 
      traffic with discard priority (DP) < 'x' is definitely still queued for 
      transmit. Traffic with DP > 'x' is definitely discarded. Traffic with 
      DP = 'x' may be either queued or discarded depending on how 
      close the value of txCellMemoryAvailable is to the next threshold as 
      displayed in txCellMemoryThreshold. For example, CLP1 traffic is 
      queued until the value indicated by txCellMemoryAvailable reaches 
      the DP3 threshold. At that point, the CLP1 traffic is discarded."
::= { mscAtmIfOperEntry 2 }

mscAtmIfUnshapedTransmitQueueingOper OBJECT-TYPE
   SYNTAX     INTEGER  {
                 perVc(0),
                 common(1) }
   ACCESS     read-only
   STATUS     obsolete
   DESCRIPTION
     "This attribute is HISTORICAL in P6.0.
      
      This attribute indicates the state of transmit queuing for unshaped 
      connections under this AtmIf. 
      
      A value of perVc indicates that any unshaped connections use per-
      VC queueing in the CQC. A value of common indicates that traffic 
      for unshaped connections uses the common queue which 
      corresponds to the atmServiceCategory for this connection."
::= { mscAtmIfOperEntry 10 }

mscAtmIfStatsTable OBJECT-TYPE
   SYNTAX     SEQUENCE OF MscAtmIfStatsEntry
   ACCESS     not-accessible
   STATUS     mandatory
   DESCRIPTION
     "This group contains operational attributes which keep statistics 
      about the behavior of the AtmIf component."
::= { mscAtmIf 150 }

mscAtmIfStatsEntry OBJECT-TYPE
   SYNTAX     MscAtmIfStatsEntry
   ACCESS     not-accessible
   STATUS     mandatory
   DESCRIPTION
     "An entry in the mscAtmIfStatsTable."
   INDEX {
      mscAtmIfIndex }
::= { mscAtmIfStatsTable 1 }

MscAtmIfStatsEntry ::= SEQUENCE {
   mscAtmIfTransmittedCells
      PassportCounter64,
   mscAtmIfTxCell
      PassportCounter64,
   mscAtmIfTxCellClp
      PassportCounter64,
   mscAtmIfTxCellEfci
      PassportCounter64,
   mscAtmIfTxCellDiscard
      PassportCounter64,
   mscAtmIfTxCellDiscardClp
      PassportCounter64,
   mscAtmIfTxFrameDiscard
      PassportCounter64,
   mscAtmIfTxFrameDiscardClp
      PassportCounter64,
   mscAtmIfReceivedCells
      PassportCounter64,
   mscAtmIfRxCell
      PassportCounter64,
   mscAtmIfRxCellClp
      PassportCounter64,
   mscAtmIfRxCellEfci
      PassportCounter64,
   mscAtmIfRxCellDiscard
      PassportCounter64,
   mscAtmIfRxCellDiscardClp
      PassportCounter64,
   mscAtmIfRxFrameDiscard
      PassportCounter64,
   mscAtmIfRxFrameDiscardClp
      PassportCounter64,
   mscAtmIfDroppedRxCells
      PassportCounter64,
   mscAtmIfLastDroppedRxCellConnection
      IntegerSequence,
   mscAtmIfAal5RxErrors
      Counter32,
   mscAtmIfLastAal5RxErrorConnection
      IntegerSequence,
   mscAtmIfLrcFrameErrors
      Counter32,
   mscAtmIfLastLrcFrameErrorConnection
      IntegerSequence,
   mscAtmIfAal5RxAborts
      Counter32,
   mscAtmIfLastAal5RxAbortConnection
      IntegerSequence,
   mscAtmIfTxLinkUtilization
      Gauge32,
   mscAtmIfRxLinkUtilization
      Gauge32 }

mscAtmIfTransmittedCells OBJECT-TYPE
   SYNTAX     PassportCounter64 
   ACCESS     read-only
   STATUS     obsolete
   DESCRIPTION
     "This attribute is renamed in P6.0 to txCell for naming compatibility 
      with the Vcc and Vpc components.
      
      This attribute counts cells transmitted from the ATM interface. The 
      counter is reset to zero when the component is created, or when any 
      critical attribute of the component is changed. The counter wraps to 
      zero when it exceeds the maximum value of (2**64)-1."
::= { mscAtmIfStatsEntry 10 }

mscAtmIfTxCell OBJECT-TYPE
   SYNTAX     PassportCounter64 
   ACCESS     read-only
   STATUS     mandatory
   DESCRIPTION
     "This attribute counts cells transmitted from the ATM interface. It 
      does not include cells discarded due to congestion before transmit. 
      The counter is reset to zero when the component is activated, or 
      when any critical attribute of the component is changed. The 
      counter wraps to zero when it exceeds its maximum value of 
      (2**64)-1."
::= { mscAtmIfStatsEntry 13 }

mscAtmIfTxCellClp OBJECT-TYPE
   SYNTAX     PassportCounter64 
   ACCESS     read-only
   STATUS     mandatory
   DESCRIPTION
     "This attribute is not applicable and is not displayed on CQC-based 
      ATM cards. 
      
      This attribute counts cells transmitted from the ATM interface 
      which have the CLP bit set to 1. This count is included in the txCell 
      attribute. The counter is reset to zero when the component is 
      activated, or when any critical attribute of the component is 
      changed. The counter wraps to zero when it exceeds its maximum 
      value of (2**64)-1."
::= { mscAtmIfStatsEntry 14 }

mscAtmIfTxCellEfci OBJECT-TYPE
   SYNTAX     PassportCounter64 
   ACCESS     read-only
   STATUS     mandatory
   DESCRIPTION
     "This attribute is not applicable and is not displayed on CQC-based 
      ATM cards. 
      
      This attribute counts cells transmitted from the ATM interface 
      which have the EFCI bit set to 1. This count is included in the 
      txCell attribute. The counter is reset to zero when the component is 
      activated, or when any critical attribute of the component is 
      changed. The counter wraps to zero when it exceeds its maximum 
      value of (2**64)-1."
::= { mscAtmIfStatsEntry 15 }

mscAtmIfTxCellDiscard OBJECT-TYPE
   SYNTAX     PassportCounter64 
   ACCESS     read-only
   STATUS     mandatory
   DESCRIPTION
     "This attribute is not applicable and is not displayed on CQC-based 
      ATM cards. 
      
      This attribute counts cells discarded and not transmitted out the 
      ATM interface. Since cells are discarded before they are 
      transmitted, this count is not included in the txCell attribute. This 
      count is independent of the txFrameDiscard attribute. 
      
      Transmit cells are discarded due to transmit congestion, Partial 
      Packet Discard (PPD), Early Packet Discard (EPD), and Weighted 
      Random Early Detection (W-RED) mechanisms, or when the 
      connection's interface is disabled.
      
      The counter is reset to zero when the component is activated, or 
      when any critical attribute of the component is changed. The 
      counter wraps to zero when it exceeds its maximum value of 
      (2**64)-1."
::= { mscAtmIfStatsEntry 16 }

mscAtmIfTxCellDiscardClp OBJECT-TYPE
   SYNTAX     PassportCounter64 
   ACCESS     read-only
   STATUS     mandatory
   DESCRIPTION
     "This attribute is not applicable and is not displayed on CQC-based 
      ATM cards. 
      
      This attribute counts cells discarded and not transmitted out the 
      ATM interface which have the CLP bit set to 1. Since cells are 
      discarded before they are transmitted, this count is not included in 
      the txCellClp attribute. This count is included in the txCellDiscard 
      attribute, but it is independent of the txFrameDiscardClp attribute. 
      
      Transmit cells are discarded due to transmit congestion, Partial 
      Packet Discard (PPD), Early Packet Discard (EPD), and Weighted 
      Random Early Detection (W-RED) mechanisms, or when the 
      connection's interface is disabled.
      
      The counter is reset to zero when the component is activated, or 
      when any critical attribute of the component is changed. The 
      counter wraps to zero when it exceeds its maximum value of 
      (2**64)-1."
::= { mscAtmIfStatsEntry 17 }

mscAtmIfTxFrameDiscard OBJECT-TYPE
   SYNTAX     PassportCounter64 
   ACCESS     read-only
   STATUS     mandatory
   DESCRIPTION
     "This attribute is not applicable and is not displayed on CQC-based 
      ATM cards. 
      
      This attribute counts frames discarded and not transmitted out the 
      ATM interface. This count is independent of txCellDiscard. 
      
      Transmit frames are discarded due to congestion, Partial Packet 
      Discard (PPD), Early Packet Discard (EPD), and Weighted Random 
      Early Detection (W-RED) mechanisms, or when the connection 
      interface is disabled.
      
      The counter is reset to zero when the component is activated, or 
      when any critical attribute of the component is changed. The 
      counter wraps to zero when it exceeds its maximum value of 
      (2**64)-1."
::= { mscAtmIfStatsEntry 18 }

mscAtmIfTxFrameDiscardClp OBJECT-TYPE
   SYNTAX     PassportCounter64 
   ACCESS     read-only
   STATUS     mandatory
   DESCRIPTION
     "This attribute is not applicable and is not displayed on CQC-based 
      ATM cards. 
      
      This attribute counts frames which have at least one cell with the 
      CLP bit set to 1, and have been discarded and not transmitted out 
      the ATM interface. It is independent of the txCellDiscard attribute. 
      This count is included in the txFrameDiscard attribute. 
      
      Transmit frames are discarded due to congestion, Partial Packet 
      Discard (PPD), Early Packet Discard (EPD), and Weighted Random 
      Early Detection (W-RED) mechanisms, or when the connection 
      interface is disabled.
      
      The counter is reset to zero when the component is activated, or 
      when any critical attribute of the component is changed. The 
      counter wraps to zero when it exceeds its maximum value of 
      (2**64)-1."
::= { mscAtmIfStatsEntry 19 }

mscAtmIfReceivedCells OBJECT-TYPE
   SYNTAX     PassportCounter64 
   ACCESS     read-only
   STATUS     obsolete
   DESCRIPTION
     "This attribute is renamed in P6.0 to rxCell for naming compatibility 
      with the Vcc and Vpc component.
      
      This attribute counts valid cells received from the ATM interface. 
      The counter is reset to zero when the component is created, or when 
      any critical attribute of the component is changed. The counter 
      wraps to zero when it exceeds its maximum value of (2**64)-1."
::= { mscAtmIfStatsEntry 20 }

mscAtmIfRxCell OBJECT-TYPE
   SYNTAX     PassportCounter64 
   ACCESS     read-only
   STATUS     mandatory
   DESCRIPTION
     "This attribute counts valid cells received from the ATM interface. 
      This count includes cells which may be subsequently discarded. 
      The counter is reset to zero when the component is activated, or 
      when any critical attribute of the component is changed. On ATM 
      IP FPs valid cells include cells that arrive on a VCC whose 
      VPI.VCI cannot be identified. These cells are also counted under 
      the droppedRxCell attribute. The value of this attribute on ATM IP 
      FPs should be greater than or equal to the sum of droppedRxCell 
      and all the VCC and VPC rxCell attributes under this interface. The 
      counter wraps to zero when it exceeds its maximum value of 
      (2**64)-1."
::= { mscAtmIfStatsEntry 23 }

mscAtmIfRxCellClp OBJECT-TYPE
   SYNTAX     PassportCounter64 
   ACCESS     read-only
   STATUS     mandatory
   DESCRIPTION
     "This attribute is not applicable and is not displayed on CQC-based 
      ATM cards. 
      
      This attribute counts valid cells received from the ATM interface 
      which have the CLP bit set to 1. This count includes cells which 
      may be subsequently discarded. This count is included in the rxCell 
      attribute. The counter is reset to zero when the component is 
      activated, or when any critical attribute of the component is 
      changed. The counter wraps to zero when it exceeds its maximum 
      value of (2**64)-1."
::= { mscAtmIfStatsEntry 24 }

mscAtmIfRxCellEfci OBJECT-TYPE
   SYNTAX     PassportCounter64 
   ACCESS     read-only
   STATUS     mandatory
   DESCRIPTION
     "This attribute is not applicable and is not displayed on CQC-based 
      ATM cards. 
      
      This attribute counts valid cells received from the ATM interface 
      which have the EFCI bit set to 1. This count includes cells which 
      may be subsequently discarded. This count is included in the rxCell 
      attribute. The counter is reset to zero when the component is 
      activated, or when any critical attribute of the component is 
      changed. The counter wraps to zero when it exceeds its maximum 
      value of (2**64)-1."
::= { mscAtmIfStatsEntry 25 }

mscAtmIfRxCellDiscard OBJECT-TYPE
   SYNTAX     PassportCounter64 
   ACCESS     read-only
   STATUS     mandatory
   DESCRIPTION
     "This attribute is not applicable and is not displayed on CQC-based 
      ATM cards. 
      
      This attribute counts cells received from the ATM interface which 
      have been discarded. This count is included in the rxCell attribute. 
      
      This count includes cells discarded due to non-conformance with 
      UPC, cells which are part of a frame which has been discarded due 
      to an AAL5 frame reassembly error, cells which are discarded due 
      to congestion, or cells which are received while the next hop 
      connection to which the traffic is directed across the backplane is 
      down. The next hop connection is the Vcc or Vpc identified by the 
      nextHop attribute of the Nrp or Rp component. 
      
      The counter is reset to zero when the component is activated, or 
      when any critical attribute of the component is changed. The 
      counter wraps to zero when it exceeds its maximum value of 
      (2**64)-1."
::= { mscAtmIfStatsEntry 26 }

mscAtmIfRxCellDiscardClp OBJECT-TYPE
   SYNTAX     PassportCounter64 
   ACCESS     read-only
   STATUS     mandatory
   DESCRIPTION
     "This attribute is not applicable and is not displayed on CQC-based 
      ATM cards. 
      
      This attribute counts valid cells received from the ATM interface 
      which have the CLP bit set to 1, which have been discarded. This 
      count is included in the rxCell and rxCellDiscard attributes. 
      
      This count includes cells discarded due to non-conformance with 
      UPC, cells which are part of a frame which has been discarded due 
      to an AAL5 frame reassembly error, cells which are discarded due 
      to congestion, or cells which are received while the next hop 
      connection to which the traffic is directed across the backplane is 
      down. The next hop connection is the Vcc or Vpc identified by the 
      nextHop attribute of the Nrp or Rp component. 
      
      This counter is reset to zero when the component is activated, or 
      when any critical attribute of the component is changed. The 
      counter wraps to zero when it exceeds its maximum value of 
      (2**64)-1."
::= { mscAtmIfStatsEntry 27 }

mscAtmIfRxFrameDiscard OBJECT-TYPE
   SYNTAX     PassportCounter64 
   ACCESS     read-only
   STATUS     mandatory
   DESCRIPTION
     "This attribute is not applicable and is not displayed on CQC-based 
      ATM cards. 
      
      This attribute counts frames received from the ATM interface which 
      have been discarded. This count includes the count of 
      rxFrameDiscardClp and aal5RxErrors. It is independent of the 
      rxCellDiscard attribute. 
      
      This count includes frames discarded due to an AAL5 frame 
      reassembly error, frames discarded due to early packet discard 
      (EPD), and frames discarded due to processor (CPU) congestion. 
      This attribute is applicable only for connections that reassemble 
      incoming cells into frames. Connections which reassemble cells 
      into frames have a connectionPointType of connectionEndPoint. 
      AAL1 connections are an exception to this rule; even though they 
      have a connectionPointType of connectionEndPoint, they do not 
      do adaptation at this point.
      
      The counter is reset to zero when the component is activated, or 
      when any critical attribute of the component is changed. The 
      counter wraps to zero when it exceeds its maximum value of 
      (2**64)-1."
::= { mscAtmIfStatsEntry 28 }

mscAtmIfRxFrameDiscardClp OBJECT-TYPE
   SYNTAX     PassportCounter64 
   ACCESS     read-only
   STATUS     mandatory
   DESCRIPTION
     "This attribute is not applicable and is not displayed on CQC-based 
      ATM cards. 
      
      This attribute counts frames received from the ATM interface which 
      have been discarded and which have at least one cell with the CLP 
      bit set to 1. This count is included in the rxFrameDiscard attribute. 
      It is independent of the rxCellDiscardClp attribute. 
      
      This count includes frames discarded due to an AAL5 frame 
      reassembly error, frames discarded due to early packet discard 
      (EPD), and frames discarded due to processor (CPU) congestion. 
      This attribute is applicable only for connections that reassemble 
      incoming cells into frames. Connections which reassemble cells 
      into frames have a connectionPointType of connectionEndPoint. 
      AAL1 connections are an exception to this rule; even though they 
      have a connectionPointType of connectionEndPoint, they do not 
      do adaptation at this point.
      
      The counter is reset to zero when the component is activated, or 
      when any critical attribute of the component is changed. The 
      counter wraps to zero when it exceeds its maximum value of 
      (2**64)-1."
::= { mscAtmIfStatsEntry 29 }

mscAtmIfDroppedRxCells OBJECT-TYPE
   SYNTAX     PassportCounter64 
   ACCESS     read-only
   STATUS     mandatory
   DESCRIPTION
     "This attribute counts cells received from the interface that were 
      dropped because they contained invalid VPI or VCI values, or 
      dropped because they had no associated connection for the VPI or 
      VCI. On ATM IP FPs this count is included in the rxCell count for 
      the interface. Note that this attribute does not keep an exact count. 
      Idle cells and unassigned cells are ignored without being counted as 
      dropped cells. The counter is reset to zero when the component is 
      created, or when any critical attribute of the component is changed. 
      The counter wraps to zero when it exceeds its maximum value of 
      (2**64)-1. 
      
      The VPI and VCI of the last dropped cell are indicated in the 
      attribute lastDroppedRxCellConnection."
::= { mscAtmIfStatsEntry 30 }

mscAtmIfLastDroppedRxCellConnection OBJECT-TYPE
   SYNTAX     IntegerSequence (SIZE (3..10))
   ACCESS     read-only
   STATUS     mandatory
   DESCRIPTION
     "This attribute indicates the VPI and VCI of the last cell that was 
      dropped. Cells are dropped because they have no associated 
      connection for the VPI and VCI.
      
      Dropped cells are counted in the attribute droppedRxCells."
::= { mscAtmIfStatsEntry 31 }

mscAtmIfAal5RxErrors OBJECT-TYPE
   SYNTAX     Counter32 
   ACCESS     read-only
   STATUS     mandatory
   DESCRIPTION
     "This attribute counts AAL5 frame reassembly errors which have 
      occurred since the component was activated. These errors are either 
      CRC errors or length errors, possibly caused by dropped cells.This 
      attribute includes the count of AAL5 aborted frames. This count is 
      included in the rxFrameDiscard count.
      
      The counter is reset to zero when the component is created, or when 
      any critical attribute of the component is changed. The counter 
      wraps to zero if it exceeds its maximum value of (2**64)-1.
      
      The VPI and VCI of the last connection which exhibited AAL5 
      reassembly errors are indicated in the attribute 
      lastAal5ErrorConnection."
::= { mscAtmIfStatsEntry 32 }

mscAtmIfLastAal5RxErrorConnection OBJECT-TYPE
   SYNTAX     IntegerSequence (SIZE (3..10))
   ACCESS     read-only
   STATUS     mandatory
   DESCRIPTION
     "This attribute indicates the VPI and VCI of the last connection that 
      exhibited AAL5 reassembly errors.
      
      These errors are counted in the attribute aal5RxErrors."
::= { mscAtmIfStatsEntry 33 }

mscAtmIfLrcFrameErrors OBJECT-TYPE
   SYNTAX     Counter32 
   ACCESS     read-only
   STATUS     mandatory
   DESCRIPTION
     "This attribute counts egress LRC frame errors on frames received 
      across the bus. The likely cause of this is a hardware fault on either 
      the sending or receiving card. The counter is reset to zero when the 
      component is created, or when any critical attribute of the 
      component is changed. The counter wraps to zero when it exceeds 
      its maximum value of (2**64)-1.
      
      The VPI and VCI of the last connection which exhibited LRC errors 
      are indicated in the attribute lastLrcFrameErrorConnection."
::= { mscAtmIfStatsEntry 34 }

mscAtmIfLastLrcFrameErrorConnection OBJECT-TYPE
   SYNTAX     IntegerSequence (SIZE (3..10))
   ACCESS     read-only
   STATUS     mandatory
   DESCRIPTION
     "This attribute indicates the VPI and VCI of the last connection that 
      had LRC frame errors on frames received across the bus.
      These errors are counted in the attribute lrcFrameErrors."
::= { mscAtmIfStatsEntry 35 }

mscAtmIfAal5RxAborts OBJECT-TYPE
   SYNTAX     Counter32 
   ACCESS     read-only
   STATUS     mandatory
   DESCRIPTION
     "This attribute is not supported on any card type in Release 6.0 or 
      earlier. 
      
      This attribute counts AAL5 frame aborts which have been received 
      since the component was activated. An AAL5 aborted frame is one 
      in which the AAL5 frame length has been set to zero. This count is 
      included in aal5RxErrors. 
      
      The counter is reset to zero when the component is created, or when 
      any critical attribute of the component is changed. The counter 
      wraps to zero when it exceeds its maximum value of (2**64)-1. 
      
      The VPI and VCI of the last connection which received AAL5 abort 
      errors are displayed in the attribute lastAal5RxAbortConnection."
::= { mscAtmIfStatsEntry 40 }

mscAtmIfLastAal5RxAbortConnection OBJECT-TYPE
   SYNTAX     IntegerSequence (SIZE (3..10))
   ACCESS     read-only
   STATUS     mandatory
   DESCRIPTION
     "This attribute is not supported on any card type in Release 6.0 or 
      earlier. 
      
      This attribute indicates the VPI and VCI of the last connection that 
      exhibited AAL5 aborts. These errors are counted in the attribute 
      aal5RxAborts."
::= { mscAtmIfStatsEntry 50 }

mscAtmIfTxLinkUtilization OBJECT-TYPE
   SYNTAX     Gauge32 (0..100)
   ACCESS     read-only
   STATUS     mandatory
   DESCRIPTION
     "This attribute indicates the current transmit interface utilization 
      during the most recent minute, expressed as a percentage of the 
      total bandwidth which can be carried by this ATM interface.
      
      The attribute is not supported for 4pOC12SmIrAtm and 
      4pOC12SmLrAtm cards when working in chanelized mode."
::= { mscAtmIfStatsEntry 59 }

mscAtmIfRxLinkUtilization OBJECT-TYPE
   SYNTAX     Gauge32 (0..100)
   ACCESS     read-only
   STATUS     mandatory
   DESCRIPTION
     "This attribute indicates the current receive interface utilization 
      during the most recent minute, expressed as a percentage of the 
      total bandwidth which can be carried by this ATM interface. This 
      attribute does not consider cells that are counted by the 
      droppedRxCells attribute, nor idle cells, nor unassigned cells. 
      
      The attribute is not supported for 4pOC12SmIrAtm and 
      4pOC12SmLrAtm cards when working in chanelized mode."
::= { mscAtmIfStatsEntry 60 }

mscAtmIfTxCellMemoryThresholdTable OBJECT-TYPE
   SYNTAX     SEQUENCE OF MscAtmIfTxCellMemoryThresholdEntry
   ACCESS     not-accessible
   STATUS     mandatory
   DESCRIPTION
     "This attribute is only valid for AtmIf's on ATM IP FPs. It is not 
      displayed for AtmIf's on other card types. 
      
      This attribute indicates the transmit cell memory size and three 
      discard thresholds for this AtmIf. Transmit cell memory is used for 
      storing ATM cells to be transmitted by connections under this 
      AtmIf. 
      
      The first value indicates the the total transmit cell memory size. 
      This is derived based upon the txCellMemoryThreshold 0 attribute 
      of the Lp/x eng arc aqm/0 component and Lp/x eng arc aqm/0 Ov, 
      and on the txCellMemory attribute of this AtmIf. 
      
      When the txCellMemoryAvailable attribute decreases to the second 
      value, the txCellMemoryCongestionState changes from 3 to 2. In 
      congestion state 2, traffic with discard priority (DP) > 2 is 
      discarded. This threshold is set approximately at 25 percent of the 
      first value, the transmit cell memory size. 
      
      When the txCellMemoryAvailable attribute decreases to the third 
      value, the txCellMemoryCongestionState changes from 2 to 1. In 
      congestion state 1, traffic with discard priority (DP) > 1 is 
      discarded. This threshold is set approximately at 20 percent of the 
      first value, the transmit cell memory size. 
      
      When the txCellMemoryAvailable attribute decreases to the fourth 
      value, the txCellMemoryCongestionState changes from 1 to 0. In 
      congestion state 0, traffic with discard priority (DP) > 0 is 
      discarded. This threshold is set approximately at 10 percent of the 
      first value, the transmit cell memory size. 
      
      The opposite effect occurs when the txCellMemoryAvailable 
      attribute increases (txCellMemoryCongestionState changes from 0 
      to 3 accordingly)."
::= { mscAtmIf 441 }

mscAtmIfTxCellMemoryThresholdEntry OBJECT-TYPE
   SYNTAX     MscAtmIfTxCellMemoryThresholdEntry
   ACCESS     not-accessible
   STATUS     mandatory
   DESCRIPTION
     "An entry in the mscAtmIfTxCellMemoryThresholdTable."
   INDEX {
      mscAtmIfIndex,
      mscAtmIfTxCellMemoryThresholdIndex }
::= { mscAtmIfTxCellMemoryThresholdTable 1 }

MscAtmIfTxCellMemoryThresholdEntry ::= SEQUENCE {
   mscAtmIfTxCellMemoryThresholdIndex
      Integer32,
   mscAtmIfTxCellMemoryThresholdValue
      Unsigned32 }

mscAtmIfTxCellMemoryThresholdIndex OBJECT-TYPE
   SYNTAX     Integer32 (0..3)
   ACCESS     not-accessible
   STATUS     mandatory
   DESCRIPTION
     "This variable represents the mscAtmIfTxCellMemoryThresholdTable
      specific index for the mscAtmIfTxCellMemoryThresholdTable."
::= { mscAtmIfTxCellMemoryThresholdEntry 1 }

mscAtmIfTxCellMemoryThresholdValue OBJECT-TYPE
   SYNTAX     Unsigned32 (0..163839)
   ACCESS     read-only
   STATUS     mandatory
   DESCRIPTION
     "This variable represents an individual value for the
      mscAtmIfTxCellMemoryThresholdTable."
::= { mscAtmIfTxCellMemoryThresholdEntry 2 }

mscAtmIfOpShapingRatesTable OBJECT-TYPE
   SYNTAX     SEQUENCE OF MscAtmIfOpShapingRatesEntry
   ACCESS     not-accessible
   STATUS     mandatory
   DESCRIPTION
     "This attribute displays the values of the 31 shaping rates currently in 
      use at the interface. It is avector of 31 elements, each representing a 
      shaping rate value. A rate entry of '0' means the entry is empty and 
      can be used. This attribute is only valid for AtmIf's on APC-based 
      FPs. It is not displayed for AtmIf's on other card types."
::= { mscAtmIf 839 }

mscAtmIfOpShapingRatesEntry OBJECT-TYPE
   SYNTAX     MscAtmIfOpShapingRatesEntry
   ACCESS     not-accessible
   STATUS     mandatory
   DESCRIPTION
     "An entry in the mscAtmIfOpShapingRatesTable."
   INDEX {
      mscAtmIfIndex,
      mscAtmIfOpShapingRatesIndex }
::= { mscAtmIfOpShapingRatesTable 1 }

MscAtmIfOpShapingRatesEntry ::= SEQUENCE {
   mscAtmIfOpShapingRatesIndex
      Integer32,
   mscAtmIfOpShapingRatesValue
      Unsigned32 }

mscAtmIfOpShapingRatesIndex OBJECT-TYPE
   SYNTAX     Integer32 (0..30)
   ACCESS     not-accessible
   STATUS     mandatory
   DESCRIPTION
     "This variable represents the mscAtmIfOpShapingRatesTable
      specific index for the mscAtmIfOpShapingRatesTable."
::= { mscAtmIfOpShapingRatesEntry 1 }

mscAtmIfOpShapingRatesValue OBJECT-TYPE
   SYNTAX     Unsigned32 (0..163839)
   ACCESS     read-only
   STATUS     mandatory
   DESCRIPTION
     "This variable represents an individual value for the
      mscAtmIfOpShapingRatesTable."
::= { mscAtmIfOpShapingRatesEntry 2 }

mscAtmIfShapeUsageTable OBJECT-TYPE
   SYNTAX     SEQUENCE OF MscAtmIfShapeUsageEntry
   ACCESS     not-accessible
   STATUS     mandatory
   DESCRIPTION
     "This attribute displays the number of VCs that currently use the 31 
      shaping rates. It is a vector of 31 elements each representing the 
      number of VCs using the particular rate which is displayed with the 
      same element index in the opShapingRates attribute. This attribute 
      is only valid for AtmIf's on APC-based FPs. It is not displayed for 
      AtmIf's on other card types."
::= { mscAtmIf 840 }

mscAtmIfShapeUsageEntry OBJECT-TYPE
   SYNTAX     MscAtmIfShapeUsageEntry
   ACCESS     not-accessible
   STATUS     mandatory
   DESCRIPTION
     "An entry in the mscAtmIfShapeUsageTable."
   INDEX {
      mscAtmIfIndex,
      mscAtmIfShapeUsageIndex }
::= { mscAtmIfShapeUsageTable 1 }

MscAtmIfShapeUsageEntry ::= SEQUENCE {
   mscAtmIfShapeUsageIndex
      Integer32,
   mscAtmIfShapeUsageValue
      Unsigned32 }

mscAtmIfShapeUsageIndex OBJECT-TYPE
   SYNTAX     Integer32 (0..30)
   ACCESS     not-accessible
   STATUS     mandatory
   DESCRIPTION
     "This variable represents the mscAtmIfShapeUsageTable
      specific index for the mscAtmIfShapeUsageTable."
::= { mscAtmIfShapeUsageEntry 1 }

mscAtmIfShapeUsageValue OBJECT-TYPE
   SYNTAX     Unsigned32 (0..163839)
   ACCESS     read-only
   STATUS     mandatory
   DESCRIPTION
     "This variable represents an individual value for the
      mscAtmIfShapeUsageTable."
::= { mscAtmIfShapeUsageEntry 2 }


-- AtmIf/n ConnectionMapping
-- The ConnectionMapping component is used to to view the VCC 
-- space supported by an ATM interface on card types 3pOC3MmAtm, 
-- 3pOC3SmAtm, 3pE3Atm, 3pDS3Atm, 3pE1Atm, 3pDS1Atm, and 
-- 2pJ6MAtm. Only VPI and VCI values that lie within the VCC 
-- space may be used for VCC connections.
-- 
-- Any VPI values not assigned to the VCC space are, by implication, 
-- consigned to the VPC space. Only VPI values that lie within the 
-- VPC space may be used to support VPC connections.

mscAtmIfConnMap OBJECT IDENTIFIER ::= { mscAtmIf 2 }



mscAtmIfConnMapRowStatusTable OBJECT-TYPE
   SYNTAX     SEQUENCE OF MscAtmIfConnMapRowStatusEntry
   ACCESS     not-accessible
   STATUS     mandatory
   DESCRIPTION
     "This entry controls the addition and deletion of 
      mscAtmIfConnMap components."
::= { mscAtmIfConnMap 1 }

mscAtmIfConnMapRowStatusEntry OBJECT-TYPE
   SYNTAX     MscAtmIfConnMapRowStatusEntry
   ACCESS     not-accessible
   STATUS     mandatory
   DESCRIPTION
     "A single entry in the table represents a single 
      mscAtmIfConnMap component."
   INDEX {
      mscAtmIfIndex,
      mscAtmIfConnMapIndex }
::= { mscAtmIfConnMapRowStatusTable 1 }

MscAtmIfConnMapRowStatusEntry ::= SEQUENCE {
   mscAtmIfConnMapRowStatus
      RowStatus,
   mscAtmIfConnMapComponentName
      DisplayString,
   mscAtmIfConnMapStorageType
      StorageType,
   mscAtmIfConnMapIndex
      NonReplicated }

mscAtmIfConnMapRowStatus OBJECT-TYPE
   SYNTAX     RowStatus 
   ACCESS     read-write
   STATUS     mandatory
   DESCRIPTION
     "This variable is used as the basis for SNMP naming of
      mscAtmIfConnMap components.
      These components can be added and deleted."
::= { mscAtmIfConnMapRowStatusEntry 1 }

mscAtmIfConnMapComponentName OBJECT-TYPE
   SYNTAX     DisplayString 
   ACCESS     read-only
   STATUS     mandatory
   DESCRIPTION
     "This variable provides the component's string name for
      use with the ASCII Console Interface"
::= { mscAtmIfConnMapRowStatusEntry 2 }

mscAtmIfConnMapStorageType OBJECT-TYPE
   SYNTAX     StorageType 
   ACCESS     read-only
   STATUS     mandatory
   DESCRIPTION
     "This variable represents the storage type value for the
      mscAtmIfConnMap tables."
::= { mscAtmIfConnMapRowStatusEntry 4 }

mscAtmIfConnMapIndex OBJECT-TYPE
   SYNTAX     NonReplicated 
   ACCESS     not-accessible
   STATUS     mandatory
   DESCRIPTION
     "This variable represents the index for the mscAtmIfConnMap tables."
::= { mscAtmIfConnMapRowStatusEntry 10 }

mscAtmIfConnMapVccProvTable OBJECT-TYPE
   SYNTAX     SEQUENCE OF MscAtmIfConnMapVccProvEntry
   ACCESS     not-accessible
   STATUS     obsolete
   DESCRIPTION
     "This group is obsolete. Please refer to the Override component 
      below for the current provisioning group
      
      This group contains provisionable attributes which specify the VCC 
      space to be supported by an ATM interface. The VCC space 
      consists of an optional 'VPI Zero VCC Space' and an optional 
      'Programmable VCC Space'.
      
      The VPI Zero VCC Space is used to support VCCs with a VPI of 
      zero. The VCI values supported in this space range from 0 to a 
      provisioned maximum. The size of the VPI Zero VCC Space must 
      either be 0 or a multiple of 256. A value of 0 implies that no 
      programmable VCCs can be used. In this case 
      atmNumberOfNonZeroVpisForVccs_m must also be 0.
      
      The optional Programmable VCC Space is used to support VCCs 
      with a VPI other than zero. The VPI values supported in this space 
      must lie in a single contiguous range which excludes VPI 0. The 
      VCI values supported in this space range from 0 to a provisioned 
      maximum. The size of the Programmable VCC Space (should it 
      exist) must adhere to the following rules:
      
      If (firstNonZeroVpiForVccs = 1) THEN
      (numNonZeroVpisForVccs + 1) *
      numVccsPerNonZeroVpi must be a multiple of 256
      OTHERWISE
      numNonZeroVpisForVccs * numVccsPerNonZeroVpi
      must be a multiple of 256
      
      If the AtmIf is linked to a LogicalProcessor with a cardType of 
      3pE3Atm, 3pDS3Atm, 3pOC3MmAtm, 3pOC3SmAtm, 3pE1Atm, 
      3pDS1Atm or 2pJ6MAtm, the size of the entire VCC space (both 
      mandatory and optional parts) and VPC space must not exceed the 
      capacity of the port to which the interface is linked, which is 
      defined in the Arc component's totalConnectionPoolCapacity or 
      connectionPoolCapacity attribute (whichever is non-zero). When 
      using the totalConnectionPoolCapacity attribute, the capacity of the 
      port is (totalConnectionPoolCapacity divided by the number of 
      physical ports). The number of connection identifiers in the VCC 
      and VPC space can be determined as follows:
      
      IF (numNonZeroVpisForVccs = 0) THEN
      number of connection ids = 256 + numVccsForVpiZero
      OTHERWISE IF (firstNonZeroVpiForVccs = 1) THEN
      number of connection ids = 256 + numVccsForVpiZero +
      (numNonZeroVpisForVccs + 1) *
      numVccsPerNonZeroVpi
      OTHERWISE
      number of connection ids = 256 + numVccsForVpiZero +
      (numNonZeroVpisForVccs * numVccsPerNonZeroVpi)"
::= { mscAtmIfConnMap 100 }

mscAtmIfConnMapVccProvEntry OBJECT-TYPE
   SYNTAX     MscAtmIfConnMapVccProvEntry
   ACCESS     not-accessible
   STATUS     obsolete
   DESCRIPTION
     "An entry in the mscAtmIfConnMapVccProvTable."
   INDEX {
      mscAtmIfIndex,
      mscAtmIfConnMapIndex }
::= { mscAtmIfConnMapVccProvTable 1 }

MscAtmIfConnMapVccProvEntry ::= SEQUENCE {
   mscAtmIfConnMapNumVccsForVpiZero
      Unsigned32,
   mscAtmIfConnMapNumNonZeroVpisForVccs
      Unsigned32,
   mscAtmIfConnMapFirstNonZeroVpiForVccs
      Unsigned32,
   mscAtmIfConnMapNumVccsPerNonZeroVpi
      Unsigned32 }

mscAtmIfConnMapNumVccsForVpiZero OBJECT-TYPE
   SYNTAX     Unsigned32 (0..16128)
   ACCESS     write-only
   STATUS     obsolete
   DESCRIPTION
     "This attribute is obsolete. Please refer to the Override component 
      for the new attribute.
      
      This attribute specifies the number of VCCs supported for the VPI 
      Zero VCC Space. The VCI values of these VCCs range from 0 to 
      (numVccsForVpiZero - 1).
      
      The size of the VPI Zero VCC Space must either be 0 or a multiple 
      of 256. A value of 0 implies that no programmable VCCs can be 
      used. In this case atmNumberOfNonZeroVpisForVccs_m must also 
      be 0. 
      
      The VCC Space as a whole must adhere to the guidelines laid down 
      in the description of the AtmConnMappingVccProv group."
   DEFVAL     { 768 }
::= { mscAtmIfConnMapVccProvEntry 10 }

mscAtmIfConnMapNumNonZeroVpisForVccs OBJECT-TYPE
   SYNTAX     Unsigned32 (0..255)
   ACCESS     write-only
   STATUS     obsolete
   DESCRIPTION
     "This attribute is obsolete. Please refer to the Override component 
      for the new attribute.
      
      This attribute specifies the number of conti	guous VPIs supported in 
      the optional Programmable VCC Space.
      
      If numNonZeroVpisForVccs is 0 the Programmable VCC Space 
      does not exist. If numNonZeroVpisForVccs is greater than 0 the 
      Programmable VCC Space exists and covers the VPI values ranging 
      from firstNonZeroVpiForVccs to (firstNonZeroVpiForVccs + 
      numNonZeroVpisForVccs - 1).
      
      The VCC Space as a whole must adhere to the guidelines laid down 
      in the description of the AtmConnMappingVccProv group."
   DEFVAL     { 0 }
::= { mscAtmIfConnMapVccProvEntry 20 }

mscAtmIfConnMapFirstNonZeroVpiForVccs OBJECT-TYPE
   SYNTAX     Unsigned32 (1 | 16 | 32 | 48 | 64 | 80 | 96 | 112 | 128 | 144 | 160 | 176 | 192 | 208 | 224 | 240)
   ACCESS     write-only
   STATUS     obsolete
   DESCRIPTION
     "This attribute is obsolete. Please refer to the Override component 
      for the new attribute.
      
      This attribute specifies the initial VPI of the optional Programmable 
      VCC Space.
      
      If numNonZeroVpisForVccs is 0 the Programmable VCC Space 
      does not exist. If numNonZeroVpisForVccs is greater than 0 the 
      Programmable VCC Space exists and covers the VPI values ranging 
      from firstNonZeroVpiForVccs to (firstNonZeroVpiForVccs + 
      numNonZeroVpisForVccs - 1).
      
      The initial VPI of the Programmable VCC Space must either be 1 
      or a non-zero multiple of 16.
      
      The VCC Space as a whole must adhere to the guidelines laid down 
      in the description of the AtmConnMappingVccProv group."
   DEFVAL     { 1 }
::= { mscAtmIfConnMapVccProvEntry 30 }

mscAtmIfConnMapNumVccsPerNonZeroVpi OBJECT-TYPE
   SYNTAX     Unsigned32 (2 | 4 | 8 | 16 | 32 | 64 | 128 | 256 | 512 | 1024 | 2048)
   ACCESS     write-only
   STATUS     obsolete
   DESCRIPTION
     "This attribute is obsolete. Please refer to the Override component 
      for the new attribute.
      
      This attribute specifies the number of VCCs supported for each VPI 
      in the Programmable VCC Space. The VCI values of these VCCs 
      range from 0 to (numVccsPerNonZeroVpi - 1) for each VPI in this 
      space.
      
      The size of the Programmable VCC Space must be a power of 2.
      
      The VCC Space as a whole must adhere to the guidelines laid down 
      in the description of the AtmConnMappingVccProv group."
   DEFVAL     { 64 }
::= { mscAtmIfConnMapVccProvEntry 40 }

mscAtmIfConnMapOperTable OBJECT-TYPE
   SYNTAX     SEQUENCE OF MscAtmIfConnMapOperEntry
   ACCESS     not-accessible
   STATUS     mandatory
   DESCRIPTION
     "This group contains operational attributes which specify the VCC 
      space to be supported by an ATM interface. The VCC space 
      consists of an optional 'VPI Zero VCC Space' and an optional 
      'Programmable VCC Space'.
      
      The VPI Zero VCC Space is used to support VCCs with a VPI of 
      zero. The VCI values supported in this space range from 0 to an 
      optionally provisioned maximum of numVccsForVpiZero. The size 
      of the VPI Zero VCC Space is either 0 or a multiple of 256. A value 
      of 0 implies that not only can no VCCs be provisioned in the VPI 
      Zero VCC Space but no Programmable VCCs can be used. In this 
      case numNonZeroVpisForVccs will also be 0.
      
      The optional Programmable VCC Space supports VCCs with a VPI 
      other than zero. The VPI values supported in this space lie in a 
      single contiguous range which excludes VPI 0. The VCI values 
      supported in this space range from 0 to an optionally provisioned 
      maximum.
      
      The number of connection identifier resources in the VCC and VPC 
      space (not all of which are available for user connections) is the 
      value reported in the Lp/n Eng Arc totalConnectionPoolAvailable 
      attribute divided by the number of physical ports on the card, and 
      can be determined as follows:
      
      IF (numNonZeroVpisForVccs = 0) THEN
      number of connection ID resources =
      256 + numVccsForVpiZero
      OTHERWISE IF (firstNonZeroVpiForVccs = 1) THEN
      number of connection ID resources =
      256 + numVccsForVpiZero +
      (numNonZeroVpisForVccs + 1) * numVccsPerNonZeroVpi
      OTHERWISE
      number of connection ID resources =
      256 + numVccsForVpiZero +
      (numNonZeroVpisForVccs * numVccsPerNonZeroVpi)"
::= { mscAtmIfConnMap 110 }

mscAtmIfConnMapOperEntry OBJECT-TYPE
   SYNTAX     MscAtmIfConnMapOperEntry
   ACCESS     not-accessible
   STATUS     mandatory
   DESCRIPTION
     "An entry in the mscAtmIfConnMapOperTable."
   INDEX {
      mscAtmIfIndex,
      mscAtmIfConnMapIndex }
::= { mscAtmIfConnMapOperTable 1 }

MscAtmIfConnMapOperEntry ::= SEQUENCE {
   mscAtmIfConnMapNumVccsForVpiZeroOper
      Unsigned32,
   mscAtmIfConnMapNumNonZeroVpisForVccsOper
      Unsigned32,
   mscAtmIfConnMapFirstNonZeroVpiForVccsOper
      Unsigned32,
   mscAtmIfConnMapNumVccsPerNonZeroVpiOper
      Unsigned32 }

mscAtmIfConnMapNumVccsForVpiZeroOper OBJECT-TYPE
   SYNTAX     Unsigned32 (0..16384)
   ACCESS     read-only
   STATUS     mandatory
   DESCRIPTION
     "This attribute indicates the number of VCCs supported for the VPI 
      Zero VCC Space. The VCI values of these VCCs range from 0 to 
      (numVccsForVpiZero - 1). For Apc-based cards, the maximum 
      value is 16384. For CQC-based cards, the maximum value is 
      16128.
      
      To override the system default, see the AtmIf ConnMap Ov attribute 
      numVccsForVpiZero."
::= { mscAtmIfConnMapOperEntry 10 }

mscAtmIfConnMapNumNonZeroVpisForVccsOper OBJECT-TYPE
   SYNTAX     Unsigned32 (0..4095)
   ACCESS     read-only
   STATUS     mandatory
   DESCRIPTION
     "This attribute indicates the number of contiguous VPIs supported in 
      the optional Programmable VCC Space.
      
      If numNonZeroVpisForVccs is 0 the Programmable VCC Space 
      does not exist. If numNonZeroVpisForVccs is greater than 0 the 
      Programmable VCC Space exists and covers the VPI values ranging 
      from firstNonZeroVpiForVccs to (firstNonZeroVpiForVccs + 
      numNonZeroVpisForVccs - 1). For Apc-based cards, the maximum 
      value of this attribute is 255 for UNI applications and 4095 for NNI 
      applications. For CQC-based cards, the maximum value is 255.
      
      To override the system default, see the AtmIf ConnMap Ov attribute 
      numNonZeroVpisForVccs."
::= { mscAtmIfConnMapOperEntry 20 }

mscAtmIfConnMapFirstNonZeroVpiForVccsOper OBJECT-TYPE
   SYNTAX     Unsigned32 (1..4095)
   ACCESS     read-only
   STATUS     mandatory
   DESCRIPTION
     "This attribute indicates the initial VPI of the optional Programmable 
      VCC Space.
      
      If numNonZeroVpisForVccs is 0 the Programmable VCC Space 
      does not exist. If numNonZeroVpisForVccs is greater than 0 the 
      Programmable VCC Space exists and covers the VPI values ranging 
      from firstNonZeroVpiForVccs to (firstNonZeroVpiForVccs + 
      numNonZeroVpisForVccs - 1). For Apc-based cards, the maximum 
      value of this attribute is 255 for UNI applications and 4095 for NNI 
      applications. For CQC-based cards, the maximum value is 240.
      
      
      To override the system default, see the AtmIf ConnMap Ov attribute 
      firstNonZeroVpiForVccs."
::= { mscAtmIfConnMapOperEntry 30 }

mscAtmIfConnMapNumVccsPerNonZeroVpiOper OBJECT-TYPE
   SYNTAX     Unsigned32 (2 | 4 | 8 | 16 | 32 | 64 | 128 | 256 | 512 | 1024 | 2048 | 4096 | 8192 | 16384)
   ACCESS     read-only
   STATUS     mandatory
   DESCRIPTION
     "This attribute indicates the number of VCCs supported for each VPI 
      in the Programmable VCC Space. The VCI values of these VCCs 
      range from 0 to (numVccsPerNonZeroVpi - 1) for each VPI in this 
      space. For Apc-based cards, the maximum value is 16384. For 
      CQC-based cards, the maximum value is 2048).
      
      To override the system default, see the AtmIf ConnMap Ov attribute 
      numVccsPerNonZeroVpi."
::= { mscAtmIfConnMapOperEntry 40 }


-- AtmIf/n ConnMap Override
-- The Override component is used to specify the VCC space to be 
-- supported on an ATM interface on card types 3pOC3MmAtm, 
-- 3pOC3SmAtm, 3pE3Atm, 3pDS3Atm, 3pE1Atm, 3pDS1Atm, and 
-- 2pJ6MAtm. Only VPI and VCI values that lie within the VCC 
-- space may be used for VCC connections.
-- 
-- Any VPI values not assigned to the VCC space are, by implication, 
-- consigned to the VPC space. Only VPI values that lie within the 
-- VPC space may be used to support VPC connections.
-- 
-- This component is used to override the default values used for the 
-- parent ConnectionMapping component.

mscAtmIfConnMapOv OBJECT IDENTIFIER ::= { mscAtmIfConnMap 120 }



mscAtmIfConnMapOvRowStatusTable OBJECT-TYPE
   SYNTAX     SEQUENCE OF MscAtmIfConnMapOvRowStatusEntry
   ACCESS     not-accessible
   STATUS     mandatory
   DESCRIPTION
     "This entry controls the addition and deletion of 
      mscAtmIfConnMapOv components."
::= { mscAtmIfConnMapOv 1 }

mscAtmIfConnMapOvRowStatusEntry OBJECT-TYPE
   SYNTAX     MscAtmIfConnMapOvRowStatusEntry
   ACCESS     not-accessible
   STATUS     mandatory
   DESCRIPTION
     "A single entry in the table represents a single 
      mscAtmIfConnMapOv component."
   INDEX {
      mscAtmIfIndex,
      mscAtmIfConnMapIndex,
      mscAtmIfConnMapOvIndex }
::= { mscAtmIfConnMapOvRowStatusTable 1 }

MscAtmIfConnMapOvRowStatusEntry ::= SEQUENCE {
   mscAtmIfConnMapOvRowStatus
      RowStatus,
   mscAtmIfConnMapOvComponentName
      DisplayString,
   mscAtmIfConnMapOvStorageType
      StorageType,
   mscAtmIfConnMapOvIndex
      NonReplicated }

mscAtmIfConnMapOvRowStatus OBJECT-TYPE
   SYNTAX     RowStatus 
   ACCESS     read-only
   STATUS     mandatory
   DESCRIPTION
     "This variable is used as the basis for SNMP naming of
      mscAtmIfConnMapOv components.
      These components cannot be added nor deleted."
::= { mscAtmIfConnMapOvRowStatusEntry 1 }

mscAtmIfConnMapOvComponentName OBJECT-TYPE
   SYNTAX     DisplayString 
   ACCESS     read-only
   STATUS     mandatory
   DESCRIPTION
     "This variable provides the component's string name for
      use with the ASCII Console Interface"
::= { mscAtmIfConnMapOvRowStatusEntry 2 }

mscAtmIfConnMapOvStorageType OBJECT-TYPE
   SYNTAX     StorageType 
   ACCESS     read-only
   STATUS     mandatory
   DESCRIPTION
     "This variable represents the storage type value for the
      mscAtmIfConnMapOv tables."
::= { mscAtmIfConnMapOvRowStatusEntry 4 }

mscAtmIfConnMapOvIndex OBJECT-TYPE
   SYNTAX     NonReplicated 
   ACCESS     not-accessible
   STATUS     mandatory
   DESCRIPTION
     "This variable represents the index for the mscAtmIfConnMapOv tables."
::= { mscAtmIfConnMapOvRowStatusEntry 10 }

mscAtmIfConnMapOvProvTable OBJECT-TYPE
   SYNTAX     SEQUENCE OF MscAtmIfConnMapOvProvEntry
   ACCESS     not-accessible
   STATUS     mandatory
   DESCRIPTION
     "This group contains provisionable attributes which specify the VCC 
      space to be supported by this ATM interface. The VCC space 
      consists of an optional 'VPI Zero VCC Space' and an optional 
      'Programmable VCC Space'. If not specified otherwise, the 
      semantic checks described below are applicable only for the CQC-
      based cards.
      
      
      The VPI Zero VCC Space is used to support VCCs with a VPI of 
      zero. The VCI values supported in this space range from 0 to a 
      provisioned maximum. The size of the VPI Zero VCC Space must 
      either be 0 or a multiple of 256. A value of 0 implies that no 
      programmable VCCs can be used. In this case 
      numNonZeroVpisForVccs must also be 0.
      
      The optional Programmable VCC Space is used to support VCCs 
      with a VPI other than zero. The VPI values supported in this space 
      must lie in a single contiguous range which excludes VPI 0. The 
      VCI values supported in this space range from 0 to a provisioned 
      maximum. The size of the Programmable VCC Space (should it 
      exist) must adhere to the following rules:
      
      If (firstNonZeroVpiForVccs = 1) THEN
      (numNonZeroVpisForVccs + 1) * numVccsPerNonZeroVpi
      must be a multiple of 256
      OTHERWISE
      numNonZeroVpisForVccs * numVccsPerNonZeroVpi
      must be a multiple of 256
      
      The number of connection identifier resources in the VCC and VPC 
      space can be determined as follows:
      
      The number of connection identifier resources in the VCC and VPC 
      space (not all of which are available for user connections) is 
      reported in the Lp/n Eng Arc totalConnectionPoolAvailable 
      attribute, and can be determined as follows:
      
      IF (numNonZeroVpisForVccs = 0) THEN
      number of connection ID resources =
      256 + numVccsForVpiZero
      OTHERWISE IF (firstNonZeroVpiForVccs = 1) THEN
      number of connection ID resources =
      256 + numVccsForVpiZero +
      (numNonZeroVpisForVccs + 1) * numVccsPerNonZeroVpi
      OTHERWISE
      number of connection ID resources =
      256 + numVccsForVpiZero +
      (numNonZeroVpisForVccs * numVccsPerNonZeroVpi)
      
      The number of connection identifier resources must not exceed the 
      capacity of the port to which the interface is linked. If the Lp has an 
      Eng Arc Cqc Ov component provisioned with a non-zero 
      connectionPoolCapacity the port's capacity is specified by this 
      attribute. Otherwise the port's capacity is indicated by the Lp/n Eng 
      Arc totalConnectionPoolAvailable divided by the number of 
      physical ports on the card."
::= { mscAtmIfConnMapOv 100 }

mscAtmIfConnMapOvProvEntry OBJECT-TYPE
   SYNTAX     MscAtmIfConnMapOvProvEntry
   ACCESS     not-accessible
   STATUS     mandatory
   DESCRIPTION
     "An entry in the mscAtmIfConnMapOvProvTable."
   INDEX {
      mscAtmIfIndex,
      mscAtmIfConnMapIndex,
      mscAtmIfConnMapOvIndex }
::= { mscAtmIfConnMapOvProvTable 1 }

MscAtmIfConnMapOvProvEntry ::= SEQUENCE {
   mscAtmIfConnMapOvNumVccsForVpiZero
      Unsigned32,
   mscAtmIfConnMapOvNumNonZeroVpisForVccs
      Unsigned32,
   mscAtmIfConnMapOvFirstNonZeroVpiForVccs
      Unsigned32,
   mscAtmIfConnMapOvNumVccsPerNonZeroVpi
      Unsigned32 }

mscAtmIfConnMapOvNumVccsForVpiZero OBJECT-TYPE
   SYNTAX     Unsigned32 (0..16384)
   ACCESS     read-write
   STATUS     mandatory
   DESCRIPTION
     "For Apc-based cards, the maximum value of this attribute is 16384, 
      and the default value is 1024. The allowed values are either 1 or 
      powers of 2. For CQC-based cards the following constraints apply: 
      The maximum value is 16128, and the default is 768. This attribute 
      specifies the number of VCCs supported for the VPI Zero VCC 
      Space. The VCI values of these VCCs range from 0 to 
      (numVccsForVpiZero - 1).
      
      The size of the VPI Zero VCC Space must either be 0 or a multiple 
      of 256. A value of 0 implies that no programmable VCCs can be 
      used. In this case numNonZeroVpisForVccs must also 
      be 0. 
      
      The values of all attributes provisioned in this group must adhere to 
      the guidelines laid down in the description of the Provisioned 
      group."
   DEFVAL     { 768 }
::= { mscAtmIfConnMapOvProvEntry 10 }

mscAtmIfConnMapOvNumNonZeroVpisForVccs OBJECT-TYPE
   SYNTAX     Unsigned32 (0..4095)
   ACCESS     read-write
   STATUS     mandatory
   DESCRIPTION
     "This attribute specifies the number of contiguous VPIs supported in 
      the optional Programmable VCC Space.
      
      For Apc-based cards, the maximum value of this attribute is 255 for 
      UNI applications and 4095 for NNI applications. For CQC-based 
      cards the following constraints apply: The maximum value is 255. 
      If numNonZeroVpisForVccs is 0 the Programmable VCC Space 
      does not exist. If numNonZeroVpisForVccs is greater than 0 the 
      Programmable VCC Space exists and covers the VPI values ranging 
      from firstNonZeroVpiForVccs to (firstNonZeroVpiForVccs + 
      numNonZeroVpisForVccs - 1). 
      
      The values of all attributes provisioned in this group must adhere to 
      the guidelines laid down in the description of the Provisioned 
      group."
   DEFVAL     { 0 }
::= { mscAtmIfConnMapOvProvEntry 20 }

mscAtmIfConnMapOvFirstNonZeroVpiForVccs OBJECT-TYPE
   SYNTAX     Unsigned32 (1..4095)
   ACCESS     read-write
   STATUS     mandatory
   DESCRIPTION
     "This attribute specifies the initial VPI of the optional Programmable 
      VCC Space.
      
      If numNonZeroVpisForVccs is 0 then the Programmable VCC 
      Space does not exist and the value of this attribute is ignored. If 
      numNonZeroVpisForVccs is greater than 0 the Programmable VCC 
      Space exists and covers the VPI values ranging from 
      firstNonZeroVpiForVccs to (firstNonZeroVpiForVccs + 
      numNonZeroVpisForVccs - 1).
      
      For Apc-based cards, this value can be any integer number between 
      1 and 255 for UNI applications and between 1 and 4095 for NNI 
      applications. For CQC-based cards the initial VPI of the 
      Programmable VCC Space must be no greater than 240, and either 
      1 or a non-zero multiple of 16. The values of all attributes 
      provisioned in this group must adhere to the guidelines laid down in 
      the description of the Provisioned group."
   DEFVAL     { 1 }
::= { mscAtmIfConnMapOvProvEntry 30 }

mscAtmIfConnMapOvNumVccsPerNonZeroVpi OBJECT-TYPE
   SYNTAX     Unsigned32 (2 | 4 | 8 | 16 | 32 | 64 | 128 | 256 | 512 | 1024 | 2048 | 4096 | 8192 | 16384)
   ACCESS     read-write
   STATUS     mandatory
   DESCRIPTION
     "This attribute specifies the number of VCCs supported for each VPI 
      in the Programmable VCC Space. The VCI values of these VCCs 
      range from 0 to (numVccsPerNonZeroVpi - 1) for each VPI in this 
      space. For Apc-based cards, the maximum value of this attribute is 
      16384. For CQC-based cards, the maximum value is 2048.
      
      The values of all attributes provisioned in this group must adhere to 
      the guidelines laid down in the description of the Provisioned 
      group."
   DEFVAL     { 64 }
::= { mscAtmIfConnMapOvProvEntry 40 }


-- AtmIf/n ConnectionAdministrator
-- This component controls connection admission, and reports 
-- statistics about the ATM connections which have been admitted on 
-- this ATM interface.

mscAtmIfCA OBJECT IDENTIFIER ::= { mscAtmIf 3 }



mscAtmIfCARowStatusTable OBJECT-TYPE
   SYNTAX     SEQUENCE OF MscAtmIfCARowStatusEntry
   ACCESS     not-accessible
   STATUS     mandatory
   DESCRIPTION
     "This entry controls the addition and deletion of 
      mscAtmIfCA components."
::= { mscAtmIfCA 1 }

mscAtmIfCARowStatusEntry OBJECT-TYPE
   SYNTAX     MscAtmIfCARowStatusEntry
   ACCESS     not-accessible
   STATUS     mandatory
   DESCRIPTION
     "A single entry in the table represents a single 
      mscAtmIfCA component."
   INDEX {
      mscAtmIfIndex,
      mscAtmIfCAIndex }
::= { mscAtmIfCARowStatusTable 1 }

MscAtmIfCARowStatusEntry ::= SEQUENCE {
   mscAtmIfCARowStatus
      RowStatus,
   mscAtmIfCAComponentName
      DisplayString,
   mscAtmIfCAStorageType
      StorageType,
   mscAtmIfCAIndex
      NonReplicated }

mscAtmIfCARowStatus OBJECT-TYPE
   SYNTAX     RowStatus 
   ACCESS     read-only
   STATUS     mandatory
   DESCRIPTION
     "This variable is used as the basis for SNMP naming of
      mscAtmIfCA components.
      These components cannot be added nor deleted."
::= { mscAtmIfCARowStatusEntry 1 }

mscAtmIfCAComponentName OBJECT-TYPE
   SYNTAX     DisplayString 
   ACCESS     read-only
   STATUS     mandatory
   DESCRIPTION
     "This variable provides the component's string name for
      use with the ASCII Console Interface"
::= { mscAtmIfCARowStatusEntry 2 }

mscAtmIfCAStorageType OBJECT-TYPE
   SYNTAX     StorageType 
   ACCESS     read-only
   STATUS     mandatory
   DESCRIPTION
     "This variable represents the storage type value for the
      mscAtmIfCA tables."
::= { mscAtmIfCARowStatusEntry 4 }

mscAtmIfCAIndex OBJECT-TYPE
   SYNTAX     NonReplicated 
   ACCESS     not-accessible
   STATUS     mandatory
   DESCRIPTION
     "This variable represents the index for the mscAtmIfCA tables."
::= { mscAtmIfCARowStatusEntry 10 }

mscAtmIfCAProvTable OBJECT-TYPE
   SYNTAX     SEQUENCE OF MscAtmIfCAProvEntry
   ACCESS     not-accessible
   STATUS     mandatory
   DESCRIPTION
     "This group contains provisioned attributes which specify the 
      behavior of Connection Admission Control (CAC) for the ATM 
      connections configured on an ATM interface. Note that the names 
      of some of the attributes follow the conventions of UNI 4.0 for 
      forward compatibility reasons. This does not imply conformance in 
      general with the UNI 4.0 specification."
::= { mscAtmIfCA 100 }

mscAtmIfCAProvEntry OBJECT-TYPE
   SYNTAX     MscAtmIfCAProvEntry
   ACCESS     not-accessible
   STATUS     mandatory
   DESCRIPTION
     "An entry in the mscAtmIfCAProvTable."
   INDEX {
      mscAtmIfIndex,
      mscAtmIfCAIndex }
::= { mscAtmIfCAProvTable 1 }

MscAtmIfCAProvEntry ::= SEQUENCE {
   mscAtmIfCAMaxVpcs
      Unsigned32,
   mscAtmIfCAMaxVccs
      Unsigned32,
   mscAtmIfCAMinMulticastBranches
      Unsigned32,
   mscAtmIfCAMaxMulticastBranches
      Unsigned32,
   mscAtmIfCAMaxVpts
      Unsigned32,
   mscAtmIfCAMinAutoSelectedVci
      Unsigned32,
   mscAtmIfCAMinAutoSelectedVciForVpiZero
      Unsigned32,
   mscAtmIfCAMinAutoSelectedVciForNonZeroVpi
      Unsigned32,
   mscAtmIfCAPermittedSvcAtmServiceCategories
      OCTET STRING,
   mscAtmIfCACbrPool
      INTEGER,
   mscAtmIfCACbrCdvt
      Unsigned32,
   mscAtmIfCACbrCellLossRatio
      INTEGER,
   mscAtmIfCASvcCbrHoldingPriority
      INTEGER,
   mscAtmIfCASvcVbrRtHoldingPriority
      INTEGER,
   mscAtmIfCASvcVbrNrtHoldingPriority
      INTEGER,
   mscAtmIfCAVbrRtPool
      INTEGER,
   mscAtmIfCAVbrRtCdvt
      Unsigned32,
   mscAtmIfCAVbrRtCellLossRatio
      INTEGER,
   mscAtmIfCAVbrNrtPool
      INTEGER,
   mscAtmIfCAVbrNrtCdvt
      Unsigned32,
   mscAtmIfCAMaxCaVpcs
      Unsigned32,
   mscAtmIfCAMaxCaVpts
      Unsigned32,
   mscAtmIfCAVbrNrtCellLossRatio
      INTEGER,
   mscAtmIfCAUbrMaxConnections
      Unsigned32,
   mscAtmIfCAMinAutoSelectedVpi
      Unsigned32,
   mscAtmIfCAPermittedAtmServiceCategories
      OCTET STRING,
   mscAtmIfCAMaxAutoSelectedVpi
      Unsigned32,
   mscAtmIfCAMaxAutoSelectedVciForVpiZero
      Unsigned32,
   mscAtmIfCAMaxAutoSelectedVciForNonZeroVpi
      Unsigned32 }

mscAtmIfCAMaxVpcs OBJECT-TYPE
   SYNTAX     Unsigned32 (0..4096)
   ACCESS     read-write
   STATUS     obsolete
   DESCRIPTION
     "This attribute specifies the maximum number of Vpcs that can be 
      activated on this AtmIf. 
      
      If the AtmIf is linked to a LogicalProcessor of cardType other than 
      3pE3Atm, 3pDS3Atm, 3pOC3MmAtm, 3pOC3SmAtm, 3pE1Atm, 
      3pDS1Atm, 2pJ6MAtm, the sum of (maxVccs + maxVpcs +1) 
      across all spared AtmIfs linked to that Lp must not exceed the 
      protectedConnectionPoolCapacity attribute of the Arc component. 
      The sum of (maxVpts * 3) across all spared AtmIfs and (maxVccs + 
      maxVpcs + (maxVpts * 3) + 1) across all unspared AtmIfs linked to 
      that Lp must not exceed connectionPoolCapacity attribute of the 
      Arc component. Note that 3 connections are used for every standard 
      Vpt and 2 for each basic Vpt. Vpts on a spared AtmIf are considered 
      unspared, their resources are allocated from 
      connectionPoolCapacity. If the Arc component doesn't exist, the 
      default value of the Arc connectionPoolCapacity and 
      protectedConnectionPoolCapacity attribute is used as the limit.
      
      This attribute has been obsoleted and its value migrated to the 
      maxVpcs attribute."
   DEFVAL     { 128 }
::= { mscAtmIfCAProvEntry 5 }

mscAtmIfCAMaxVccs OBJECT-TYPE
   SYNTAX     Unsigned32 (0..16384 | 65535)
   ACCESS     read-write
   STATUS     mandatory
   DESCRIPTION
     "This attribute specifies the maximum number of usable Vccs (and 
      Vpt Vccs) that can be configured on this AtmIf. The value must not 
      exceed the number of non-reserved Vcc identifiers in the Vcc space 
      supported by this AtmIf (which is specified by the 
      ConnectionMapping component).
      
      Furthermore, if the AtmIf is linked to a LogicalProcessor of 
      cardType other than 3pE3Atm, 3pDS3Atm, 3pOC3MmAtm, 
      3pOC3SmAtm, 3pE1Atm, 3pDS1Atm, 2pJ6MAtm, the sum of 
      (maxVccs + maxVpcs + (maxVpts * 3) + 1) across all spared 
      AtmIfs linked to that Lp must not exceed the 
      protectedConnectionPoolCapacity attribute of the Arc component. 
      The sum of (maxVccs + maxVpcs + (maxVpts * 3) + 1) across all 
      unspared AtmIfs linked to that Lp must not exceed 
      connectionPoolCapacity attribute of the Arc component. Note that 3 
      connections are used for every standard Vpt and 2 for each basic 
      Vpt. If the Arc component doesn't exist, the default value of the Arc 
      connectionPoolCapacity and protectedConnectionPoolCapacity 
      attribute is used as the limit.
      
      If this attribute is set to autoConfigure, then on 32 port Multi-
      Service Access cards its value is configured as 100, and on all other 
      cards it is 255.

      VALUES (

      65535 = autoConfigure

      )"
   DEFVAL     { 65535 }
::= { mscAtmIfCAProvEntry 6 }

mscAtmIfCAMinMulticastBranches OBJECT-TYPE
   SYNTAX     Unsigned32 (0..16384)
   ACCESS     read-write
   STATUS     mandatory
   DESCRIPTION
     "This attribute specifies the guaranteed number of switched multicast 
      branches that can be activated on this AtmIf, including those 
      activated beneath a Vpt.
      
      The sum of minMulticastBranches and the number of provisioned 
      branches listed in the nextHop attribute of all Mnrps across all 
      spared AtmIfs linked to that Lp must not exceed the 
      protectedMcstBranchesCapacity attribute of the Arc component. 
      The sum of minMulticastBranches and the number of provisioned 
      branches listed in the nextHop attribute of all Mnrps across all 
      unspared AtmIfs linked to that Lp must not exceed 
      multicastBranchesCapacity attribute of the Arc component.
      
      For CQC-based ATM cards, the value of the attribute can not 
      exceed 10752.
      
      If this value is non zero, the Arc component must exist and have 
      multicastBranchesCapacity set to a value greater than or equal to 
      this attribute."
   DEFVAL     { 0 }
::= { mscAtmIfCAProvEntry 7 }

mscAtmIfCAMaxMulticastBranches OBJECT-TYPE
   SYNTAX     Unsigned32 (0 | 1..16384)
   ACCESS     read-write
   STATUS     mandatory
   DESCRIPTION
     "This attribute specifies the maximum number of provisionable 
      multicast branches that can be activated on this AtmIf, including 
      those activated beneath a Vpt.
      
      If this attribute is set to a value other than autoConfigure, it must 
      be greater than or equal to the value of minMulticastBranches of 
      this AtmIf.
      
      For CQC-based ATM cards, the value of the attribute can not 
      exceed 10752.
      
      When this attribute is set to autoConfigure, an appropriate value is 
      selected based on the card type. It is set to 10752 for all CQC-based 
      ATM cards, and to 16384 for ATM IP cards.

      VALUES (

      0 = autoConfigure

      )"
   DEFVAL     { 0 }
::= { mscAtmIfCAProvEntry 8 }

mscAtmIfCAMaxVpts OBJECT-TYPE
   SYNTAX     Unsigned32 (0..4096)
   ACCESS     read-write
   STATUS     obsolete
   DESCRIPTION
     "This attribute specifies the maximum number of Vpts that can be 
      activated on this AtmIf. 
      
      If the AtmIf is linked to a LogicalProcessor of cardType other than 
      3pE3Atm, 3pDS3Atm, 3pOC3MmAtm, 3pOC3SmAtm, 3pE1Atm, 
      3pDS1Atm, 2pJ6MAtm, the sum of (maxVccs + maxVpcs +1) 
      across all spared AtmIfs linked to that Lp must not exceed the 
      protectedConnectionPoolCapacity attribute of the Arc component. 
      The sum of (maxVpts * 3) across all spared AtmIfs and (maxVccs + 
      maxVpcs + (maxVpts * 3) + 1) across all unspared AtmIfs linked to 
      that Lp must not exceed connectionPoolCapacity attribute of the 
      Arc component. Note that 3 connections are used for every standard 
      Vpt and 2 for each basic Vpt. Vpts on a spared AtmIf are considered 
      unspared, their resources are allocated from 
      connectionPoolCapacity. If the Arc component doesn't exist, the 
      default value of the Arc connectionPoolCapacity and 
      protectedConnectionPoolCapacity attribute is used as the limit.
      
      This attribute has been obsoleted and its value migrated to the 
      maxVpts attribute."
   DEFVAL     { 128 }
::= { mscAtmIfCAProvEntry 9 }

mscAtmIfCAMinAutoSelectedVci OBJECT-TYPE
   SYNTAX     Unsigned32 (32..65535)
   ACCESS     read-write
   STATUS     obsolete
   DESCRIPTION
     "This attribute specifies the default lower boundary for VCIs which 
      are automatically allocated for a switched Vcc. A VCI number is 
      automatically allocated when a switched Vcc does not request a 
      specific VCI number. This attribute has been obsoleted and its value 
      migrated to the minAutoSelectedVciForVpiZero attribute."
   DEFVAL     { 32 }
::= { mscAtmIfCAProvEntry 10 }

mscAtmIfCAMinAutoSelectedVciForVpiZero OBJECT-TYPE
   SYNTAX     Unsigned32 (0..65535)
   ACCESS     read-write
   STATUS     mandatory
   DESCRIPTION
     "This attribute specifies the minimum VCI value which is 
      automatically allocated for a switched Vcc with VPI value of zero. 
      A VCI number is automatically allocated when a switched Vcc does 
      not request a specific VCI number. This value also applies to 
      switched Vccs created beneath Vpt/0."
   DEFVAL     { 32 }
::= { mscAtmIfCAProvEntry 15 }

mscAtmIfCAMinAutoSelectedVciForNonZeroVpi OBJECT-TYPE
   SYNTAX     Unsigned32 (5..65535)
   ACCESS     read-write
   STATUS     mandatory
   DESCRIPTION
     "This attribute specifies the minimum VCI value which is 
      automatically allocated for a switched Vcc with a non-zero VPI 
      value. A VCI number is automatically allocated when a switched 
      Vcc does not request a specific VCI number. This value also applies 
      to switched Vccs created beneath a Vpt."
   DEFVAL     { 32 }
::= { mscAtmIfCAProvEntry 20 }

mscAtmIfCAPermittedSvcAtmServiceCategories OBJECT-TYPE
   SYNTAX     OCTET STRING (SIZE (1))
   ACCESS     read-write
   STATUS     obsolete
   DESCRIPTION
     "This attribute specifies which ATM service categories are permitted 
      on this interface for SVCs. The value of this attribute does not affect 
      control VCCs, such as signalling and ILMI channels. If the value is 
      empty, no SVCs may use this interface.
      This attribute has been obsoleted and its value migrated to the 
      permittedAtmServiceCategories attribute.

      Description of bits:
      unspecifiedBitRate(0)
      constantBitRate(1)
      rtVariableBitRate(2)
      nrtVariableBitRate(3)"
   DEFVAL     { 'f0'H }
::= { mscAtmIfCAProvEntry 25 }

mscAtmIfCACbrPool OBJECT-TYPE
   SYNTAX     INTEGER  {
                 notApplicable(0),
                 pool1(1),
                 pool2(2),
                 pool3(3) }
   ACCESS     read-write
   STATUS     obsolete
   DESCRIPTION
     "This attribute has been obsoleted and migrated under the Cbr 
      subcomponent. In addition, notApplicable is no longer a valid value 
      of the new attribute.
      This attribute specifies the bandwidth pool which is to be used to 
      support the constant bit rate (CBR) service category. When the user 
      does not intend to support the CBR service category, this attribute 
      should be set to notApplicable. Otherwise, one of the three 
      bandwidth pools should be selected. The percentage of link capacity 
      reserved for the given bandwidth pool is the maximum bandwidth 
      that can be allocated to CBR traffic."
   DEFVAL     { pool1 }
::= { mscAtmIfCAProvEntry 30 }

mscAtmIfCACbrCdvt OBJECT-TYPE
   SYNTAX     Unsigned32 (1..10000)
   ACCESS     read-write
   STATUS     obsolete
   DESCRIPTION
     "This attribute has been obsoleted and migrated under the Cbr 
      subcomponent.
      This attribute specifies the cell delay variation tolerance (CDVT) 
      which is to be applied to the entire ATM Interface for CBR traffic."
   DEFVAL     { 250 }
::= { mscAtmIfCAProvEntry 40 }

mscAtmIfCACbrCellLossRatio OBJECT-TYPE
   SYNTAX     INTEGER (-10..0)
   ACCESS     read-write
   STATUS     obsolete
   DESCRIPTION
     "This attribute has been obsoleted and migrated under the Cbr 
      subcomponent. In addition, the type and range of the new attribute 
      have been changed.
      This attribute specifies the tolerable cell loss ratio (CLR) for CBR 
      traffic. The number is the logarithm (base 10) of the CLR. In other 
      words if the target CLR = 1E-10 then cbrCellLossRatio = -10. This 
      number must be the same as the vbrRtCellLossRatio since CBR and 
      rt-VBR traffic have the same discard priority. The cbrCellLossRatio 
      is used by the Connection Admission Control (CAC) algorithm to 
      compute the required (equivalent) cell rate for CBR connections. 
      
      There is a trade-off between the service category CLR and the 
      achievable link utilization. To guarantee an excellent service 
      category, the CLR should be as small as possible (e.g., 1E-10). 
      However, a smaller CLR results in a larger equivalent cell rate for a 
      given connection and hence a lower link utilization."
   DEFVAL     { -10 }
::= { mscAtmIfCAProvEntry 50 }

mscAtmIfCASvcCbrHoldingPriority OBJECT-TYPE
   SYNTAX     INTEGER  {
                 n0(0),
                 n1(1),
                 n2(2),
                 n3(3),
                 n4(4) }
   ACCESS     read-write
   STATUS     obsolete
   DESCRIPTION
     "This attribute has been obsoleted and migrated under the Cbr 
      subcomponent. 
      This attribute specifies the default holding priority which applies for 
      SVC CBR connections. It takes a value from 0 (highest priority) to 
      4 (lowest priority). In a situation where the link bandwidth 
      fluctuates, such as over an IMA link, holding priority is used to 
      determine which connections are held and which are released. 
      Holding priority 4 connections are the first to be released. Holding 
      priority 0 connections are the last to be released."
   DEFVAL     { n3 }
::= { mscAtmIfCAProvEntry 51 }

mscAtmIfCASvcVbrRtHoldingPriority OBJECT-TYPE
   SYNTAX     INTEGER  {
                 n0(0),
                 n1(1),
                 n2(2),
                 n3(3),
                 n4(4) }
   ACCESS     read-write
   STATUS     obsolete
   DESCRIPTION
     "This attribute has been obsoleted and migrated under the RtVbr 
      subcomponent.
      This attribute specifies the default holding priority which applies for 
      SVC rt-VBR connections. It takes a value from 0 (highest priority) 
      to 4 (lowest priority). In a situation where the link bandwidth 
      fluctuates, such as over an IMA link, holding priority is used to 
      determine which connections are held and which are released. 
      Holding priority 4 connections are the first to be released. Holding 
      priority 0 connections are the last to be released."
   DEFVAL     { n3 }
::= { mscAtmIfCAProvEntry 52 }

mscAtmIfCASvcVbrNrtHoldingPriority OBJECT-TYPE
   SYNTAX     INTEGER  {
                 n0(0),
                 n1(1),
                 n2(2),
                 n3(3),
                 n4(4) }
   ACCESS     read-write
   STATUS     obsolete
   DESCRIPTION
     "This attribute has been obsoleted and migrated under the NrtVbr 
      subcomponent.
      This attribute specifies the default holding priority which applies for 
      SVC nrt-VBR connections. It takes a value from 0 (highest priority) 
      to 4 (lowest priority). In a situation where the link bandwidth 
      fluctuates, such as over an IMA link, holding priority is used to 
      determine which connections are held and which are released. 
      Holding priority 4 connections are the first to be released. Holding 
      priority 0 connections are the last to be released."
   DEFVAL     { n3 }
::= { mscAtmIfCAProvEntry 53 }

mscAtmIfCAVbrRtPool OBJECT-TYPE
   SYNTAX     INTEGER  {
                 notApplicable(0),
                 pool1(1),
                 pool2(2),
                 pool3(3) }
   ACCESS     read-write
   STATUS     obsolete
   DESCRIPTION
     "This attribute has been obsoleted and migrated under the RtVbr 
      subcomponent. In addition, notApplicable is no longer a valid value 
      of the new attribute.
      This attribute specifies the bandwidth pool which is to be used to 
      support the variable bit rate real time (rt-VBR) service category. 
      When the user does not intend to support the rt-VBR service 
      category, this attribute should be set to notApplicable. Otherwise, 
      one of the three bandwidth pools should be selected. The percentage 
      of link capacity reserved for the given bandwidth pool is the 
      maximum bandwidth that can be allocated to rt-VBR traffic."
   DEFVAL     { pool1 }
::= { mscAtmIfCAProvEntry 60 }

mscAtmIfCAVbrRtCdvt OBJECT-TYPE
   SYNTAX     Unsigned32 (1..1200000)
   ACCESS     read-write
   STATUS     obsolete
   DESCRIPTION
     "This attribute has been obsoleted and migrated under the RtVbr 
      subcomponent.
      This attribute specifies the cell delay variation tolerance (CDVT) 
      which is to be applied to the entire ATM Interface for rt-VBR 
      traffic."
   DEFVAL     { 250 }
::= { mscAtmIfCAProvEntry 70 }

mscAtmIfCAVbrRtCellLossRatio OBJECT-TYPE
   SYNTAX     INTEGER (-10..0)
   ACCESS     read-write
   STATUS     obsolete
   DESCRIPTION
     "This attribute has been obsoleted and migrated under the RtVbr 
      subcomponent. In addition, the type and range of this attribute has 
      been changed.
      This attribute specifies the tolerable cell loss ratio (CLR) for rt-
      VBR traffic. The number is the logarithm (base 10) of the CLR. In 
      other words if the target CLR = 1E-10 then vbrRtCellLossRatio = -
      10. This number must be the same as the cbrCellLossRatio since 
      CBR and rt-VBR traffic have the same discard priority. The 
      vbrRtCellLossRatio is used by the Connection Admission Control 
      (CAC) algorithm to compute the required (equivalent) cell rate for 
      rt-VBR connections. This number must be less than or equal to the 
      vbrNrtCellLossRatio, since rt-VBR traffic has a higher discard 
      priority.
      
      There is a trade-off between the service category CLR and the 
      achievable link utilization. To guarantee an excellent service 
      category, the CLR should be as small as possible (e.g., 1E-10). 
      However, a smaller CLR results in a larger equivalent cell rate for a 
      given connection and hence a lower link utilization."
   DEFVAL     { -10 }
::= { mscAtmIfCAProvEntry 80 }

mscAtmIfCAVbrNrtPool OBJECT-TYPE
   SYNTAX     INTEGER  {
                 notApplicable(0),
                 pool1(1),
                 pool2(2),
                 pool3(3) }
   ACCESS     read-write
   STATUS     obsolete
   DESCRIPTION
     "This attribute has been obsoleted and migrated under the NrtVbr 
      subcomponent. In addition, notApplicable is no longer a valid value 
      of the new attribute.
      This attribute specifies the bandwidth pool which is to be used to 
      support the variable bit rate non-real time (nrt-VBR) service 
      category. When the user does not intend to support the nrt-VBR, 
      this attribute should be set to notApplicable. Otherwise, one of the 
      three bandwidth pools should be selected. The percentage of link 
      capacity reserved for the given bandwidth pool is the maximum 
      bandwidth that can be allocated to nrt-VBR traffic."
   DEFVAL     { pool1 }
::= { mscAtmIfCAProvEntry 90 }

mscAtmIfCAVbrNrtCdvt OBJECT-TYPE
   SYNTAX     Unsigned32 (1..1200000)
   ACCESS     read-write
   STATUS     obsolete
   DESCRIPTION
     "This attribute has been obsoleted and migrated under the NrtVbr 
      subcomponent.
      This attribute specifies the cell delay variation tolerance (CDVT), 
      which is to be applied to the entire ATM Interface for nrt-VBR 
      traffic."
   DEFVAL     { 250 }
::= { mscAtmIfCAProvEntry 100 }

mscAtmIfCAMaxCaVpcs OBJECT-TYPE
   SYNTAX     Unsigned32 (0..4096 | 65535)
   ACCESS     read-write
   STATUS     mandatory
   DESCRIPTION
     "This attribute specifies the maximum number of Vpcs that can be 
      activated on this AtmIf. 
      
      If the AtmIf is linked to a LogicalProcessor of cardType other than 
      3pE3Atm, 3pDS3Atm, 3pOC3MmAtm, 3pOC3SmAtm, 3pE1Atm, 
      3pDS1Atm, 2pJ6MAtm, the sum of (maxVccs + maxVpcs + 
      (maxVpts * 3) + 1) across all spared AtmIfs linked to that Lp must 
      not exceed the protectedConnectionPoolCapacity attribute of the 
      Arc component. The sum of (maxVccs + maxVpcs + (maxVpts * 3) 
      + 1) across all unspared AtmIfs linked to that Lp must not exceed 
      connectionPoolCapacity attribute of the Arc component. Note that 3 
      connections are used for every standard Vpt and 2 for each basic 
      Vpt. If the Arc component doesn't exist, the default value of the Arc 
      connectionPoolCapacity and protectedConnectionPoolCapacity 
      attribute is used as the limit.
      
      If this attribute is set to autoConfigure, then on 32 port Multi-
      Service Access cards its value is configured as 16, and on all other 
      cards it is 128.

      VALUES (

      65535 = autoConfigure

      )"
   DEFVAL     { 65535 }
::= { mscAtmIfCAProvEntry 105 }

mscAtmIfCAMaxCaVpts OBJECT-TYPE
   SYNTAX     Unsigned32 (0..4096 | 65535)
   ACCESS     read-write
   STATUS     mandatory
   DESCRIPTION
     "This attribute specifies the maximum number of Vpts that can be 
      activated on this AtmIf. 
      
      If the AtmIf is linked to a LogicalProcessor of cardType other than 
      3pE3Atm, 3pDS3Atm, 3pOC3MmAtm, 3pOC3SmAtm, 3pE1Atm, 
      3pDS1Atm, 2pJ6MAtm, the sum of (maxVccs + maxVpcs + 
      (maxVpts * 3) + 1) across all spared AtmIfs linked to that Lp must 
      not exceed the protectedConnectionPoolCapacity attribute of the 
      Arc component. The sum of (maxVccs + maxVpcs + (maxVpts * 3) 
      + 1) across all unspared AtmIfs linked to that Lp must not exceed 
      connectionPoolCapacity attribute of the Arc component. Note that 3 
      connections are used for every standard Vpt and 2 for each basic 
      Vpt. If the Arc component doesn't exist, the default value of the Arc 
      connectionPoolCapacity and protectedConnectionPoolCapacity 
      attribute is used as the limit.
      
      If this attribute is set to autoConfigure, then on 32 port Multi-
      Service Access cards its value is configured as 16, and on all other 
      cards it is 128.

      VALUES (

      65535 = autoConfigure

      )"
   DEFVAL     { 65535 }
::= { mscAtmIfCAProvEntry 106 }

mscAtmIfCAVbrNrtCellLossRatio OBJECT-TYPE
   SYNTAX     INTEGER (-10..0)
   ACCESS     read-write
   STATUS     obsolete
   DESCRIPTION
     "This attribute has been obsoleted and migrated under the NrtVbr 
      subcomponent. In addition, the type and range of new attribute has 
      been changed.
      This attribute specifies the tolerable cell loss ratio (CLR) for nrt-
      VBR traffic. The number is the logarithm (base 10) of the CLR. In 
      other words if the target CLR = 1E-10 then vbrNrtCellLossRatio = -
      10.This number must be greater than or equal to 
      vbrRtCellLossRatio since rt-VBR traffic has a higher discard 
      priority. The vbrNrtCellLossRatio is used by the Connection 
      Admission Control (CAC) algorithm to compute the required 
      (equivalent) cell rate for nrt-VBR connections. 
      
      There is a trade-off between the service category CLR and the 
      achievable link utilization. To guarantee an excellent service 
      category, the CLR should be as small as possible (e.g., 1E-10). 
      However, a smaller CLR results in a larger equivalent cell rate for a 
      given connection and hence a lower link utilization."
   DEFVAL     { -7 }
::= { mscAtmIfCAProvEntry 110 }

mscAtmIfCAUbrMaxConnections OBJECT-TYPE
   SYNTAX     Unsigned32 (0..16384)
   ACCESS     read-write
   STATUS     obsolete
   DESCRIPTION
     "This attribute is obsolete in P6.0, and has been migrated to the CA 
      Ubr/0 maxVccs and maxVpcs attributes. 
      
      This attribute specifies the maximum number of unspecified bit rate 
      (UBR) connections which are to be admitted managed by this CA. 
      This number is enforced by the connection admission control 
      (CAC) algorithm for this AtmIf."
   DEFVAL     { 16384 }
::= { mscAtmIfCAProvEntry 120 }

mscAtmIfCAMinAutoSelectedVpi OBJECT-TYPE
   SYNTAX     Unsigned32 (1..4095)
   ACCESS     read-write
   STATUS     mandatory
   DESCRIPTION
     "This attribute specifies the minimum VPI value which will be 
      automatically allocated for a switched Vpc. A VPI number is 
      automatically allocated when a switched Vpc does not request a 
      specific VPI number."
   DEFVAL     { 1 }
::= { mscAtmIfCAProvEntry 121 }

mscAtmIfCAPermittedAtmServiceCategories OBJECT-TYPE
   SYNTAX     OCTET STRING (SIZE (1))
   ACCESS     read-write
   STATUS     mandatory
   DESCRIPTION
     "This attribute specifies which ATM service categories are permitted 
      on this interface for SVPs and SVCs. The value of this attribute 
      does not affect control VCCs, such as signalling and ILMI channels. 
      If the value is empty, no non-control SVPs or SVCs will use this 
      interface. This attribute is ignored for the admission of provisioned 
      VCCs, VPCs, VPTs, S-PVCs, and S-PVPs.
      
      The value of the permittedAtmServiceCategories in a VPT CA 
      overrides this AtmIf CA setting for all the given VPT's VCCs.

      Description of bits:
      unspecifiedBitRate(0)
      constantBitRate(1)
      rtVariableBitRate(2)
      nrtVariableBitRate(3)"
   DEFVAL     { 'f0'H }
::= { mscAtmIfCAProvEntry 122 }

mscAtmIfCAMaxAutoSelectedVpi OBJECT-TYPE
   SYNTAX     Unsigned32 (1..4095)
   ACCESS     read-write
   STATUS     mandatory
   DESCRIPTION
     "This attribute specifies the maximumVPI value which will be 
      automatically allocated for a switched Vpc or Vcc. A VPI number is 
      automatically allocated when a switched Vpc or Vcc does not 
      request a specific VPI number."
   DEFVAL     { 128 }
::= { mscAtmIfCAProvEntry 125 }

mscAtmIfCAMaxAutoSelectedVciForVpiZero OBJECT-TYPE
   SYNTAX     Unsigned32 (0..65535)
   ACCESS     read-write
   STATUS     mandatory
   DESCRIPTION
     "This attribute specifies the maximum VCI value which is 
      automatically allocated for a switched Vcc. A VCI number is 
      automatically allocated when a switched Vcc does not request a 
      specific VCI number. This value also applies to switched Vccs 
      created beneath Vpt/0."
   DEFVAL     { 767 }
::= { mscAtmIfCAProvEntry 126 }

mscAtmIfCAMaxAutoSelectedVciForNonZeroVpi OBJECT-TYPE
   SYNTAX     Unsigned32 (5..65535)
   ACCESS     read-write
   STATUS     mandatory
   DESCRIPTION
     "This attribute specifies the maximum VCI value which is 
      automatically allocated for a switched Vcc. A VCI number is 
      automatically allocated when a switched Vcc does not request a 
      specific VCI number. This value also applies to switched Vccs 
      created beneath non zero Vpts."
   DEFVAL     { 63 }
::= { mscAtmIfCAProvEntry 127 }

mscAtmIfCAOperTable OBJECT-TYPE
   SYNTAX     SEQUENCE OF MscAtmIfCAOperEntry
   ACCESS     not-accessible
   STATUS     mandatory
   DESCRIPTION
     "This group contains operational attributes giving statistics about the 
      ATM connections configured on an ATM interface."
::= { mscAtmIfCA 110 }

mscAtmIfCAOperEntry OBJECT-TYPE
   SYNTAX     MscAtmIfCAOperEntry
   ACCESS     not-accessible
   STATUS     mandatory
   DESCRIPTION
     "An entry in the mscAtmIfCAOperTable."
   INDEX {
      mscAtmIfIndex,
      mscAtmIfCAIndex }
::= { mscAtmIfCAOperTable 1 }

MscAtmIfCAOperEntry ::= SEQUENCE {
   mscAtmIfCAActualMaxVccs
      Unsigned32,
   mscAtmIfCAPermanentVpcs
      Unsigned32,
   mscAtmIfCAPermanentVpts
      Unsigned32,
   mscAtmIfCAPermanentVccs
      Unsigned32,
   mscAtmIfCASwitchedVccs
      Gauge32,
   mscAtmIfCASwitchedMulticastBranches
      Gauge32,
   mscAtmIfCAPermanentMulticastBranches
      Gauge32,
   mscAtmIfCATroubledVpcs
      Unsigned32,
   mscAtmIfCATroubledVpts
      Unsigned32,
   mscAtmIfCATroubledVccs
      Unsigned32,
   mscAtmIfCAUbrAvailableConnections
      Gauge32,
   mscAtmIfCAConnectionPoolUsage
      Gauge32,
   mscAtmIfCASwitchedVpcs
      Gauge32,
   mscAtmIfCAActualMaxVpcs
      Unsigned32,
   mscAtmIfCAActualMaxVpts
      Unsigned32 }

mscAtmIfCAActualMaxVccs OBJECT-TYPE
   SYNTAX     Unsigned32 (0..16384)
   ACCESS     read-only
   STATUS     mandatory
   DESCRIPTION
     "This attribute indicates the maximum number of VCC connections 
      that can be supported on this interface. The value includes both 
      provisioned and dynamic connections. The value is determined 
      from the provisioned attribute maxVccs."
::= { mscAtmIfCAOperEntry 6 }

mscAtmIfCAPermanentVpcs OBJECT-TYPE
   SYNTAX     Unsigned32 (0..4096)
   ACCESS     read-only
   STATUS     mandatory
   DESCRIPTION
     "This attribute indicates the number of permanent Vpcs that are 
      currently provisioned on this interface."
::= { mscAtmIfCAOperEntry 10 }

mscAtmIfCAPermanentVpts OBJECT-TYPE
   SYNTAX     Unsigned32 (0..4096)
   ACCESS     read-only
   STATUS     mandatory
   DESCRIPTION
     "This attribute indicates the number of permanent Vpts that are 
      currently provisioned on this interface."
::= { mscAtmIfCAOperEntry 15 }

mscAtmIfCAPermanentVccs OBJECT-TYPE
   SYNTAX     Unsigned32 (0..16384)
   ACCESS     read-only
   STATUS     mandatory
   DESCRIPTION
     "This attribute indicates the number of permanent Vccs that are 
      currently provisioned on this interface (this includes Vccs having 
      SrcPvc subcomponents). Vpt Vccs are also included in this count."
::= { mscAtmIfCAOperEntry 20 }

mscAtmIfCASwitchedVccs OBJECT-TYPE
   SYNTAX     Gauge32 (0..16384)
   ACCESS     read-only
   STATUS     mandatory
   DESCRIPTION
     "This attribute indicates the number of switched Vccs that are 
      currently active on this interface. Vpt Vccs are also included in this 
      count."
::= { mscAtmIfCAOperEntry 30 }

mscAtmIfCASwitchedMulticastBranches OBJECT-TYPE
   SYNTAX     Gauge32 (0..10752)
   ACCESS     read-only
   STATUS     mandatory
   DESCRIPTION
     "This attribute indicates the number of multicast branches used in 
      switched Vccs, including Vpt Vccs, that are currently active on this 
      interface.
      The sum of this attribute for all AtmIf components linked to an Lp 
      added to the sum of permanentMulticastBranches for all AtmIf 
      components linked to the same Lp gives the value of 
      multiCastBranchesUsage in the Arc component."
::= { mscAtmIfCAOperEntry 40 }

mscAtmIfCAPermanentMulticastBranches OBJECT-TYPE
   SYNTAX     Gauge32 (0..10752)
   ACCESS     read-only
   STATUS     mandatory
   DESCRIPTION
     "This attribute indicates the number of multicast branches used in 
      permanent Vccs and Vpcs that are currently active on this interface.
      The sum of this attribute for all AtmIf components linked to an Lp 
      added to the sum of switchedMulticastBranches for all AtmIf 
      components linked to the same Lp gives the value of 
      multiCastBranchesUsage in the Arc component."
::= { mscAtmIfCAOperEntry 55 }

mscAtmIfCATroubledVpcs OBJECT-TYPE
   SYNTAX     Unsigned32 (0..4096)
   ACCESS     read-only
   STATUS     mandatory
   DESCRIPTION
     "This attribute indicates the number of troubled Vpcs on this 
      interface. A Vpc is 'troubled' if its operational troubled attribute 
      has the value yes."
::= { mscAtmIfCAOperEntry 60 }

mscAtmIfCATroubledVpts OBJECT-TYPE
   SYNTAX     Unsigned32 (0..4096)
   ACCESS     read-only
   STATUS     mandatory
   DESCRIPTION
     "This attribute indicates the number of troubled Vpts on this 
      interface. A Vpt is 'troubled' if its operational troubled attribute has 
      the value yes."
::= { mscAtmIfCAOperEntry 65 }

mscAtmIfCATroubledVccs OBJECT-TYPE
   SYNTAX     Unsigned32 (0..16384)
   ACCESS     read-only
   STATUS     mandatory
   DESCRIPTION
     "This attribute indicates the number of troubled Vccs on this 
      interface. A Vcc is 'troubled' if its operational troubled attribute 
      has the value yes."
::= { mscAtmIfCAOperEntry 70 }

mscAtmIfCAUbrAvailableConnections OBJECT-TYPE
   SYNTAX     Gauge32 (0..16384)
   ACCESS     read-only
   STATUS     obsolete
   DESCRIPTION
     "This attribute is historical in P6.0. Refer instead to the vccUsage 
      and vpcUsage under the AtmIf CA Ubr component.
      
      This attribute indicates the available UBR connections. Its value is 
      ubrMaxConnections minus the number of admitted connections."
::= { mscAtmIfCAOperEntry 80 }

mscAtmIfCAConnectionPoolUsage OBJECT-TYPE
   SYNTAX     Gauge32 (0..16384)
   ACCESS     read-only
   STATUS     mandatory
   DESCRIPTION
     "This attribute indicates the number of enabled VCCs, VPCs, and 
      VPTs in this AtmIf. An example of a VCC not in the enabled state is 
      a Vcc with a Test subcomponent where the test is not started.
      
      Each Vcc or Vpc is counted as 1 connection. Each basic Vpt is 
      counted as 2 connections and each standard Vpt is counted as 3 
      connections.
      
      Each connection appropriately reduces the number of connections 
      indicated in Arc totalConnectionPoolAvailable and increases the 
      number of connections indicated in Arc totalConnectionPoolUsage."
::= { mscAtmIfCAOperEntry 81 }

mscAtmIfCASwitchedVpcs OBJECT-TYPE
   SYNTAX     Gauge32 (0..4095)
   ACCESS     read-only
   STATUS     mandatory
   DESCRIPTION
     "This attribute indicates the number of switched Vpcs that are 
      currently active on this interface."
::= { mscAtmIfCAOperEntry 82 }

mscAtmIfCAActualMaxVpcs OBJECT-TYPE
   SYNTAX     Unsigned32 (0..4096)
   ACCESS     read-only
   STATUS     mandatory
   DESCRIPTION
     "This attribute indicates the maximum number of VPC connections 
      that can be supported on this interface. The value includes both 
      provisioned and dynamic connections. The value is determined 
      from the provisioned attribute maxVpcs."
::= { mscAtmIfCAOperEntry 105 }

mscAtmIfCAActualMaxVpts OBJECT-TYPE
   SYNTAX     Unsigned32 (0..4096)
   ACCESS     read-only
   STATUS     mandatory
   DESCRIPTION
     "This attribute indicates the maximum number of VPT connections 
      that can be supported on this interface. The value includes both 
      provisioned and dynamic connections. The value is determined 
      from the provisioned attribute maxVpts."
::= { mscAtmIfCAOperEntry 106 }

mscAtmIfCAPmTable OBJECT-TYPE
   SYNTAX     SEQUENCE OF MscAtmIfCAPmEntry
   ACCESS     not-accessible
   STATUS     mandatory
   DESCRIPTION
     "This group contains the operational attributes indicating the total 
      number of connections on the interface with active Cell Loss Ratio 
      (CLR) and Availability Ratio (AR) measurements on the interface."
::= { mscAtmIfCA 120 }

mscAtmIfCAPmEntry OBJECT-TYPE
   SYNTAX     MscAtmIfCAPmEntry
   ACCESS     not-accessible
   STATUS     mandatory
   DESCRIPTION
     "An entry in the mscAtmIfCAPmTable."
   INDEX {
      mscAtmIfIndex,
      mscAtmIfCAIndex }
::= { mscAtmIfCAPmTable 1 }

MscAtmIfCAPmEntry ::= SEQUENCE {
   mscAtmIfCAOamFPmConnections
      Unsigned32,
   mscAtmIfCAOamBrPmConnections
      Unsigned32,
   mscAtmIfCAOamCcConnections
      Unsigned32 }

mscAtmIfCAOamFPmConnections OBJECT-TYPE
   SYNTAX     Unsigned32 (0..255)
   ACCESS     read-only
   STATUS     mandatory
   DESCRIPTION
     "This attribute indicates the total number of connections on the 
      interface receiving OAM Forward Performance Monitoring (FPM) 
      cells on the interface."
::= { mscAtmIfCAPmEntry 1 }

mscAtmIfCAOamBrPmConnections OBJECT-TYPE
   SYNTAX     Unsigned32 (0..255)
   ACCESS     read-only
   STATUS     mandatory
   DESCRIPTION
     "This attribute indicates the total number of connections receiving 
      OAM Backward Reporting (BR) cells on the interface."
::= { mscAtmIfCAPmEntry 2 }

mscAtmIfCAOamCcConnections OBJECT-TYPE
   SYNTAX     Unsigned32 (0..255)
   ACCESS     read-only
   STATUS     mandatory
   DESCRIPTION
     "This attribute indicates the total number of connections receiving 
      OAM Continuity Check (CC) cells on the interface."
::= { mscAtmIfCAPmEntry 3 }

mscAtmIfCABwPoolTable OBJECT-TYPE
   SYNTAX     SEQUENCE OF MscAtmIfCABwPoolEntry
   ACCESS     not-accessible
   STATUS     mandatory
   DESCRIPTION
     "Link capacity is partitioned into five bandwidth pools. This attribute 
      specifies the percentage of link bandwidth that is allowed for each 
      pool. The percentage for each pool ranges from 0% to 12,800%. 
      This allows for both under and over subscription of the link. Under 
      subscription occurs when the sum of the percentages assigned to the 
      five pools is less than 100%. Over subscription occurs when the 
      sum of the percentages for the five pools exceeds 100%."
::= { mscAtmIfCA 293 }

mscAtmIfCABwPoolEntry OBJECT-TYPE
   SYNTAX     MscAtmIfCABwPoolEntry
   ACCESS     not-accessible
   STATUS     mandatory
   DESCRIPTION
     "An entry in the mscAtmIfCABwPoolTable."
   INDEX {
      mscAtmIfIndex,
      mscAtmIfCAIndex,
      mscAtmIfCABwPoolIndex }
::= { mscAtmIfCABwPoolTable 1 }

MscAtmIfCABwPoolEntry ::= SEQUENCE {
   mscAtmIfCABwPoolIndex
      Integer32,
   mscAtmIfCABwPoolValue
      Unsigned32 }

mscAtmIfCABwPoolIndex OBJECT-TYPE
   SYNTAX     Integer32 (1..5)
   ACCESS     not-accessible
   STATUS     mandatory
   DESCRIPTION
     "This variable represents the mscAtmIfCABwPoolTable
      specific index for the mscAtmIfCABwPoolTable."
::= { mscAtmIfCABwPoolEntry 1 }

mscAtmIfCABwPoolValue OBJECT-TYPE
   SYNTAX     Unsigned32 (0..12800)
   ACCESS     read-write
   STATUS     mandatory
   DESCRIPTION
     "This variable represents an individual value for the
      mscAtmIfCABwPoolTable."
::= { mscAtmIfCABwPoolEntry 2 }

mscAtmIfCAPoolRequBwTable OBJECT-TYPE
   SYNTAX     SEQUENCE OF MscAtmIfCAPoolRequBwEntry
   ACCESS     not-accessible
   STATUS     mandatory
   DESCRIPTION
     "This attribute indicates the total requested bandwidth from 
      bandwidthPool. This attribute does not include bandwidth for ATM 
      networking signalling connections, or bandwidth for connections 
      managed by a Vpt CA. Its value is the sum of the equivalent cell 
      rates (ECR) for connections which are admitted, and for 
      connections which are requesting admission but have not yet been 
      admitted."
::= { mscAtmIfCA 296 }

mscAtmIfCAPoolRequBwEntry OBJECT-TYPE
   SYNTAX     MscAtmIfCAPoolRequBwEntry
   ACCESS     not-accessible
   STATUS     mandatory
   DESCRIPTION
     "An entry in the mscAtmIfCAPoolRequBwTable."
   INDEX {
      mscAtmIfIndex,
      mscAtmIfCAIndex,
      mscAtmIfCAPoolRequBwIndex }
::= { mscAtmIfCAPoolRequBwTable 1 }

MscAtmIfCAPoolRequBwEntry ::= SEQUENCE {
   mscAtmIfCAPoolRequBwIndex
      Integer32,
   mscAtmIfCAPoolRequBwValue
      Gauge32 }

mscAtmIfCAPoolRequBwIndex OBJECT-TYPE
   SYNTAX     Integer32 (1..5)
   ACCESS     not-accessible
   STATUS     mandatory
   DESCRIPTION
     "This variable represents the mscAtmIfCAPoolRequBwTable
      specific index for the mscAtmIfCAPoolRequBwTable."
::= { mscAtmIfCAPoolRequBwEntry 1 }

mscAtmIfCAPoolRequBwValue OBJECT-TYPE
   SYNTAX     Gauge32 (0..2147483647)
   ACCESS     read-only
   STATUS     mandatory
   DESCRIPTION
     "This variable represents an individual value for the
      mscAtmIfCAPoolRequBwTable."
::= { mscAtmIfCAPoolRequBwEntry 2 }

mscAtmIfCAPoolAdmitBwTable OBJECT-TYPE
   SYNTAX     SEQUENCE OF MscAtmIfCAPoolAdmitBwEntry
   ACCESS     not-accessible
   STATUS     mandatory
   DESCRIPTION
     "This attribute indicates the total admitted bandwidth in 
      bandwidthPool. This attribute does not include bandwidth for ATM 
      networking signalling connections, or bandwidth for connections 
      managed by a Vpt CA. Its value is the sum of the equivalent cell 
      rates (ECR) of the admitted connections."
::= { mscAtmIfCA 299 }

mscAtmIfCAPoolAdmitBwEntry OBJECT-TYPE
   SYNTAX     MscAtmIfCAPoolAdmitBwEntry
   ACCESS     not-accessible
   STATUS     mandatory
   DESCRIPTION
     "An entry in the mscAtmIfCAPoolAdmitBwTable."
   INDEX {
      mscAtmIfIndex,
      mscAtmIfCAIndex,
      mscAtmIfCAPoolAdmitBwIndex }
::= { mscAtmIfCAPoolAdmitBwTable 1 }

MscAtmIfCAPoolAdmitBwEntry ::= SEQUENCE {
   mscAtmIfCAPoolAdmitBwIndex
      Integer32,
   mscAtmIfCAPoolAdmitBwValue
      Gauge32 }

mscAtmIfCAPoolAdmitBwIndex OBJECT-TYPE
   SYNTAX     Integer32 (1..5)
   ACCESS     not-accessible
   STATUS     mandatory
   DESCRIPTION
     "This variable represents the mscAtmIfCAPoolAdmitBwTable
      specific index for the mscAtmIfCAPoolAdmitBwTable."
::= { mscAtmIfCAPoolAdmitBwEntry 1 }

mscAtmIfCAPoolAdmitBwValue OBJECT-TYPE
   SYNTAX     Gauge32 (0..2147483647)
   ACCESS     read-only
   STATUS     mandatory
   DESCRIPTION
     "This variable represents an individual value for the
      mscAtmIfCAPoolAdmitBwTable."
::= { mscAtmIfCAPoolAdmitBwEntry 2 }

mscAtmIfCAPoolAvailBwTable OBJECT-TYPE
   SYNTAX     SEQUENCE OF MscAtmIfCAPoolAvailBwEntry
   ACCESS     not-accessible
   STATUS     obsolete
   DESCRIPTION
     "This attribute indicates the total available bandwidth in 
      bandwidthPool. Its value is the link capacity reduced by the sum of 
      the equivalent cell rates (ECR) of the admitted connections."
::= { mscAtmIfCA 300 }

mscAtmIfCAPoolAvailBwEntry OBJECT-TYPE
   SYNTAX     MscAtmIfCAPoolAvailBwEntry
   ACCESS     not-accessible
   STATUS     obsolete
   DESCRIPTION
     "An entry in the mscAtmIfCAPoolAvailBwTable."
   INDEX {
      mscAtmIfIndex,
      mscAtmIfCAIndex,
      mscAtmIfCAPoolAvailBwIndex }
::= { mscAtmIfCAPoolAvailBwTable 1 }

MscAtmIfCAPoolAvailBwEntry ::= SEQUENCE {
   mscAtmIfCAPoolAvailBwIndex
      Integer32,
   mscAtmIfCAPoolAvailBwValue
      Gauge32 }

mscAtmIfCAPoolAvailBwIndex OBJECT-TYPE
   SYNTAX     Integer32 (1..3)
   ACCESS     not-accessible
   STATUS     obsolete
   DESCRIPTION
     "This variable represents the mscAtmIfCAPoolAvailBwTable
      specific index for the mscAtmIfCAPoolAvailBwTable."
::= { mscAtmIfCAPoolAvailBwEntry 1 }

mscAtmIfCAPoolAvailBwValue OBJECT-TYPE
   SYNTAX     Gauge32 (0..2147483647)
   ACCESS     read-only
   STATUS     obsolete
   DESCRIPTION
     "This variable represents an individual value for the
      mscAtmIfCAPoolAvailBwTable."
::= { mscAtmIfCAPoolAvailBwEntry 2 }

mscAtmIfCAPoolProvBwTable OBJECT-TYPE
   SYNTAX     SEQUENCE OF MscAtmIfCAPoolProvBwEntry
   ACCESS     not-accessible
   STATUS     mandatory
   DESCRIPTION
     "This attribute indicates the total bandwidth from bandwidthPool 
      which is specified by provisioned connections except for those 
      managed by a Vpt CA. Its value is the sum of the equivalent cell 
      rates (ECR) of the provisioned connections. Provisioned 
      connections include provisioned AtmIf Vccs, AtmIf Vpcs, AtmIf 
      Vpts, Vpt Vccs, and Vccs or Vpcs with a Src component under them."
::= { mscAtmIfCA 319 }

mscAtmIfCAPoolProvBwEntry OBJECT-TYPE
   SYNTAX     MscAtmIfCAPoolProvBwEntry
   ACCESS     not-accessible
   STATUS     mandatory
   DESCRIPTION
     "An entry in the mscAtmIfCAPoolProvBwTable."
   INDEX {
      mscAtmIfIndex,
      mscAtmIfCAIndex,
      mscAtmIfCAPoolProvBwIndex }
::= { mscAtmIfCAPoolProvBwTable 1 }

MscAtmIfCAPoolProvBwEntry ::= SEQUENCE {
   mscAtmIfCAPoolProvBwIndex
      Integer32,
   mscAtmIfCAPoolProvBwValue
      Gauge32 }

mscAtmIfCAPoolProvBwIndex OBJECT-TYPE
   SYNTAX     Integer32 (1..5)
   ACCESS     not-accessible
   STATUS     mandatory
   DESCRIPTION
     "This variable represents the mscAtmIfCAPoolProvBwTable
      specific index for the mscAtmIfCAPoolProvBwTable."
::= { mscAtmIfCAPoolProvBwEntry 1 }

mscAtmIfCAPoolProvBwValue OBJECT-TYPE
   SYNTAX     Gauge32 (0..2147483647)
   ACCESS     read-only
   STATUS     mandatory
   DESCRIPTION
     "This variable represents an individual value for the
      mscAtmIfCAPoolProvBwTable."
::= { mscAtmIfCAPoolProvBwEntry 2 }

mscAtmIfCAPoolWaitAdmConnsTable OBJECT-TYPE
   SYNTAX     SEQUENCE OF MscAtmIfCAPoolWaitAdmConnsEntry
   ACCESS     not-accessible
   STATUS     mandatory
   DESCRIPTION
     "This attribute indicates the total number of connections which have 
      currently requested admission in bandwidthPool but are not yet 
      admitted. This attribute does not include ATM networking 
      signalling connections, or connections managed by a Vpt CA."
::= { mscAtmIfCA 320 }

mscAtmIfCAPoolWaitAdmConnsEntry OBJECT-TYPE
   SYNTAX     MscAtmIfCAPoolWaitAdmConnsEntry
   ACCESS     not-accessible
   STATUS     mandatory
   DESCRIPTION
     "An entry in the mscAtmIfCAPoolWaitAdmConnsTable."
   INDEX {
      mscAtmIfIndex,
      mscAtmIfCAIndex,
      mscAtmIfCAPoolWaitAdmConnsIndex }
::= { mscAtmIfCAPoolWaitAdmConnsTable 1 }

MscAtmIfCAPoolWaitAdmConnsEntry ::= SEQUENCE {
   mscAtmIfCAPoolWaitAdmConnsIndex
      Integer32,
   mscAtmIfCAPoolWaitAdmConnsValue
      Gauge32 }

mscAtmIfCAPoolWaitAdmConnsIndex OBJECT-TYPE
   SYNTAX     Integer32 (1..5)
   ACCESS     not-accessible
   STATUS     mandatory
   DESCRIPTION
     "This variable represents the mscAtmIfCAPoolWaitAdmConnsTable
      specific index for the mscAtmIfCAPoolWaitAdmConnsTable."
::= { mscAtmIfCAPoolWaitAdmConnsEntry 1 }

mscAtmIfCAPoolWaitAdmConnsValue OBJECT-TYPE
   SYNTAX     Gauge32 (0..16384)
   ACCESS     read-only
   STATUS     mandatory
   DESCRIPTION
     "This variable represents an individual value for the
      mscAtmIfCAPoolWaitAdmConnsTable."
::= { mscAtmIfCAPoolWaitAdmConnsEntry 2 }

mscAtmIfCAPoolAdmConnsTable OBJECT-TYPE
   SYNTAX     SEQUENCE OF MscAtmIfCAPoolAdmConnsEntry
   ACCESS     not-accessible
   STATUS     mandatory
   DESCRIPTION
     "This attribute indicates the total number of connections which are 
      currently admitted in bandwidthPool. This attribute does not 
      include ATM networking signalling connections, or connections 
      managed by a Vpt CA."
::= { mscAtmIfCA 321 }

mscAtmIfCAPoolAdmConnsEntry OBJECT-TYPE
   SYNTAX     MscAtmIfCAPoolAdmConnsEntry
   ACCESS     not-accessible
   STATUS     mandatory
   DESCRIPTION
     "An entry in the mscAtmIfCAPoolAdmConnsTable."
   INDEX {
      mscAtmIfIndex,
      mscAtmIfCAIndex,
      mscAtmIfCAPoolAdmConnsIndex }
::= { mscAtmIfCAPoolAdmConnsTable 1 }

MscAtmIfCAPoolAdmConnsEntry ::= SEQUENCE {
   mscAtmIfCAPoolAdmConnsIndex
      Integer32,
   mscAtmIfCAPoolAdmConnsValue
      Gauge32 }

mscAtmIfCAPoolAdmConnsIndex OBJECT-TYPE
   SYNTAX     Integer32 (1..5)
   ACCESS     not-accessible
   STATUS     mandatory
   DESCRIPTION
     "This variable represents the mscAtmIfCAPoolAdmConnsTable
      specific index for the mscAtmIfCAPoolAdmConnsTable."
::= { mscAtmIfCAPoolAdmConnsEntry 1 }

mscAtmIfCAPoolAdmConnsValue OBJECT-TYPE
   SYNTAX     Gauge32 (0..16384)
   ACCESS     read-only
   STATUS     mandatory
   DESCRIPTION
     "This variable represents an individual value for the
      mscAtmIfCAPoolAdmConnsTable."
::= { mscAtmIfCAPoolAdmConnsEntry 2 }

mscAtmIfCAPoolAvailableBwTable OBJECT-TYPE
   SYNTAX     SEQUENCE OF MscAtmIfCAPoolAvailableBwEntry
   ACCESS     not-accessible
   STATUS     mandatory
   DESCRIPTION
     "This attribute indicates the total available bandwidth in 
      bandwidthPool. A positive number indicates that there is still 
      bandwidth available in the pool which has not been allocated. A 
      negative value indicates that some bandwidth-elastic provisioned 
      connections are running in reduced mode, where their allocated 
      bandwidth is below their originally allocated ECR. The negative 
      amount is equal to the sum of the bwReduction attribute for all 
      connections under this bandwidthPool."
::= { mscAtmIfCA 326 }

mscAtmIfCAPoolAvailableBwEntry OBJECT-TYPE
   SYNTAX     MscAtmIfCAPoolAvailableBwEntry
   ACCESS     not-accessible
   STATUS     mandatory
   DESCRIPTION
     "An entry in the mscAtmIfCAPoolAvailableBwTable."
   INDEX {
      mscAtmIfIndex,
      mscAtmIfCAIndex,
      mscAtmIfCAPoolAvailableBwIndex }
::= { mscAtmIfCAPoolAvailableBwTable 1 }

MscAtmIfCAPoolAvailableBwEntry ::= SEQUENCE {
   mscAtmIfCAPoolAvailableBwIndex
      Integer32,
   mscAtmIfCAPoolAvailableBwValue
      INTEGER }

mscAtmIfCAPoolAvailableBwIndex OBJECT-TYPE
   SYNTAX     Integer32 (1..5)
   ACCESS     not-accessible
   STATUS     mandatory
   DESCRIPTION
     "This variable represents the mscAtmIfCAPoolAvailableBwTable
      specific index for the mscAtmIfCAPoolAvailableBwTable."
::= { mscAtmIfCAPoolAvailableBwEntry 1 }

mscAtmIfCAPoolAvailableBwValue OBJECT-TYPE
   SYNTAX     INTEGER (-2147483648..2147483647)
   ACCESS     read-only
   STATUS     mandatory
   DESCRIPTION
     "This variable represents an individual value for the
      mscAtmIfCAPoolAvailableBwTable."
::= { mscAtmIfCAPoolAvailableBwEntry 2 }


-- AtmIf/n CA ConstantBitRate/n 
-- This component manages the default characteristics of the constant 
-- bit rate (CBR) service category.

mscAtmIfCACbr OBJECT IDENTIFIER ::= { mscAtmIfCA 2 }



mscAtmIfCACbrRowStatusTable OBJECT-TYPE
   SYNTAX     SEQUENCE OF MscAtmIfCACbrRowStatusEntry
   ACCESS     not-accessible
   STATUS     mandatory
   DESCRIPTION
     "This entry controls the addition and deletion of 
      mscAtmIfCACbr components."
::= { mscAtmIfCACbr 1 }

mscAtmIfCACbrRowStatusEntry OBJECT-TYPE
   SYNTAX     MscAtmIfCACbrRowStatusEntry
   ACCESS     not-accessible
   STATUS     mandatory
   DESCRIPTION
     "A single entry in the table represents a single 
      mscAtmIfCACbr component."
   INDEX {
      mscAtmIfIndex,
      mscAtmIfCAIndex,
      mscAtmIfCACbrIndex }
::= { mscAtmIfCACbrRowStatusTable 1 }

MscAtmIfCACbrRowStatusEntry ::= SEQUENCE {
   mscAtmIfCACbrRowStatus
      RowStatus,
   mscAtmIfCACbrComponentName
      DisplayString,
   mscAtmIfCACbrStorageType
      StorageType,
   mscAtmIfCACbrIndex
      Integer32 }

mscAtmIfCACbrRowStatus OBJECT-TYPE
   SYNTAX     RowStatus 
   ACCESS     read-write
   STATUS     mandatory
   DESCRIPTION
     "This variable is used as the basis for SNMP naming of
      mscAtmIfCACbr components.
      These components can be added."
::= { mscAtmIfCACbrRowStatusEntry 1 }

mscAtmIfCACbrComponentName OBJECT-TYPE
   SYNTAX     DisplayString 
   ACCESS     read-only
   STATUS     mandatory
   DESCRIPTION
     "This variable provides the component's string name for
      use with the ASCII Console Interface"
::= { mscAtmIfCACbrRowStatusEntry 2 }

mscAtmIfCACbrStorageType OBJECT-TYPE
   SYNTAX     StorageType 
   ACCESS     read-only
   STATUS     mandatory
   DESCRIPTION
     "This variable represents the storage type value for the
      mscAtmIfCACbr tables."
::= { mscAtmIfCACbrRowStatusEntry 4 }

mscAtmIfCACbrIndex OBJECT-TYPE
   SYNTAX     Integer32 (0)
   ACCESS     not-accessible
   STATUS     mandatory
   DESCRIPTION
     "This variable represents the index for the mscAtmIfCACbr tables."
::= { mscAtmIfCACbrRowStatusEntry 10 }

mscAtmIfCACbrProvTable OBJECT-TYPE
   SYNTAX     SEQUENCE OF MscAtmIfCACbrProvEntry
   ACCESS     not-accessible
   STATUS     mandatory
   DESCRIPTION
     "This group contains provisioned attributes which control the CBR 
      service category for this interface."
::= { mscAtmIfCACbr 100 }

mscAtmIfCACbrProvEntry OBJECT-TYPE
   SYNTAX     MscAtmIfCACbrProvEntry
   ACCESS     not-accessible
   STATUS     mandatory
   DESCRIPTION
     "An entry in the mscAtmIfCACbrProvTable."
   INDEX {
      mscAtmIfIndex,
      mscAtmIfCAIndex,
      mscAtmIfCACbrIndex }
::= { mscAtmIfCACbrProvTable 1 }

MscAtmIfCACbrProvEntry ::= SEQUENCE {
   mscAtmIfCACbrProvPool
      INTEGER,
   mscAtmIfCACbrProvCdvt
      Unsigned32,
   mscAtmIfCACbrCdv
      Unsigned32,
   mscAtmIfCACbrMaxCtd
      Unsigned32,
   mscAtmIfCACbrProvClr
      Unsigned32,
   mscAtmIfCACbrTxQueueLimit
      Unsigned32,
   mscAtmIfCACbrHoldingPriority
      INTEGER,
   mscAtmIfCACbrSvcHoldingPriority
      INTEGER,
   mscAtmIfCACbrSvcMpHoldingPriority
      INTEGER,
   mscAtmIfCACbrMinPerVcQueueLimit
      Unsigned32,
   mscAtmIfCACbrPerVcQueueLimitReferenceRate
      Unsigned32,
   mscAtmIfCACbrEmissionPriority
      Unsigned32,
   mscAtmIfCACbrTrafficShaping
      INTEGER,
   mscAtmIfCACbrShapeRecoupPolicy
      INTEGER,
   mscAtmIfCACbrUnshapedTransmitQueueing
      INTEGER,
   mscAtmIfCACbrWeightPolicy
      INTEGER,
   mscAtmIfCACbrForceTagging
      INTEGER,
   mscAtmIfCACbrUsageParameterControl
      INTEGER }

mscAtmIfCACbrProvPool OBJECT-TYPE
   SYNTAX     INTEGER  {
                 pool1(1),
                 pool2(2),
                 pool3(3),
                 pool4(4),
                 pool5(5) }
   ACCESS     read-write
   STATUS     mandatory
   DESCRIPTION
     "This attribute specifies the bandwidth pool which is to be used to 
      support the constant bit rate (CBR) service category except for 
      connections managed by a Vpt CA. The percentage of link capacity 
      reserved for the given bandwidth pool is the maximum bandwidth 
      that can be allocated to CBR traffic. The percentage allocated to 
      each bandwidth pool can be provisioned through the bandwidthPool 
      attribute under the CA."
   DEFVAL     { pool1 }
::= { mscAtmIfCACbrProvEntry 10 }

mscAtmIfCACbrProvCdvt OBJECT-TYPE
   SYNTAX     Unsigned32 (1..10000)
   ACCESS     read-write
   STATUS     mandatory
   DESCRIPTION
     "This attribute specifies the default cell delay variation tolerance 
      (CDVT) for all connections of the CBR service category except 
      those managed by a Vpt CA. An override to this default may be 
      specified for a provisioned connection under the Vcd Tm or Vpd Tm 
      component.
      
      This attribute is used by the CAC function to compute the 
      equivalent cell rate (ECR) required by a given CBR connection. The 
      larger the value of CDVT, the larger is its ECR. 
      
      If Usage Parameter Control (UPC) is enabled for a connection, 
      CDVT is used by the UPC function to decide whether a cell is 
      conforming or non-conforming based on the connection's traffic 
      descriptor type. The larger the CDVT value, the more tolerant is the 
      UPC of bandwidth usage beyond the traffic contract."
   DEFVAL     { 250 }
::= { mscAtmIfCACbrProvEntry 20 }

mscAtmIfCACbrCdv OBJECT-TYPE
   SYNTAX     Unsigned32 (0..2147483647)
   ACCESS     read-write
   STATUS     mandatory
   DESCRIPTION
     "This attribute specifies the peak-to-peak cell delay variation (CDV) 
      which is contributed to the entire ATM Interface for CBR traffic. 
      
      The CDV is a measure of the delay jitter introduced mostly by 
      traffic buffering and cell scheduling. The worst case value of this 
      attribute can be computed as the txQueueLimit divided by the link 
      rate of this ATM Interface.
      
      The value of this attribute is used by PNNI in the Resource 
      Availability Information Group (RAIG) topology updates and route 
      selection. It is also used by CAC at connection set-up time to 
      determine whether this ATM Interface can meet the CDV 
      requirements of the connection. If so, the value of this attribute is 
      added to the cumulative CDV field of the extended QoS information 
      element."
   DEFVAL     { 250 }
::= { mscAtmIfCACbrProvEntry 30 }

mscAtmIfCACbrMaxCtd OBJECT-TYPE
   SYNTAX     Unsigned32 (0..2147483647)
   ACCESS     read-write
   STATUS     mandatory
   DESCRIPTION
     "This attribute specifies the maximum cell transfer delay (MaxCTD) 
      which is applied to the entire ATM Interface for CBR traffic.
      
      MaxCTD is the sum of the fixed delay and the CDV. The 
      components of the fixed delay include propagation delay through 
      the physical media, delays induced by the transmission system, and 
      fixed components of switch processing delay. 
      
      This attribute is used by PNNI in the Resource Availability 
      Information Group (RAIG) topology updates and route selection. It 
      is also used by CAC at connection set-up time to determine whether 
      this ATM Interface can meet the ATM connection's MaxCTD 
      requirement."
   DEFVAL     { 1000 }
::= { mscAtmIfCACbrProvEntry 40 }

mscAtmIfCACbrProvClr OBJECT-TYPE
   SYNTAX     Unsigned32 (0..15)
   ACCESS     read-write
   STATUS     mandatory
   DESCRIPTION
     "This attribute specifies the tolerable cell loss ratio (CLR) for CBR 
      traffic except for connections managed by a Vpt CA. The number is 
      the negative logarithm (base 10) of the CLR. For example, if the 
      target CLR = 1E-10 then Cbr cellLossRatio = 10. This number must 
      be the same as the RtVbr cellLossRatio since CBR and rt-VBR 
      traffic have the same discard priority. The Cbr cellLossRatio is used 
      by the Connection Admission Control (CAC) algorithm to compute 
      the required (equivalent) cell rate for CBR connections. 
      
      There is a trade-off between the service category CLR and the 
      achievable link utilization. To guarantee an excellent service 
      category, the CLR should be as small as possible (e.g., 1E-10). 
      However, a smaller CLR results in a larger equivalent cell rate for a 
      given connection and hence a lower link utilization.
      
      Setting this attribute to 0 means that a CLR of 1 can be tolerated. In 
      this case, no bandwidth is reserved for CBR connections, and CAC 
      is effectively turned off. All CBR connections are admitted."
   DEFVAL     { 10 }
::= { mscAtmIfCACbrProvEntry 50 }

mscAtmIfCACbrTxQueueLimit OBJECT-TYPE
   SYNTAX     Unsigned32 (0 | 5..512000)
   ACCESS     read-write
   STATUS     mandatory
   DESCRIPTION
     "This attribute specifies the default maximum queue length for the 
      emission queues used to buffer the traffic of the CBR service 
      category. It is used as the basis for setting the discard thresholds on 
      both common and per-VC queues. For the common queue, the 
      discard thresholds are set at approximately 35, 75, and 90 percent of 
      the value of this attribute for traffic at discard priority 3 (DP=3), 
      DP=2 and DP=1 respectively.
      
      For a per-VC queue, the actual limit may be reduced depending on 
      the shaping rate of the connection (for standard Vpt Vccs, this is the 
      shaping rate of the Vpt). The discard thresholds are set at 
      approximately 35, 75 and 90 percent of the scaled queue limit for 
      traffic at discard priority 3 (DP=3), DP=2 and DP=1 respectively. 
      However, a reduction will never result in a value that is less than the 
      value set for the minPerVcQueueLimit attribute. CQC-based ATM 
      cards and 1pOC12SmLrAtm cards do not support per-VC queues at 
      the CBR service category.
      
      When this attribute is set to autoConfigure, an appropriate value is 
      selected based on the card type. It is set to 96 for all Passport ATM 
      cards (DS1, E1, IMA, JT2, DS3, E3, OC3, both CQC- and ATM IP-
      based), except 1pOC12SmLrAtm. For the 1pOC12SmLrAtm card, 
      the value is set to 350.
      
      For ATM IP FPs, the per-VC queue limit may be overridden for a 
      permanent connection by specifying a value in the Vcd Tm or Vpd 
      Tm txQueueLimit attribute.
      
      For CQC-based ATM cards, the valid range for this attribute is from 
      5 to 30000 inclusive.
      
      The operational value of the maximum length of a queue (common 
      or per-VC) is indicated by the Vcc Tm, Vpc Tm, or Vpt Tm 
      txQueueThresholds attribute.
      
      For standard Vpts, this attribute does not apply when using per-VC 
      queuing and only applies when using common queueing. When 
      using per-VC queueing, regardless of the Vpt's service category, 
      standard Vpts use the AtmIf Ca NrtVbr txQueueLimit value as their 
      default.
      
      This attribute does not apply to basic Vpts.

      VALUES (

      0 = autoConfigure

      )"
   DEFVAL     { 0 }
::= { mscAtmIfCACbrProvEntry 60 }

mscAtmIfCACbrHoldingPriority OBJECT-TYPE
   SYNTAX     INTEGER  {
                 n0(0),
                 n1(1),
                 n2(2),
                 n3(3),
                 n4(4) }
   ACCESS     read-write
   STATUS     mandatory
   DESCRIPTION
     "This attribute specifies the holding priority which applies to SVP 
      and SVC CBR connections. It takes a value from 0 (highest 
      priority) to 4 (lowest priority). In a situation where the link 
      bandwidth fluctuates, such as over an IMA link, holding priority is 
      used to determine which connections are held and which are 
      released. Holding priority 4 connections are the first to be released. 
      Holding priority 0 connections are the last to be released.
      
      This attribute does not apply to Vpt Vccs. When bandwidth 
      fluctuates, the entire Vpt, along with all Vpt Vccs is released as a 
      unit, according to the Vpt's holdingPriority."
   DEFVAL     { n3 }
::= { mscAtmIfCACbrProvEntry 61 }

mscAtmIfCACbrSvcHoldingPriority OBJECT-TYPE
   SYNTAX     INTEGER  {
                 n0(0),
                 n1(1),
                 n2(2),
                 n3(3),
                 n4(4) }
   ACCESS     read-write
   STATUS     obsolete
   DESCRIPTION
     "This attribute specifies the default holding priority which applies to 
      SVC CBR connections. It takes a value from 0 (highest priority) to 
      4 (lowest priority). In a situation where the link bandwidth 
      fluctuates, such as over an IMA link, holding priority is used to 
      determine which connections are held and which are released. 
      Holding priority 4 connections are the first to be released. Holding 
      priority 0 connections are the last to be released.
      This attribute has been obsoleted and its value migrated to 
      holdingPriority attribute."
   DEFVAL     { n3 }
::= { mscAtmIfCACbrProvEntry 70 }

mscAtmIfCACbrSvcMpHoldingPriority OBJECT-TYPE
   SYNTAX     INTEGER  {
                 n0(0),
                 n1(1),
                 n2(2),
                 n3(3),
                 n4(4) }
   ACCESS     read-write
   STATUS     mandatory
   DESCRIPTION
     "This attribute specifies the default holding priority which applies to 
      SVC CBR point-to-multipoint connections. It takes a value from 0 
      (highest priority) to 4 (lowest priority). In a situation where the link 
      bandwidth fluctuates, such as over an IMA link, holding priority is 
      used to determine which connections are held and which are 
      released. Holding priority 4 connections are the first to be released. 
      Holding priority 0 connections are the last to be released.
      
      This attribute does not apply to Vpt Vccs. When bandwidth 
      fluctuates, the entire Vpt, along with all Vpt Vccs is released as a 
      unit, according to the Vpt's holdingPriority."
   DEFVAL     { n3 }
::= { mscAtmIfCACbrProvEntry 71 }

mscAtmIfCACbrMinPerVcQueueLimit OBJECT-TYPE
   SYNTAX     Unsigned32 (5..12000)
   ACCESS     read-write
   STATUS     mandatory
   DESCRIPTION
     "This attribute specifies the minimum queue limit for the per-VC 
      queues of connections of the CBR service category. 
      
      This attribute is ignored on CQC-based ATM cards, 
      1pOC48SmSrAtm, and 1pOC12SmLrAtm cards, because they do 
      not support per-VC queues at the CBR service category.
      
      The queue limit of a per-VC queue is obtained by scaling down the 
      txQueueLimit based on the shaping rate of that queue (shaping rate 
      for the connection, and for standard Vpt Vccs, the shaping rate of 
      the Vpt). This produces a constant delay for various queue lengths. 
      The txQueueLimit provides an upper bound while 
      minPerVcQueueLimit provides the lower bound. The value of this 
      attribute must not be greater than the value of the txQueueLimit 
      attribute. If this service category is used by Trunks the value of 
      minPerVcQueueLimit must be at least 88.
      
      For Vpts, this attribute does not apply. Regardless of Vpt service 
      category, standard Vpts always use the AtmIf Ca NrtVbr 
      minPerVcQueueLimit value as their default. To determine the queue 
      limit of a standard Vpt Vcc, the txQueueLimit is scaled down by the 
      Vpt shaping rate."
   DEFVAL     { 88 }
::= { mscAtmIfCACbrProvEntry 80 }

mscAtmIfCACbrPerVcQueueLimitReferenceRate OBJECT-TYPE
   SYNTAX     Unsigned32 (0 | 1..1416905)
   ACCESS     read-write
   STATUS     mandatory
   DESCRIPTION
     "This attribute specifies the shaping rate to be used in computing the 
      tolerable delay for per-VC queues of connections of the CBR 
      service category. The delay is computed as the txQueueLimit 
      divided by the value of this attribute. 
      
      This attribute is ignored on CQC-based ATM cards and 
      1pOC12SmLrAtm cards, because they do not support per-VC 
      queues at the CBR service category.
      
      When the value of this attribute is autoConfigure, an appropriate 
      default is selected based on the card type. It is set to 80000 for all 
      cards which support per-VC queuing at the CBR service category 
      (3pDS3Atm2, 3pE3Atm2, 2pOC3SmAtm2, 2pOC3MmAtm2). For 
      4pOC12SmIrAtm and 4pOC12SmLrAtm cards, the reference rate is 
      set to 65511 for DS3 and OC3 channels, and set to 262044 for 
      OC12 channels. For Apc-based cards the maximum value is 
      1416905. For all other cards, the maximum value is 943396.
      
      For Vpts, this attribute does not apply. Regardless of Vpt service 
      category, standard Vpts always use the AtmIf Ca NrtVbr 
      perVcQueueLimitReferenceRate value as their default.

      VALUES (

      0 = autoConfigure

      )"
   DEFVAL     { 0 }
::= { mscAtmIfCACbrProvEntry 90 }

mscAtmIfCACbrEmissionPriority OBJECT-TYPE
   SYNTAX     Unsigned32 (0..7)
   ACCESS     read-write
   STATUS     mandatory
   DESCRIPTION
     "This attribute is not applicable and is ignored for CQC-based ATM 
      cards.
      
      This attribute specifies the emission priority (EP) which is used to 
      transmit traffic of the CBR service category. A lower numerical 
      value for this attribute specifies a higher emission priority. 0 is the 
      highest EP and 7 is the lowest. Cells at a higher emission priority 
      receive higher preference for link bandwidth. EPs 0 and 1 are in the 
      absolute priority range, and are unaffected by any minimum 
      bandwidth guarantees. EPs 2 through 7 are in the guaranteed 
      bandwidth range. Minimum bandwidth guarantee is specified in the 
      AtmIf/n Ep/m component. 
      
      Emission priority setting must comply with all of the following 
      constraints: 
      1. The emission priority numbers must be in the following order: 
      CBR <= rt-VBR <= nrt-VBR <= ABR <= UBR 
      2. Two different ATM service categories may share the same EP 
      only if they are both shaped. 
      3. CBR and rt-VBR may be placed either in the absolute priority 
      range (EP 0 or 1) or in the guaranteed bandwidth range (EP 2 
      through 7). 
      4. If both CBR and rt-VBR are shaped, rt-VBR must share the 
      same EP with CBR or ABR. If either one of CBR or rt-VBR are 
      not shaped, then they cannot share the same EP. 
      5. ABR service category is always deemed to be shaped. If nrt-VBR 
      is shaped, it must share the same EP with ABR. If nrt-VBR is not 
      shaped it must have a higher EP than ABR.
      6. If UBR is shaped, it must share the same EP with ABR. If UBR 
      is not shaped, it must have a lower EP than ABR.
      
      This attribute does not apply to basic Vpts, and standard Vpt Vccs."
   DEFVAL     { 0 }
::= { mscAtmIfCACbrProvEntry 100 }

mscAtmIfCACbrTrafficShaping OBJECT-TYPE
   SYNTAX     INTEGER  {
                 disabled(1),
                 enabled(5),
                 inverseUpc(6) }
   ACCESS     read-write
   STATUS     mandatory
   DESCRIPTION
     "This attribute specifies the default traffic shaping option for 
      connections of the CBR service category. An override to this default 
      may be specified for a provisioned connection under the Vcd Tm or 
      Vpd Tm component.
      
      When this attribute is set to disabled, traffic shaping cannot be 
      enabled for any CBR connections. 
      
      For CQC-based ATM FPs and 1pOC12SmLrAtm FPs, this attribute 
      must be set to disabled. Traffic shaping is not supported for CBR 
      connections on CQC-based ATM FPs. 
      
      If the Vcc Tm, Vpc Tm, or Vpt Tm, txTrafficDescType indicates type 
      1 or 2, this attribute is ignored, and traffic shaping is not applicable 
      for that connection. 
      
      When this attribute is set to inverseUpc, traffic shaping for a 
      connection is enabled according to the value of the Vcc Tm, Vpc 
      Tm, or Vpt Tm txTrafficDescType. For 4pOC12SmIrAtm and 
      4pOC12SmLrAtm cards, inverseUpc shaping is not available.
      
      If this attribute is set to inverseUpc, and the txTrafficDescType is 3, 
      4, or 5, linear traffic shaping is enabled. Linear traffic shaping uses 
      a single static traffic shaping rate. 
      
      If this attribute is set to inverseUpc, and the txTrafficDescType is 6, 
      7, or 8, inverse-UPC (also referred to as VBR or dual leaky bucket) 
      traffic shaping is enabled. Inverse-UPC traffic shaping can burst 
      above the sustained cell rate to the peak cell rate for the duration 
      defined by maximum burst size. Inverse-UPC traffic shaping exactly 
      conforms to the requirements of a dual leaky bucket UPC enforcer. 
      
      When this attribute is set to enabled and the txTrafficDescType is 3, 
      4, 5, 6, 7, or 8, traffic shaping for a connection is enabled using 
      linear shaping. 
      
      Enabling or disabling traffic shaping may require a matching 
      change to the emissionPriority attribute and 
      unshapedTransmitQueueing attribute for this service category. 
      Refer to those attributes for the complete description of the 
      interactions.
      
      This attribute does not apply to basic Vpts, and standard Vpt Vccs."
   DEFVAL     { disabled }
::= { mscAtmIfCACbrProvEntry 140 }

mscAtmIfCACbrShapeRecoupPolicy OBJECT-TYPE
   SYNTAX     INTEGER  {
                 minimumCdv(0),
                 maximumEfficiency(1) }
   ACCESS     read-write
   STATUS     mandatory
   DESCRIPTION
     "This attribute specifies the shaping recoup policy for the CBR 
      service category. This is the policy which is used to recoup shaping 
      opportunities which are lost when more than one connection 
      schedules a cell for the same transmit opportunity. In this case, one 
      connection is scheduled, and the cell from the other connection is 
      delayed by one cell time. This attribute affects how the transmit 
      time is calculated for the next cell on the delayed connection. This 
      attribute is ignored if this service category is not shaped.
      
      When the connection which was delayed schedules the next cell to 
      transmit, it may calculate the time as a difference from either the 
      previous actual cell transmit time, or the time when the previous 
      cell should have been transmitted.
      
      Setting this attribute to maximumEfficiency results in each 
      connection trying to recoup or regain any delays in scheduling. The 
      transmit time from the next cell is calculated from the time when 
      the cell should originally have been sent. Cell delay variation 
      (CDV) occurs in this case since the cells are sent with less than the 
      shaping delay between them. However, in general the shaper 
      recovers (recoups) lost opportunities and improves efficiency.
      
      Setting this attribute to minimumCdv results in connections not 
      trying to recoup or regain any delays in scheduling. The transmit 
      time for the next cell is calculated from the time when the previous 
      cell was actually transmitted. This minimizes CDV, but results in 
      missed cell opportunities.
      
      This attribute does not apply to basic Vpts, and standard Vpt Vccs."
   DEFVAL     { minimumCdv }
::= { mscAtmIfCACbrProvEntry 150 }

mscAtmIfCACbrUnshapedTransmitQueueing OBJECT-TYPE
   SYNTAX     INTEGER  {
                 perVc(0),
                 common(1) }
   ACCESS     read-write
   STATUS     mandatory
   DESCRIPTION
     "This attribute specifies the default queuing option for unshaped 
      connections of the CBR service category. On ATM IP cards, this 
      attribute controls whether common or per-VC queueing is used.
      
      Per-VC queueing means that each connection has its own buffering 
      and queue limits.
      
      Common queueing means that cells are queued in First In First Out 
      order on a common queue for this service category. The common 
      queue has one set of congestion control levels for all cells enqueued 
      on it. 
      
      For 1pOC12SmLrAtm cards this attribute must be set to common or 
      autoConfigure. This attribute cannot be set to perVc since perVc 
      queueing is not available on the 1pOC12SmLrAtm card. The value 
      autoConfigure is interpreted to mean common queueing.
      
      For CQC-based ATM cards, this attribute must be set to common. 
      CQC-based ATM cards do not support per-VC queueing for the 
      CBR service category. For 4pOC12SmIrAtm and 
      4pOC12SmLrAtm cards only perVc queueing is supported. All 
      other attribute values are ignored.
      
      For ATM IP cards, if traffic shaping for this service category is not 
      disabled, this attribute must be set to perVc.
      
      This attribute does not apply to basic Vpts, and standard Vpt Vccs."
   DEFVAL     { common }
::= { mscAtmIfCACbrProvEntry 160 }

mscAtmIfCACbrWeightPolicy OBJECT-TYPE
   SYNTAX     INTEGER  {
                 scr(1),
                 pcr(2),
                 ecr(3) }
   ACCESS     read-write
   STATUS     mandatory
   DESCRIPTION
     "This attribute specifies the default policy which is applied when 
      calculating the fairness weight for unshaped connections of the 
      CBR service category. The fairness weight for a connection 
      determines the relative amount of bandwidth which that connection 
      obtains, compared to other connections in the same service 
      category. Connections with equal weight get equal transmit 
      opportunities. Connections with higher weights get more transmit 
      opportunities compared with connections that have lower weights. 
      An override to this default may be specified for a provisioned 
      connection under the Vcd Tm or Vpd Tm component. 
      
      The fairness weight for a connection is directly proportional to the 
      value of one of the traffic descriptor parameters for that connection. 
      This attribute specifies which traffic descriptor parameter is used for 
      connections of the CBR service category. 
      
      This attribute is ignored on CQC-based ATM cards. This attribute is 
      also ignored on ATM IP cards if unshapedTransmitQueueing is set 
      for common queuing. 
      
      If this attribute is set to scr, the fairness weight is proportional to the 
      transmit sustained cell rate (SCR) of a connection. Connections 
      with a higher SCR have a higher fairness weight. For connections 
      with txTrafficDescType 3, which have no SCR, the sustained cell 
      rate is assumed to be equal to the peak cell rate. 
      
      If this attribute is set to pcr, the fairness weight is proportional to 
      the transmit peak cell rate (PCR) of a connection. Connections with 
      a higher PCR have a higher fairness weight. Connections with 
      txTrafficDescType 1 or 2 get a minimum weight, which is 1. 
      
      If this attribute is set to ecr, the fairness weight is proportional to 
      the equivalent cell rate (ECR) of a connection as calculated by 
      connection admission control (CAC). Connections with a higher 
      ECR have a higher fairness weight. Connections with an ECR of 0 
      get a minimum weight, which is 1. 
      
      The weight of a connection is visible in the Vcc Tm, Vpc Tm, or Vpt 
      Tm weight attribute. 
      
      This attribute does not apply to basic Vpts, and standard Vpt Vccs."
   DEFVAL     { ecr }
::= { mscAtmIfCACbrProvEntry 165 }

mscAtmIfCACbrForceTagging OBJECT-TYPE
   SYNTAX     INTEGER  {
                 enabled(0),
                 disabled(1) }
   ACCESS     read-write
   STATUS     mandatory
   DESCRIPTION
     "This attribute specifies the default of whether to force tagging 
      (CLP=1) of all cells for all CBR connections. An override to this 
      default may be specified for a provisioned connection under the Vcd 
      Tm or Vpd Tm component. This attribute is not supported by 
      4pOC12SmIrAtm and 4pOC12SmLrAtm cards.
      
      When this attribute is set to enabled, CLP is set to 1 for all cells in 
      the transmit direction. Force tagging is only supported on ATM IP 
      FPs. 
      
      On CQC-based ATM FPs, this attribute must be set to disabled. 
      When this attribute is set to disabled, CLP is unchanged for all cells 
      in the transmit direction.
      
      This attribute never applies to any type of Vpt."
   DEFVAL     { disabled }
::= { mscAtmIfCACbrProvEntry 169 }

mscAtmIfCACbrUsageParameterControl OBJECT-TYPE
   SYNTAX     INTEGER  {
                 enforced(0),
                 disabled(1),
                 monitored(4) }
   ACCESS     read-write
   STATUS     mandatory
   DESCRIPTION
     "This attribute specifies the default usage parameter control (UPC) 
      option for connections of the CBR service category. This attribute is 
      ignored if the rxTrafficDescriptorType indicates 1 or 2. An override 
      to this default may be specified for a provisioned connection under 
      the Vcd Tm or Vpd Tm component. 
      
      When this attribute is set to enforced, UPC is enforced by default 
      for each connection. When UPC is enforced, non-conforming cells 
      are either tagged or discarded depending on the 
      rxTrafficDescriptorType. 
      
      On ATM IP FPs, when this attribute is set to monitored, UPC 
      conformance checking is performed, except, instead of the non-
      conforming cells being tagged or discarded, they are merely 
      counted in the UPC violations counts, and passed on unchanged. 
      
      On CQC-based ATM FPs, when this attribute is set to monitored, it 
      has the same effect as setting it to disabled. 
      
      When this attribute is set to disabled, UPC is disabled on the receive 
      path for all CBR connections.
      
      This attribute never applies to any type of Vpt."
   DEFVAL     { disabled }
::= { mscAtmIfCACbrProvEntry 170 }

mscAtmIfCACbrOperTable OBJECT-TYPE
   SYNTAX     SEQUENCE OF MscAtmIfCACbrOperEntry
   ACCESS     not-accessible
   STATUS     mandatory
   DESCRIPTION
     "This group contains operational attributes for the CBR service 
      category."
::= { mscAtmIfCACbr 110 }

mscAtmIfCACbrOperEntry OBJECT-TYPE
   SYNTAX     MscAtmIfCACbrOperEntry
   ACCESS     not-accessible
   STATUS     mandatory
   DESCRIPTION
     "An entry in the mscAtmIfCACbrOperTable."
   INDEX {
      mscAtmIfIndex,
      mscAtmIfCAIndex,
      mscAtmIfCACbrIndex }
::= { mscAtmIfCACbrOperTable 1 }

MscAtmIfCACbrOperEntry ::= SEQUENCE {
   mscAtmIfCACbrEpdOffset
      Unsigned32 }

mscAtmIfCACbrEpdOffset OBJECT-TYPE
   SYNTAX     Unsigned32 (0 | 5..1024)
   ACCESS     read-only
   STATUS     mandatory
   DESCRIPTION
     "This attribute indicates the Early Packet Discard (EPD) offset which 
      is currently in use for this service category. The EPD offset is used 
      to derive the EPD thresholds for each CC level.
      
      Any connection under this service category which requires the 
      txPacketWiseDiscard feature must specify a transmit queue limit 
      which is at least 5.71 times this offset. This ensures that the derived 
      Epd threshold will never be less than 17.5 % of the transmit queue 
      limit. If this is not done, txPacketWiseDiscard for the connection 
      will be automatically disabled.
      
      The value of this EPD offset is specified under the lp/x eng arc aqm 
      ov component."
::= { mscAtmIfCACbrOperEntry 10 }


-- AtmIf/n CA RealTimeVariableBitRate/n 
-- This component manages the default characteristics of the real-time 
-- variable bit rate (rt-VBR) service category.

mscAtmIfCARtVbr OBJECT IDENTIFIER ::= { mscAtmIfCA 3 }



mscAtmIfCARtVbrRowStatusTable OBJECT-TYPE
   SYNTAX     SEQUENCE OF MscAtmIfCARtVbrRowStatusEntry
   ACCESS     not-accessible
   STATUS     mandatory
   DESCRIPTION
     "This entry controls the addition and deletion of 
      mscAtmIfCARtVbr components."
::= { mscAtmIfCARtVbr 1 }

mscAtmIfCARtVbrRowStatusEntry OBJECT-TYPE
   SYNTAX     MscAtmIfCARtVbrRowStatusEntry
   ACCESS     not-accessible
   STATUS     mandatory
   DESCRIPTION
     "A single entry in the table represents a single 
      mscAtmIfCARtVbr component."
   INDEX {
      mscAtmIfIndex,
      mscAtmIfCAIndex,
      mscAtmIfCARtVbrIndex }
::= { mscAtmIfCARtVbrRowStatusTable 1 }

MscAtmIfCARtVbrRowStatusEntry ::= SEQUENCE {
   mscAtmIfCARtVbrRowStatus
      RowStatus,
   mscAtmIfCARtVbrComponentName
      DisplayString,
   mscAtmIfCARtVbrStorageType
      StorageType,
   mscAtmIfCARtVbrIndex
      Integer32 }

mscAtmIfCARtVbrRowStatus OBJECT-TYPE
   SYNTAX     RowStatus 
   ACCESS     read-write
   STATUS     mandatory
   DESCRIPTION
     "This variable is used as the basis for SNMP naming of
      mscAtmIfCARtVbr components.
      These components can be added."
::= { mscAtmIfCARtVbrRowStatusEntry 1 }

mscAtmIfCARtVbrComponentName OBJECT-TYPE
   SYNTAX     DisplayString 
   ACCESS     read-only
   STATUS     mandatory
   DESCRIPTION
     "This variable provides the component's string name for
      use with the ASCII Console Interface"
::= { mscAtmIfCARtVbrRowStatusEntry 2 }

mscAtmIfCARtVbrStorageType OBJECT-TYPE
   SYNTAX     StorageType 
   ACCESS     read-only
   STATUS     mandatory
   DESCRIPTION
     "This variable represents the storage type value for the
      mscAtmIfCARtVbr tables."
::= { mscAtmIfCARtVbrRowStatusEntry 4 }

mscAtmIfCARtVbrIndex OBJECT-TYPE
   SYNTAX     Integer32 (0)
   ACCESS     not-accessible
   STATUS     mandatory
   DESCRIPTION
     "This variable represents the index for the mscAtmIfCARtVbr tables."
::= { mscAtmIfCARtVbrRowStatusEntry 10 }

mscAtmIfCARtVbrProvTable OBJECT-TYPE
   SYNTAX     SEQUENCE OF MscAtmIfCARtVbrProvEntry
   ACCESS     not-accessible
   STATUS     mandatory
   DESCRIPTION
     "This group contains provisioned attributes which control the rt-VBR 
      service category for this interface."
::= { mscAtmIfCARtVbr 100 }

mscAtmIfCARtVbrProvEntry OBJECT-TYPE
   SYNTAX     MscAtmIfCARtVbrProvEntry
   ACCESS     not-accessible
   STATUS     mandatory
   DESCRIPTION
     "An entry in the mscAtmIfCARtVbrProvTable."
   INDEX {
      mscAtmIfIndex,
      mscAtmIfCAIndex,
      mscAtmIfCARtVbrIndex }
::= { mscAtmIfCARtVbrProvTable 1 }

MscAtmIfCARtVbrProvEntry ::= SEQUENCE {
   mscAtmIfCARtVbrPool
      INTEGER,
   mscAtmIfCARtVbrCdvt
      Unsigned32,
   mscAtmIfCARtVbrCdv
      Unsigned32,
   mscAtmIfCARtVbrMaxCtd
      Unsigned32,
   mscAtmIfCARtVbrCellLossRatio
      Unsigned32,
   mscAtmIfCARtVbrTxQueueLimit
      Unsigned32,
   mscAtmIfCARtVbrMinPerVcQueueLimit
      Unsigned32,
   mscAtmIfCARtVbrPerVcQueueLimitReferenceRate
      Unsigned32,
   mscAtmIfCARtVbrHoldingPriority
      INTEGER,
   mscAtmIfCARtVbrSvcHoldingPriority
      INTEGER,
   mscAtmIfCARtVbrSvcMpHoldingPriority
      INTEGER,
   mscAtmIfCARtVbrEmissionPriority
      Unsigned32,
   mscAtmIfCARtVbrTrafficShaping
      INTEGER,
   mscAtmIfCARtVbrShapeRecoupPolicy
      INTEGER,
   mscAtmIfCARtVbrUnshapedTransmitQueueing
      INTEGER,
   mscAtmIfCARtVbrUsageParameterControl
      INTEGER,
   mscAtmIfCARtVbrWeightPolicy
      INTEGER,
   mscAtmIfCARtVbrForceTagging
      INTEGER }

mscAtmIfCARtVbrPool OBJECT-TYPE
   SYNTAX     INTEGER  {
                 pool1(1),
                 pool2(2),
                 pool3(3),
                 pool4(4),
                 pool5(5) }
   ACCESS     read-write
   STATUS     mandatory
   DESCRIPTION
     "This attribute specifies the bandwidth pool which is to be used to 
      support the real-time variable bit rate (rt-VBR) service category 
      except for connections managed by a Vpt CA. The percentage of 
      link capacity reserved for the given bandwidth pool is the maximum 
      bandwidth that can be allocated to rt-VBR traffic. The percentage 
      allocated to each bandwidth pool can be provisioned through the 
      bandwidthPool attribute under the CA."
   DEFVAL     { pool1 }
::= { mscAtmIfCARtVbrProvEntry 10 }

mscAtmIfCARtVbrCdvt OBJECT-TYPE
   SYNTAX     Unsigned32 (1..1200000)
   ACCESS     read-write
   STATUS     mandatory
   DESCRIPTION
     "This attribute specifies the default cell delay variation tolerance 
      (CDVT) for all connections of the rt-VBR service category. An 
      override to this default may be specified for a provisioned 
      connection under the Vcd Tm or Vpd Tm component.
      
      If Usage Parameter Control (UPC) is enabled for a connection, 
      CDVT is used by the UPC function to decide whether a cell is 
      conforming or non-conforming based on the connection's traffic 
      descriptor type. The larger the CDVT value, the more tolerant is the 
      UPC to bandwidth usage beyond the traffic contract."
   DEFVAL     { 250 }
::= { mscAtmIfCARtVbrProvEntry 20 }

mscAtmIfCARtVbrCdv OBJECT-TYPE
   SYNTAX     Unsigned32 (0..2147483647)
   ACCESS     read-write
   STATUS     mandatory
   DESCRIPTION
     "This attribute specifies the peak-to-peak cell delay variation (CDV) 
      which is contributed to the entire ATM Interface for rt-VBR traffic. 
      
      The CDV is a measure of the delay jitter introduced mostly by 
      traffic buffering and cell scheduling. The worst case value of this 
      attribute can be computed as the txQueueLimit divided by the link 
      rate of this ATM Interface.
      
      The value of this attribute is used by PNNI in the Resource 
      Availability Information Group (RAIG) topology updates and route 
      selection. It is also used by CAC at connection set-up time to 
      determine whether this ATM Interface can meet the CDV 
      requirement for that connection. If so, the value of this attribute is 
      added to the cumulative CDV field of the extended QoS information 
      element."
   DEFVAL     { 1268 }
::= { mscAtmIfCARtVbrProvEntry 30 }

mscAtmIfCARtVbrMaxCtd OBJECT-TYPE
   SYNTAX     Unsigned32 (0..2147483647)
   ACCESS     read-write
   STATUS     mandatory
   DESCRIPTION
     "This attribute specifies the maximum cell transfer delay (MaxCTD) 
      which is applied to the entire ATM Interface for rt-VBR traffic.
      
      MaxCTD is the sum of the fixed delay and the CDV. The 
      components of the fixed delay include propagation delay through 
      the physical media, delays induced by the transmission system, and 
      fixed components of switch processing delay.
      
      This attribute is used by PNNI in the Resource Availability 
      Information Group (RAIG) topology updates and route selection. It 
      is also used by CAC at connection set-up time to determine whether 
      this ATM Interface can meet the ATM connection's MaxCTD 
      requirement."
   DEFVAL     { 2000 }
::= { mscAtmIfCARtVbrProvEntry 40 }

mscAtmIfCARtVbrCellLossRatio OBJECT-TYPE
   SYNTAX     Unsigned32 (0..15)
   ACCESS     read-write
   STATUS     mandatory
   DESCRIPTION
     "This attribute specifies the tolerable cell loss ratio (CLR) for rt-
      VBR traffic except for connections managed by a Vpt CA. The 
      number is the negative logarithm (base 10) of the CLR. For 
      example, if the target CLR = 1E-10 then RtVbr cellLossRatio = 10. 
      This number must be the same as the Cbr cellLossRatio since CBR 
      and rt-VBR traffic have the same discard priority. The RtVbr 
      cellLossRatio is used by the Connection Admission Control (CAC) 
      algorithm to compute the required (equivalent) cell rate for rt-VBR 
      connections. This number must be less than or equal to the NrtVbr 
      cellLossRatio, since rt-VBR traffic has a higher discard priority.
      
      There is a trade-off between the service category CLR and the 
      achievable link utilization. To guarantee an excellent service 
      category, the CLR should be as small as possible (e.g., 1E-10). 
      However, a smaller CLR results in a larger equivalent cell rate for a 
      given connection and hence a lower link utilization. 
      
      Setting this attribute to 0 means that a CLR of 1 can be tolerated. In 
      this case, no bandwidth is reserved for rt-VBR connections, and 
      CAC is effectively turned off. All rt-VBR are admitted."
   DEFVAL     { 10 }
::= { mscAtmIfCARtVbrProvEntry 50 }

mscAtmIfCARtVbrTxQueueLimit OBJECT-TYPE
   SYNTAX     Unsigned32 (0 | 5..512000)
   ACCESS     read-write
   STATUS     mandatory
   DESCRIPTION
     "This attribute specifies the default maximum queue length for the 
      emission queues used to buffer the traffic of the rt-VBR service 
      category. It is used as the basis for setting the discard thresholds on 
      both common and per-VC queues. For the common queue, the 
      discard thresholds are set at approximately 35, 75, and 90 percent of 
      the value of this attribute for traffic at discard priority 3 (DP=3), 
      DP=2, and DP=1 respectively. 
      
      For a per-VC queue, the actual limit may be reduced depending on 
      the shaping rate of the connection (for standard Vpt Vccs, this is the 
      shaping rate of the Vpt). The discard thresholds are set at 
      approximately 35, 75, and 90 percent of the scaled queue limit for 
      traffic at discard priority 3 (DP=3), DP=2, and DP=1, respectively. 
      However, a reduction will never result in a value that is less than the 
      value set for the minPerVcQueueLimit attribute.
      
      When the value of this attribute is autoConfigure, an appropriate 
      value is selected based on the card type. It is set to 288 for low 
      speed cards such as DS1, E1 and IMA, and set to 480 for high 
      speed cards such as JT2, DS3, E3 and OC3 (including ATM IP 
      FPs). For the 1pOC12SmLrAtm card, the value is set to 2048.
      For the 1pOC48SmSrAtm card, the value is set to 12288.
      
      For ATM IP FPs, the per-VC queue limit may be overridden for a 
      permanent connection by specifying a value in the Vcd Tm or Vpd 
      Tm txQueueLimit attribute. 
      
      For CQC-based ATM cards, the valid range for this attribute is from 
      5 to 30000 inclusive.
      
      For 1pOC48SmSrAtm cards, the value of this attribute is used to set 
      the maximum size of the link-class queue for buffering this traffic 
      type on the egress path.
      
      The operational value of the maximum length of a queue (common 
      or per-VC) is indicated by the Vcc Tm, Vpc Tm, or Vpt Tm 
      txQueueThresholds attribute.
      
      For standard Vpts, this attribute does not apply when using per-VC 
      queuing and only applies when using common queueing. When 
      using per-VC queueing, regardless of the Vpt's service category, 
      standard Vpts use the AtmIf Ca NrtVbr txQueueLimit value as their 
      default.

      VALUES (

      0 = autoConfigure

      )"
   DEFVAL     { 0 }
::= { mscAtmIfCARtVbrProvEntry 60 }

mscAtmIfCARtVbrMinPerVcQueueLimit OBJECT-TYPE
   SYNTAX     Unsigned32 (5..160000)
   ACCESS     read-write
   STATUS     mandatory
   DESCRIPTION
     "This attribute specifies the minimum queue limit for the per-VC 
      queues of connections of the rt-VBR service category.
      
      The queue limit of a per-VC queue is obtained by scaling down the 
      txQueueLimit based on the shaping rate of that queue (shaping rate 
      for the connection, and for standard Vpt Vccs, the shaping rate of 
      the Vpt). This produces a constant delay for various queue lengths. 
      The txQueueLimit provides an upper bound while 
      minPerVcQueueLimit provides the lower bound. The value of this 
      attribute must not be greater than the value of the txQueueLimit 
      attribute. If this service category is used by Trunks the value of 
      minPerVcQueueLimit must be at least 88.
      
      For the 1pOC12SmLrAtm and 1pOC48SmSrAtm cards, this 
      attribute does not apply since per-VC queueing is not available.
      
      For Vpts, this attribute does not apply. Regardless of Vpt service 
      category, standard Vpts always use the AtmIf Ca NrtVbr 
      minPerVcQueueLimit value as their default. To determine the queue 
      limit of a standard Vpt Vcc, the txQueueLimit is scaled down by the 
      Vpt shaping rate."
   DEFVAL     { 88 }
::= { mscAtmIfCARtVbrProvEntry 70 }

mscAtmIfCARtVbrPerVcQueueLimitReferenceRate OBJECT-TYPE
   SYNTAX     Unsigned32 (0 | 1..1416905)
   ACCESS     read-write
   STATUS     mandatory
   DESCRIPTION
     "This attribute specifies the shaping rate to be used in computing the 
      tolerable delay for per-VC queues of connections of the rt-VBR 
      service category. The delay is computed as the txQueueLimit 
      divided by the value of this attribute. 
      
      When the value of this attribute is autoConfigure, an appropriate 
      default is selected based on the card type. It is set to 3685 for low 
      speed cards such as DS1, E1, and IMA, and set to 14740 for high 
      speed cards such as JT2, DS3, E3 and OC3. For 4pOC12SmIrAtm 
      and 4pOC12SmLrAtm cards, the reference rate is set to 65511 for 
      DS3 and OC3 channels, and set to 262044 for OC12 channels. For 
      Apc-based cards the maximum value is 1416905. For all other 
      cards, the maximum value is 943396.
      
      For the 1pOC12SmLrAtm and 1pOC48SmSrAtm cards, this 
      attribute does not apply since per-VC queueing is not available.
      
      For Vpts, this attribute does not apply. Regardless of Vpt service 
      category, standard Vpts always use the AtmIf Ca NrtVbr 
      perVcQueueLimitReferenceRate value as their default.

      VALUES (

      0 = autoConfigure

      )"
   DEFVAL     { 0 }
::= { mscAtmIfCARtVbrProvEntry 75 }

mscAtmIfCARtVbrHoldingPriority OBJECT-TYPE
   SYNTAX     INTEGER  {
                 n0(0),
                 n1(1),
                 n2(2),
                 n3(3),
                 n4(4) }
   ACCESS     read-write
   STATUS     mandatory
   DESCRIPTION
     "This attribute specifies the default holding priority which applies to 
      SVP and SVC rt-VBR connections. It takes a value from 0 (highest 
      priority) to 4 (lowest priority). In a situation where the link 
      bandwidth fluctuates, such as over an IMA link, holding priority is 
      used to determine which connections are held and which are 
      released. Holding priority 4 connections are the first to be released. 
      Holding priority 0 connections are the last to be released.
      
      This attribute does not apply to Vpt Vccs. When bandwidth 
      fluctuates, the entire Vpt, along with all Vpt Vccs are released as a 
      unit, according to the Vpt's holdingPriority."
   DEFVAL     { n3 }
::= { mscAtmIfCARtVbrProvEntry 76 }

mscAtmIfCARtVbrSvcHoldingPriority OBJECT-TYPE
   SYNTAX     INTEGER  {
                 n0(0),
                 n1(1),
                 n2(2),
                 n3(3),
                 n4(4) }
   ACCESS     read-write
   STATUS     obsolete
   DESCRIPTION
     "This attribute specifies the default holding priority which applies to 
      SVC rt-VBR connections. It takes a value from 0 (highest priority) 
      to 4 (lowest priority). In a situation where the link bandwidth 
      fluctuates, such as over an IMA link, holding priority is used to 
      determine which connections are held and which are released. 
      Holding priority 4 connections are the first to be released. Holding 
      priority 0 connections are the last to be released.
      This attribute has been obsoleted and its value migrated to 
      holdingPriority attribute."
   DEFVAL     { n3 }
::= { mscAtmIfCARtVbrProvEntry 80 }

mscAtmIfCARtVbrSvcMpHoldingPriority OBJECT-TYPE
   SYNTAX     INTEGER  {
                 n0(0),
                 n1(1),
                 n2(2),
                 n3(3),
                 n4(4) }
   ACCESS     read-write
   STATUS     mandatory
   DESCRIPTION
     "This attribute specifies the default holding priority which applies to 
      SVC rt-VBR point-to-multipoint connections. It takes a value from 
      0 (highest priority) to 4 (lowest priority). In a situation where the 
      link bandwidth fluctuates, such as over an IMA link, holding 
      priority is used to determine which connections are held and which 
      are released. Holding priority 4 connections are the first to be 
      released. Holding priority 0 connections are the last to be released.
      
      This attribute does not apply to Vpt Vccs. When bandwidth 
      fluctuates, the entire Vpt, along with all Vpt Vccs is released as a 
      unit, according to the Vpt's holdingPriority."
   DEFVAL     { n3 }
::= { mscAtmIfCARtVbrProvEntry 81 }

mscAtmIfCARtVbrEmissionPriority OBJECT-TYPE
   SYNTAX     Unsigned32 (0..7)
   ACCESS     read-write
   STATUS     mandatory
   DESCRIPTION
     "This attribute is not applicable and is ignored for CQC-based ATM 
      cards.
      
      For the 1pOC48SmSrAtm card, only the default value is supported. 
      For 4pOC12SmIrAtm and 4pOC12SmLrAtm cards the default 
      value is 2.
      
      This attribute specifies the emission priority (EP) which is used to 
      transmit traffic of the rt-VBR service category. A lower numerical 
      value for this attribute specifies a higher emission priority. 0 is the 
      highest EP and 7 is the lowest. Cells at a higher emission priority 
      receive higher preference for link bandwidth. EPs 0 and 1 are in the 
      absolute priority range, and are unaffected by any minimum 
      bandwidth guarantees. EPs 2 through 7 are in the guaranteed 
      bandwidth range. Minimum bandwidth guarantee is specified in the 
      AtmIf/n Ep/m component. 
      
      Emission priority setting must comply with all of the following 
      constraints: 
      1. The emission priority numbers must be in the following order: 
      CBR <= rt-VBR <= nrt-VBR <= ABR <= UBR 
      2. Two different ATM service categories may share the same EP 
      only if they are both shaped. 
      3. CBR and rt-VBR may be placed either in the absolute priority 
      range (EP 0 or 1) or in the guaranteed bandwidth range (EP 2 
      through 7). 
      4. If both CBR and rt-VBR are shaped, rt-VBR must share the 
      same EP with CBR or ABR. If either one of CBR or rt-VBR are 
      not shaped, then they cannot share the same EP. 
      5. ABR service category is always deemed to be shaped. If nrt-VBR 
      is shaped, it must share the same EP with ABR. If nrt-VBR is not 
      shaped it must have a higher EP than ABR.
      6. If UBR is shaped, it must share the same EP with ABR. If UBR 
      is not shaped, it must have a lower EP than ABR.
      
      This attribute does not apply to basic Vpts, and standard Vpt Vccs."
   DEFVAL     { 1 }
::= { mscAtmIfCARtVbrProvEntry 82 }

mscAtmIfCARtVbrTrafficShaping OBJECT-TYPE
   SYNTAX     INTEGER  {
                 disabled(1),
                 enabled(5),
                 inverseUpc(6) }
   ACCESS     read-write
   STATUS     mandatory
   DESCRIPTION
     "This attribute specifies the default traffic shaping option for 
      connections of the rt-VBR service category. An override to this 
      default may be specified for a provisioned connection under the Vcd 
      Tm or Vpd Tm component.
      
      When this attribute is set to disabled, traffic shaping cannot be 
      enabled for any rt-VBR connections. On 1pOC12SmLrAtm cards, 
      this attribute must be set to disabled.
      
      For CQC-based ATM cards, this attribute may be set to enabled 
      only if the interface supports shaping, as defined by the 
      perVcQueueInterfaces attribute in the AtmResourceControl Cqc 
      Override component. If that component does not exist, this attribute 
      must be set to disabled.
      
      If the Vcc Tm, Vpc Tm, or Vpt Tm txTrafficDescType indicates type 
      1 or 2, this attribute is ignored, and traffic shaping is not applicable 
      for that connection. 
      
      When this attribute is set to inverseUpc, traffic shaping for a 
      connection is enabled according to card type and the value of the 
      Vcc Tm, Vpc Tm, or Vpt Tm txTrafficDescType. For 
      4pOC12SmIrAtm and 4pOC12SmLrAtm cards, inverseUpc shaping 
      is not available.
      
      If this attribute is set to inverseUpc, and the txTrafficDescType is 3, 
      4, or 5, linear traffic shaping is enabled. Linear traffic shaping uses 
      a single static traffic shaping rate. 
      
      On CQC-based ATM FPs, if this attribute is set to inverseUpc, and 
      the txTrafficDescType is 6, 7, or 8, linear traffic shaping is enabled.
      
      On ATM IP FPs, if this attribute is set to inverseUpc, and the 
      txTrafficDescType is 6, 7, or 8, inverse-UPC (also referred to as 
      VBR or dual leaky bucket) traffic shaping is enabled. Inverse-UPC 
      traffic shaping can burst above the sustained cell rate to the peak 
      cell rate for the duration defined by maximum burst size. Inverse-
      UPC traffic shaping exactly conforms to the requirements of a dual 
      leaky bucket UPC enforcer. 
      
      When this attribute is set to enabled and the txTrafficDescType is 3, 
      4, 5, 6, 7, or 8, traffic shaping for a connection is enabled using 
      linear shaping. 
      
      Enabling or disabling traffic shaping may require a matching 
      change to the emissionPriority attribute and 
      unshapedTransmitQueueing attribute for this service category. 
      Refer to those attributes for the complete description of the 
      interactions.
      
      This attribute does not apply to basic Vpts, and standard Vpt Vccs."
   DEFVAL     { disabled }
::= { mscAtmIfCARtVbrProvEntry 86 }

mscAtmIfCARtVbrShapeRecoupPolicy OBJECT-TYPE
   SYNTAX     INTEGER  {
                 minimumCdv(0),
                 maximumEfficiency(1) }
   ACCESS     read-write
   STATUS     mandatory
   DESCRIPTION
     "This attribute specifies the shaping recoup policy for the rt-VBR 
      service category. This is the policy which is used to recoup shaping 
      opportunities which are lost when more than one connection 
      schedules a cell for the same transmit opportunity. In this case, one 
      connection is scheduled, and the cell from another connection is 
      delayed by one cell time. This attribute affects how the transmit 
      time is calculated for the next cell on the delayed connection. This 
      attribute is ignored if this service category is not shaped.
      
      When the connection which was delayed schedules the next cell to 
      transmit, it may calculate the time as a difference from either the 
      previous actual cell transmit time, or the time when the previous 
      cell should have been transmitted.
      
      Setting this attribute to maximumEfficiency results in each 
      connection trying to recoup or regain delays in scheduling. The 
      transmit time from the next cell is calculated from the time when 
      the cell should originally have been sent. Cell delay variation 
      (CDV) occurs in this case since the cells are sent with less than the 
      shaping delay between them. However, in general the shaper 
      recovers (recoups) lost opportunities and improves efficiency.
      
      Setting this attribute to minimumCdv results in connections not 
      trying to recoup or regain any delays in scheduling. The transmit 
      time for the next cell is calculated from the time when the previous 
      cell was actually transmitted. This minimizes CDV, but results in 
      missed cell opportunities."
   DEFVAL     { minimumCdv }
::= { mscAtmIfCARtVbrProvEntry 87 }

mscAtmIfCARtVbrUnshapedTransmitQueueing OBJECT-TYPE
   SYNTAX     INTEGER  {
                 perVc(0),
                 common(1),
                 autoConfigure(2) }
   ACCESS     read-write
   STATUS     mandatory
   DESCRIPTION
     "This attribute specifies the default queuing option for unshaped 
      connections of the rt-VBR service category. This attribute controls 
      whether common or per-VC queueing is used. 
      
      Per-VC queueing means that each connection has its own buffering 
      and queue limits.
      
      Common queueing means that cells are queued in First In First Out 
      order on a common queue for this service category. The common 
      queue has one set of congestion control levels for all cells enqueued 
      on it.
      
      For 1pOC12SmLrAtm and 1pOC48SmSrAtm cards this attribute 
      must be set to common or autoConfigure. This attribute cannot be 
      set to perVc since per-Vc queueing is not available on the 
      1pOC12SmLrAtm and 1pOC48SmSrAtm cards. The value 
      autoConfigure is interpreted to mean common queueing.
      
      For ATM IP cards, if traffic shaping for this service category is 
      disabled, this attribute may take any of the three values. In this case, 
      the value autoConfigure is interpreted to mean per-VC queueing.
      
      For ATM IP cards, if traffic shaping for this service category is not 
      disabled, the only permitted values are perVc and autoConfigure. 
      In this case, the result is that all connections use per-VC queueing.
      
      For CQC-based ATM cards, if the perVcQueueInterfaces attribute 
      of the Lp Eng Arc Cqc component permits shaping for this 
      interface, then this attribute may take any of the three values. In this 
      case, the value autoConfigure is interpreted to mean per-VC 
      queueing. For 4pOC12SmIrAtm and 4pOC12SmLrAtm cards only 
      perVc queueing is supported. All other attribute values are ignored.
      
      
      For CQC-based ATM cards, if the perVcQueueInterfaces attribute 
      of the Lp Eng Arc Cqc component does not permit shaping for this 
      interface, then this attribute may take values common or 
      autoConfigure. In this case, the value autoConfigure is interpreted 
      to mean common queueing. 
      
      If this attribute is set to autoConfigure, an override to this default 
      may be specified for a provisioned connection under the Vcd Tm or 
      Vpd Tm component. 
      
      The opUnshapedTransmitQueueing attribute of this component 
      indicates whether the transmit queueing is perVc or common.
      
      This attribute does not apply to basic Vpts, and standard Vpt Vccs."
   DEFVAL     { autoConfigure }
::= { mscAtmIfCARtVbrProvEntry 88 }

mscAtmIfCARtVbrUsageParameterControl OBJECT-TYPE
   SYNTAX     INTEGER  {
                 enforced(0),
                 disabled(1),
                 monitored(4) }
   ACCESS     read-write
   STATUS     mandatory
   DESCRIPTION
     "This attribute specifies the default usage parameter control (UPC) 
      option for connections of the rt-VBR service category. This attribute 
      is ignored if the rxTrafficDescriptorType indicates 1 or 2. An 
      override to this default may be specified for a provisioned 
      connection under the Vcd Tm or Vpd Tm component.
      
      When this attribute is set to enforced, UPC is enforced for each 
      connection. When UPC is enforced, non-conforming cells are either 
      tagged or discarded depending on the rxTrafficDescriptorType. 
      
      On ATM IP FPs, when this attribute is set to monitored, UPC 
      conformance checking is performed, except, instead of the non-
      conforming cells being tagged or discarded, they are merely 
      counted in the UPC violations counts, and passed on unchanged. 
      
      On CQC-based ATM FPs, when this attribute is set to monitored, it 
      has the same effect as setting it to disabled. 
      
      When this attribute is set to disabled, UPC is disabled on the receive 
      path for all rt-VBR connections.
      
      This attribute does not apply to basic Vpts, and standard Vpt Vccs."
   DEFVAL     { disabled }
::= { mscAtmIfCARtVbrProvEntry 89 }

mscAtmIfCARtVbrWeightPolicy OBJECT-TYPE
   SYNTAX     INTEGER  {
                 scr(1),
                 pcr(2),
                 ecr(3) }
   ACCESS     read-write
   STATUS     mandatory
   DESCRIPTION
     "This attribute specifies the policy which is applied when calculating 
      the fairness weight for unshaped connections of the rt-VBR service 
      category. The fairness weight for a connection determines the 
      relative amount of bandwidth which that connection obtains, 
      compared to other connections in the same service category. 
      Connections with equal weight get equal transmit opportunities. 
      Connections with higher weights get more transmit opportunities 
      compared with connections that have lower weights. An override to 
      this default may be specified for a provisioned connection under the 
      Vcd Tm or Vpd Tm component. 
      
      The fairness weight for a connection is directly proportional to the 
      value of one of the traffic descriptor parameters for that connection. 
      This attribute specifies which traffic descriptor parameter is used for 
      connections of the rt-VBR service category. 
      
      This attribute is ignored on CQC-based ATM cards and the 
      1pOC48SmSrAtm card. This attribute is also ignored on ATM IP 
      cards if unshapedTransmitQueueing is set for common queuing. 
      
      If this attribute is set to scr, the fairness weight is proportional to the 
      transmit sustained cell rate (SCR) of a connection. Connections 
      with a higher SCR have a higher fairness weight. For connections 
      with txTrafficDescType 3, which have no SCR, the sustained cell 
      rate is assumed to be equal to the peak cell rate. 
      
      If this attribute is set to pcr, the fairness weight is proportional to 
      the transmit peak cell rate (PCR) of a connection. Connections with 
      a higher PCR have a higher fairness weight. Connections with 
      txTrafficDescType 1 or 2 get a minimum weight, which is 1. 
      
      If this attribute is set to ecr, the fairness weight is proportional to 
      the equivalent cell rate (ECR) of a connection as calculated by 
      connection admission control (CAC). Connections with a higher 
      ECR have a higher fairness weight. Connections with an ECR of 0 
      get a minimum weight, which is 1. 
      
      The weight of a connection is visible in the Vcc Tm, Vpc Tm, or Vpt 
      Tm weight attribute.
      
      This attribute does not apply to basic Vpts, and standard Vpt Vccs."
   DEFVAL     { ecr }
::= { mscAtmIfCARtVbrProvEntry 90 }

mscAtmIfCARtVbrForceTagging OBJECT-TYPE
   SYNTAX     INTEGER  {
                 enabled(0),
                 disabled(1) }
   ACCESS     read-write
   STATUS     mandatory
   DESCRIPTION
     "This attribute specifies the default of whether to force tagging 
      (CLP=1) of all cells for all rt-VBR connections. An override to this 
      default may be specified for a provisioned connection under the Vcd 
      Tm or Vpd Tm component. This attribute is not supported by 
      4pOC12SmIrAtm and 4pOC12SmLrAtm cards.
      
      
      When this attribute is set to enabled, CLP is set to 1 for all cells in 
      the transmit direction. Force tagging is only supported on ATM IP 
      FPs. 
      
      On CQC-based ATM FPs, this attribute must be set to disabled. 
      When this attribute is set to disabled, CLP is unchanged for all cells 
      in the transmit direction.
      
      This attribute never applies to any type of Vpt."
   DEFVAL     { disabled }
::= { mscAtmIfCARtVbrProvEntry 91 }

mscAtmIfCARtVbrOperTable OBJECT-TYPE
   SYNTAX     SEQUENCE OF MscAtmIfCARtVbrOperEntry
   ACCESS     not-accessible
   STATUS     mandatory
   DESCRIPTION
     "This group contains operational attributes for the rt-VBR service 
      category."
::= { mscAtmIfCARtVbr 110 }

mscAtmIfCARtVbrOperEntry OBJECT-TYPE
   SYNTAX     MscAtmIfCARtVbrOperEntry
   ACCESS     not-accessible
   STATUS     mandatory
   DESCRIPTION
     "An entry in the mscAtmIfCARtVbrOperTable."
   INDEX {
      mscAtmIfIndex,
      mscAtmIfCAIndex,
      mscAtmIfCARtVbrIndex }
::= { mscAtmIfCARtVbrOperTable 1 }

MscAtmIfCARtVbrOperEntry ::= SEQUENCE {
   mscAtmIfCARtVbrOpUnshapedTransmitQueueing
      INTEGER,
   mscAtmIfCARtVbrEpdOffset
      Unsigned32 }

mscAtmIfCARtVbrOpUnshapedTransmitQueueing OBJECT-TYPE
   SYNTAX     INTEGER  {
                 perVc(0),
                 common(1) }
   ACCESS     read-only
   STATUS     mandatory
   DESCRIPTION
     "This attribute indicates the state of transmit queueing for unshaped 
      rt-VBR connections.
      
      A value of perVc indicates that any unshaped connections use per-
      VC queueing. A value of common indicates that traffic for 
      unshaped connections uses the common queue which corresponds 
      to the EP for this service category."
::= { mscAtmIfCARtVbrOperEntry 10 }

mscAtmIfCARtVbrEpdOffset OBJECT-TYPE
   SYNTAX     Unsigned32 (0 | 5..1024)
   ACCESS     read-only
   STATUS     mandatory
   DESCRIPTION
     "This attribute indicates the Early Packet Discard (EPD) offset which 
      is currently in use for this service category. The EPD offset is used 
      to derive the EPD thresholds for each CC level.
      
      Any connection under this service category which requires the 
      txPacketWiseDiscard feature must specify a transmit queue limit 
      which is at least 5.71 times this offset. This ensures that the derived 
      Epd threshold will never be less than 17.5 % of the transmit queue 
      limit. If this is not done, txPacketWiseDiscard for the connection 
      will be automatically disabled.
      
      The value of this EPD offset is specified under the lp/x eng arc aqm 
      ov component."
::= { mscAtmIfCARtVbrOperEntry 11 }


-- AtmIf/n CA NonRealTimeVariableBitRate/n 
-- This component manages the default characteristics of the non-real-
-- time variable bit rate (nrt-VBR) service category.

mscAtmIfCANrtVbr OBJECT IDENTIFIER ::= { mscAtmIfCA 4 }



mscAtmIfCANrtVbrRowStatusTable OBJECT-TYPE
   SYNTAX     SEQUENCE OF MscAtmIfCANrtVbrRowStatusEntry
   ACCESS     not-accessible
   STATUS     mandatory
   DESCRIPTION
     "This entry controls the addition and deletion of 
      mscAtmIfCANrtVbr components."
::= { mscAtmIfCANrtVbr 1 }

mscAtmIfCANrtVbrRowStatusEntry OBJECT-TYPE
   SYNTAX     MscAtmIfCANrtVbrRowStatusEntry
   ACCESS     not-accessible
   STATUS     mandatory
   DESCRIPTION
     "A single entry in the table represents a single 
      mscAtmIfCANrtVbr component."
   INDEX {
      mscAtmIfIndex,
      mscAtmIfCAIndex,
      mscAtmIfCANrtVbrIndex }
::= { mscAtmIfCANrtVbrRowStatusTable 1 }

MscAtmIfCANrtVbrRowStatusEntry ::= SEQUENCE {
   mscAtmIfCANrtVbrRowStatus
      RowStatus,
   mscAtmIfCANrtVbrComponentName
      DisplayString,
   mscAtmIfCANrtVbrStorageType
      StorageType,
   mscAtmIfCANrtVbrIndex
      Integer32 }

mscAtmIfCANrtVbrRowStatus OBJECT-TYPE
   SYNTAX     RowStatus 
   ACCESS     read-write
   STATUS     mandatory
   DESCRIPTION
     "This variable is used as the basis for SNMP naming of
      mscAtmIfCANrtVbr components.
      These components can be added."
::= { mscAtmIfCANrtVbrRowStatusEntry 1 }

mscAtmIfCANrtVbrComponentName OBJECT-TYPE
   SYNTAX     DisplayString 
   ACCESS     read-only
   STATUS     mandatory
   DESCRIPTION
     "This variable provides the component's string name for
      use with the ASCII Console Interface"
::= { mscAtmIfCANrtVbrRowStatusEntry 2 }

mscAtmIfCANrtVbrStorageType OBJECT-TYPE
   SYNTAX     StorageType 
   ACCESS     read-only
   STATUS     mandatory
   DESCRIPTION
     "This variable represents the storage type value for the
      mscAtmIfCANrtVbr tables."
::= { mscAtmIfCANrtVbrRowStatusEntry 4 }

mscAtmIfCANrtVbrIndex OBJECT-TYPE
   SYNTAX     Integer32 (0)
   ACCESS     not-accessible
   STATUS     mandatory
   DESCRIPTION
     "This variable represents the index for the mscAtmIfCANrtVbr tables."
::= { mscAtmIfCANrtVbrRowStatusEntry 10 }

mscAtmIfCANrtVbrProvTable OBJECT-TYPE
   SYNTAX     SEQUENCE OF MscAtmIfCANrtVbrProvEntry
   ACCESS     not-accessible
   STATUS     mandatory
   DESCRIPTION
     "This group contains provisioned attributes which control the nrt-
      VBR service category for this interface."
::= { mscAtmIfCANrtVbr 100 }

mscAtmIfCANrtVbrProvEntry OBJECT-TYPE
   SYNTAX     MscAtmIfCANrtVbrProvEntry
   ACCESS     not-accessible
   STATUS     mandatory
   DESCRIPTION
     "An entry in the mscAtmIfCANrtVbrProvTable."
   INDEX {
      mscAtmIfIndex,
      mscAtmIfCAIndex,
      mscAtmIfCANrtVbrIndex }
::= { mscAtmIfCANrtVbrProvTable 1 }

MscAtmIfCANrtVbrProvEntry ::= SEQUENCE {
   mscAtmIfCANrtVbrPool
      INTEGER,
   mscAtmIfCANrtVbrCdvt
      Unsigned32,
   mscAtmIfCANrtVbrCellLossRatio
      Unsigned32,
   mscAtmIfCANrtVbrTxQueueLimit
      Unsigned32,
   mscAtmIfCANrtVbrSvcHoldingPriority
      INTEGER,
   mscAtmIfCANrtVbrMinPerVcQueueLimit
      Unsigned32,
   mscAtmIfCANrtVbrPerVcQueueLimitReferenceRate
      Unsigned32,
   mscAtmIfCANrtVbrSvcMpHoldingPriority
      INTEGER,
   mscAtmIfCANrtVbrHoldingPriority
      INTEGER,
   mscAtmIfCANrtVbrEmissionPriority
      Unsigned32,
   mscAtmIfCANrtVbrTrafficShaping
      INTEGER,
   mscAtmIfCANrtVbrShapeRecoupPolicy
      INTEGER,
   mscAtmIfCANrtVbrUnshapedTransmitQueueing
      INTEGER,
   mscAtmIfCANrtVbrUsageParameterControl
      INTEGER,
   mscAtmIfCANrtVbrWeightPolicy
      INTEGER,
   mscAtmIfCANrtVbrForceTagging
      INTEGER }

mscAtmIfCANrtVbrPool OBJECT-TYPE
   SYNTAX     INTEGER  {
                 pool1(1),
                 pool2(2),
                 pool3(3),
                 pool4(4),
                 pool5(5) }
   ACCESS     read-write
   STATUS     mandatory
   DESCRIPTION
     "This attribute specifies the bandwidth pool which is to be used to 
      support the non-real-time variable bit rate (nrt-VBR) service 
      category except for connections managed by a Vpt CA. The 
      percentage of link capacity reserved for the given bandwidth pool is 
      the maximum bandwidth that can be allocated to nrt-VBR traffic. 
      The percentage allocated to each bandwidth pool can be 
      provisioned through the bandwidthPool attribute under the CA."
   DEFVAL     { pool1 }
::= { mscAtmIfCANrtVbrProvEntry 1 }

mscAtmIfCANrtVbrCdvt OBJECT-TYPE
   SYNTAX     Unsigned32 (1..1200000)
   ACCESS     read-write
   STATUS     mandatory
   DESCRIPTION
     "This attribute specifies the default cell delay variation tolerance 
      (CDVT) for all connections of the nrt-VBR service category. An 
      override to this default may be specified for a provisioned 
      connection under the Vcd Tm or Vpd Tm component.
      
      If Usage Parameter Control (UPC) is enabled for a connection, 
      CDVT is used by the UPC function to decide whether a cell is 
      conforming or non-conforming based on the connection's traffic 
      descriptor type. The larger the CDVT value, the more tolerant is the 
      UPC of bandwidth usage beyond the traffic contract."
   DEFVAL     { 250 }
::= { mscAtmIfCANrtVbrProvEntry 2 }

mscAtmIfCANrtVbrCellLossRatio OBJECT-TYPE
   SYNTAX     Unsigned32 (0..15)
   ACCESS     read-write
   STATUS     mandatory
   DESCRIPTION
     "This attribute specifies the tolerable cell loss ratio (CLR) for nrt-
      VBR traffic except for connections managed by a Vpt CA. The 
      number is the negative logarithm (base 10) of the CLR. In other 
      words if the target CLR = 1E-10 then NrtVbr cellLossRatio = 10. 
      This number must be greater than or equal to RtVbr cellLossRatio 
      since rt-VBR traffic has a higher discard priority. The NrtVbr 
      cellLossRatio is used by the Connection Admission Control (CAC) 
      algorithm to compute the required (equivalent) cell rate for nrt-VBR 
      connections. 
      
      There is a trade-off between the service category CLR and the 
      achievable link utilization. To guarantee an excellent service 
      category, the CLR should be as small as possible (e.g., 1E-10). 
      However, a smaller CLR results in a larger equivalent cell rate for a 
      given connection and hence a lower link utilization. 
      
      Setting this attribute to 0 means that a CLR of 1 can be tolerated. In 
      this case no bandwidth is reserved for nrt-VBR connections, and 
      CAC is effectively turned off. All nrt-VBR connections are 
      admitted."
   DEFVAL     { 7 }
::= { mscAtmIfCANrtVbrProvEntry 3 }

mscAtmIfCANrtVbrTxQueueLimit OBJECT-TYPE
   SYNTAX     Unsigned32 (0 | 5..512000)
   ACCESS     read-write
   STATUS     mandatory
   DESCRIPTION
     "This attribute specifies the default maximum queue length for the 
      emission queues used to buffer the traffic of the nrt-VBR service 
      category. It is used as the basis for setting the discard thresholds on 
      both common and per-VC queues. For the common queue, the 
      discard thresholds are set at approximately 35, 75, and 90 percent of 
      the value of this attribute for traffic at discard priority 3 (DP=3), 
      DP=2, and DP=1 respectively. 
      
      For per-VC queue, the actual limit may be reduced depending on 
      the shaping rate of the connection (for standard Vpt Vccs, this is the 
      shaping rate of the Vpt). The discard thresholds are set at 
      approximately 35, 75, and 90 percent of the scaled queue limit for 
      traffic at discard priority 3 (DP=3), DP=2, and DP=1 respectively. 
      However, a reduction will never result in a value that is less than the 
      value set for the minPerVcQueueLimit attribute.
      
      When the value of this attribute is autoConfigure, an appropriate 
      value is selected based on the card type. It is set to 1792 for low 
      speed cards such as DS1, E1, and IMA, set to 2304 for high speed 
      CQC-based ATM cards such as JT2, DS3, E3 and OC3, and set to 
      10240 for high speed ATM IP cards such as 3pDS3Atm2, 
      3pE3Atm2, 2pOC3SmAtm2 and 2pOC3MmAtm2. 
      
      For the 1pOC12SmLrAtm card, if autoConfigure is selected for 
      this attribute then the value is set to 7680.
      
      For the 1pOC48SmSrAtm card, if autoConfigure is selected for this 
      attribute the the value is set to 122880.
      
      For ATM IP FPs, the per-VC queue limit may be overridden for a 
      permanent connection by specifying a value in the Vcd Tm or Vpd 
      Tm txQueueLimit attribute. 
      
      For the 1pOC48SmSrAtm card, the value of this attribute is used to 
      set the maximum size of the link-class queue for buffering the nrt-
      VBR traffic on the egress path.
      
      On CQC-based ATM cards, this attribute must be set to the same 
      value for CA NrtVbr, Abr and Ubr components, and the valid range 
      is from 5 to 30000 inclusive.
      
      The operational value of the maximum length of a queue (common 
      or per-VC) is indicated by the Vcc Tm, Vpc Tm, or Vpt Tm 
      txQueueThresholds attribute.
      
      When using per-VC queueing, this attribute is used as the default 
      txQueueLimit for all standard Vpts, regardless of their 
      atmServiceCategory.

      VALUES (

      0 = autoConfigure

      )"
   DEFVAL     { 0 }
::= { mscAtmIfCANrtVbrProvEntry 4 }

mscAtmIfCANrtVbrSvcHoldingPriority OBJECT-TYPE
   SYNTAX     INTEGER  {
                 n0(0),
                 n1(1),
                 n2(2),
                 n3(3),
                 n4(4) }
   ACCESS     read-write
   STATUS     obsolete
   DESCRIPTION
     "This attribute specifies the default holding priority which applies to 
      SVC nrt-VBR connections. It takes a value from 0 (highest priority) 
      to 4 (lowest priority). In a situation where the link bandwidth 
      fluctuates, such as over an IMA link, holding priority is used to 
      determine which connections are held and which are released. 
      Holding priority 4 connections are the first to be released. Holding 
      priority 0 connections are the last to be released.
      This attribute has been obsoleted and its value migrated to 
      holdingPriority attribute."
   DEFVAL     { n3 }
::= { mscAtmIfCANrtVbrProvEntry 5 }

mscAtmIfCANrtVbrMinPerVcQueueLimit OBJECT-TYPE
   SYNTAX     Unsigned32 (5..160000)
   ACCESS     read-write
   STATUS     mandatory
   DESCRIPTION
     "This attribute specifies the minimum queue limit for the per-VC 
      queues of connections of the nrt-VBR service category.
      
      The queue limit of a per-VC queue is obtained by scaling down the 
      txQueueLimit based on the shaping rate of that queue (shaping rate 
      for the connection, and for standard Vpt Vccs, the shaping rate of 
      the Vpt). This produces a constant delay for various queue lengths. 
      The txQueueLimit provides an upper bound while 
      minPerVcQueueLimit provides the lower bound. The value of this 
      attribute must not be greater than the value of the txQueueLimit 
      attribute. If this service category is used by Trunks the value of 
      minPerVcQueueLimit must be at least 88.
      
      On CQC-based ATM cards, this attribute must be set to the same 
      value for CA NrtVbr, Abr and Ubr components.
      
      This attribute does not apply for the 1pOC12SmLrAtm and 
      1pOC48SmSrAtm cards, since per-VC queueing is not available.
      
      This attribute is used as the default minPerVcQueueLimit for all 
      standard Vpts, regardless of their atmServiceCategory.
      
      This attribute does not apply to basic Vpts."
   DEFVAL     { 88 }
::= { mscAtmIfCANrtVbrProvEntry 6 }

mscAtmIfCANrtVbrPerVcQueueLimitReferenceRate OBJECT-TYPE
   SYNTAX     Unsigned32 (0 | 1..1416905)
   ACCESS     read-write
   STATUS     mandatory
   DESCRIPTION
     "This attribute specifies the shaping rate to be used in computing the 
      tolerable delay for per-VC queues of connections of the nrt-VBR 
      service category. The delay is computed as the txQueueLimit 
      divided by the value of this attribute. 
      
      When the value of this attribute is autoConfigure, an appropriate 
      default is selected based on the card type. It is set to 3685 for low 
      speed cards such as DS1, E1 and IMA, set to 14740 for high speed 
      CQC-based ATM cards such as JT2, DS3, E3 and OC3, and set to 
      65511 for high speed ATM IP cards such as 3pDS3Atm2, 
      3pE3Atm2, 2pOC3SmAtm2 and 2pOC3MmAtm2. For 
      4pOC12SmIrAtm and 4pOC12SmLrAtm cards, the reference rate is 
      set to 65511 for DS3 and OC3 channels, and set to 262044 for 
      OC12 channels. For Apc-based cards the maximum value is 
      1416905. For all other cards, the maximum value is 943396.
      
      On CQC-based ATM cards, this attribute must be set to the same 
      value for CA NrtVbr, Abr and Ubr components.
      
      For the 1pOC12SmLrAtm and 1pOC48SmSrAtm cards, this 
      attribute does not apply since per-VC queueing is not available.
      
      This attribute is used as the default perVcQueueLimitReferenceRate 
      for all standard Vpts, regardless of their atmServiceCategory.
      
      This attribute does not apply to basic Vpts.

      VALUES (

      0 = autoConfigure

      )"
   DEFVAL     { 0 }
::= { mscAtmIfCANrtVbrProvEntry 7 }

mscAtmIfCANrtVbrSvcMpHoldingPriority OBJECT-TYPE
   SYNTAX     INTEGER  {
                 n0(0),
                 n1(1),
                 n2(2),
                 n3(3),
                 n4(4) }
   ACCESS     read-write
   STATUS     mandatory
   DESCRIPTION
     "This attribute specifies the default holding priority which applies to 
      SVC nrt-VBR point-to-multipoint connections. It takes a value from 
      0 (highest priority) to 4 (lowest priority). In a situation where the 
      link bandwidth fluctuates, such as over an IMA link, holding 
      priority is used to determine which connections are held and which 
      are released. Holding priority 4 connections are the first to be 
      released. Holding priority 0 connections are the last to be released.
      
      This attribute does not apply to Vpt Vccs. When bandwidth 
      fluctuates, the entire Vpt, along with all Vpt Vccs is released as a 
      unit, according to the Vpt's holdingPriority."
   DEFVAL     { n3 }
::= { mscAtmIfCANrtVbrProvEntry 8 }

mscAtmIfCANrtVbrHoldingPriority OBJECT-TYPE
   SYNTAX     INTEGER  {
                 n0(0),
                 n1(1),
                 n2(2),
                 n3(3),
                 n4(4) }
   ACCESS     read-write
   STATUS     mandatory
   DESCRIPTION
     "This attribute specifies the holding priority which applies to SVP 
      and SVC nrt-VBR connections. It takes a value from 0 (highest 
      priority) to 4 (lowest priority). In a situation where the link 
      bandwidth fluctuates, such as over an IMA link, holding priority is 
      used to determine which connections are held and which are 
      released. Holding priority 4 connections are the first to be released. 
      Holding priority 0 connections are the last to be released.
      
      This attribute does not apply to Vpt Vccs. When bandwidth 
      fluctuates, the entire Vpt, along with all Vpt Vccs is released as a 
      unit, according to the Vpt's holdingPriority."
   DEFVAL     { n3 }
::= { mscAtmIfCANrtVbrProvEntry 9 }

mscAtmIfCANrtVbrEmissionPriority OBJECT-TYPE
   SYNTAX     Unsigned32 (0..7)
   ACCESS     read-write
   STATUS     mandatory
   DESCRIPTION
     "This attribute is not applicable and is ignored for CQC-based ATM 
      cards.
      
      For the 1pOC48SmSrAtm card, only the default value is supported.
      
      This attribute specifies the emission priority (EP) which is used to 
      transmit traffic of the nrt-VBR service category. A lower numerical 
      value for this attribute specifies a higher emission priority. 0 is the 
      highest EP and 7 is the lowest. Cells at a higher emission priority 
      receive higher preference for link bandwidth. EPs 0 and 1 are in the 
      absolute priority range, and are unaffected by any minimum 
      bandwidth guarantees. EPs 2 through 7 are in the guaranteed 
      bandwidth range. Minimum bandwidth guarantee is specified in the 
      AtmIf/n Ep/m component. 
      
      Emission priority setting must comply with all of the following 
      constraints: 
      1. The emission priority numbers must be in the following order: 
      CBR <= rt-VBR <= nrt-VBR <= ABR <= UBR 
      2. Two different ATM service categories may share the same EP 
      only if they are both shaped. 
      3. CBR and rt-VBR may be placed either in the absolute priority 
      range (EP 0 or 1) or in the guaranteed bandwidth range (EP 2 
      through 7). 
      4. If both CBR and rt-VBR are shaped, rt-VBR must share the 
      same EP with CBR or ABR. If either one of CBR or rt-VBR are 
      not shaped, then they cannot share the same EP. 
      5. ABR service category is always deemed to be shaped. If nrt-VBR 
      is shaped, it must share the same EP with ABR. If nrt-VBR is not 
      shaped it must have a higher EP than ABR.
      6. If UBR is shaped, it must share the same EP with ABR. If UBR 
      is not shaped, it must have a lower EP than ABR. 
      
      This attribute does not apply to basic Vpts, and standard Vpt Vccs."
   DEFVAL     { 4 }
::= { mscAtmIfCANrtVbrProvEntry 10 }

mscAtmIfCANrtVbrTrafficShaping OBJECT-TYPE
   SYNTAX     INTEGER  {
                 disabled(1),
                 enabled(5),
                 inverseUpc(6) }
   ACCESS     read-write
   STATUS     mandatory
   DESCRIPTION
     "This attribute specifies the default traffic shaping option for 
      connections of the nrt-VBR service category. An override to this 
      default may be specified for a provisioned connection under the Vcd 
      Tm or Vpd Tm component.
      
      When this attribute is set to disabled, traffic shaping cannot be 
      enabled for any nrt-VBR connections. On 1pOC12SmLrAtm and 
      1pOC48SmSrAtm cards, this attribute must be set to disabled.
      
      For CQC-based ATM cards, this attribute may be set to enabled 
      only if the interface supports shaping, as defined by the 
      perVcQueueInterfaces attribute in the AtmResourceControl Cqc 
      Override component. If that component does not exist, this attribute 
      must be set to disabled.
      
      If the Vcc Tm, Vpc Tm, or Vpt Tm txTrafficDescType indicates type 
      1 or 2, this attribute is ignored, and traffic shaping is not applicable 
      for that connection. 
      
      When this attribute is set to inverseUpc, traffic shaping for a 
      connection is enabled according to card type and the value of the 
      Vcc Tm, Vpc Tm, or Vpt Tm txTrafficDescType. For 
      4pOC12SmIrAtm and 4pOC12SmLrAtm cards, inverseUpc shaping 
      is not available.
      
      If this attribute is set to inverseUpc, and the txTrafficDescType is 3, 
      4, or 5, linear traffic shaping is enabled. Linear traffic shaping uses 
      a single static traffic shaping rate. 
      
      On CQC-based ATM FPs, if this attribute is set to inverseUpc, and 
      the txTrafficDescType is 6, 7, or 8, linear traffic shaping is enabled.
      
      On ATM IP FPs, if this attribute is set to inverseUpc, and the 
      txTrafficDescType is 6, 7, or 8, inverse-UPC (also referred to as 
      VBR or dual leaky bucket) traffic shaping is enabled. Inverse-UPC 
      traffic shaping can burst above the sustained cell rate to the peak 
      cell rate for the duration defined by maximum burst size. Inverse-
      UPC traffic shaping exactly conforms to the requirements of a dual 
      leaky bucket UPC enforcer. 
      
      When this attribute is set to enabled and the txTrafficDescType is 3, 
      4, 5, 6, 7, or 8, traffic shaping for a connection is enabled using 
      linear shaping. 
      
      Enabling or disabling traffic shaping may require a matching 
      change to the emissionPriority attribute and 
      unshapedTransmitQueueing attribute for this service category. 
      Refer to those attributes for the complete description of the 
      interactions.
      
      This attribute does not apply to basic Vpts, and standard Vpt Vccs."
   DEFVAL     { disabled }
::= { mscAtmIfCANrtVbrProvEntry 14 }

mscAtmIfCANrtVbrShapeRecoupPolicy OBJECT-TYPE
   SYNTAX     INTEGER  {
                 minimumCdv(0),
                 maximumEfficiency(1) }
   ACCESS     read-write
   STATUS     mandatory
   DESCRIPTION
     "This attribute specifies the shaping recoup policy for the nrt-VBR 
      service category. This is the policy which is used to recoup shaping 
      opportunities which are lost when more than one connection 
      schedules a cell for the same transmit opportunity. In this case, one 
      connection is scheduled, and the cell from the other connection is 
      delayed by one cell time. This attribute affects how the transmit 
      time is calculated for the next cell on the delayed connection. This 
      attribute is ignored if this service category is not shaped.
      
      When the connection which was delayed schedules the next cell to 
      transmit, it may calculate the time as a difference from either the 
      previous actual cell transmit time, or the time when the previous 
      cell should have been transmitted.
      
      Setting this attribute to maximumEfficiency results in each 
      connection trying to recoup or regain any delays in scheduling. The 
      transmit time from the next cell is calculated from the time when 
      the cell should originally have been sent. Cell delay variation 
      (CDV) occurs in this case since the cells are sent with less than the 
      shaping delay between them. However, in general the shaper 
      recovers (recoups) lost opportunities and improves efficiency.
      
      Setting this attribute to minimumCdv results in connections not 
      trying to recoup or regain any delays in scheduling. The transmit 
      time for the next cell is calculated from the time when the previous 
      cell was actually transmitted. This minimizes CDV, but results in 
      missed cell opportunities.
      
      This attribute does not apply to basic Vpts, and standard Vpt Vccs."
   DEFVAL     { maximumEfficiency }
::= { mscAtmIfCANrtVbrProvEntry 15 }

mscAtmIfCANrtVbrUnshapedTransmitQueueing OBJECT-TYPE
   SYNTAX     INTEGER  {
                 perVc(0),
                 common(1),
                 autoConfigure(2) }
   ACCESS     read-write
   STATUS     mandatory
   DESCRIPTION
     "This attribute specifies the default queuing option for unshaped 
      connections of the nrt-VBR service category. This attribute controls 
      whether common or per-VC queueing is used. 
      
      Per-VC queueing means that each connection has its own buffering 
      and queue limits.
      
      Common queueing means that cells are queued in First In First Out 
      order on a common queue. The common queue has one set of 
      congestion control levels for all cells enqueued on it. For ATM IP 
      cards, there is one common queue for the nrt-VBR service category. 
      For CQC-based ATM cards, there is one common queue which is 
      shared by the nrt-VBR, ABR and UBR service categories. 
      
      For ATM IP cards, if traffic shaping for this service category is 
      disabled, this attribute may take any of the three values. In this case, 
      the value autoConfigure is interpreted to mean per-VC queueing.
      
      For 1pOC12SmLrAtm and 1pOC48SmSrAtm cards this attribute 
      must be set to common or autoConfigure. This attribute cannot be 
      set to perVc since per-Vc queueing is not available on the 
      1pOC12SmLrAtm and 1pOC48SmSrAtm cards. The value 
      autoConfigure is interpreted to mean common queueing.
      
      For ATM IP cards, if traffic shaping for this service category is not 
      disabled, the only permitted values are perVc and autoConfigure. 
      In this case, the result is that all connections use per-VC queueing.
      
      For CQC-based ATM cards, if the perVcQueueInterfaces attribute 
      of the Lp Eng Arc Cqc component permits shaping for this 
      interface, then this attribute may take any of the three values. In this 
      case, the value autoConfigure is interpreted to mean per-VC 
      queueing. For 4pOC12SmIrAtm and 4pOC12SmLrAtm cards only 
      perVc queueing is supported. All other attribute values are ignored.
      
      
      For CQC-based ATM cards, if the perVcQueueInterfaces attribute 
      of the Lp Eng Arc Cqc component does not permit shaping for this 
      interface, then this attribute may take the values common or 
      autoConfigure. In this case, the value autoConfigure is interpreted 
      to mean common queueing. 
      
      If this attribute is set to autoConfigure, an override to this default 
      may be specified for a provisioned connection under the Vcd Tm or 
      Vpd Tm component. 
      
      The opUnshapedTransmitQueueing attribute of this component 
      indicates whether the transmit queueing is perVc or common.
      
      This attribute does not apply to basic Vpts, and standard Vpt Vccs."
   DEFVAL     { autoConfigure }
::= { mscAtmIfCANrtVbrProvEntry 16 }

mscAtmIfCANrtVbrUsageParameterControl OBJECT-TYPE
   SYNTAX     INTEGER  {
                 enforced(0),
                 disabled(1),
                 monitored(4) }
   ACCESS     read-write
   STATUS     mandatory
   DESCRIPTION
     "This attribute specifies the default usage parameter control (UPC) 
      option for connections of the nrt-VBR service category. This 
      attribute is ignored if the rxTrafficDescriptorType indicates 1 or 2. 
      An override to this default may be specified for a provisioned 
      connection under the Vcd Tm or Vpd Tm component.
      
      When this attribute is set to enforced, UPC is enabled for each 
      connection. When UPC is enforced, non-conforming cells are either 
      tagged or discarded depending on the rxTrafficDescriptorType. 
      
      On ATM IP FPs, when this attribute is set to monitored, UPC 
      conformance checking is performed, except, instead of the non-
      conforming cells being tagged or discarded, they are merely 
      counted in the UPC violations counts, and passed on unchanged.
      
      On CQC-based ATM FPs, when this attribute is set to monitored, it 
      has the same effect as setting it to disabled. 
      
      For the 1pOC48SmSrAtm card, the value of this attribute must be 
      set to disabled. When this attribute is set to disabled, UPC is 
      disabled on the receive path for all nrt-VBR connections.
      
      This attribute does not apply to basic Vpts, and standard Vpt Vccs."
   DEFVAL     { disabled }
::= { mscAtmIfCANrtVbrProvEntry 17 }

mscAtmIfCANrtVbrWeightPolicy OBJECT-TYPE
   SYNTAX     INTEGER  {
                 scr(1),
                 pcr(2),
                 ecr(3) }
   ACCESS     read-write
   STATUS     mandatory
   DESCRIPTION
     "This attribute specifies the policy which is applied when calculating 
      the fairness weight for unshaped connections of the nrt-VBR 
      service category. The fairness weight for a connection determines 
      the relative amount of bandwidth which that connection obtains, 
      compared to other connections in the same service category. 
      Connections with equal weight get equal transmit opportunities. 
      Connections with higher weights get more transmit opportunities 
      compared with connections that have lower weights. An override to 
      this default may be specified for a provisioned connection under the 
      Vcd Tm or Vpd Tm component. 
      
      The fairness weight for a connection is directly proportional to the 
      value of one of the traffic descriptor parameters for that connection. 
      This attribute specifies which traffic descriptor parameter is used for 
      connections of the nrt-VBR service category. 
      
      This attribute is ignored on CQC-based ATM cards. This attribute is 
      also ignored on ATM IP cards if unshapedTransmitQueueing is set 
      for common queuing. 
      
      This attribute is also ignored for 1pOC48SmSrAtm cards.
      
      If this attribute is set to scr, the fairness weight is proportional to the 
      transmit sustained cell rate (SCR) of a connection. Connections 
      with a higher SCR have a higher fairness weight. For connections 
      with txTrafficDescType 3, which have no SCR, the sustained cell 
      rate is assumed to be equal to the peak cell rate. 
      
      If this attribute is set to pcr, the fairness weight is proportional to 
      the transmit peak cell rate (PCR) of a connection. Connections with 
      a higher PCR have a higher fairness weight. Connections with 
      txTrafficDescType 1 or 2 get a minimum weight, which is 1. 
      
      If this attribute is set to ecr, the fairness weight is proportional to 
      the equivalent cell rate (ECR) of a connection as calculated by 
      connection admission control (CAC). Connections with a higher 
      ECR have a higher fairness weight. Connections with an ECR of 0 
      get a minimum weight, which is 1. 
      
      The weight of a connection is visible in the Vcc Tm, Vpc Tm, or Vpt 
      Tm weight attribute.
      
      This attribute does not apply to basic Vpts, and standard Vpt Vccs."
   DEFVAL     { ecr }
::= { mscAtmIfCANrtVbrProvEntry 18 }

mscAtmIfCANrtVbrForceTagging OBJECT-TYPE
   SYNTAX     INTEGER  {
                 enabled(0),
                 disabled(1) }
   ACCESS     read-write
   STATUS     mandatory
   DESCRIPTION
     "This attribute specifies the default of whether to force tagging 
      (CLP=1) of all cells for all nrt-VBR connections. An override to 
      this default may be specified for a provisioned connection under the 
      Vcd Tm or Vpd Tm component. This attribute is not supported by 
      4pOC12SmIrAtm and 4pOC12SmLrAtm cards.
      
      
      When this attribute is set to enabled, CLP is set to 1 for all cells in 
      the transmit direction. Force tagging is only supported on ATM IP 
      FPs. 
      
      On CQC-based ATM FPs, this attribute must be set to disabled. 
      When this attribute is set to disabled, CLP is unchanged for all cells 
      in the transmit direction.
      
      This attribute never applies to any type of Vpt."
   DEFVAL     { disabled }
::= { mscAtmIfCANrtVbrProvEntry 19 }

mscAtmIfCANrtVbrOperTable OBJECT-TYPE
   SYNTAX     SEQUENCE OF MscAtmIfCANrtVbrOperEntry
   ACCESS     not-accessible
   STATUS     mandatory
   DESCRIPTION
     "This group contains operational attributes for the nrt-VBR service 
      category."
::= { mscAtmIfCANrtVbr 110 }

mscAtmIfCANrtVbrOperEntry OBJECT-TYPE
   SYNTAX     MscAtmIfCANrtVbrOperEntry
   ACCESS     not-accessible
   STATUS     mandatory
   DESCRIPTION
     "An entry in the mscAtmIfCANrtVbrOperTable."
   INDEX {
      mscAtmIfIndex,
      mscAtmIfCAIndex,
      mscAtmIfCANrtVbrIndex }
::= { mscAtmIfCANrtVbrOperTable 1 }

MscAtmIfCANrtVbrOperEntry ::= SEQUENCE {
   mscAtmIfCANrtVbrOpUnshapedTransmitQueueing
      INTEGER,
   mscAtmIfCANrtVbrEpdOffset
      Unsigned32 }

mscAtmIfCANrtVbrOpUnshapedTransmitQueueing OBJECT-TYPE
   SYNTAX     INTEGER  {
                 perVc(0),
                 common(1) }
   ACCESS     read-only
   STATUS     mandatory
   DESCRIPTION
     "This attribute indicates the state of transmit queueing for unshaped 
      nrt-VBR connections.
      
      A value of perVc indicates that any unshaped connections use per-
      VC queueing. A value of common indicates that traffic for 
      unshaped connections uses the common queue which corresponds 
      to the EP for this service category."
::= { mscAtmIfCANrtVbrOperEntry 10 }

mscAtmIfCANrtVbrEpdOffset OBJECT-TYPE
   SYNTAX     Unsigned32 (0 | 5..1024)
   ACCESS     read-only
   STATUS     mandatory
   DESCRIPTION
     "This attribute indicates the Early Packet Discard (EPD) offset which 
      is currently in use for this service category. The EPD offset is used 
      to derive the EPD thresholds for each CC level.
      
      Any connection under this service category which requires the 
      txPacketWiseDiscard feature must specify a transmit queue limit 
      which is at least 5.71 times this offset. This ensures that the derived 
      Epd threshold will never be less than 17.5 % of the transmit queue 
      limit. If this is not done, txPacketWiseDiscard for the connection 
      will be automatically disabled.
      
      The value of this EPD offset is specified under the lp/x eng arc aqm 
      ov component."
::= { mscAtmIfCANrtVbrOperEntry 11 }


-- AtmIf/n CA AvailableBitRate/n
-- This component manages the default characteristics of the available 
-- bit rate (ABR) service category. There is full support for ABR 
-- connections on ATM IP cards except the 1pOC12SmLrAtm card. 
-- On CQC-based ATM cards and the 1pOC12SmLrAtm card there is 
-- limited support for ABR connections.

mscAtmIfCAAbr OBJECT IDENTIFIER ::= { mscAtmIfCA 5 }



mscAtmIfCAAbrRowStatusTable OBJECT-TYPE
   SYNTAX     SEQUENCE OF MscAtmIfCAAbrRowStatusEntry
   ACCESS     not-accessible
   STATUS     mandatory
   DESCRIPTION
     "This entry controls the addition and deletion of 
      mscAtmIfCAAbr components."
::= { mscAtmIfCAAbr 1 }

mscAtmIfCAAbrRowStatusEntry OBJECT-TYPE
   SYNTAX     MscAtmIfCAAbrRowStatusEntry
   ACCESS     not-accessible
   STATUS     mandatory
   DESCRIPTION
     "A single entry in the table represents a single 
      mscAtmIfCAAbr component."
   INDEX {
      mscAtmIfIndex,
      mscAtmIfCAIndex,
      mscAtmIfCAAbrIndex }
::= { mscAtmIfCAAbrRowStatusTable 1 }

MscAtmIfCAAbrRowStatusEntry ::= SEQUENCE {
   mscAtmIfCAAbrRowStatus
      RowStatus,
   mscAtmIfCAAbrComponentName
      DisplayString,
   mscAtmIfCAAbrStorageType
      StorageType,
   mscAtmIfCAAbrIndex
      Integer32 }

mscAtmIfCAAbrRowStatus OBJECT-TYPE
   SYNTAX     RowStatus 
   ACCESS     read-write
   STATUS     mandatory
   DESCRIPTION
     "This variable is used as the basis for SNMP naming of
      mscAtmIfCAAbr components.
      These components can be added."
::= { mscAtmIfCAAbrRowStatusEntry 1 }

mscAtmIfCAAbrComponentName OBJECT-TYPE
   SYNTAX     DisplayString 
   ACCESS     read-only
   STATUS     mandatory
   DESCRIPTION
     "This variable provides the component's string name for
      use with the ASCII Console Interface"
::= { mscAtmIfCAAbrRowStatusEntry 2 }

mscAtmIfCAAbrStorageType OBJECT-TYPE
   SYNTAX     StorageType 
   ACCESS     read-only
   STATUS     mandatory
   DESCRIPTION
     "This variable represents the storage type value for the
      mscAtmIfCAAbr tables."
::= { mscAtmIfCAAbrRowStatusEntry 4 }

mscAtmIfCAAbrIndex OBJECT-TYPE
   SYNTAX     Integer32 (0)
   ACCESS     not-accessible
   STATUS     mandatory
   DESCRIPTION
     "This variable represents the index for the mscAtmIfCAAbr tables."
::= { mscAtmIfCAAbrRowStatusEntry 10 }

mscAtmIfCAAbrProvTable OBJECT-TYPE
   SYNTAX     SEQUENCE OF MscAtmIfCAAbrProvEntry
   ACCESS     not-accessible
   STATUS     mandatory
   DESCRIPTION
     "This group contains provisioned attributes which control the ABR 
      service category for this interface."
::= { mscAtmIfCAAbr 100 }

mscAtmIfCAAbrProvEntry OBJECT-TYPE
   SYNTAX     MscAtmIfCAAbrProvEntry
   ACCESS     not-accessible
   STATUS     mandatory
   DESCRIPTION
     "An entry in the mscAtmIfCAAbrProvTable."
   INDEX {
      mscAtmIfIndex,
      mscAtmIfCAIndex,
      mscAtmIfCAAbrIndex }
::= { mscAtmIfCAAbrProvTable 1 }

MscAtmIfCAAbrProvEntry ::= SEQUENCE {
   mscAtmIfCAAbrPool
      INTEGER,
   mscAtmIfCAAbrCdvt
      Unsigned32,
   mscAtmIfCAAbrTxQueueLimit
      Unsigned32,
   mscAtmIfCAAbrMinPerVcQueueLimit
      Unsigned32,
   mscAtmIfCAAbrPerVcQueueLimitReferenceRate
      Unsigned32,
   mscAtmIfCAAbrEmissionPriority
      Unsigned32,
   mscAtmIfCAAbrFairnessPolicy
      INTEGER,
   mscAtmIfCAAbrFrttPortion
      Unsigned32,
   mscAtmIfCAAbrAbrConnectionType
      INTEGER,
   mscAtmIfCAAbrUsageParameterControl
      INTEGER,
   mscAtmIfCAAbrInitialCellRate
      Unsigned32,
   mscAtmIfCAAbrRateDecreaseFactor
      Unsigned32,
   mscAtmIfCAAbrRateIncreaseFactor
      Unsigned32,
   mscAtmIfCAAbrMaxCellPerRmCell
      Unsigned32,
   mscAtmIfCAAbrMaxTimeBetweenRmCell
      Unsigned32,
   mscAtmIfCAAbrCutoffDecreaseFactor
      Unsigned32,
   mscAtmIfCAAbrAcrDecreaseTimeFactor
      Unsigned32,
   mscAtmIfCAAbrDgcraMaximumDelay
      Unsigned32,
   mscAtmIfCAAbrDgcraMinimumDelay
      Unsigned32,
   mscAtmIfCAAbrHoldingPriority
      INTEGER }

mscAtmIfCAAbrPool OBJECT-TYPE
   SYNTAX     INTEGER  {
                 pool1(1),
                 pool2(2),
                 pool3(3),
                 pool4(4),
                 pool5(5) }
   ACCESS     read-write
   STATUS     mandatory
   DESCRIPTION
     "This attribute specifies the bandwidth pool which is to be used to 
      support the available bit rate (ABR) service category except for 
      connections managed by a Vpt CA. The percentage of link capacity 
      reserved for the given bandwidth pool is the maximum bandwidth 
      that can be allocated to ABR traffic. The percentage allocated to 
      each bandwidth pool can be provisioned through the bandwidthPool 
      attribute under the CA."
   DEFVAL     { pool1 }
::= { mscAtmIfCAAbrProvEntry 10 }

mscAtmIfCAAbrCdvt OBJECT-TYPE
   SYNTAX     Unsigned32 (1..1200000)
   ACCESS     read-write
   STATUS     mandatory
   DESCRIPTION
     "This attribute specifies the default cell delay variation tolerance 
      (CDVT) for all connections of the ABR service category. An 
      override to this default may be specified for a provisioned 
      connection under the Vcd Tm or Vpd Tm component, or signalled in 
      the SVC Traffic Descriptor Information Element. 
      
      This attribute is used by dynamic generic cell rate algorithm 
      (DGCRA) policer on ATM IP cards. On CQC-based ATM cards 
      ABR UPC is enforced using PCR and CDVT."
   DEFVAL     { 250 }
::= { mscAtmIfCAAbrProvEntry 11 }

mscAtmIfCAAbrTxQueueLimit OBJECT-TYPE
   SYNTAX     Unsigned32 (0 | 5..63488)
   ACCESS     read-write
   STATUS     mandatory
   DESCRIPTION
     "This attribute specifies the default maximum queue length for the 
      emission queues used to buffer the traffic of the ABR service 
      category. It is used as the basis for setting the discard thresholds on 
      ABR per-VC queues. 
      
      For per-VC queue, the actual limit may be reduced depending on 
      the peak cell rate. The discard thresholds are set at approximately 
      35, 75 and 90 percent of the scaled queue limit for traffic at discard 
      priority 3 (DP=3), DP=2 and DP=1 respectively. However, a 
      reduction will never result in a value that is less than the value set 
      for the minPerVcQueueLimit attribute.
      
      When the value of this attribute is autoConfigure, an appropriate 
      value is selected based on the card type. It is set to 1792 for low 
      speed cards such as DS1, E1 and IMA, set to 2304 for high speed 
      CQC-based ATM cards such as JT2, DS3, E3 and OC3, and set to 
      10240 for high speed ATM IP cards such as 3pDS3Atm2, 
      3pE3Atm2, 2pOC3SmAtm2 and 2pOC3MmAtm2. For the 
      1pOC12SmLrAtm card, the value is set to 6144.
      
      On CQC-based ATM cards, this attribute must be set to the same 
      value for CA NrtVbr, Abr and Ubr components, and the valid range 
      is from 5 to 30000 inclusive. 
      
      For ATM IP FPs, the per-VC queue limit may be overridden for a 
      permanent connection by specifying a value in the Vcd Tm or Vpd 
      Tm txQueueLimit attribute. 
      
      The operational value of the maximum length of a queue (common 
      or per-VC) is indicated by the Vcc Tm, Vpc Tm, or Vpt Tm 
      txQueueThresholds attribute.
      
      For standard Vpts, this attribute does not apply when using per-VC 
      queuing and only applies when using common queueing. When 
      using per-VC queueing, regardless of the Vpt's service category, 
      standard Vpts use the AtmIf Ca NrtVbr txQueueLimit value as their 
      default.
      
      This attribute does not apply to basic Vpts.

      VALUES (

      0 = autoConfigure

      )"
   DEFVAL     { 0 }
::= { mscAtmIfCAAbrProvEntry 12 }

mscAtmIfCAAbrMinPerVcQueueLimit OBJECT-TYPE
   SYNTAX     Unsigned32 (5..30000)
   ACCESS     read-write
   STATUS     mandatory
   DESCRIPTION
     "This attribute specifies the minimum queue limit for the per-VC 
      queues of connections of the ABR service category.
      
      The queue limit of a per-VC queue is obtained by scaling down the 
      txQueueLimit based on the peak cell rate of that queue. This 
      produces a constant delay for various queue lengths. The 
      txQueueLimit provides an upper bound while minPerVcQueueLimit 
      provides the lower bound. The value of this attribute must not be 
      greater than the value of the txQueueLimit attribute. If this service 
      category is used by Trunks the value of minPerVcQueueLimit must 
      be at least 88.
      
      On CQC-based ATM cards, this attribute must be set to the same 
      value for CA NrtVbr, Abr and Ubr components.
      
      For the 1pOC12SmLrAtm card, this attribute does not apply since 
      per-VC queueing is not available.
      
      For Vpts, this attribute does not apply. Regardless of Vpt service 
      category, standard Vpts always use the AtmIf Ca NrtVbr 
      minPerVcQueueLimit value as their default. To determine the queue 
      limit of a standard Vpt Vcc, the txQueueLimit is scaled down by the 
      Vpt shaping rate."
   DEFVAL     { 88 }
::= { mscAtmIfCAAbrProvEntry 13 }

mscAtmIfCAAbrPerVcQueueLimitReferenceRate OBJECT-TYPE
   SYNTAX     Unsigned32 (0 | 1..943396)
   ACCESS     read-write
   STATUS     mandatory
   DESCRIPTION
     "This attribute specifies the shaping rate to be used in computing the 
      tolerable delay for per-VC queues of connections of the ABR 
      service category. The delay is computed as the txQueueLimit 
      divided by the value of this attribute. 
      
      When the value of this attribute is autoConfigure, an appropriate 
      default is selected based on the card type. It is set to 3685 for low 
      speed cards such as DS1, E1 and IMA, set to 14740 for high speed 
      CQC-based ATM cards such as JT2, DS3, E3 and OC3, and set to 
      65511 for high speed ATM IP cards such as 3pDS3Atm2, 
      3pE3Atm2, 2pOC3SmAtm2 and 2pOC3MmAtm2. 
      
      On CQC-based ATM cards, this attribute must be set to the same 
      value for CA NrtVbr, Abr and Ubr components.
      
      For the 1pOC12SmLrAtm card, this attribute does not apply since 
      per-VC queueing is not available.
      
      For Vpts, this attribute does not apply. Regardless of Vpt service 
      category, standard Vpts always use the AtmIf Ca NrtVbr 
      perVcQueueLimitReferenceRate value as their default.

      VALUES (

      0 = autoConfigure

      )"
   DEFVAL     { 0 }
::= { mscAtmIfCAAbrProvEntry 14 }

mscAtmIfCAAbrEmissionPriority OBJECT-TYPE
   SYNTAX     Unsigned32 (0..7)
   ACCESS     read-write
   STATUS     mandatory
   DESCRIPTION
     "This attribute is not applicable and is ignored for CQC-based ATM 
      cards.
      
      This attribute specifies the emission priority (EP) which is used to 
      transmit traffic of the ABR service category. A lower numerical 
      value for this attribute specifies a higher emission priority. 0 is the 
      highest EP and 7 is the lowest. Cells at a higher emission priority 
      receive higher preference for link bandwidth. EPs 0 and 1 are in the 
      absolute priority range, and are unaffected by any minimum 
      bandwidth guarantees. EPs 2 through 7 are in the guaranteed 
      bandwidth range. Minimum bandwidth guarantee is specified in the 
      AtmIf/n Ep/m component. 
      
      Emission priority setting must comply with all of the following 
      constraints: 
      1. The emission priority numbers must be in the following order: 
      CBR <= rt-VBR <= nrt-VBR <= ABR <= UBR 
      2. Two different ATM service categories may share the same EP 
      only if they are both shaped. 
      3. CBR and rt-VBR may be placed either in the absolute priority 
      range (EP 0 or 1) or in the guaranteed bandwidth range (EP 2 
      through 7). 
      4. If both CBR and rt-VBR are shaped, rt-VBR must share the 
      same EP with CBR or ABR. If either one of CBR or rt-VBR are 
      not shaped, then they cannot share the same EP. 
      5. ABR service category is always deemed to be shaped. If nrt-VBR 
      is shaped, it must share the same EP with ABR. If nrt-VBR is not 
      shaped it must have a higher EP than ABR.
      6. If UBR is shaped, it must share the same EP with ABR. If UBR 
      is not shaped, it must have a lower EP than ABR.
      
      This attribute does not apply to basic Vpts, and standard Vpt Vccs."
   DEFVAL     { 6 }
::= { mscAtmIfCAAbrProvEntry 15 }

mscAtmIfCAAbrFairnessPolicy OBJECT-TYPE
   SYNTAX     INTEGER  {
                 mcr(0),
                 pcr(2),
                 pcrMinusMcr(4) }
   ACCESS     read-write
   STATUS     mandatory
   DESCRIPTION
     "This attribute specifies the fairness policy which is applied to 
      available bandwidth when performing the ER calculation in the 
      ABR service category. This applies to any connection point 
      performing explicit rate calculations. Each ABR connection is 
      assigned a weight. Connections with a higher weight get a greater 
      proportion of the available ABR bandwidth compared with 
      connections that have lower weights. This attribute is ignored on 
      CQC-based ATM cards. 
      
      If the value is mcr, the congestion fairness weight is based on the 
      Minimum Cell Rate (MCR) of the connection.
      
      If the value is pcr, the congestion fairness weight is based on the 
      Peak Cell Rate (PCR) of the connection. 
      
      If the value is pcrMinusMcr, the congestion fairness weight is 
      based on the difference between the Peak Cell Rate and the 
      Minimum Cell Rate (PCR - MCR) of the connection."
   DEFVAL     { pcrMinusMcr }
::= { mscAtmIfCAAbrProvEntry 19 }

mscAtmIfCAAbrFrttPortion OBJECT-TYPE
   SYNTAX     Unsigned32 (0..10000)
   ACCESS     read-write
   STATUS     mandatory
   DESCRIPTION
     "This attribute specifies the portion of the Fixed Round Trip Time 
      (FRTT) which is added to each ABR call setup which traverses this 
      interface. The FRTT for the entire call is the sum of the FRTT 
      portions for each interface traversed by the call. FRTT is used by 
      the ABR Source or Virtual Source to adjust the value of ICR 
      according to the rules specified in the ATM Forum TM Version 4.0 
      specification.
      
      The frttPortion includes propagation delay through the physical 
      media, plus delays included by the transmission system, plus fixed 
      components of switch processing delay.
      
      This attribute is used by ATM Networking at call set-up time for 
      ABR connections directed over this interface."
   DEFVAL     { 5 }
::= { mscAtmIfCAAbrProvEntry 20 }

mscAtmIfCAAbrAbrConnectionType OBJECT-TYPE
   SYNTAX     INTEGER  {
                 abrSwitch(0),
                 virtualSourceDest(3),
                 nonAbrInterworking(5) }
   ACCESS     read-write
   STATUS     mandatory
   DESCRIPTION
     "This attribute specifies the default type for ABR connections. It may 
      be overridden by the abrConnectionType attribute under the Vcd Tm 
      or Vpd Tm component, or by other configuration options. For 
      example, for ABR end point connections originating at this switch, 
      the Vcc Tm abrConnectionType will show sourceDest regardless of 
      the setting of this attribute. 
      
      If this attribute is set to abrSwitch, traversing ABR connections 
      default to type abrSwitchEr or abrSwitchEfci, depending on the 
      card type. If the interface to which traffic is directed across the 
      backplane is configured as type virtualSourceDest and this is a 
      ATM IP FP, then connection points under this AtmIf are activated as 
      type virtualSourceDest. 
      
      If this attribute is set to virtualSourceDest, traversing ABR 
      connections may be instantiated as one of the following types: 
      abrSwitchEr, abrSwitchEfci, or virtualSourceDest. A Virtual 
      Source-Virtual Destination (VS/VD) boundary forms a break in the 
      end to end flow of RM cells as defined in the ATM Forum 
      Specification for Traffic Management Version 4.0. On ATM IP 
      cards, a VS/VD boundary can be configured for a connection 
      providing all of the following conditions are met: 
      1. the ABR connection is traversing (not terminating at) this 
      interface; 
      2. both this interface and next hop interface to which traffic is 
      directed across the backplane are located on ATM IP cards; 
      3. one or both connecting points are configured as 
      virtualSourceDest, 
      4. the next hop interface to which traffic is directed across the 
      backplane is not configured as nonAbrInterworking. 
      
      If this attribute is set to nonAbrInterworking, this interface is 
      defined as a point of interworking between an ABR and a non-ABR 
      connection. In this case the next hop interface to which traffic is 
      directed across the backplane is activated as type sourceDest. 
      
      The Vcc Tm or Vpc Tm abrConnectionType operational attribute 
      indicates what type of ABR connection was activated."
   DEFVAL     { abrSwitch }
::= { mscAtmIfCAAbrProvEntry 21 }

mscAtmIfCAAbrUsageParameterControl OBJECT-TYPE
   SYNTAX     INTEGER  {
                 enforced(0),
                 disabled(1),
                 monitored(4) }
   ACCESS     read-write
   STATUS     mandatory
   DESCRIPTION
     "This attribute specifies the default usage parameter control (UPC) 
      option for connections of the ABR service category. An override to 
      this default may be specified for a provisioned connection under the 
      Vcd Tm or Vpd Tm component.
      
      For ATM IP cards, if this attribute is set to enforced, UPC for ABR 
      connection is enforced as a Dynamic Generic Cell Rate Algorithm 
      (DGCRA) based on the connection traffic descriptor. 
      
      For CQC-based ATM cards, if this attribute is set to enforced, the 
      connection enforces a single GCRA policer at the defined PCR and 
      CDVT for this connection. 
      
      When UPC is enforced on an ABR connection, non-conforming 
      cells are discarded. 
      
      On ATM IP FPs, when this attribute is set to monitored, UPC 
      conformance checking is performed, except, instead of the non-
      conforming cells being discarded, they are merely counted in the 
      UPC violations counts, and passed on unchanged. 
      
      On CQC-based ATM FPs, when this attribute is set to monitored, it 
      has the same effect as setting it to disabled. 
      
      When this attribute is set to disabled, UPC is disabled on the receive 
      path for all ABR connections.
      
      This attribute does not apply to basic Vpts, and standard Vpt Vccs."
   DEFVAL     { disabled }
::= { mscAtmIfCAAbrProvEntry 22 }

mscAtmIfCAAbrInitialCellRate OBJECT-TYPE
   SYNTAX     Unsigned32 (0..16777215 | 16777217 | 16777218)
   ACCESS     read-write
   STATUS     mandatory
   DESCRIPTION
     "This attribute specifies the default Initial Cell Rate (ICR) parameter 
      for ABR connections. An override to this default may be specified 
      for a provisioned connection under the Vcd Tm Abr or Vpd Tm Abr 
      component, or signalled in the ABR Setup Parameters Information 
      Element. 
      
      ICR is the rate at which a source should send initially and after an 
      idle period.
      
      When this attribute is set to useMcr, ICR is set to the same value as 
      the Minimum Cell Rate (MCR) for the connection.
      
      When this attribute is set to usePcr, ICR is set to the same value as 
      the Peak Cell Rate (PCR) for the connection.
      
      When this attribute is set to some explicit number, that number is 
      used as the ICR, provided it is between MCR and PCR. If the 
      explicit number is below MCR, then MCR is used as ICR. If the 
      explicit number is above PCR, then PCR is used as ICR.

      VALUES (

      16777217 = useMcr

      16777218 = usePcr

      )"
   DEFVAL     { 16777218 }
::= { mscAtmIfCAAbrProvEntry 23 }

mscAtmIfCAAbrRateDecreaseFactor OBJECT-TYPE
   SYNTAX     Unsigned32 (0..15)
   ACCESS     read-write
   STATUS     mandatory
   DESCRIPTION
     "This attribute specifies the default Rate Decrease Factor (RDF) for 
      ABR connections. An override to this default may be specified for a 
      provisioned connection under the Vcd Tm Abr or Vpd Tm Abr 
      component, or signalled in the ABR Setup Parameters Information 
      Element.
      
      The RDF value is computed by using the provisioned value of this 
      attribute, n, as 2 to the inverse power n. For example, if the value of 
      this attribute is 8, RDF is 2E-8 = 1/256.
      
      RDF controls the amount by which the cell transmission rate may 
      decrease upon receipt of a backward Resource Management (B-
      RM) cell. For example, if a backward RM cell is received with the 
      Congestion Indication (CI) field set to 1, the Allowed Cell Rate 
      (ACR) value would be reduced by the amount (RDF*ACR). The 
      ACR is not allowed to fall below the Minimum Cell Rate (MCR), in 
      which case the ACR is set to MCR."
   DEFVAL     { 15 }
::= { mscAtmIfCAAbrProvEntry 24 }

mscAtmIfCAAbrRateIncreaseFactor OBJECT-TYPE
   SYNTAX     Unsigned32 (0..15)
   ACCESS     read-write
   STATUS     mandatory
   DESCRIPTION
     "This attribute specifies the default Rate Increase Factor (RIF) for 
      ABR connections. An override to this default may be specified for a 
      provisioned connection under the Vcd Tm Abr or Vpd Tm Abr 
      component, or signalled in the ABR Setup Parameters Information 
      Element.
      
      The RIF value is computed by using the provisioned value of this 
      attribute, n, as 2 to the inverse power n. For example, if the value of 
      this attribute is 6, RIF is 2E-6 = 1/64.
      
      RIF controls the amount by which the cell transmission rate may 
      increase upon receipt of a backward Resource Management (B-RM) 
      cell. For example, if a backward RM cell is received with the 
      Congestion Indication (CI) and the No Increase (NI) fields both set 
      to 0, the Allowed Cell Rate (ACR) value would be increased by the 
      amount (RIF*ACR). The ACR is not allowed to exceed the Peak 
      Cell Rate (PCR), in which case the ACR is set to PCR."
   DEFVAL     { 0 }
::= { mscAtmIfCAAbrProvEntry 25 }

mscAtmIfCAAbrMaxCellPerRmCell OBJECT-TYPE
   SYNTAX     Unsigned32 (2 | 4 | 8 | 16 | 32 | 64 | 128 | 256)
   ACCESS     read-write
   STATUS     mandatory
   DESCRIPTION
     "This attribute specifies the default number of user cells per 
      Resource Management cell (NRM) for ABR connections. An 
      override to this default may be specified for a provisioned 
      connection under the Vcd Tm Abr or Vpd Tm Abr component, or 
      signalled as the NRM parameter in the ABR Additional Parameters 
      Information Element. 
      
      NRM is the maximum number of cells an ABR source may transmit 
      for each forward Resource Management (F-RM) cell. The count of 
      the cells transmitted includes user cells, OAM cells, backward RM 
      cells, and the forward RM cell.
      
      Note that a value of 2 is not recommended even though it is 
      permitted according to the ATM Forum standard. When this 
      attribute is set to a value of 2, it is possible that only one forward 
      and one backward RM cell are repeatedly transmitted, and all data 
      traffic is queued up indefinitely.
      
      This attribute is ignored under all conditions where the Vcc Tm or 
      Vpc Tm operational attribute abrConnectionType indicates 
      explicitRateMarking."
   DEFVAL     { 256 }
::= { mscAtmIfCAAbrProvEntry 26 }

mscAtmIfCAAbrMaxTimeBetweenRmCell OBJECT-TYPE
   SYNTAX     Unsigned32 (781 | 1563 | 3125 | 6250 | 12500 | 25000 | 50000 | 100000)
   ACCESS     read-write
   STATUS     mandatory
   DESCRIPTION
     "This attribute specifies the default time between Resource 
      Management cells (TRM) for ABR connections. An override to this 
      default may be specified for a provisioned connection under the Vcd 
      Tm Abr or Vpd Tm Abr component, or signalled in the ABR 
      Additional Parameters Information Element.
      
      TRM provides an upper bound on the time interval between forward 
      Resource Management (F-RM) cells for an ABR source. Since the 
      last F-RM cell was sent, if at least TRM time has elapsed and at 
      least 2 other cells have been sent, the next cell to be transmitted 
      would be a forward RM cell.
      
      This attribute is ignored under all conditions where the Vcc Tm or 
      Vcd Tm operational attribute abrConnectionType is displayed as 
      explicitRateMarking.
      
      The provisioned value of 781 is signalled in the ABR Additional 
      Parameters Information Element as 0. 
      1563 is signalled as 1. 
      3125 is signalled as 2. 
      6250 is signalled as 3. 
      12500 is signalled as 4. 
      25000 is signalled as 5. 
      50000 is signalled as 6. 
      100000 is signalled as 7."
   DEFVAL     { 100000 }
::= { mscAtmIfCAAbrProvEntry 27 }

mscAtmIfCAAbrCutoffDecreaseFactor OBJECT-TYPE
   SYNTAX     Unsigned32 (0 | 1 | 2 | 4 | 8 | 16 | 32 | 64)
   ACCESS     read-write
   STATUS     mandatory
   DESCRIPTION
     "This attribute specifies the default Cutoff Decrease Factor (CDF) 
      parameter for ABR connections. An override to this default may be 
      specified for a provisioned connection under the Vcd Tm Abr or Vpd 
      Tm Abr component, or signalled in the ABR Additional Parameters 
      Information Element.
      
      When the value of this attribute is non-zero, CDF is computed as 
      the inverse of the value. For example, if the value is 32, the value of 
      CDF is 1/32. When the value of this attribute is 0, CDF is also zero.
      
      CDF controls the decrease in the Allowed Cell Rate (ACR) 
      associated with the CRM parameter. CRM is the limit of the 
      number of forward Resource Management (F-RM) cells which may 
      be sent in the absence of received backward RM cells. When this 
      limit is crossed, the ACR value would be decreased by the amount 
      (CDF*ACR). The ACR is not allowed to fall below the MCR, in 
      which case the ACR is set to MCR."
   DEFVAL     { 16 }
::= { mscAtmIfCAAbrProvEntry 28 }

mscAtmIfCAAbrAcrDecreaseTimeFactor OBJECT-TYPE
   SYNTAX     Unsigned32 (0..1023)
   ACCESS     read-write
   STATUS     mandatory
   DESCRIPTION
     "This attribute specifies the default Allowed Cell Rate Decrease 
      Time Factor (ADTF) parameter for ABR connections. An override 
      to this default may be specified for a provisioned connection under 
      the Vcd Tm Abr or Vpd Tm Abr component, or signalled in the ABR 
      Additional Parameters Information Element.
      
      ADTF is the time interval permitted between sending forward 
      Resource Management (F-RM) cells before the Allowed Cell Rate 
      (ACR) is decreased to the Initial Cell Rate (ICR). In other words, if 
      the source does not transmit a forward RM cell for a period of 
      ADTF centi-seconds (hundredths of a second), it will reduce its 
      ACR to the value of its ICR. If ACR is already at or below ICR, 
      further rate reductions are defined by the CRM ABR parameter."
   DEFVAL     { 50 }
::= { mscAtmIfCAAbrProvEntry 29 }

mscAtmIfCAAbrDgcraMaximumDelay OBJECT-TYPE
   SYNTAX     Unsigned32 (1..16700000)
   ACCESS     read-write
   STATUS     mandatory
   DESCRIPTION
     "This attribute specifies the default maximum delay for Dynamic 
      General Cell Rate Algorithm (DGCRA) rate changes for ABR 
      connections. An override to this default may be specified for a 
      provisioned connection under the Vcd Tm Abr or Vpd Tm Abr 
      component.
      
      This attribute specifies an upper bound on the delay after which the 
      rate change induced by a backward Resource Management (B-RM) 
      cell departing from this interface (in the backward direction) is 
      expected to be observed at the interface (in the forward connection).
      
      This upper bound may be approximated as the round trip sum of the 
      fixed and propagation delays and the maximum queueing delays 
      between the ABR source and this interface.
      
      The value of this attribute is used in policing an ABR connection 
      using the DGCRA. A larger value for this attribute implies a more 
      lenient policer. When there is a decrease in the Allowed Cell Rate 
      (ACR), the policer waits a correspondingly longer period of time 
      before it enforces the new cell rate.
      
      The value of this attribute must be greater than or equal to 
      dgcraMinimumDelay, since the maximum delay must be greater 
      than or equal to the minimum delay."
   DEFVAL     { 10000 }
::= { mscAtmIfCAAbrProvEntry 30 }

mscAtmIfCAAbrDgcraMinimumDelay OBJECT-TYPE
   SYNTAX     Unsigned32 (1..16700000)
   ACCESS     read-write
   STATUS     mandatory
   DESCRIPTION
     "This attribute specifies the default minimum delay for Dynamic 
      General Cell Rate Algorithm (DGCRA) rate changes for ABR 
      connections. An override to this default may be specified for a 
      provisioned connection under the Vcd Tm Abr or Vpd Tm Abr 
      component.
      
      This attribute specifies a lower bound on the delay after which the 
      rate change induced by a backward Resource Management (B-RM) 
      cell departing from this interface (in the backward direction) is 
      expected to be observed at the interface (in the forward connection).
      
      This lower bound may be approximated as the round trip sum of the 
      fixed and propagation delays between the ABR source and this 
      interface.
      
      The value of this attribute is used in policing an ABR connection 
      using the DGCRA. A smaller value for this attribute implies a more 
      lenient policer. When there is an increase in the Allowed Cell Rate 
      (ACR), the policer waits for a correspondingly shorter period of 
      time before it enforces the new cell rate.
      
      The value of this attribute must be less than or equal to 
      dgcraMaximumDelay, since the maximum delay must be greater 
      than or equal to the minimum delay."
   DEFVAL     { 1 }
::= { mscAtmIfCAAbrProvEntry 31 }

mscAtmIfCAAbrHoldingPriority OBJECT-TYPE
   SYNTAX     INTEGER  {
                 n0(0),
                 n1(1),
                 n2(2),
                 n3(3),
                 n4(4) }
   ACCESS     read-write
   STATUS     mandatory
   DESCRIPTION
     "This attribute specifies the default holding priority which applies to 
      SVP and SVC ABR connections. It takes a value from 0 (highest 
      priority) to 4 (lowest priority). In a situation where the link 
      bandwidth fluctuates, such as over an IMA link, holding priority is 
      used to determine which connections are held and which are 
      released. Holding priority 4 connections are the first to be released. 
      Holding priority 0 connections are the last to be released.
      
      This attribute does not apply to Vpt Vccs. When bandwidth 
      fluctuates, the entire Vpt, along with all Vpt Vccs is released as a 
      unit, according to the Vpt's holdingPriority."
   DEFVAL     { n3 }
::= { mscAtmIfCAAbrProvEntry 32 }

mscAtmIfCAAbrOperTable OBJECT-TYPE
   SYNTAX     SEQUENCE OF MscAtmIfCAAbrOperEntry
   ACCESS     not-accessible
   STATUS     mandatory
   DESCRIPTION
     "This group contains operational attributes for the ABR service 
      category."
::= { mscAtmIfCAAbr 110 }

mscAtmIfCAAbrOperEntry OBJECT-TYPE
   SYNTAX     MscAtmIfCAAbrOperEntry
   ACCESS     not-accessible
   STATUS     mandatory
   DESCRIPTION
     "An entry in the mscAtmIfCAAbrOperTable."
   INDEX {
      mscAtmIfIndex,
      mscAtmIfCAIndex,
      mscAtmIfCAAbrIndex }
::= { mscAtmIfCAAbrOperTable 1 }

MscAtmIfCAAbrOperEntry ::= SEQUENCE {
   mscAtmIfCAAbrEpdOffset
      Unsigned32 }

mscAtmIfCAAbrEpdOffset OBJECT-TYPE
   SYNTAX     Unsigned32 (0 | 5..1024)
   ACCESS     read-only
   STATUS     mandatory
   DESCRIPTION
     "This attribute indicates the Early Packet Discard (EPD) offset which 
      is currently in use for this service category. The EPD offset is used 
      to derive the EPD thresholds for each CC level.
      
      Any connection under this service category which requires the 
      txPacketWiseDiscard feature must specify a transmit queue limit 
      which is at least 5.71 times this offset. This ensures that the derived 
      Epd threshold will never be less than 17.5 % of the transmit queue 
      limit. If this is not done, txPacketWiseDiscard for the connection 
      will be automatically disabled.
      
      The value of this EPD offset is specified under the lp/x eng arc aqm 
      ov component."
::= { mscAtmIfCAAbrOperEntry 10 }


-- AtmIf/n CA UnspecifiedBitRate/n
-- This component manages the default characteristics of the 
-- unspecified bit rate (UBR) service category.

mscAtmIfCAUbr OBJECT IDENTIFIER ::= { mscAtmIfCA 6 }



mscAtmIfCAUbrRowStatusTable OBJECT-TYPE
   SYNTAX     SEQUENCE OF MscAtmIfCAUbrRowStatusEntry
   ACCESS     not-accessible
   STATUS     mandatory
   DESCRIPTION
     "This entry controls the addition and deletion of 
      mscAtmIfCAUbr components."
::= { mscAtmIfCAUbr 1 }

mscAtmIfCAUbrRowStatusEntry OBJECT-TYPE
   SYNTAX     MscAtmIfCAUbrRowStatusEntry
   ACCESS     not-accessible
   STATUS     mandatory
   DESCRIPTION
     "A single entry in the table represents a single 
      mscAtmIfCAUbr component."
   INDEX {
      mscAtmIfIndex,
      mscAtmIfCAIndex,
      mscAtmIfCAUbrIndex }
::= { mscAtmIfCAUbrRowStatusTable 1 }

MscAtmIfCAUbrRowStatusEntry ::= SEQUENCE {
   mscAtmIfCAUbrRowStatus
      RowStatus,
   mscAtmIfCAUbrComponentName
      DisplayString,
   mscAtmIfCAUbrStorageType
      StorageType,
   mscAtmIfCAUbrIndex
      Integer32 }

mscAtmIfCAUbrRowStatus OBJECT-TYPE
   SYNTAX     RowStatus 
   ACCESS     read-write
   STATUS     mandatory
   DESCRIPTION
     "This variable is used as the basis for SNMP naming of
      mscAtmIfCAUbr components.
      These components can be added."
::= { mscAtmIfCAUbrRowStatusEntry 1 }

mscAtmIfCAUbrComponentName OBJECT-TYPE
   SYNTAX     DisplayString 
   ACCESS     read-only
   STATUS     mandatory
   DESCRIPTION
     "This variable provides the component's string name for
      use with the ASCII Console Interface"
::= { mscAtmIfCAUbrRowStatusEntry 2 }

mscAtmIfCAUbrStorageType OBJECT-TYPE
   SYNTAX     StorageType 
   ACCESS     read-only
   STATUS     mandatory
   DESCRIPTION
     "This variable represents the storage type value for the
      mscAtmIfCAUbr tables."
::= { mscAtmIfCAUbrRowStatusEntry 4 }

mscAtmIfCAUbrIndex OBJECT-TYPE
   SYNTAX     Integer32 (0)
   ACCESS     not-accessible
   STATUS     mandatory
   DESCRIPTION
     "This variable represents the index for the mscAtmIfCAUbr tables."
::= { mscAtmIfCAUbrRowStatusEntry 10 }

mscAtmIfCAUbrProvTable OBJECT-TYPE
   SYNTAX     SEQUENCE OF MscAtmIfCAUbrProvEntry
   ACCESS     not-accessible
   STATUS     mandatory
   DESCRIPTION
     "This group contains provisioned attributes for the UBR service 
      category."
::= { mscAtmIfCAUbr 100 }

mscAtmIfCAUbrProvEntry OBJECT-TYPE
   SYNTAX     MscAtmIfCAUbrProvEntry
   ACCESS     not-accessible
   STATUS     mandatory
   DESCRIPTION
     "An entry in the mscAtmIfCAUbrProvTable."
   INDEX {
      mscAtmIfIndex,
      mscAtmIfCAIndex,
      mscAtmIfCAUbrIndex }
::= { mscAtmIfCAUbrProvTable 1 }

MscAtmIfCAUbrProvEntry ::= SEQUENCE {
   mscAtmIfCAUbrMaxVpcs
      Unsigned32,
   mscAtmIfCAUbrMaxVccs
      Unsigned32,
   mscAtmIfCAUbrMaxVpts
      Unsigned32,
   mscAtmIfCAUbrPool
      INTEGER,
   mscAtmIfCAUbrMinimumCellRate
      Unsigned32,
   mscAtmIfCAUbrTxQueueLimit
      Unsigned32,
   mscAtmIfCAUbrMinPerVcQueueLimit
      Unsigned32,
   mscAtmIfCAUbrPerVcQueueLimitReferenceRate
      Unsigned32,
   mscAtmIfCAUbrEmissionPriority
      Unsigned32,
   mscAtmIfCAUbrTrafficShaping
      INTEGER,
   mscAtmIfCAUbrShapeRecoupPolicy
      INTEGER,
   mscAtmIfCAUbrUnshapedTransmitQueueing
      INTEGER,
   mscAtmIfCAUbrUsageParameterControl
      INTEGER,
   mscAtmIfCAUbrWeightPolicy
      INTEGER,
   mscAtmIfCAUbrForceTagging
      INTEGER,
   mscAtmIfCAUbrCdvt
      Unsigned32,
   mscAtmIfCAUbrHoldingPriority
      INTEGER,
   mscAtmIfCAUbrSvcMpHoldingPriority
      INTEGER }

mscAtmIfCAUbrMaxVpcs OBJECT-TYPE
   SYNTAX     Unsigned32 (0..4096 | 16385)
   ACCESS     read-write
   STATUS     mandatory
   DESCRIPTION
     "This attribute specifies the maximum number of UBR Vpcs that can 
      be activated on this AtmIf. The value must not exceed the maxVpcs 
      attribute of the parent CA component.
      
      If this attribute is specified as sameAsCa, the maximum number of 
      Vpcs is defined by the AtmIf/n CA maxVpcs attribute. 
      
      Changes to this attribute do not affect existing Vpcs. If the value is 
      changed to a number smaller than the current number of active 
      UBR VPCs, no new UBR VPCs are admitted until the number of 
      active UBR VPCs drops below the value of this attribute. The 
      current number of active UBR VPCs is indicated by the Ubr/0 
      vpcUsage operational attribute.

      VALUES (

      16385 = sameAsCa

      )"
   DEFVAL     { 16385 }
::= { mscAtmIfCAUbrProvEntry 5 }

mscAtmIfCAUbrMaxVccs OBJECT-TYPE
   SYNTAX     Unsigned32 (0..16384 | 16385)
   ACCESS     read-write
   STATUS     mandatory
   DESCRIPTION
     "This attribute specifies the maximum number of UBR Vccs that can 
      be activated on this AtmIf, including UBR Vpt Vccs. The value must 
      not exceed the maxVccs attribute of the parent CA component.
      
      If this attribute is specified as sameAsCa, the maximum number of 
      Vccs is defined by the AtmIf/n CA maxVccs attribute. 
      
      Changes to this attribute do not affect existing Vccs. If the value is 
      changed to a number smaller than the current number of active 
      UBR VCCs, no new UBR VCCs are admitted until the number of 
      active UBR VCCs drops below the value of this attribute. The 
      current number of active UBR VCCs is indicated by the Ubr/0 
      vccUsage operational attribute.

      VALUES (

      16385 = sameAsCa

      )"
   DEFVAL     { 16385 }
::= { mscAtmIfCAUbrProvEntry 6 }

mscAtmIfCAUbrMaxVpts OBJECT-TYPE
   SYNTAX     Unsigned32 (0..4096 | 16385)
   ACCESS     read-write
   STATUS     mandatory
   DESCRIPTION
     "This attribute specifies the maximum number of UBR Vpts that can 
      be activated on this AtmIf. The value must not exceed the maxVpts 
      attribute of the parent CA component.
      
      If this attribute is specified as sameAsCa, the maximum number of 
      Vpts is defined by the AtmIf/n CA maxVpts attribute. 
      
      Changes to this attribute do not affect existing Vpts. If the value is 
      changed to a number smaller than the current number of active 
      UBR VPTs, no new UBR VPTs are admitted until the number of 
      active UBR VPTs drops below the value of this attribute. The 
      current number of active UBR VPTs is indicated by the Ubr/0 
      vptUsage operational attribute.

      VALUES (

      16385 = sameAsCa

      )"
   DEFVAL     { 16385 }
::= { mscAtmIfCAUbrProvEntry 7 }

mscAtmIfCAUbrPool OBJECT-TYPE
   SYNTAX     INTEGER  {
                 pool1(1),
                 pool2(2),
                 pool3(3),
                 pool4(4),
                 pool5(5) }
   ACCESS     read-write
   STATUS     mandatory
   DESCRIPTION
     "This attribute specifies the bandwidth pool which is to be used to 
      support the unspecified bit rate (UBR) service category except for 
      connections managed by a Vpt CA. The percentage of link capacity 
      reserved for the given bandwidth pool is the maximum bandwidth 
      that can be allocated to UBR traffic. The percentage allocated to 
      each bandwidth pool can be provisioned through the bandwidthPool 
      attribute under the CA.
      
      The amount of bandwidth reserved for each UBR connection is 
      specified in the minimumCellRate attribute."
   DEFVAL     { pool1 }
::= { mscAtmIfCAUbrProvEntry 10 }

mscAtmIfCAUbrMinimumCellRate OBJECT-TYPE
   SYNTAX     Unsigned32 (0..2147483647)
   ACCESS     read-write
   STATUS     mandatory
   DESCRIPTION
     "This attribute specifies the minimum cell rate (MCR) which is 
      allocated from the UBR bandwidth pool for each UBR connection 
      which is admitted using Connection Admission Control (CAC) 
      except for connections managed by a Vpt CA. UBR connections 
      normally are serviced on a best effort basis, but this attribute allows 
      allocation of a default minimum bandwidth for each connection."
   DEFVAL     { 0 }
::= { mscAtmIfCAUbrProvEntry 11 }

mscAtmIfCAUbrTxQueueLimit OBJECT-TYPE
   SYNTAX     Unsigned32 (0 | 5..512000)
   ACCESS     read-write
   STATUS     mandatory
   DESCRIPTION
     "This attribute specifies the default maximum queue length for the 
      emission queues used to buffer the traffic of the UBR service 
      category. It is used as the basis for setting the discard thresholds on 
      both common and per-VC queues. For the common queue, the 
      discard thresholds are set at approximately 35, 75 and 90 percent of 
      the value of this attribute for traffic at discard priority 3 (DP=3), 
      DP=2 and DP=1 respectively.
      
      For per-VC queue, the actual limit may be reduced depending on 
      the shaping rate of the connection (for standard Vpt Vccs, this is the 
      shaping rate of the Vpt). The discard thresholds are set at 
      approximately 35, 75 and 90 percent of the scaled queue limit for 
      traffic at discard priority 3 (DP=3), DP=2 and DP=1 respectively. 
      However, a reduction will never result in a value that is less than the 
      value set for the minPerVcQueueLimit attribute.
      
      When the value of this attribute is autoConfigure, an appropriate 
      value is selected based on the card type. It is set to 1792 for low 
      speed cards such as DS1, E1 and IMA, set to 2304 for high speed 
      CQC-based ATM cards such as JT2, DS3, E3 and OC3, and set to 
      10240 for high speed ATM IP cards such as 3pDS3Atm2, 
      3pE3Atm2, 2pOC3SmAtm2 and 2pOC3MmAtm2. For the 
      1pOC12SmLrAtm card, the value is set to 4096.
      
      On CQC-based ATM cards, this attribute must be set to the same 
      value for CA NrtVbr, Abr and Ubr components, and the valid range 
      is from 5 to 30000 inclusive. 
      
      For ATM IP FPs, the per-VC queue limit may be overridden for a 
      permanent connection by specifying a value in the Vcd Tm or Vpd 
      Tm txQueueLimit attribute. 
      
      The operational value of the maximum length of a queue (common 
      or per-VC) is indicated by the Vcc Tm, Vpc Tm, or Vpt Tm 
      txQueueThresholds attribute.
      
      For standard Vpts, this attribute does not apply when using per-VC 
      queuing and only applies when using common queueing. When 
      using per-VC queueing, regardless of the Vpt's service category, 
      standard Vpts use the AtmIf Ca NrtVbr txQueueLimit value as their 
      default.
      
      This attribute does not apply to basic Vpts.

      VALUES (

      0 = autoConfigure

      )"
   DEFVAL     { 0 }
::= { mscAtmIfCAUbrProvEntry 12 }

mscAtmIfCAUbrMinPerVcQueueLimit OBJECT-TYPE
   SYNTAX     Unsigned32 (5..30000)
   ACCESS     read-write
   STATUS     mandatory
   DESCRIPTION
     "This attribute specifies the minimum queue limit for the per-VC 
      queues of connections of the UBR service category.
      
      The queue limit of a per-VC queue is obtained by scaling down the 
      txQueueLimit based on the shaping rate of that queue (shaping rate 
      for the connection, and for standard Vpt Vccs, the shaping rate of 
      the Vpt). This produces a constant delay for various queue lengths. 
      The txQueueLimit provides an upper bound while 
      minPerVcQueueLimit provides the lower bound. The value of this 
      attribute must not be greater than the value of the txQueueLimit 
      attribute. If this service category is used by Trunks the value of 
      minPerVcQueueLimit must be at least 88.
      
      On CQC-based ATM cards, this attribute must be set to the same 
      value for CA NrtVbr, Abr and Ubr components.
      
      For the 1pOC12SmLrAtm card, this attribute does not apply since 
      per-VC queueing is not available.
      
      For Vpts, this attribute does not apply. Regardless of Vpt service 
      category, standard Vpts always use the AtmIf Ca NrtVbr 
      minPerVcQueueLimit value as their default. To determine the queue 
      limit of a standard Vpt Vcc, the txQueueLimit is scaled down by the 
      Vpt shaping rate."
   DEFVAL     { 88 }
::= { mscAtmIfCAUbrProvEntry 13 }

mscAtmIfCAUbrPerVcQueueLimitReferenceRate OBJECT-TYPE
   SYNTAX     Unsigned32 (0 | 1..1416905)
   ACCESS     read-write
   STATUS     mandatory
   DESCRIPTION
     "This attribute specifies the shaping rate to be used in computing the 
      tolerable delay for per-VC queues of connections of the UBR 
      service category. The delay is computed as the txQueueLimit 
      divided by the value of this attribute. 
      
      When the value of this attribute is autoConfigure, an appropriate 
      default is selected based on the card type. It is set to 3685 for low 
      speed cards such as DS1, E1 and IMA, set to 14740 for high speed 
      cards such as JT2, DS3, E3 and OC3, and set to 65511 for high 
      speed ATM IP cards such as 3pDS3Atm2, 3pE3Atm2, 
      2pOC3SmAtm2 and 2pOC3MmAtm2. For 4pOC12SmIrAtm and 
      4pOC12SmLrAtm cards, the reference rate is set to 65511 for DS3 
      and OC3 channels, and set to 262044 for OC12 channels. For Apc-
      based cards the maximum value is 1416905. For all other cards, the 
      maximum value is 943396.
      
      On CQC-based ATM cards, this attribute must be set to the same 
      value for CA NrtVbr, Abr and Ubr components.
      
      For the 1pOC12SmLrAtm card, this attribute does not apply since 
      per-VC queueing is not available.
      
      For Vpts, this attribute does not apply. Regardless of Vpt service 
      category, standard Vpts always use the AtmIf Ca NrtVbr 
      perVcQueueLimitReferenceRate value as their default.

      VALUES (

      0 = autoConfigure

      )"
   DEFVAL     { 0 }
::= { mscAtmIfCAUbrProvEntry 14 }

mscAtmIfCAUbrEmissionPriority OBJECT-TYPE
   SYNTAX     Unsigned32 (0..7)
   ACCESS     read-write
   STATUS     mandatory
   DESCRIPTION
     "This attribute is not applicable and is ignored for CQC-based ATM 
      cards.
      
      This attribute specifies the emission priority (EP) which is used to 
      transmit traffic of the UBR service category. A lower numerical 
      value for this attribute specifies a higher emission priority. 0 is the 
      highest EP and 7 is the lowest. Cells at a higher emission priority 
      receive higher preference for link bandwidth. EPs 0 and 1 are in the 
      absolute priority range, and are unaffected by any minimum 
      bandwidth guarantees. EPs 2 through 7 are in the guaranteed 
      bandwidth range. Minimum bandwidth guarantee is specified in the 
      AtmIf/n Ep/m component. 
      
      Emission priority setting must comply with all of the following 
      constraints: 
      1. The emission priority numbers must be in the following order: 
      CBR <= rt-VBR <= nrt-VBR <= ABR <= UBR 
      2. Two different ATM service categories may share the same EP 
      only if they are both shaped. 
      3. CBR and rt-VBR may be placed either in the absolute priority 
      range (EP 0 or 1) or in the guaranteed bandwidth range (EP 2 
      through 7). 
      4. If both CBR and rt-VBR are shaped, rt-VBR must share the 
      same EP with CBR or ABR. If either one of CBR or rt-VBR are 
      not shaped, then they cannot share the same EP. 
      5. ABR service category is always deemed to be shaped. If nrt-VBR 
      is shaped, it must share the same EP with ABR. If nrt-VBR is not 
      shaped it must have a higher EP than ABR.
      6. If UBR is shaped, it must share the same EP with ABR. If UBR 
      is not shaped, it must have a lower EP than ABR.
      
      This attribute does not apply to basic Vpts, and standard Vpt Vccs."
   DEFVAL     { 7 }
::= { mscAtmIfCAUbrProvEntry 15 }

mscAtmIfCAUbrTrafficShaping OBJECT-TYPE
   SYNTAX     INTEGER  {
                 disabled(1),
                 enabled(5),
                 inverseUpc(6) }
   ACCESS     read-write
   STATUS     mandatory
   DESCRIPTION
     "This attribute specifies the default traffic shaping option for 
      connections of the UBR service category. An override to this default 
      may be specified for a provisioned connection under the Vcd Tm or 
      Vpd Tm component.
      
      When this attribute is set to disabled, traffic shaping cannot be 
      enabled for any UBR connection. On 1pOC12SmLrAtm cards, this 
      attribute must be set to disabled.
      
      For CQC-based ATM cards, this attribute may be set to enabled 
      only if the interface supports shaping, as defined by the 
      perVcQueueInterfaces attribute in the AtmResourceControl Cqc 
      Override component. If that component does not exist, this attribute 
      must be set to disabled.
      
      If the Vcc Tm, Vpc Tm, or Vpt Tm txTrafficDescType indicates type 
      1 or 2, this attribute is ignored, and traffic shaping is not applicable 
      for that connection. 
      
      When this attribute is set to inverseUpc, traffic shaping for a 
      connection is enabled according to card type and the value of the 
      Vcc Tm, Vpc Tm, or Vpt Tm txTrafficDescType. For 
      4pOC12SmIrAtm and 4pOC12SmLrAtm cards, inverseUpc shaping 
      is not available.
      
      If this attribute is set to inverseUpc, and the txTrafficDescType is 3, 
      4, or 5, linear traffic shaping is enabled. Linear traffic shaping uses 
      a single static traffic shaping rate. 
      
      On CQC-based ATM FPs, if this attribute is set to inverseUpc, and 
      the txTrafficDescType is 6, 7, or 8, linear traffic shaping is enabled.
      
      On ATM IP FPs, if this attribute is set to inverseUpc, and the 
      txTrafficDescType is 6, 7, or 8, inverse-UPC (also referred to as 
      VBR or dual leaky bucket) traffic shaping is enabled. Inverse-UPC 
      traffic shaping can burst above the sustained cell rate to the peak 
      cell rate for the duration defined by maximum burst size. Inverse-
      UPC traffic shaping exactly conforms to the requirements of a dual 
      leaky bucket UPC enforcer. 
      
      When this attribute is set to enabled and the txTrafficDescType is 3, 
      4, 5, 6, 7, or 8, traffic shaping for a connection is enabled using 
      linear shaping. 
      
      Enabling or disabling traffic shaping may require a matching 
      change to the emissionPriority attribute and 
      unshapedTransmitQueueing attribute for this service category. 
      Refer to those attributes for the complete description of the 
      interactions.
      
      This attribute does not apply to basic Vpts, and standard Vpt Vccs."
   DEFVAL     { disabled }
::= { mscAtmIfCAUbrProvEntry 19 }

mscAtmIfCAUbrShapeRecoupPolicy OBJECT-TYPE
   SYNTAX     INTEGER  {
                 minimumCdv(0),
                 maximumEfficiency(1) }
   ACCESS     read-write
   STATUS     mandatory
   DESCRIPTION
     "This attribute specifies the shaping recoup policy for the UBR 
      service category. This is the policy which is used to recoup shaping 
      opportunities which are lost when more than one connection 
      schedules a cell for the same transmit opportunity. In this case, one 
      connection is scheduled, and the cell from the other connection is 
      delayed by one cell time. This attribute affects how the transmit 
      time is calculated for the next cell on the delayed connection. This 
      attribute is ignored if this service category is not shaped.
      
      When the connection which was delayed schedules the next cell to 
      transmit, it may calculate the time as a difference from either the 
      previous actual cell transmit time, or the time when the previous 
      cell should have been transmitted.
      
      Setting this attribute to maximumEfficiency results in each 
      connection trying to recoup or regain any delays in scheduling. The 
      transmit time from the next cell is calculated from the time when 
      the cell should originally have been sent. Cell delay variation 
      (CDV) occurs in this case since the cells are sent with less than the 
      shaping delay between them. However, in general the shaper 
      recovers (recoups) lost opportunities and improves efficiency.
      
      Setting this attribute to minimumCdv results in connections not 
      trying to recoup or regain any delays in scheduling. The transmit 
      time for the next cell is calculated from the time when the previous 
      cell was actually transmitted. This minimizes CDV, but results in 
      missed cell opportunities.
      
      This attribute does not apply to basic Vpts, and standard Vpt Vccs."
   DEFVAL     { maximumEfficiency }
::= { mscAtmIfCAUbrProvEntry 20 }

mscAtmIfCAUbrUnshapedTransmitQueueing OBJECT-TYPE
   SYNTAX     INTEGER  {
                 perVc(0),
                 common(1),
                 autoConfigure(2) }
   ACCESS     read-write
   STATUS     mandatory
   DESCRIPTION
     "This attribute specifies the default queuing option for unshaped 
      connections of the UBR service category. This attribute controls 
      whether common or per-VC queueing is used. 
      
      Per-VC queueing means that each connection has its own buffering 
      and queue limits.
      
      Common queueing means that cells are queued in First In First Out 
      order on a common queue. The common queue has one set of 
      congestion control levels for all cells enqueued on it. For ATM IP 
      cards, there is one common queue for the UBR service category. 
      For CQC-based ATM cards, there is one common queue which is 
      shared by the nrt-VBR, ABR and UBR service categories.
      
      For 1pOC12SmLrAtm cards this attribute must be set to common or 
      autoConfigure. This attribute cannot be set to perVc since per-Vc 
      queueing is not available on the 1pOC12SmLrAtm card. The value 
      autoConfigure is interpreted to mean common queueing.
      
      For ATM IP cards, if traffic shaping for this service category is 
      disabled, this attribute may take any of the three values. In this case, 
      the value autoConfigure is interpreted to mean per-VC queueing.
      
      For ATM IP cards, if traffic shaping for this service category is not 
      disabled, the only permitted values are perVc and autoConfigure. 
      In this case, the result is that all connections use per-VC queueing.
      
      For CQC-based ATM cards, if the perVcQueueInterfaces attribute 
      of the Lp Eng Arc Cqc component permits shaping for this 
      interface, then this attribute may take any of the three values. In this 
      case, the value autoConfigure is interpreted to mean per-VC 
      queueing. For 4pOC12SmIrAtm and 4pOC12SmLrAtm cards only 
      perVc queueing is supported. All other attribute values are ignored.
      
      
      For CQC-based ATM cards, if the perVcQueueInterfaces attribute 
      of the Lp Eng Arc Cqc component does not permit shaping for this 
      interface, then this attribute may take the values common or 
      autoConfigure. In this case, the value autoConfigure is interpreted 
      to mean common queueing.
      
      If this attribute is set to autoConfigure, an override to this default 
      may be specified for a provisioned connection under the Vcd Tm or 
      Vpd Tm component. 
      
      The opUnshapedTransmitQueueing attribute of this component 
      indicates whether the transmit queueing is perVc or common.
      
      This attribute does not apply to basic Vpts, andstandard Vpt Vccs."
   DEFVAL     { autoConfigure }
::= { mscAtmIfCAUbrProvEntry 21 }

mscAtmIfCAUbrUsageParameterControl OBJECT-TYPE
   SYNTAX     INTEGER  {
                 enforced(0),
                 disabled(1),
                 monitored(4) }
   ACCESS     read-write
   STATUS     mandatory
   DESCRIPTION
     "This attribute specifies the default usage parameter control (UPC) 
      option for connections of the UBR service category. This attribute is 
      ignored if the rxTrafficDescriptorType indicates 1 or 2. An override 
      to this default may be specified for a provisioned connection under 
      the Vcd Tm or Vpd Tm component.
      
      When this attribute is set to enforced, UPC is enforced for each 
      connection. When UPC is enforced, non-conforming cells are either 
      tagged or discarded depending on the rxTrafficDescriptorType. 
      
      On ATM IP FPs, when this attribute is set to monitored, UPC 
      conformance checking is performed, except, instead of the non-
      conforming cells being tagged or discarded, they are merely 
      counted in the UPC violations counts, and passed on unchanged. 
      
      On CQC-based ATM FPs, when this attribute is set to monitored, it 
      has the same effect as setting it to disabled. 
      
      When this attribute is set to disabled, UPC is disabled on the receive 
      path for all UBR connections.
      
      This attribute does not apply to basic Vpts, and standard Vpt Vccs."
   DEFVAL     { disabled }
::= { mscAtmIfCAUbrProvEntry 22 }

mscAtmIfCAUbrWeightPolicy OBJECT-TYPE
   SYNTAX     INTEGER  {
                 mcr(0),
                 pcr(2),
                 ecr(3) }
   ACCESS     read-write
   STATUS     mandatory
   DESCRIPTION
     "This attribute specifies the policy which is applied when calculating 
      the fairness weight for unshaped connections of the UBR service 
      category. The fairness weight for a connection determines the 
      relative amount of bandwidth which that connection obtains, 
      compared to other connections in the same service category. 
      Connections with equal weight get equal transmit opportunities. 
      Connections with higher weights get more transmit opportunities 
      compared with connections that have lower weights. An override to 
      this default may be specified for a provisioned connection under the 
      Vcd Tm or Vpd Tm component. 
      
      The fairness weight for a connection is directly proportional to the 
      value of one of the traffic descriptor parameters for that connection. 
      This attribute specifies which traffic descriptor parameter is used for 
      connections of the UBR service category. 
      
      This attribute is ignored on CQC-based ATM cards. This attribute is 
      also ignored on ATM IP cards if unshapedTransmitQueueing is set 
      for common queuing. 
      
      If this attribute is set to mcr, the fairness weight is proportional to 
      the default minimum cell rate (MCR) for UBR connections. If the 
      default minimum cell rate is 0, all UBR connections get a minimum 
      weight, which is 1. 
      
      If this attribute is set to pcr, the fairness weight is proportional to 
      the transmit peak cell rate (PCR) of a connection. Connections with 
      a higher PCR have a higher fairness weight. Connections with 
      txTrafficDescType 1 or 2 get a minimum weight, which is 1. 
      
      If this attribute is set to ecr, the fairness weight is proportional to 
      the equivalent cell rate (ECR) of a connection as calculated by 
      connection admission control (CAC). Connections with a higher 
      ECR have a higher fairness weight. Connections with an ECR of 0 
      get a minimum weight, which is 1. 
      
      The weight of a connection is visible in the Vcc Tm, Vpc Tm, or Vpt 
      Tm weight attribute.
      
      This attribute does not apply to basic Vpts, and standard Vpt Vccs."
   DEFVAL     { pcr }
::= { mscAtmIfCAUbrProvEntry 23 }

mscAtmIfCAUbrForceTagging OBJECT-TYPE
   SYNTAX     INTEGER  {
                 enabled(0),
                 disabled(1) }
   ACCESS     read-write
   STATUS     mandatory
   DESCRIPTION
     "This attribute specifies the default of whether to force tagging 
      (CLP=1) of all cells for all UBR connections. An override to this 
      default may be specified for a provisioned connection under the Vcd 
      Tm or Vpd Tm component. This attribute is not supported by 
      4pOC12SmIrAtm and 4pOC12SmLrAtm cards.
      
      
      When this attribute is set to enabled, CLP is set to 1 for all cells in 
      the transmit direction. This is in conformance with the ATM Forum 
      TM4.0 UBR.2 service definition. Force tagging is only supported 
      on ATM IP FPs. 
      
      On CQC-based ATM FPs, this attribute must be set to disabled. 
      When this attribute is set to disabled, CLP is unchanged for all cells 
      in the transmit direction. This is in conformance with the ATM 
      Forum TM4.0 UBR.1 service definition. 
      
      This attribute never applies to any type of Vpt."
   DEFVAL     { disabled }
::= { mscAtmIfCAUbrProvEntry 24 }

mscAtmIfCAUbrCdvt OBJECT-TYPE
   SYNTAX     Unsigned32 (1..1200000)
   ACCESS     read-write
   STATUS     mandatory
   DESCRIPTION
     "This attribute specifies the default cell delay variation tolerance 
      (CDVT) for all connections of the UBR service category. An 
      override to this default may be specified for a provisioned 
      connection under the Vcd Tm or Vpd Tm component.
      
      If Usage Parameter Control (UPC) is enabled for a connection, 
      CDVT is used by the UPC function to decide whether a cell is 
      conforming or non-conforming based on the connection's traffic 
      descriptor type. The larger the CDVT value, the more tolerant is the 
      UPC of bandwidth usage beyond the traffic contract."
   DEFVAL     { 250 }
::= { mscAtmIfCAUbrProvEntry 30 }

mscAtmIfCAUbrHoldingPriority OBJECT-TYPE
   SYNTAX     INTEGER  {
                 n0(0),
                 n1(1),
                 n2(2),
                 n3(3),
                 n4(4) }
   ACCESS     read-write
   STATUS     mandatory
   DESCRIPTION
     "This attribute specifies the default holding priority which applies to 
      SVP and SVC UBR connections. It takes a value from 0 (highest 
      priority) to 4 (lowest priority). In a situation where the link 
      bandwidth fluctuates, such as over an IMA link, holding priority is 
      used to determine which connections are held and which are 
      released. Holding priority 4 connections are the first to be released. 
      Holding priority 0 connections are the last to be released.
      
      This attribute does not apply to Vpt Vccs. When bandwidth 
      fluctuates, the entire Vpt, along with all Vpt Vccs is released as a 
      unit, according to the Vpt's holdingPriority."
   DEFVAL     { n3 }
::= { mscAtmIfCAUbrProvEntry 40 }

mscAtmIfCAUbrSvcMpHoldingPriority OBJECT-TYPE
   SYNTAX     INTEGER  {
                 n0(0),
                 n1(1),
                 n2(2),
                 n3(3),
                 n4(4) }
   ACCESS     read-write
   STATUS     mandatory
   DESCRIPTION
     "This attribute specifies the default holding priority which applies to 
      SVC UBR point-to-multipoint connections. It takes a value from 0 
      (highest priority) to 4 (lowest priority). In a situation where the link 
      bandwidth fluctuates, such as over an IMA link, holding priority is 
      used to determine which connections are held and which are 
      released. Holding priority 4 connections are the first to be released. 
      Holding priority 0 connections are the last to be released.
      
      This attribute does not apply to Vpt Vccs. When bandwidth 
      fluctuates, the entire Vpt, along with all Vpt Vccs is released as a 
      unit, according to the Vpt's holdingPriority."
   DEFVAL     { n3 }
::= { mscAtmIfCAUbrProvEntry 50 }

mscAtmIfCAUbrOperTable OBJECT-TYPE
   SYNTAX     SEQUENCE OF MscAtmIfCAUbrOperEntry
   ACCESS     not-accessible
   STATUS     mandatory
   DESCRIPTION
     "This group contains operational attributes for the UBR service 
      category."
::= { mscAtmIfCAUbr 110 }

mscAtmIfCAUbrOperEntry OBJECT-TYPE
   SYNTAX     MscAtmIfCAUbrOperEntry
   ACCESS     not-accessible
   STATUS     mandatory
   DESCRIPTION
     "An entry in the mscAtmIfCAUbrOperTable."
   INDEX {
      mscAtmIfIndex,
      mscAtmIfCAIndex,
      mscAtmIfCAUbrIndex }
::= { mscAtmIfCAUbrOperTable 1 }

MscAtmIfCAUbrOperEntry ::= SEQUENCE {
   mscAtmIfCAUbrOpUnshapedTransmitQueueing
      INTEGER,
   mscAtmIfCAUbrVpcUsage
      Unsigned32,
   mscAtmIfCAUbrVccUsage
      Unsigned32,
   mscAtmIfCAUbrVptUsage
      Unsigned32,
   mscAtmIfCAUbrEpdOffset
      Unsigned32 }

mscAtmIfCAUbrOpUnshapedTransmitQueueing OBJECT-TYPE
   SYNTAX     INTEGER  {
                 perVc(0),
                 common(1) }
   ACCESS     read-only
   STATUS     mandatory
   DESCRIPTION
     "This attribute indicates the state of transmit queueing for unshaped 
      UBR connections.
      
      A value of perVc indicates that any unshaped connections use per-
      VC queueing. A value of common indicates that traffic for 
      unshaped connections uses the common queue which corresponds 
      to the EP for this service category."
::= { mscAtmIfCAUbrOperEntry 10 }

mscAtmIfCAUbrVpcUsage OBJECT-TYPE
   SYNTAX     Unsigned32 (0..4096)
   ACCESS     read-only
   STATUS     mandatory
   DESCRIPTION
     "This attribute indicates the number of active UBR Vpcs under this 
      interface. It includes switched and permanent connections."
::= { mscAtmIfCAUbrOperEntry 11 }

mscAtmIfCAUbrVccUsage OBJECT-TYPE
   SYNTAX     Unsigned32 (0..16384)
   ACCESS     read-only
   STATUS     mandatory
   DESCRIPTION
     "This attribute indicates the number of active UBR Vccs under this 
      interface. It includes switched and permanent connections, and Vpt 
      Vccs."
::= { mscAtmIfCAUbrOperEntry 12 }

mscAtmIfCAUbrVptUsage OBJECT-TYPE
   SYNTAX     Unsigned32 (0..4096)
   ACCESS     read-only
   STATUS     mandatory
   DESCRIPTION
     "This attribute indicates the number of active UBR Vpts under this 
      interface."
::= { mscAtmIfCAUbrOperEntry 13 }

mscAtmIfCAUbrEpdOffset OBJECT-TYPE
   SYNTAX     Unsigned32 (0 | 5..1024)
   ACCESS     read-only
   STATUS     mandatory
   DESCRIPTION
     "This attribute indicates the Early Packet Discard (EPD) offset which 
      is currently in use for this service category. The EPD offset is used 
      to derive the EPD thresholds for each CC level.
      
      Any connection under this service category which requires the 
      txPacketWiseDiscard feature must specify a transmit queue limit 
      which is at least 5.71 times this offset. This ensures that the derived 
      Epd threshold will never be less than 17.5 % of the transmit queue 
      limit. If this is not done, txPacketWiseDiscard for the connection 
      will be automatically disabled.
      
      The value of this EPD offset is specified under the lp/x eng arc aqm 
      ov component."
::= { mscAtmIfCAUbrOperEntry 14 }


-- AtmIf/n VirtualPathConnection/vpi
-- This component represents a virtual path connection (VPC). The 
-- instance value defines the VPI value for this connectionfor 
-- example, Vpc/120 defines a path with a VPI of 120.
-- 
-- A VPC is always a relay point. and as such can only have a either a 
-- NRP or a Loop subcomponent.

mscAtmIfVpc OBJECT IDENTIFIER ::= { mscAtmIf 4 }



mscAtmIfVpcRowStatusTable OBJECT-TYPE
   SYNTAX     SEQUENCE OF MscAtmIfVpcRowStatusEntry
   ACCESS     not-accessible
   STATUS     mandatory
   DESCRIPTION
     "This entry controls the addition and deletion of 
      mscAtmIfVpc components."
::= { mscAtmIfVpc 1 }

mscAtmIfVpcRowStatusEntry OBJECT-TYPE
   SYNTAX     MscAtmIfVpcRowStatusEntry
   ACCESS     not-accessible
   STATUS     mandatory
   DESCRIPTION
     "A single entry in the table represents a single 
      mscAtmIfVpc component."
   INDEX {
      mscAtmIfIndex,
      mscAtmIfVpcIndex }
::= { mscAtmIfVpcRowStatusTable 1 }

MscAtmIfVpcRowStatusEntry ::= SEQUENCE {
   mscAtmIfVpcRowStatus
      RowStatus,
   mscAtmIfVpcComponentName
      DisplayString,
   mscAtmIfVpcStorageType
      StorageType,
   mscAtmIfVpcIndex
      Integer32 }

mscAtmIfVpcRowStatus OBJECT-TYPE
   SYNTAX     RowStatus 
   ACCESS     read-write
   STATUS     mandatory
   DESCRIPTION
     "This variable is used as the basis for SNMP naming of
      mscAtmIfVpc components.
      These components can be added and deleted."
::= { mscAtmIfVpcRowStatusEntry 1 }

mscAtmIfVpcComponentName OBJECT-TYPE
   SYNTAX     DisplayString 
   ACCESS     read-only
   STATUS     mandatory
   DESCRIPTION
     "This variable provides the component's string name for
      use with the ASCII Console Interface"
::= { mscAtmIfVpcRowStatusEntry 2 }

mscAtmIfVpcStorageType OBJECT-TYPE
   SYNTAX     StorageType 
   ACCESS     read-only
   STATUS     mandatory
   DESCRIPTION
     "This variable represents the storage type value for the
      mscAtmIfVpc tables."
::= { mscAtmIfVpcRowStatusEntry 4 }

mscAtmIfVpcIndex OBJECT-TYPE
   SYNTAX     Integer32 (0..4095)
   ACCESS     not-accessible
   STATUS     mandatory
   DESCRIPTION
     "This variable represents the index for the mscAtmIfVpc tables."
::= { mscAtmIfVpcRowStatusEntry 10 }

mscAtmIfVpcStateTable OBJECT-TYPE
   SYNTAX     SEQUENCE OF MscAtmIfVpcStateEntry
   ACCESS     not-accessible
   STATUS     mandatory
   DESCRIPTION
     "This group contains the three OSI State attributes. The descriptions 
      generically indicate what each state attribute implies about the 
      component. Note that not all the values and state combinations 
      described here are supported by every component which reuses this 
      group. For component-specific information and the valid state 
      combinations, refer to the appropriate NTP."
::= { mscAtmIfVpc 100 }

mscAtmIfVpcStateEntry OBJECT-TYPE
   SYNTAX     MscAtmIfVpcStateEntry
   ACCESS     not-accessible
   STATUS     mandatory
   DESCRIPTION
     "An entry in the mscAtmIfVpcStateTable."
   INDEX {
      mscAtmIfIndex,
      mscAtmIfVpcIndex }
::= { mscAtmIfVpcStateTable 1 }

MscAtmIfVpcStateEntry ::= SEQUENCE {
   mscAtmIfVpcAdminState
      INTEGER,
   mscAtmIfVpcOperationalState
      INTEGER,
   mscAtmIfVpcUsageState
      INTEGER }

mscAtmIfVpcAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock -force or 
      Lock command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscAtmIfVpcStateEntry 1 }

mscAtmIfVpcOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscAtmIfVpcStateEntry 2 }

mscAtmIfVpcUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscAtmIfVpcStateEntry 3 }

mscAtmIfVpcOperTable OBJECT-TYPE
   SYNTAX     SEQUENCE OF MscAtmIfVpcOperEntry
   ACCESS     not-accessible
   STATUS     mandatory
   DESCRIPTION
     "This group contains operational information for a Vcc, Vpc, or Vpt 
      component."
::= { mscAtmIfVpc 110 }

mscAtmIfVpcOperEntry OBJECT-TYPE
   SYNTAX     MscAtmIfVpcOperEntry
   ACCESS     not-accessible
   STATUS     mandatory
   DESCRIPTION
     "An entry in the mscAtmIfVpcOperTable."
   INDEX {
      mscAtmIfIndex,
      mscAtmIfVpcIndex }
::= { mscAtmIfVpcOperTable 1 }

MscAtmIfVpcOperEntry ::= SEQUENCE {
   mscAtmIfVpcConnectionPointType
      INTEGER }

mscAtmIfVpcConnectionPointType OBJECT-TYPE
   SYNTAX     INTEGER  {
                 connectionEndPoint(0),
                 segmentEndPoint(1),
                 connectingPoint(2),
                 unknown(3) }
   ACCESS     read-only
   STATUS     mandatory
   DESCRIPTION
     "This attribute reflects the role of the connection component at this 
      interface.
      
      A value of connectionEndPoint indicates that user cells, end-to-end 
      OAM cells, and segment OAM cells are processed by the 
      connection component.
      
      A value of segmentEndPoint indicates that user cells and end-to-
      end OAM cells are relayed by the connection component, while 
      segment OAM cells are processed by the connection component.
      
      A value of connectingPoint indicates that user cells, end-to-end 
      OAM cells, and segment OAM cells are relayed by the connection 
      component.
      
      A value of unknown indicates that the connection component is 
      inactive."
::= { mscAtmIfVpcOperEntry 10 }

mscAtmIfVpcConnInfoTable OBJECT-TYPE
   SYNTAX     SEQUENCE OF MscAtmIfVpcConnInfoEntry
   ACCESS     not-accessible
   STATUS     mandatory
   DESCRIPTION
     "This group contains operational connection characteristics 
      information for a Vcc component."
::= { mscAtmIfVpc 115 }

mscAtmIfVpcConnInfoEntry OBJECT-TYPE
   SYNTAX     MscAtmIfVpcConnInfoEntry
   ACCESS     not-accessible
   STATUS     mandatory
   DESCRIPTION
     "An entry in the mscAtmIfVpcConnInfoTable."
   INDEX {
      mscAtmIfIndex,
      mscAtmIfVpcIndex }
::= { mscAtmIfVpcConnInfoTable 1 }

MscAtmIfVpcConnInfoEntry ::= SEQUENCE {
   mscAtmIfVpcDistributionType
      INTEGER,
   mscAtmIfVpcNumLeaves
      Gauge32,
   mscAtmIfVpcCallDirection
      INTEGER }

mscAtmIfVpcDistributionType OBJECT-TYPE
   SYNTAX     INTEGER  {
                 pointToPoint(0),
                 pointToMultipoint(1) }
   ACCESS     read-only
   STATUS     mandatory
   DESCRIPTION
     "This attribute indicates the way data is distributed in the connection.
      
      A value of pointToPoint indicates this connection point is part of a 
      point-to-point connection.
      
      A value of pointToMultipoint indicates this connection point is part 
      of a point-to-multipoint connection."
   DEFVAL     { pointToPoint }
::= { mscAtmIfVpcConnInfoEntry 11 }

mscAtmIfVpcNumLeaves OBJECT-TYPE
   SYNTAX     Gauge32 (0..2147483647)
   ACCESS     read-only
   STATUS     mandatory
   DESCRIPTION
     "This attribute indicates the number of destination leaves of the 
      connection. If the distributionType is pointToPoint the value of this 
      attribute is 0."
   DEFVAL     { 0 }
::= { mscAtmIfVpcConnInfoEntry 12 }

mscAtmIfVpcCallDirection OBJECT-TYPE
   SYNTAX     INTEGER  {
                 fromLink(0),
                 toLink(1),
                 notApplicable(2) }
   ACCESS     read-only
   STATUS     mandatory
   DESCRIPTION
     "This attribute indicates the direction of the call setup request for an 
      SVC.
      
      A value of fromLink means that the call setup originated from the 
      link.
      
      A value of toLink means that the call setup was directed to the link.
      
      For PVC connections, the value of this attribute is notApplicable.
      
      For SPVC connections, the value of this attribute is notApplicable 
      for Vccs with the SourcePVC and DestinationPVC subcomponents.
      
      For Signalling channels, the value of this attribute is notApplicable."
   DEFVAL     { notApplicable }
::= { mscAtmIfVpcConnInfoEntry 13 }

mscAtmIfVpcStatusTable OBJECT-TYPE
   SYNTAX     SEQUENCE OF MscAtmIfVpcStatusEntry
   ACCESS     not-accessible
   STATUS     mandatory
   DESCRIPTION
     "This group contains operational status information for a Vcc, Vpc or 
      Vpt component."
::= { mscAtmIfVpc 120 }

mscAtmIfVpcStatusEntry OBJECT-TYPE
   SYNTAX     MscAtmIfVpcStatusEntry
   ACCESS     not-accessible
   STATUS     mandatory
   DESCRIPTION
     "An entry in the mscAtmIfVpcStatusTable."
   INDEX {
      mscAtmIfIndex,
      mscAtmIfVpcIndex }
::= { mscAtmIfVpcStatusTable 1 }

MscAtmIfVpcStatusEntry ::= SEQUENCE {
   mscAtmIfVpcOperStatus
      INTEGER,
   mscAtmIfVpcLocalFailureCause
      INTEGER,
   mscAtmIfVpcTroubled
      INTEGER,
   mscAtmIfVpcSegLinkSideLoopbackState
      INTEGER,
   mscAtmIfVpcSegSwitchSideLoopbackState
      INTEGER,
   mscAtmIfVpcEndToEndLoopbackState
      INTEGER,
   mscAtmIfVpcRxOamCellCongestionState
      INTEGER,
   mscAtmIfVpcAisState
      INTEGER,
   mscAtmIfVpcRdiState
      INTEGER }

mscAtmIfVpcOperStatus OBJECT-TYPE
   SYNTAX     INTEGER  {
                 unknown(0),
                 end2endUp(1),
                 end2endDown(2),
                 localUpEnd2endUnknown(3),
                 localDown(4) }
   ACCESS     read-only
   STATUS     mandatory
   DESCRIPTION
     "This attribute indicates the present operational status of the Vcc, 
      Vpc or Vpt component. Its value is dependent upon the current state 
      of the segLinkSideLoopbackState and endToEndLoopbackState 
      attributes.
      
      The value is end2endUp when the endToEndLoopbackState is good 
      and the segLinkSideLoopbackState is either good or unknown.
      
      The value is end2endDown when the endToEndLoopbackState is 
      bad and the segLinkSideLoopbackState is either good or unknown.
      
      The value is localUpEnd2endUnknown when the 
      endToEndLoopbackState is unknown and the 
      segLinkSideLoopbackState is good.
      
      The value is localDown when segLinkSideLoopbackState is bad.
      
      The value is localUpEnd2endUnknown when the 
      endToEndLoopbackState is notApplicable and the 
      segLinkSideLoopbackState is good.
      
      The value is unknown when the endToEndLoopbackState is either 
      unknown or notApplicable and the segLinkSideLoopbackState is 
      unknown."
::= { mscAtmIfVpcStatusEntry 20 }

mscAtmIfVpcLocalFailureCause OBJECT-TYPE
   SYNTAX     INTEGER  {
                 noFailure(0),
                 localBwLoss(1),
                 portDown(2),
                 notAdmitted(3),
                 appNotRegistered(4),
                 disabledByApp(5),
                 bwReduced(6),
                 vpDown(7) }
   ACCESS     read-only
   STATUS     mandatory
   DESCRIPTION
     "This attribute indicates the failure cause of the Vcc, Vpc or Vpt 
      component. noFailure indicates that there is currently no 
      bandwidth related failure for this connection. 
      
      portDown indicates that the interface corresponding to the parent 
      AtmIf is down. 
      
      localBwLoss indicates that the Ima corresponding to this AtmIf has 
      lost some, but not all bandwidth, and as a result, this connection has 
      been released.
      
      notAdmitted indicates that this connection has failed to be admitted 
      by the Connection Admission Control (CAC) algorithm.
      
      appNotRegistered indicates that there is no application registered to 
      use this connection. This may be the case, for example when there 
      is a Vcc Test application, but the test has not been started. Check the 
      status of the application to determine why it is not functional.
      
      disabledByApp indicates that the application using this connection 
      has requested that the connection be disabled. An example is a 
      connection used by a trunk application where the trunk has timed 
      out on an attempt to stage. Check the application to determine why 
      it is not fully functional.
      
      bwReduced indicates that this connection is operating in a reduced 
      bandwidth state. It is a bandwidth elastic connection which 
      currently has been allocated less than the requested (equivalent) 
      bandwidth.
      
      vpDown indicates that this connection has been notified of a fault 
      detected at the associated VP-layer. vpDown is applicable for Vpt 
      Vccs only."
::= { mscAtmIfVpcStatusEntry 25 }

mscAtmIfVpcTroubled OBJECT-TYPE
   SYNTAX     INTEGER  {
                 no(0),
                 yes(1) }
   ACCESS     read-only
   STATUS     mandatory
   DESCRIPTION
     "This attribute indicates whether or not the connection is in a 
      troubled state. Connections become troubled because of OAM 
      failures; when one of the attributes segLinkSideLoopbackState, 
      segSwitchSideLoopbackState, endToEndLoopbackState, aisState 
      (when receiving AIS cells only) or rdiState go bad, this attribute is 
      set to yes; otherwise it is set to no."
   DEFVAL     { no }
::= { mscAtmIfVpcStatusEntry 28 }

mscAtmIfVpcSegLinkSideLoopbackState OBJECT-TYPE
   SYNTAX     INTEGER  {
                 good(0),
                 bad(1),
                 unknown(2),
                 notApplicable(3) }
   ACCESS     read-only
   STATUS     mandatory
   DESCRIPTION
     "This attribute contains the current state of the link-side segment 
      loopback for this connection. Link-side segment loopback cells are 
      transmitted (inserted) by a connection component in the direction of 
      the link (port). The value of this attribute is dependent upon the 
      current setting of the segLinkSideLoopback provisionable attribute, 
      the connection point type as specified by the connectionPointType 
      attribute, and the current loopback state (if applicable).
      
      The value is notApplicable when the connectionPointType is a 
      connectingPoint. 
      
      The value is notApplicable when the distributionType is 
      pointToMultipoint.
      
      The value is good when the segLinkSideLoopback is on, the 
      connectionPointType is a segmentEndPoint or a 
      connectionEndPoint, and the segment link side loopback is 
      working.
      
      The value is bad when the segLinkSideLoopback is on, the 
      connectionPointType is a segmentEndPoint or a 
      connectionEndPoint, and the link side segment loopback is not 
      working.
      
      The value is unknown when the segLinkSideLoopback is off.
      
      The value is unknown when the segLinkSideLoopback is on, the 
      connectionPointType is a segmentEndPoint and the segment switch 
      side loopback has not yet been determined.
      
      The state of this attribute determines, in part, the value of the 
      operStatus attribute."
::= { mscAtmIfVpcStatusEntry 30 }

mscAtmIfVpcSegSwitchSideLoopbackState OBJECT-TYPE
   SYNTAX     INTEGER  {
                 good(0),
                 bad(1),
                 unknown(2),
                 notApplicable(3) }
   ACCESS     read-only
   STATUS     mandatory
   DESCRIPTION
     "This attribute contains the current state of the switch-side segment 
      loopback for this connection. Switch-side segment loopback cells 
      are transmitted (inserted) by a connection component in the 
      direction of the bus. The value of this attribute is dependent upon 
      the current setting of the segSwitchSideLoopback provisionable 
      attribute, the connection point type as specified by the 
      connectionPointType attribute, and the current loopback state (if 
      applicable).
      
      The value is only applicable when the connectionPointType is a 
      segmentEndPoint. 
      
      The value is notApplicable when the connectionPointType is a 
      connectingPoint or connectionEndPoint. 
      
      The value is notApplicable when the distributionType is 
      pointToMultipoint.
      
      The value is good when the segSwitchSideLoopback is on, the 
      connectionPointType is a segmentEndPoint and the segment switch 
      side loopback is working.
      
      The value is bad when the segSwitchSideLoopback is on, the 
      connectionPointType is a segmentEndPoint and the switch side 
      segment loopback is not working.
      
      The value is unknown when the segSwitchSideLoopback is off.
      
      The value is unknown when the segSwitchSideLoopback is on, the 
      connectionPointType is a segmentEndPoint and the segment switch 
      side loopback has not been determined."
::= { mscAtmIfVpcStatusEntry 40 }

mscAtmIfVpcEndToEndLoopbackState OBJECT-TYPE
   SYNTAX     INTEGER  {
                 good(0),
                 bad(1),
                 unknown(2),
                 notApplicable(3) }
   ACCESS     read-only
   STATUS     mandatory
   DESCRIPTION
     "This attribute contains the current state of the end-to-end loopback 
      for this connection. Its value is dependent upon the current setting 
      of the endToEndLoopback provisionable attribute and the 
      connection point type as specified by the connectionPointType 
      attribute.
      
      The value is only applicable when the connectionPointType is a 
      connectionEndPoint. 
      
      The value is notApplicable when the connectionPointType is a 
      connectingPoint or segmentEndPoint. 
      
      The value is notApplicable when the distributionType is a 
      pointToMultipoint.
      
      The value is good when the endToEndLoopback is on, the 
      connectionPointType is a connectionEndPoint and the end-to-end 
      loopback is working.
      
      The value is bad when the endToEndLoopback is on, the 
      connectionPointType is a connectionEndPoint and the end-to-end 
      loopback is not working.
      
      The value is unknown when the endToEndLoopback is off.
      
      The value is unknown when the endToEndLoopback is on, the 
      connectionPointType is a connectionEndPoint and the end-to-end 
      loopback status has not been determined.
      
      The state of this attribute determines, in part, the value of the 
      operStatus attribute."
::= { mscAtmIfVpcStatusEntry 50 }

mscAtmIfVpcRxOamCellCongestionState OBJECT-TYPE
   SYNTAX     INTEGER  {
                 good(0),
                 bad(1),
                 unknown(2),
                 notApplicable(3) }
   ACCESS     read-only
   STATUS     mandatory
   DESCRIPTION
     "This attribute contains the current state of the receive side OAM cell 
      congestion for this connection. Its value reflects whether the rate of 
      received OAM cells for this connection is below a specified 
      threshold. The connection maintains a count of the number of OAM 
      cells which are terminated per second. Once that count exceeds the 
      specified threshold, extraction of all OAM cells for this connection 
      is disabled for a period of one minute. This is a congestion 
      management mechanism to prevent the processor from being 
      overloaded with handling OAM cells for a particular connection. 
      This mechanism ensures that tasks, such as trunks obtain enough 
      processor cycles to remain in service, and are not adversely affected 
      by excessive rate of OAM cells on a particular connection.
      
      The value is good when the rate of received OAM cells is less than 
      the allowed threshold.
      
      The value is bad when the arrival rate has exceeded the allowed 
      threshold. It remains bad for one minute, before returning to good 
      again. During this timeout, extraction of all OAM cells is disabled 
      for this connection. As a result, other loopback failure conditions 
      may occur.
      
      The value is unknown when the application has not yet begun to 
      use this connection. An example is the Test component before a test 
      has been started.
      
      Each type of OAM cell is counted separately. The threshold for AIS 
      cells is three cells per second. If more than three AIS cells are 
      received within a one second interval, this attribute is set to bad. 
      The threshold for RDI cells and each loopback type is also three, 
      but the threshold for trace cells is 250 per second.
      
      The state of this attribute has no direct effect on the value of the 
      operStatus attribute or on the number of troubled connections."
::= { mscAtmIfVpcStatusEntry 55 }

mscAtmIfVpcAisState OBJECT-TYPE
   SYNTAX     INTEGER  {
                 good(0),
                 bad(1),
                 unknown(2),
                 notApplicable(3) }
   ACCESS     read-only
   STATUS     mandatory
   DESCRIPTION
     "This attribute contains the current state of the Alarm Indication 
      Signal for this connection.
      
      A value of good indicates that the connection's application is active 
      and no alarm has occurred.
      
      A value of bad indicates that the connection's application is active 
      and an alarm has occurred.
      
      A value of unknown indicates that the connection's application is 
      inactive.
      
      A value of notApplicable occurs when the connectionPointType is 
      either a segmentEndPoint or a connectingPoint."
::= { mscAtmIfVpcStatusEntry 60 }

mscAtmIfVpcRdiState OBJECT-TYPE
   SYNTAX     INTEGER  {
                 good(0),
                 bad(1),
                 unknown(2),
                 notApplicable(3) }
   ACCESS     read-only
   STATUS     mandatory
   DESCRIPTION
     "This attribute indicates the current state of the Remote Defect 
      Indication for this connection.
      
      A value of good indicates that the connection's application is active 
      and no alarm has occurred.
      
      A value of bad indicates that the connection's application is active 
      and an alarm has occurred.
      
      A value of unknown indicates that the connection's application is 
      inactive.
      
      A value of notApplicable occurs when the connectionPointType is 
      either a segmentEndPoint or a connectingPoint."
::= { mscAtmIfVpcStatusEntry 70 }

mscAtmIfVpcTrafficTable OBJECT-TYPE
   SYNTAX     SEQUENCE OF MscAtmIfVpcTrafficEntry
   ACCESS     not-accessible
   STATUS     mandatory
   DESCRIPTION
     "This group is HISTORICAL. Please refer to the group AtmTmOper;
      
      This attribute group contains attributes for the Vcc and Vpc 
      components to reflect operational traffic attributes."
::= { mscAtmIfVpc 130 }

mscAtmIfVpcTrafficEntry OBJECT-TYPE
   SYNTAX     MscAtmIfVpcTrafficEntry
   ACCESS     not-accessible
   STATUS     mandatory
   DESCRIPTION
     "An entry in the mscAtmIfVpcTrafficTable."
   INDEX {
      mscAtmIfIndex,
      mscAtmIfVpcIndex }
::= { mscAtmIfVpcTrafficTable 1 }

MscAtmIfVpcTrafficEntry ::= SEQUENCE {
   mscAtmIfVpcTxTrafficDescType
      INTEGER,
   mscAtmIfVpcTxQosClass
      INTEGER,
   mscAtmIfVpcFwdQosClass
      INTEGER,
   mscAtmIfVpcTxQueueLength
      INTEGER,
   mscAtmIfVpcTxQueueCongestionState
      INTEGER,
   mscAtmIfVpcHoldingPriority
      INTEGER,
   mscAtmIfVpcRxTrafficDescType
      INTEGER,
   mscAtmIfVpcRxQosClass
      INTEGER,
   mscAtmIfVpcBwdQosClass
      INTEGER,
   mscAtmIfVpcAtmServiceCategory
      INTEGER,
   mscAtmIfVpcTrafficShaping
      INTEGER,
   mscAtmIfVpcBearerClassBbc
      INTEGER,
   mscAtmIfVpcTransferCapabilityBbc
      INTEGER,
   mscAtmIfVpcClippingBbc
      INTEGER,
   mscAtmIfVpcUnshapedTransmitQueueing
      INTEGER,
   mscAtmIfVpcBestEffort
      INTEGER,
   mscAtmIfVpcUsageParameterControl
      INTEGER,
   mscAtmIfVpcTxFrameDiscard
      OCTET STRING,
   mscAtmIfVpcRxFrameDiscard
      OCTET STRING,
   mscAtmIfVpcBandwidthElastic
      INTEGER,
   mscAtmIfVpcBandwidthReduction
      INTEGER }

mscAtmIfVpcTxTrafficDescType OBJECT-TYPE
   SYNTAX     INTEGER  {
                 n1(1),
                 n2(2),
                 n3(3),
                 n4(4),
                 n5(5),
                 n6(6),
                 n7(7),
                 n8(8) }
   ACCESS     read-only
   STATUS     obsolete
   DESCRIPTION
     "This attribute is HISTORICAL. Please refer to the attribute of the 
      same name in the group AtmTmOper.
      
      This attribute indicates the type of traffic management which is 
      applied to the transmit direction of this connection as defined in the 
      ATM Forum. The txTrafficDescType determines the number and 
      meaning of the parameters in the txTrafficDescParm attribute."
::= { mscAtmIfVpcTrafficEntry 10 }

mscAtmIfVpcTxQosClass OBJECT-TYPE
   SYNTAX     INTEGER  {
                 unspecified(0),
                 constantBitRate(1),
                 variableBitRate(2),
                 connectionOriented(3),
                 connectionless(4) }
   ACCESS     read-only
   STATUS     obsolete
   DESCRIPTION
     "This attribute indicates the quality of service for the transmit 
      direction for this connection.
      
      The constantBitRate class refers to traffic offered on services such 
      as a constant bit rate video service. This traffic is highest priority.
      
      The variableBitRate class refers to traffic offered on services such 
      as packetized audio and video.
      
      The connectionOriented class refers to connection-oriented traffic 
      such as Frame Relay or X.25 traffic. 
      
      The connectionless traffic refers to traffic offered through 
      connectionless trunks such as certain LAN protocols.
      
      The unspecified class supports a 'best effort' type of service, where 
      there is a minimum guarantee of bandwidth. This traffic is lowest 
      priority.
      
      This attribute is obsolete, replaced by the UNI 4.0 attribute 
      atmServiceCategory."
::= { mscAtmIfVpcTrafficEntry 30 }

mscAtmIfVpcFwdQosClass OBJECT-TYPE
   SYNTAX     INTEGER  {
                 n0(0),
                 n1(1),
                 n2(2),
                 n3(3),
                 n4(4),
                 notApplicable(14) }
   ACCESS     read-only
   STATUS     obsolete
   DESCRIPTION
     "This attribute is HISTORICAL. Please refer to the attribute of the 
      same name in the group AtmTmOper.
      
      This attribute indicates the quality of service for the calling to called 
      direction for this connection. This is only applicable to Soft PVC 
      and SVC connections. 
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified QOS class; no objective is specified for 
      the performance parameters.
      
      A value of notApplicable is displayed in the case of nailed-up PVCs 
      for which this attribute has no significance."
::= { mscAtmIfVpcTrafficEntry 31 }

mscAtmIfVpcTxQueueLength OBJECT-TYPE
   SYNTAX     INTEGER (0..30720)
   ACCESS     read-only
   STATUS     obsolete
   DESCRIPTION
     "This attribute is HISTORICAL. Please refer to the attribute of the 
      same name in the group AtmTmOper.
      
      This attribute indicates the current length of the transmit queue for 
      this connection. If this connection has traffic shaping disabled, then 
      this attribute displays the common queue length. If traffic shaping is 
      enabled, then this attribute displays the per-VC queue length."
::= { mscAtmIfVpcTrafficEntry 32 }

mscAtmIfVpcTxQueueCongestionState OBJECT-TYPE
   SYNTAX     INTEGER (0..3)
   ACCESS     read-only
   STATUS     obsolete
   DESCRIPTION
     "This attribute is HISTORICAL. Please refer to the attribute of the 
      same name in the group AtmTmOper.
      
      This attribute indicates the congestion state of the transmit queue 
      for this connection. If the connection has traffic shaping disabled, 
      then this attribute displays the common queue congestion state. If 
      traffic shaping is enabled, then this attribute displays the per-VC 
      queue congestion state.
      
      The congestion state of a queue is indicated by a numeric value 
      ranging from 0 to 3. When a queue is in a congested state x, only 
      traffic with discard priority (DP) 0 to x are enqueued. Traffic with 
      DP > x is discarded. 
      
      Therefore, if the congestion state is 3, there is no congestion and all 
      traffic is enqueued. Likewise, when the congestion state is 0, there 
      is maximum congestion and only traffic with DP=0 is enqueued on 
      that queue."
::= { mscAtmIfVpcTrafficEntry 33 }

mscAtmIfVpcHoldingPriority OBJECT-TYPE
   SYNTAX     INTEGER  {
                 n0(0),
                 n1(1),
                 n2(2),
                 n3(3),
                 n4(4),
                 notApplicable(6) }
   ACCESS     read-only
   STATUS     obsolete
   DESCRIPTION
     "This attribute is HISTORICAL. Please refer to the attribute of the 
      same name in the group AtmTmOper.
      
      This attribute indicates the actual holding priority in effect for this 
      connection. In a situation where the link bandwidth fluctuates, such 
      as over an IMA link, holding priority is used to determine which 
      connections are held and which are released. Holding priority 4 
      connections are the first to be released. Holding priority 0 
      connections are the last to be released. Some applications, for 
      example Vcc Test, may override the provisioned holding priority. 
      
      A value of notApplicable is displayed when this is an elastic 
      connection. Holding priority does not apply to bandwidth elastic 
      connections.
      
      Holding priority has no effect for ubr atmServiceCategory or 
      txTrafficDescriptorType 1 or 2 connections."
::= { mscAtmIfVpcTrafficEntry 35 }

mscAtmIfVpcRxTrafficDescType OBJECT-TYPE
   SYNTAX     INTEGER  {
                 n1(1),
                 n2(2),
                 n3(3),
                 n4(4),
                 n5(5),
                 n6(6),
                 n7(7),
                 n8(8) }
   ACCESS     read-only
   STATUS     obsolete
   DESCRIPTION
     "This attribute is HISTORICAL. Please refer to the attribute of the 
      same name in the group AtmTmOper.
      
      This attribute indicates the type of traffic management which is 
      applied to the receive direction of this connection as defined in the 
      ATM Forum. The rxTrafficDescType determines the number and 
      meaning of the parameters in the rxTrafficDescParm attribute."
::= { mscAtmIfVpcTrafficEntry 40 }

mscAtmIfVpcRxQosClass OBJECT-TYPE
   SYNTAX     INTEGER  {
                 unspecified(0),
                 constantBitRate(1),
                 variableBitRate(2),
                 connectionOriented(3),
                 connectionless(4) }
   ACCESS     read-only
   STATUS     obsolete
   DESCRIPTION
     "This attribute reflects the value of the provisioned attribute in the 
      Vcd or Vpd. Refer to that attribute for more detailed explanation. 
      
      This attribute is obsolete replaced by the UNI 4.0 attribute 
      atmServiceCategory."
::= { mscAtmIfVpcTrafficEntry 60 }

mscAtmIfVpcBwdQosClass OBJECT-TYPE
   SYNTAX     INTEGER  {
                 n0(0),
                 n1(1),
                 n2(2),
                 n3(3),
                 n4(4),
                 notApplicable(14) }
   ACCESS     read-only
   STATUS     obsolete
   DESCRIPTION
     "This attribute is HISTORICAL. Please refer to the attribute of the 
      same name in the group AtmTmOper.
      
      This attribute indicates the quality of service for the called to calling 
      direction for this connection. This is only applicable to Soft PVC 
      and SVC connections. 
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified QOS class; no objective is specified for 
      the performance parameters.
      
      A value of notApplicable is displayed in the case of nailed-up PVCs 
      for which this attribute has no significance."
::= { mscAtmIfVpcTrafficEntry 61 }

mscAtmIfVpcAtmServiceCategory OBJECT-TYPE
   SYNTAX     INTEGER  {
                 unspecifiedBitRate(0),
                 constantBitRate(1),
                 rtVariableBitRate(2),
                 nrtVariableBitRate(3) }
   ACCESS     read-only
   STATUS     obsolete
   DESCRIPTION
     "This attribute is HISTORICAL. Please refer to the attribute of the 
      same name in the group AtmTmOper.
      
      This attribute indicates the ATM service category used for traffic in 
      both directions of the connection. 
      
      The constantBitRate service category is intended for real time 
      applications, that is, those requiring tightly constrained delay and 
      delay variation, as would be appropriate for voice and video 
      applications. The consistent availability of a fixed quantity of 
      bandwidth is considered appropriate for CBR service. Cells which 
      are delayed beyond the value specified by Cell Transfer Delay are 
      assumed to have significantly reduced value of the application.
      
      The rtVariableBitRate service category is intended for real time 
      applications; that is those requiring tightly constrained delay and 
      delay variation, as would be appropriate for voice and video 
      applications. Sources are expected to transmit at a rate which varies 
      with time. Equivalently, the source can be described as 'bursty'. 
      Cells which are delayed beyond the value specified by Cell Transfer 
      Delay are assumed to be of significantly reduced value to the 
      application. Real time VBR service may support statistical 
      multiplexing of real time sources.
      
      The nrtVariableBitRate service category is intended for non-real 
      time applications which have bursty traffic characteristics and which 
      can be characterized in terms of a PCR, SCR, and MBS. For those 
      cells which are transferred within the traffic contract, the application 
      expects a low cell loss ratio. For all connections, it expects a bound 
      on the mean cell transfer delay. Non-real time VBR service may 
      support statistical multiplexing of connections.
      
      The unspecifiedBitRate service is intended for non-real time 
      applications, that is those not requiring tightly constrained delay 
      and delay variation. UBR sources are expected to be bursty. UBR 
      service supports a high degree of statistical multiplexing among 
      sources. UBR service does not specify traffic related service 
      guarantees. No numerical commitments are made with respect to 
      the cell loss ratio experienced by a UBR connection, or as to the 
      cell transfer delay experienced by cells on the connection."
::= { mscAtmIfVpcTrafficEntry 62 }

mscAtmIfVpcTrafficShaping OBJECT-TYPE
   SYNTAX     INTEGER  {
                 enabled(0),
                 disabled(1),
                 notApplicable(4) }
   ACCESS     read-only
   STATUS     obsolete
   DESCRIPTION
     "This attribute is HISTORICAL. Please refer to the attribute of the 
      same name in the group AtmTmOper.
      
      This attribute indicates the traffic shaping state of the connection.
      
      A value of notApplicable indicates that traffic shaping is not 
      applicable or not supported for this connection. This is the case 
      when the atmServiceCategory is constantBitRate, or when the 
      txTrafficDescType is 1 or 2. In these cases, the value of 
      notApplicable is set regardless of whether traffic shaping is enabled 
      or disabled in the provisioning data.
      
      A value of disabled indicates that traffic shaping is applicable and 
      supported for the type of connection but has been turned off in the 
      provisioning data.
      
      A value of enabled indicates that traffic shaping is applicable and 
      supported for the type of connection and has been turned on in the 
      provisioning data. This is the only case that indicates that traffic 
      shaping is performed on the connection. In this case, the actual 
      shaping rate is reflected in the txTrafficDescParm attribute, 
      parameter number 4."
::= { mscAtmIfVpcTrafficEntry 70 }

mscAtmIfVpcBearerClassBbc OBJECT-TYPE
   SYNTAX     INTEGER  {
                 a(1),
                 c(3),
                 x(16),
                 vp(24),
                 notApplicable(30) }
   ACCESS     read-only
   STATUS     obsolete
   DESCRIPTION
     "This attribute is HISTORICAL. Please refer to the attribute of the 
      same name in the group AtmTmOper.
      
      This attribute indicates the bearer capability for this connection.
      
      Class a service is a connection-oriented, constant bit rate ATM 
      transport service. Class a service has end to end timing 
      requirements and may require stringent cell loss, cell delay and cell 
      delay variation performance.When a is displayed, the user is 
      requesting more than an ATM only service. The network may look 
      at the AAL to provide interworking based upon its contents. 
      
      Class c service is a connection-oriented, variable bit rate ATM 
      transport service. Class c service has no end-to-end timing 
      requirements.When c is displayed, the user is requesting more than 
      an ATM only service. The network interworking function may look 
      at the AAL and provide service based on it.
      
      Class x service is a connection-oriented ATM transport service 
      where the AAL, trafficType (cbr or vbr) and timing requirements 
      are user defined (that is, transparent to the network). When the 
      value of this attribute is x, the user is requesting an ATM only 
      service from the network. In this case, the network shall not process 
      any higher layer protocol.
      
      Class vp service is used to indicate a transparent VP service when 
      the user is requesting an ATM only service from the network. In this 
      case, the network does not process any higher layer protocol. This 
      service differs from class x service in that with the class vp service 
      both the VCI field (except for VCI values 0, 3, 4, and 6 through 15) 
      and Payload Type field are transported transparently by the network. 
      This attribute value is only applicable to SPVP and SVP 
      connections.
      
      A value of notApplicable is displayed in the case of nailed-up PVCs 
      for which this attribute has no significance."
::= { mscAtmIfVpcTrafficEntry 71 }

mscAtmIfVpcTransferCapabilityBbc OBJECT-TYPE
   SYNTAX     INTEGER  {
                 n0(0),
                 n1(1),
                 n2(2),
                 n5(5),
                 n8(8),
                 n9(9),
                 n10(10),
                 notApplicable(30) }
   ACCESS     read-only
   STATUS     obsolete
   DESCRIPTION
     "This attribute is HISTORICAL. Please refer to the attribute of the 
      same name in the group AtmTmOper.
      
      This attribute indicates the transfer capability for this connection. 
      Uni 3.0/3.1 traffic type and end-to-end timing parameters are 
      mapped into this parameter as follows:
      <transferCapability: TrafficType, Timing>
      0: NoIndication, NoIndication
      1: NoIndication, yes
      2: NoIndication, no
      5: CBR, yes
      8: VBR, NoIndication
      9: VBR, yes
      10: VBR, no
      
      A value of notApplicable is displayed in the case of nailed-up PVCs 
      for which this attribute has no significance, or in the case that the 
      transfer capability in the call request was set to NoIndication.
      
      The CBR traffic type refers to traffic offered on services such as a 
      constant bit rate video service or a circuit emulation.
      
      The VBR traffic type refers to traffic offered on services such as 
      packetized audio and video, or data.
      
      The value NoIndication for traffic type is used if the user has not set 
      the traffic type; similarly for end-to-end timing.
      
      The value yes for end-to-end timing indicates that end-to-end 
      timing is required for the connection.
      
      The value no for end-to-end timing indicates that end-to-end timing 
      is not required for the connection."
::= { mscAtmIfVpcTrafficEntry 72 }

mscAtmIfVpcClippingBbc OBJECT-TYPE
   SYNTAX     INTEGER  {
                 no(0),
                 yes(1),
                 notApplicable(14) }
   ACCESS     read-only
   STATUS     obsolete
   DESCRIPTION
     "This attribute is HISTORICAL. Please refer to the attribute of the 
      same name in the group AtmTmOper.
      
      This attribute indicates the value of the clipping susceptibility 
      parameter in the BBC Information Element.
      
      Clipping is an impairment in which the first fraction of a second of 
      information to be transferred is lost. It occurs after a call is 
      answered and before an associated connection is switched through.
      
      A value of notApplicable is displayed in the case of nailed-up PVCs 
      for which this attribute has no significance."
::= { mscAtmIfVpcTrafficEntry 74 }

mscAtmIfVpcUnshapedTransmitQueueing OBJECT-TYPE
   SYNTAX     INTEGER  {
                 perVc(0),
                 common(1),
                 notApplicable(4) }
   ACCESS     read-only
   STATUS     obsolete
   DESCRIPTION
     "This attribute is HISTORICAL. Please refer to the attribute of the 
      same name in the group AtmTmOper.
      
      This attribute indicates the unshaped transmit queuing state of the 
      connection.
      
      A value of common indicates that transmit traffic is being enqueued 
      onto common transmit queues. 
      
      A value of perVc indicates that transmit traffic is being enqueued 
      onto a per-VC queue for this connection. This is the case when 
      trafficShaping is disabled, but per-VC queueing has been 
      configured for this connection. 
      
      A value of notApplicable indicates that transmit traffic is being 
      shaped for this connection. Transmit traffic for a shaped connection 
      is enqueued onto a per-VC queue, but this attribute is only 
      applicable for unshaped connections."
::= { mscAtmIfVpcTrafficEntry 75 }

mscAtmIfVpcBestEffort OBJECT-TYPE
   SYNTAX     INTEGER  {
                 indicated(0),
                 notIndicated(1),
                 notApplicable(14) }
   ACCESS     read-only
   STATUS     obsolete
   DESCRIPTION
     "This attribute is HISTORICAL. Please refer to the attribute of the 
      same name in the group AtmTmOper.
      
      This attribute indicates value of best effort parameter in the ATM 
      Traffic Descriptor Information Element.
      
      The value indicated implies that the quality of service for this 
      connection is not guaranteed.
      
      The value notIndicated implies that the quality of service for this 
      connection is guaranteed.
      
      A value of notApplicable is displayed in the case of nailed-up PVCs 
      for which this attribute has no significance."
::= { mscAtmIfVpcTrafficEntry 76 }

mscAtmIfVpcUsageParameterControl OBJECT-TYPE
   SYNTAX     INTEGER  {
                 enabled(0),
                 disabled(1),
                 notApplicable(3) }
   ACCESS     read-only
   STATUS     obsolete
   DESCRIPTION
     "This attribute is HISTORICAL. Please refer to the attribute of the 
      same name in the group AtmTmOper.
      
      This attribute indicates the UPC state of the connection.
      
      A value of notApplicable indicates that UPC is not applicable or not 
      supported for the connection. This is the case when the connection's 
      rxTrafficDescType is 1 or 2. A value of notApplicable is set 
      regardless of whether UPC is disabled or enabled in provisioning 
      data.
      
      A value of disabled indicates that UPC is applicable and supported 
      for the type of connection but has been turned off in the 
      provisioning data.
      
      A value of enabled indicates that UPC is applicable and supported 
      for the type of connection and has been turned on in the 
      provisioning data. This is the only case that indicates that UPC is 
      enforced on the connection. In this case the traffic descriptor 
      parameters used for UPC enforcement are reflected in the 
      rxTrafficDescParms of the connection."
::= { mscAtmIfVpcTrafficEntry 80 }

mscAtmIfVpcTxFrameDiscard OBJECT-TYPE
   SYNTAX     OCTET STRING (SIZE (1))
   ACCESS     read-only
   STATUS     obsolete
   DESCRIPTION
     "This attribute is HISTORICAL. Please refer to the attribute of the 
      same name in the group AtmTmOper.
      
      This attribute indicates the set of current frame discard functions in 
      effect in the transmit data direction at this connection point.
      
      A value of ppd indicates that the Partial Packet Discard (PPD) 
      function is in effect. PPD may be applied at an interim connecting 
      point for a connection which is transporting frame traffic (AAL5 at 
      the endpoint). PPD is controlled by provisioning for PVCs and 
      SPVCs, and by call setup parameters in the AAL and Traffic 
      Descriptor Information Elements.
      
      A value of epd indicates that the Early Packet Discard (EPD) 
      function is in effect at this connection endpoint. PPD and EPD are 
      enabled by default at a connection endpoint which is performing 
      AAL5 segmentation and assembly.
      
      Frame discard functions are not applicable for Virtual Path 
      Connections (VPCs).

      Description of bits:
      ppd(0)
      epd(1)"
::= { mscAtmIfVpcTrafficEntry 85 }

mscAtmIfVpcRxFrameDiscard OBJECT-TYPE
   SYNTAX     OCTET STRING (SIZE (1))
   ACCESS     read-only
   STATUS     obsolete
   DESCRIPTION
     "This attribute is HISTORICAL. Please refer to the attribute of the 
      same name in the group AtmTmOper.
      
      This attribute indicates the set of current frame discard functions in 
      effect in the receive data direction at this connection point.
      
      A value of ppd indicates that the Partial Packet Discard (PPD) 
      function is in effect. PPD may be applied at an interim connecting 
      point for a connection which is transporting frame traffic (AAL5 at 
      the endpoint). PPD is controlled by provisioning for PVCs and 
      SPVCs, and by call setup parameters in the AAL and Traffic 
      Descriptor Information Elements.
      
      A value of epd indicates that the Early Packet Discard (EPD) 
      function is in effect at this connection endpoint. PPD and EPD are 
      enabled by default at a connection endpoint which is performing 
      AAL5 segmentation and assembly.
      
      Frame discard functions are not applicable for Virtual Path 
      Connections (VPCs).

      Description of bits:
      ppd(0)
      epd(1)"
::= { mscAtmIfVpcTrafficEntry 86 }

mscAtmIfVpcBandwidthElastic OBJECT-TYPE
   SYNTAX     INTEGER  {
                 no(0),
                 yes(1) }
   ACCESS     read-only
   STATUS     obsolete
   DESCRIPTION
     "This attribute is HISTORICAL. Please refer to the attribute of the 
      same name in the group AtmTmOper.
      
      This attribute is only of importance for connections which are 
      carried on a link with a variable bandwidth. For example, the 
      bandwidth may be reduced in the event that one or more physical 
      links in the IMA group fail, such that the originally requested 
      bandwidth cannot be maintained. This attribute shows whether the 
      application (for example, Trunk) running on this connection can 
      continue to operate if the bandwidth is reduced. If the bandwidth is 
      reduced, the amount by which it is reduced is displayed in the 
      bandwidthReduction attribute. 
      
      A value of yes, indicates that this connection is elastic, and the 
      bandwidth may be reduced but the connection is not released. 
      
      A value of no indicates that the bandwidth for this connection is not 
      reduced in the event of link bandwidth reduction. However, this 
      connection may be released based on its holdingPriority.
      
      Bandwidth elasticity has no effect for ubr atmServiceCategory or 
      txTrafficDescriptorType 1 or 2 connections."
::= { mscAtmIfVpcTrafficEntry 90 }

mscAtmIfVpcBandwidthReduction OBJECT-TYPE
   SYNTAX     INTEGER (0..2147483647)
   ACCESS     read-only
   STATUS     obsolete
   DESCRIPTION
     "This attribute is HISTORICAL. Please refer to the attribute of the 
      same name in the group AtmTmOper.
      
      This attribute shows the amount by which the bandwidth has been 
      reduced for this connection. This value is non-zero only for 
      connections which have bandwidthElastic displayed as yes, and 
      which are also operating in a reduced bandwidth mode. This is 
      typically be the case for selected connections running over an IMA 
      link. This attribute takes a value from 0 (no reduction) up to the 
      ECR. All connections which are running at their full allocated 
      bandwidth, bwReduction have the value 0. Connections which have 
      been reduced in allocated bandwidth have a positive number for this 
      attribute. The bwReduction may be subtracted from the ECR (which 
      is displayed as txTrafficDescParm 5) to determine the actual 
      bandwidth allocated to this connection."
::= { mscAtmIfVpcTrafficEntry 100 }

mscAtmIfVpcStatsTable OBJECT-TYPE
   SYNTAX     SEQUENCE OF MscAtmIfVpcStatsEntry
   ACCESS     not-accessible
   STATUS     mandatory
   DESCRIPTION
     "This group contains traffic statistics for a Vcc, Vpc, or Vpt 
      component."
::= { mscAtmIfVpc 140 }

mscAtmIfVpcStatsEntry OBJECT-TYPE
   SYNTAX     MscAtmIfVpcStatsEntry
   ACCESS     not-accessible
   STATUS     mandatory
   DESCRIPTION
     "An entry in the mscAtmIfVpcStatsTable."
   INDEX {
      mscAtmIfIndex,
      mscAtmIfVpcIndex }
::= { mscAtmIfVpcStatsTable 1 }

MscAtmIfVpcStatsEntry ::= SEQUENCE {
   mscAtmIfVpcStatsTxCell
      PassportCounter64,
   mscAtmIfVpcStatsTxCellClp
      PassportCounter64,
   mscAtmIfVpcTxDiscard
      PassportCounter64,
   mscAtmIfVpcTxDiscardClp
      PassportCounter64,
   mscAtmIfVpcStatsTxCellDiscard
      PassportCounter64,
   mscAtmIfVpcStatsTxCellDiscardClp
      PassportCounter64,
   mscAtmIfVpcStatsTxFrameDiscard
      PassportCounter64,
   mscAtmIfVpcStatsTxFrameDiscardClp
      PassportCounter64,
   mscAtmIfVpcStatsRxCell
      PassportCounter64,
   mscAtmIfVpcStatsRxCellClp
      PassportCounter64,
   mscAtmIfVpcRxDiscard
      PassportCounter64,
   mscAtmIfVpcRxDiscardClp
      PassportCounter64,
   mscAtmIfVpcStatsRxCellDiscard
      PassportCounter64,
   mscAtmIfVpcStatsRxCellDiscardClp
      PassportCounter64,
   mscAtmIfVpcStatsRxFrameDiscard
      PassportCounter64,
   mscAtmIfVpcStatsRxFrameDiscardClp
      PassportCounter64,
   mscAtmIfVpcStatsRxUpcViolationOnEnforcer1
      PassportCounter64,
   mscAtmIfVpcStatsRxUpcViolationOnEnforcer2
      PassportCounter64,
   mscAtmIfVpcStatsRxAal5FrameError
      PassportCounter64,
   mscAtmIfVpcStatsRxAal5FrameAbort
      PassportCounter64 }

mscAtmIfVpcStatsTxCell OBJECT-TYPE
   SYNTAX     PassportCounter64 
   ACCESS     read-only
   STATUS     mandatory
   DESCRIPTION
     "This attribute counts the number of cells that have been transmitted 
      from the interface on this connection. The counter wraps to zero if it 
      exceeds its maximum value of (2**64)-1."
::= { mscAtmIfVpcStatsEntry 10 }

mscAtmIfVpcStatsTxCellClp OBJECT-TYPE
   SYNTAX     PassportCounter64 
   ACCESS     read-only
   STATUS     mandatory
   DESCRIPTION
     "This attribute counts the number of cells that have been transmitted 
      from the interface on this connection with the CLP=1. The counter 
      wraps to zero if it exceeds its maximum value of (2**64)-1."
::= { mscAtmIfVpcStatsEntry 20 }

mscAtmIfVpcTxDiscard OBJECT-TYPE
   SYNTAX     PassportCounter64 
   ACCESS     read-only
   STATUS     obsolete
   DESCRIPTION
     "This attribute is replaced by new attributes txCellDiscard and 
      txFrameDiscard.
      
      This attribute counts the number of cells or frames received from 
      the bus on this connection that have been discarded.
      
      If the connection segments frames into cells, the counter indicates 
      the number of frames discarded. Connections which segment 
      frames into cells have a connectionPointType of 
      connectionEndPoint.
      
      If the connection relays cells without adaptation, the counter 
      indicates the number of cells discarded. Connections which relay 
      cells without adaptation have a connectionPointType of 
      segmentEndPoint or connectingPoint.
      
      AAL1 connections are an exception to this rule; although they have 
      a connectionPointType of connectionEndPoint, they do not do 
      adaptation at this point. Thus, in the AAL1 case, this attribute 
      counts discarded cells.
      
      Discards are done due to congestion or when the connection's 
      interface is disabled.
      
      The counter wraps to zero if it exceeds its maximum value of 
      (2**64)-1."
::= { mscAtmIfVpcStatsEntry 30 }

mscAtmIfVpcTxDiscardClp OBJECT-TYPE
   SYNTAX     PassportCounter64 
   ACCESS     read-only
   STATUS     obsolete
   DESCRIPTION
     "This attribute is replaced by new attributes txCellDiscardClp and 
      txFrameDiscardClp.
      
      This attribute counts the number of cells or frames received from 
      the bus on this connection with CLP=1 that have been discarded.
      
      If the connection segments frames into cells, the counter indicates 
      the number of frames discarded. Connections which segment 
      frames into cells have a connectionPointType of 
      connectionEndPoint.
      
      If the connection relays cells without adaptation, the counter 
      indicates the number of cells discarded. Connections which relay 
      cells without adaptation have a connectionPointType of 
      segmentEndPoint or connectingPoint.
      
      AAL1 connections are an exception to this rule; although they have 
      a connectionPointType of connectionEndPoint, they do not do 
      adaptation at this point. Thus, in the AAL1 case, this attribute 
      counts discarded cells.
      
      Discards are done due to congestion or when the connection's 
      interface is disabled.
      
      The counter wraps to zero if it exceeds its maximum value of 
      (2**64)-1."
::= { mscAtmIfVpcStatsEntry 40 }

mscAtmIfVpcStatsTxCellDiscard OBJECT-TYPE
   SYNTAX     PassportCounter64 
   ACCESS     read-only
   STATUS     mandatory
   DESCRIPTION
     "This attribute counts the number of cells received from the bus on 
      this connection that have been discarded.
      
      Discarded cells are not counted in the txCell attribute.
      
      Cells are discarded due to transmit congestion, Partial Packet 
      Discard (PPD), Early Packet Discard (EPD), and Weighted Random 
      Early Detection (W-RED) mechanisms, or when the connection's 
      interface is disabled.
      
      For CQC-based ATM cards, this attribute is applicable only to 
      connections that relay cells without adaptation. Such connections 
      usually have a connectionPointType of segmentEndPoint or 
      connectingPoint. AAL1 connections are an exception to this rule; 
      although they have a connectionPointType of connectionEndPoint, 
      they do not do adaptation at this point. For Vpts, this attribute 
      provides an aggregated total of all txCellDiscard values for all such 
      connections associated with the Vpt.
      
      For Vccs on CQC-based ATM cards, if the connection segments 
      frames into cells, this attribute is not applicable and is not 
      displayed.
      
      The counter wraps to zero if it exceeds its maximum value of 
      (2**64)-1."
::= { mscAtmIfVpcStatsEntry 42 }

mscAtmIfVpcStatsTxCellDiscardClp OBJECT-TYPE
   SYNTAX     PassportCounter64 
   ACCESS     read-only
   STATUS     mandatory
   DESCRIPTION
     "This attribute counts the number of cells received from the bus on 
      this connection with CLP=1 that have been discarded.
      
      This count is included in the txCellDiscard attribute. Discarded 
      cells are not counted in the txCellClp attribute.
      
      Cells are discarded due to transmit congestion, Partial Packet 
      Discard (PPD), Early Packet Discard (EPD), and Weighted Random 
      Early Detection (W-RED) mechanisms, or when the connection's 
      interface is disabled.
      
      For CQC-based ATM cards, this attribute is applicable only to 
      connections that relay cells without adaptation. Such connections 
      have a connectionPointType of segmentEndPoint or 
      connectingPoint. AAL1 connections are an exception to this rule; 
      although they have a connectionPointType of connectionEndPoint, 
      they do not do adaptation at this point. For Vpts, this attribute 
      provides an aggregated total of all txCellDiscardClp values for all 
      such connections associated with the Vpt.
      
      For Vccs on CQC-based ATM cards, if the connection segments 
      frames into cells, this attribute is not applicable and is not 
      displayed.
      
      The counter wraps to zero if it exceeds its maximum value of 
      (2**64)-1."
::= { mscAtmIfVpcStatsEntry 43 }

mscAtmIfVpcStatsTxFrameDiscard OBJECT-TYPE
   SYNTAX     PassportCounter64 
   ACCESS     read-only
   STATUS     mandatory
   DESCRIPTION
     "This attribute counts the number of frames received from the bus on 
      this connection that have been discarded.
      
      Frames are discarded due to congestion, Partial Packet Discard 
      (PPD), Early Packet Discard (EPD), and Weighted Random Early 
      Detection (W-RED) mechanisms, or when the connection interface 
      is disabled.
      
      This count is independent of the txCell or txCellDiscard attribute.
      
      For CQC-based ATM cards, this attribute is applicable only to 
      connections that segment frames into cells. Such connections have a 
      connectionPointType of connectionEndPoint. AAL1 connections 
      are an exception to this rule; although they have a 
      connectionPointType of connectionEndPoint, they do not do 
      adaptation at this point. For Vpts, this attribute provides an 
      aggregated total of all txFrameDiscard values for all such 
      connections associated with the Vpt.
      
      For CQC-based ATM cards, for Vpcs, and Vccs that relay cells 
      without adaptation, this attribute is not applicable and is not 
      displayed.
      
      Discards due to EPD, PPD, and W-RED for a standard Vpt Vcc are 
      not included in this attribute. These discards are counted in the 
      Vcc's parent Vpt txFrameDiscard attribute.
      
      The counter wraps to zero if it exceeds its maximum value of 
      (2**64)-1."
::= { mscAtmIfVpcStatsEntry 46 }

mscAtmIfVpcStatsTxFrameDiscardClp OBJECT-TYPE
   SYNTAX     PassportCounter64 
   ACCESS     read-only
   STATUS     mandatory
   DESCRIPTION
     "This attribute counts the number of discarded frames on this 
      connection that were received from the bus and composed of one or 
      more CLP=1 cells.
      
      Frames are discarded due to congestion, Partial Packet Discard 
      (PPD), Early Packet Discard (EPD), and Weighted Random Early 
      Detection (W-RED) mechanisms, or when the connection interface 
      is disabled.
      
      This count is included in the txFrameDiscard attribute.
      
      For CQC-based ATM cards, this attribute is applicable only to 
      connections that segment frames into cells. Such connections have a 
      connectionPointType of connectionEndPoint. AAL1 connections 
      are an exception to this rule; although they have a 
      connectionPointType of connectionEndPoint, they do not do 
      adaptation at this point. For Vpts, this attribute provides an 
      aggregated total of all txFrameDiscardClp values for all such 
      connections associated with the Vpt.
      
      For CQC-based ATM cards, for Vpcs and Vccs that relay cells 
      without adaptation, this attribute is not applicable and is not 
      displayed.
      
      
      Discards due to EPD, PPD, and W-RED for a standard Vpt Vcc are 
      not included in this attribute. These discards are counted in the 
      Vcc's parent Vpt txFrameDiscardClp attribute.
      
      The counter wraps to zero if it exceeds its maximum value of 
      (2**64)-1."
::= { mscAtmIfVpcStatsEntry 47 }

mscAtmIfVpcStatsRxCell OBJECT-TYPE
   SYNTAX     PassportCounter64 
   ACCESS     read-only
   STATUS     mandatory
   DESCRIPTION
     "This attribute counts the number of cells that have been received 
      from the interface on this connection. The counter wraps to zero if it 
      exceeds its maximum value of (2**64)-1."
::= { mscAtmIfVpcStatsEntry 50 }

mscAtmIfVpcStatsRxCellClp OBJECT-TYPE
   SYNTAX     PassportCounter64 
   ACCESS     read-only
   STATUS     mandatory
   DESCRIPTION
     "This attribute counts the number of cells that have been received 
      from the interface on this connection with the CLP=1. The counter 
      wraps to zero if it exceeds its maximum value of (2**64)-1."
::= { mscAtmIfVpcStatsEntry 60 }

mscAtmIfVpcRxDiscard OBJECT-TYPE
   SYNTAX     PassportCounter64 
   ACCESS     read-only
   STATUS     obsolete
   DESCRIPTION
     "This attribute is replaced by new attributes rxCellDiscard and 
      rxFrameDiscard.
      
      This attribute counts the number of cells or frames received from 
      the interface on this connection that have been discarded.
      
      If the connection segments frames into cells, the counter indicates 
      the number of frames discarded. Connections which segment 
      frames into cells have a connectionPointType of 
      connectionEndPoint.
      
      If the connection relays cells without adaptation, the counter 
      indicates the number of cells discarded. Connections which relay 
      cells without adaptation have a connectionPointType of 
      segmentEndPoint or connectingPoint.
      
      AAL1 connections are an exception to this rule; although they have 
      a connectionPointType of connectionEndPoint, they do not do 
      adaptation at this point. Thus, in the AAL1 case, this attribute 
      counts discarded cells.
      
      Discards are done due to congestion, non-conformance with UPC or 
      AAL reassembly problems.
      
      The counter wraps to zero if it exceeds its maximum value of 
      (2**64)-1."
::= { mscAtmIfVpcStatsEntry 70 }

mscAtmIfVpcRxDiscardClp OBJECT-TYPE
   SYNTAX     PassportCounter64 
   ACCESS     read-only
   STATUS     obsolete
   DESCRIPTION
     "This attribute is replaced by new attributes rxCellDiscardClp and 
      rxFrameDiscardClp.
      
      This attribute counts the number of cells or frames received from 
      the interface on this connection with CLP=1 that have been 
      discarded.
      
      If the connection segments frames into cells, the counter indicates 
      the number of frames discarded. Connections which segment 
      frames into cells have a connectionPointType of 
      connectionEndPoint.
      
      If the connection relays cells without adaptation, the counter 
      indicates the number of cells discarded. Connections which relay 
      cells without adaptation have a connectionPointType of 
      segmentEndPoint or connectingPoint.
      
      AAL1 connections are an exception to this rule; although they have 
      a connectionPointType of connectionEndPoint, they do not do 
      adaptation at this point. Thus, in the AAL1 case, this attribute 
      counts discarded cells.
      
      Discards are done due to congestion, non-conformance with UPC or 
      AAL reassembly problems.
      
      The counter wraps to zero if it exceeds its maximum value of 
      (2**64)-1."
::= { mscAtmIfVpcStatsEntry 80 }

mscAtmIfVpcStatsRxCellDiscard OBJECT-TYPE
   SYNTAX     PassportCounter64 
   ACCESS     read-only
   STATUS     mandatory
   DESCRIPTION
     "This attribute counts the number of cells received from the interface 
      on this connection that have been discarded. This count is included 
      in the rxCell attribute.
      
      This count includes cells discarded due to non-conformance with 
      UPC, cells which are part of a frame which has been discarded due 
      to an AAL5 frame reassembly error, cells which are discarded due 
      to congestion, or cells which are received while the next hop 
      connection to which the traffic is directed across the backplane is 
      down. The next hop connection is the Vcc or Vpc identified by the 
      nextHop attribute of the Nrp or Rp component. 
      
      For CQC-based ATM cards, this attribute is applicable only to 
      connections that relay cells without adaptation. Such connections 
      have a connectionPointType of connectionEndPoint or 
      connectingPoint. AAL1 connections are an exception to this rule; 
      although they have a connectionPointType of connectionEndPoint, 
      they do not do adaptation at this point. For Vpts, this attribute 
      provides an aggregated total of all rxCellDiscard values for all such 
      connections associated with the Vpt.
      
      For CQC-based ATM cards, for Vpcs, and Vccs that relay cells 
      without adaptation, this attribute is not applicable and is not 
      displayed.
      
      Discards due to non-conformance with UPC at the VP layer, for a 
      standard Vpt Vcc, are not included in this attribute. These discards 
      are counted in the Vcc's parent Vpt rxCellDiscard attribute. 
      
      The counter wraps to zero if it exceeds its maximum value of 
      (2**64)-1."
::= { mscAtmIfVpcStatsEntry 82 }

mscAtmIfVpcStatsRxCellDiscardClp OBJECT-TYPE
   SYNTAX     PassportCounter64 
   ACCESS     read-only
   STATUS     mandatory
   DESCRIPTION
     "This attribute counts the number of cells received from the interface 
      on this connection with CLP=1 that have been discarded. This count 
      is included in the rxCell and rxCellDiscard attributes.
      
      This count includes cells discarded due to non-conformance with 
      UPC, cells which are part of a frame which has been discarded due 
      to an AAL5 frame reassembly error, cells which are discarded due 
      to congestion, or cells which are received while the next hop 
      connection to which the traffic is directed across the backplane is 
      down. The next hop connection is the Vcc or Vpc identified by the 
      nextHop attribute of the Nrp or Rp component. 
      
      For CQC-based ATM cards, this attribute is applicable only to 
      connections that relay cells without adaptation. Such connections 
      have a connectionPointType of connectionEndPoint or 
      connectingPoint. AAL1 connections are an exception to this rule; 
      although they have a connectionPointType of connectionEndPoint, 
      they do not do adaptation at this point. For Vpts, this attribute 
      provides an aggregated total of all rxCellDiscard values for all such 
      connections associated with the Vpt.
      
      For CQC-based ATM cards, for Vpcs, and Vccs that relay cells 
      without adaptation, this attribute is not applicable and is not 
      displayed.
      
      Discards due to non-conformance with UPC at the VP layer, for a 
      standard Vpt Vcc, are not included in this attribute. These discards 
      are counted in the Vcc's parent Vpt rxCellDiscard attribute.
      
      The counter wraps to zero if it exceeds its maximum value of 
      (2**64)-1."
::= { mscAtmIfVpcStatsEntry 83 }

mscAtmIfVpcStatsRxFrameDiscard OBJECT-TYPE
   SYNTAX     PassportCounter64 
   ACCESS     read-only
   STATUS     mandatory
   DESCRIPTION
     "This attribute counts the number of frames received from the 
      interface on this connection that have been discarded. This count is 
      independent of the rxCellDiscard attribute.
      
      This count includes frames discarded due to an AAL5 frame 
      reassembly error, frames discarded due to early packet discard 
      (EPD), and frames discarded due to processor (CPU) congestion. 
      This attribute is applicable only to connections that reassemble 
      incoming cells into frames. Connections which reassemble cells 
      into frames have a connectionPointType of connectionEndPoint. 
      AAL1 connections are an exception to this rule; even though they 
      have a connectionPointType of connectionEndPoint, they do not 
      do adaptation at this point. For Vpts, this attribute provides an 
      aggregated total of all rxFrameDiscard values for all applicable 
      connections associated with the Vpt.
      
      For Vpcs and for Vccs that relay cells without adaptation, this 
      attribute is not applicable and is not displayed.
      
      The counter wraps to zero if it exceeds its maximum value of 
      (2**64)-1."
::= { mscAtmIfVpcStatsEntry 86 }

mscAtmIfVpcStatsRxFrameDiscardClp OBJECT-TYPE
   SYNTAX     PassportCounter64 
   ACCESS     read-only
   STATUS     mandatory
   DESCRIPTION
     "This attribute counts the number of discarded frames on this 
      connection that were received from the interface and composed of 
      one or more CLP1 cells. This count is included in the 
      rxFrameDiscard attribute. It is independent of the rxCellDiscard 
      attribute.
      
      This count includes frames discarded due to an AAL5 frame 
      reassembly error, frames discarded due to early packet discard 
      (EPD), and frames discarded due to processor (CPU) congestion. 
      This attribute is applicable only to connections that reassemble 
      incoming cells into frames. Such connections have a 
      connectionPointType of connectionEndPoint. AAL1 connections 
      are an exception to this rule; although they have a 
      connectionPointType of connectionEndPoint, they do not do 
      adaptation at this point. For Vpts, this attribute provides an 
      aggregated total of all rxFrameDiscardClp values for all applicable 
      connections associated with the Vpt.
      
      For Vpcs and for Vccs that relay cells without adaptation, this 
      attribute is not applicable and is not displayed.
      
      The counter wraps to zero if it exceeds its maximum value of 
      (2**64)-1."
::= { mscAtmIfVpcStatsEntry 88 }

mscAtmIfVpcStatsRxUpcViolationOnEnforcer1 OBJECT-TYPE
   SYNTAX     PassportCounter64 
   ACCESS     read-only
   STATUS     mandatory
   DESCRIPTION
     "This attribute counts the number of UPC violations observed by the 
      Generic Cell Rate Algorithm (GCRA) Enforcer 1. This attribute is 
      only applicable if UPC is enforced or monitored. This attribute is 
      not applicable for standard Vpt Vccs. This attribute is not applicable 
      and is not displayed on CQC-based ATM cards.
      
      When the value of rxTrafficDescType for this connection is 3, 4, 5, 
      6, 7 or 8, Enforcer 1 enforces conformance of traffic received from 
      the interface to PCR CLP0+1.
      
      When the value of rxTrafficDescType for this connection is 9, 
      Enforcer 1 performs the Dynamic Generic Cell Rate Algorithm 
      (DGCRA) used for the Available Bit Rate (ABR) service category.
      
      If UPC is enforced all non-conforming cells are discarded by this 
      enforcer. These discarded cells are included in rxCellDiscard. 
      
      For basic Vpts, this attribute provides an aggregated total of all 
      rxUpcViolationOnEnforcer1 values for the Vccs associated with the 
      Vpt.
      
      The counter wraps to zero if it exceeds its maximum value of 
      (2**64)-1."
::= { mscAtmIfVpcStatsEntry 90 }

mscAtmIfVpcStatsRxUpcViolationOnEnforcer2 OBJECT-TYPE
   SYNTAX     PassportCounter64 
   ACCESS     read-only
   STATUS     mandatory
   DESCRIPTION
     "This attribute counts the number of UPC violations observed by the 
      Generic Cell Rate Algorithm (GCRA) Enforcer 2. This attribute is 
      only applicable if UPC is enforced or monitored. This attribute is 
      not applicable for standard Vpt Vccs. This attribute is not applicable 
      and is not displayed on CQC-based ATM cards.
      
      Enforcer2 is applicable only if the rxTrafficDescType for this 
      connection is 4, 5, 6, 7 or 8.
      
      When the value of rxTrafficDescType 4 or 5, Enforcer 2 enforces 
      conformance of traffic received from the interface to PCR CLP0.
      
      When the value of rxTrafficDescType 6, Enforcer 2 enforces 
      conformance of traffic received from the interface to SCR CLP0+1.
      
      When the value of rxTrafficDescType 7 or 8, Enforcer 2 enforces 
      conformance of traffic received from the interface to SCR CLP0.
      
      If UPC is enforced, enforcer 2 discards non-conforming cells for 
      rxTrafficDescType values of 4, 6 and 7. It tags non-conforming cells 
      for rxTrafficDescType values of 5 and 8. Discarded cells are 
      counted in the rxCellDiscard attribute. 
      
      For basic Vpts, this attribute provides an aggregated total of all 
      rxUpcViolationOnEnforcer2 values for the Vccs associated with 
      the Vpt.
      
      The counter wraps to zero if it exceeds its maximum value of 
      (2**64)-1."
::= { mscAtmIfVpcStatsEntry 92 }

mscAtmIfVpcStatsRxAal5FrameError OBJECT-TYPE
   SYNTAX     PassportCounter64 
   ACCESS     read-only
   STATUS     mandatory
   DESCRIPTION
     "This attribute counts the number of frames received from the 
      interface on this connection that have AAL5 length errors or AAL5 
      CRC errors. 
      
      This attribute is not applicable and is not displayed on CQC-based 
      ATM cards.
      
      AAL5 length or CRC errors typically occur because of cell discards 
      due to congestion, UPC, or due to corruption of data between the 
      AAL5 segmentation and reassembly end points.
      
      This attribute is applicable only to connections that reassemble 
      incoming cells into frames. Such connections have a 
      connectionPointType of connectionEndPoint. AAL1 connections 
      are an exception to this rule; although they have a 
      connectionPointType of connectionEndPoint, they do not do 
      adaptation at this point. For Vpts, this attribute provides an 
      aggregated total of all rxAal5FrameError values for all applicable 
      connections associated with the Vpt.
      
      For Vpcs and for Vccs that relay cells without adaptation, this 
      attribute is not applicable and is not displayed.
      
      The counter wraps to zero if it exceeds its maximum value of 
      (2**64)-1."
::= { mscAtmIfVpcStatsEntry 100 }

mscAtmIfVpcStatsRxAal5FrameAbort OBJECT-TYPE
   SYNTAX     PassportCounter64 
   ACCESS     read-only
   STATUS     mandatory
   DESCRIPTION
     "This attribute counts the number of frames received from the 
      interface on this connection that have the AAL5 length field set to 
      zero. 
      
      This attribute is not applicable and is not displayed for CQC-based 
      ATM cards.
      
      An AAL5 length of zero is an indication by the far end 
      segmentation point to this reassembly point that the frame is to be 
      discarded without reassembly. This mechanism is typically used by 
      a segmentation point if it detects an error in a frame after some of 
      the cells belonging to that frame have already been transmitted.
      
      This attribute is applicable only to connections that reassemble 
      incoming cells into frames. Such connections have a 
      connectionPointType of connectionEndPoint. AAL1 connections 
      are an exception to this rule; although they have a 
      connectionPointType of connectionEndPoint, they do not do 
      adaptation at this point. For Vpts, this attribute provides an 
      aggregated total of all rxAal5FrameAbort values for all applicable 
      connections associated with the Vpt.
      
      For Vpcs and for Vccs that relay cells without adaptation, this 
      attribute is not applicable and is not displayed.
      
      The counter wraps to zero if it exceeds its maximum value of 
      (2**64)-1."
::= { mscAtmIfVpcStatsEntry 102 }

mscAtmIfVpcPerfTable OBJECT-TYPE
   SYNTAX     SEQUENCE OF MscAtmIfVpcPerfEntry
   ACCESS     not-accessible
   STATUS     mandatory
   DESCRIPTION
     "This group contains operational attributes which keep performance 
      statistics about the behavior of the AtmIf component."
::= { mscAtmIfVpc 150 }

mscAtmIfVpcPerfEntry OBJECT-TYPE
   SYNTAX     MscAtmIfVpcPerfEntry
   ACCESS     not-accessible
   STATUS     mandatory
   DESCRIPTION
     "An entry in the mscAtmIfVpcPerfTable."
   INDEX {
      mscAtmIfIndex,
      mscAtmIfVpcIndex }
::= { mscAtmIfVpcPerfTable 1 }

MscAtmIfVpcPerfEntry ::= SEQUENCE {
   mscAtmIfVpcLastMinimumCtd
      Unsigned32,
   mscAtmIfVpcLastMaximumCtd
      Unsigned32,
   mscAtmIfVpcLastAverageCtd
      Unsigned32,
   mscAtmIfVpcCurrentCtd
      Unsigned32,
   mscAtmIfVpcLastCtdSampleSize
      Unsigned32 }

mscAtmIfVpcLastMinimumCtd OBJECT-TYPE
   SYNTAX     Unsigned32 (0 | 1..2147483647)
   ACCESS     read-only
   STATUS     mandatory
   DESCRIPTION
     "This attribute indicates the minimum calculated cell transfer delay 
      value for this connection from the previous TODA (time of day 
      accounting) interval if TODA is enabled; or for the previous 12 hour 
      interval if TODA is disabled. Cell transfer delay is calculated as half 
      of the measured segment round trip delay of a loopback cell.
      
      The value is noMeasurement when the ctdCalculation attribute of 
      the AtmIf component is off.
      
      The value is noMeasurement when the accountCollection attribute 
      of the AtmIf Uni or AtmIf Iisp component has a non-empty reason.
      
      The value is noMeasurement when the segSwitchSideLoopback 
      attribute value is off for the connection.
      
      The value is noMeasurement when the switch-side loopback is not 
      working.
      
      The value is noMeasurement when the switch-side loopback status 
      cannot be determined.

      VALUES (

      0 = noMeasurement

      )"
::= { mscAtmIfVpcPerfEntry 10 }

mscAtmIfVpcLastMaximumCtd OBJECT-TYPE
   SYNTAX     Unsigned32 (0 | 1..2147483647)
   ACCESS     read-only
   STATUS     mandatory
   DESCRIPTION
     "This attribute indicates the maximum calculated cell transfer delay 
      value for this connection from the previous TODA (time of day 
      accounting) interval if TODA is enabled; or for the previous 12 hour 
      interval if TODA is disabled. Cell transfer delay is calculated as half 
      of the measured segment round trip delay of a loopback cell.
      
      The value is noMeasurement when the ctdCalculation attribute of 
      the AtmIf component is off.
      
      The value is noMeasurement when the accountCollection attribute 
      of the AtmIf Uni or AtmIf Iisp component has a non-empty reason.
      
      The value is noMeasurement when the segSwitchSideLoopback 
      attribute value is off for the connection.
      
      The value is noMeasurement when the switch-side loopback is not 
      working.
      
      The value is noMeasurement when the switch-side loopback status 
      cannot be determined.

      VALUES (

      0 = noMeasurement

      )"
::= { mscAtmIfVpcPerfEntry 20 }

mscAtmIfVpcLastAverageCtd OBJECT-TYPE
   SYNTAX     Unsigned32 (0 | 1..2147483647)
   ACCESS     read-only
   STATUS     mandatory
   DESCRIPTION
     "This attribute indicates the average of all calculated cell transfer 
      delay values for this connection from the previous TODA (time of 
      day accounting) interval if TODA is enabled; or for the previous 12 
      hour interval if TODA is disabled. Cell transfer delay is calculated 
      as half of the measured segment round trip delay of a loopback cell.
      
      The value is noMeasurement when the ctdCalculation attribute of 
      the AtmIf component is off.
      
      The value is noMeasurement when the accountCollection attribute 
      of the AtmIf Uni or AtmIf Iisp component has a non-empty reason.
      
      The value is noMeasurement when the segSwitchSideLoopback 
      attribute value is off for the connection.
      
      The value is noMeasurement when the switch-side loopback is not 
      working.
      
      The value is noMeasurement when the switch-side loopback status 
      cannot be determined.

      VALUES (

      0 = noMeasurement

      )"
::= { mscAtmIfVpcPerfEntry 30 }

mscAtmIfVpcCurrentCtd OBJECT-TYPE
   SYNTAX     Unsigned32 (0 | 1..2147483647)
   ACCESS     read-only
   STATUS     mandatory
   DESCRIPTION
     "This attribute indicates the most recent cell transfer delay value 
      calculated for this connection. Cell transfer delay is calculated as 
      half of the measured segment round trip delay of a loopback cell.
      
      The value is noMeasurement when the ctdCalculation attribute of 
      the AtmIf component is off.
      
      The value is noMeasurement when the segSwitchSideLoopback 
      attribute value is off for the connection.
      
      The value is noMeasurement when the switch-side loopback is not 
      working.
      
      The value is noMeasurement when the switch-side loopback status 
      cannot be determined.

      VALUES (

      0 = noMeasurement

      )"
::= { mscAtmIfVpcPerfEntry 40 }

mscAtmIfVpcLastCtdSampleSize OBJECT-TYPE
   SYNTAX     Unsigned32 (0..16384)
   ACCESS     read-only
   STATUS     mandatory
   DESCRIPTION
     "This attribute indicates the number of loopback cells sampled for 
      cell transfer delay calculations during the previous TODA (time of 
      day accounting) interval if TODA is enabled; or for the previous 12 
      hour interval of TODA is disabled."
::= { mscAtmIfVpcPerfEntry 50 }

mscAtmIfVpcTxTdpTable OBJECT-TYPE
   SYNTAX     SEQUENCE OF MscAtmIfVpcTxTdpEntry
   ACCESS     not-accessible
   STATUS     obsolete
   DESCRIPTION
     "This attribute is HISTORICAL. Please refer to the attribute of the 
      same name in the group AtmTmOper.
      
      This attribute is a vector of five transmit traffic parameters. The first 
      three elements reflect the settings of the first three elements of the 
      txTrafficDescParm attribute in the AtmTrafficProv group. 
      
      When txTrafficDescType is 1 or 2, parameters 1 through 5 are 
      unused.
      
      In this description, PCR is the greater of either the PCR or the 
      requested shaping rate (parameter 1 or parameter 5) specified in the 
      Traffic group under the Vcd or Vpd.
      
      When txTrafficDescType is 3, parameter 1 represents the PCR for 
      CLP equal to 0 or 1 traffic; parameters 2 and 3 are unused.
      
      When txTrafficDescType is 4, parameter 1 represents the PCR for 
      CLP equal to 0 and 1 traffic; parameter 2 represents the PCR for 
      CLP equal to 0 traffic with cell discard.
      
      When txTrafficDescType is 5, parameter 1 represents the PCR for 
      CLP equal to 0 and 1 traffic; parameter 2 represents the PCR for 
      CLP equal to 0 traffic with cell tagging.
      
      When txTrafficDescType is 6, parameter 1 represents the PCR for 
      CLP equal to 0 and 1 traffic; parameter 2 represents the SCR for 
      CLP equal to 0 and 1 traffic; parameter 3 represents the MBS for 
      CLP equal to 0 and 1 traffic.
      
      When txTrafficDescType is 7, parameter 1 represents the PCR for 
      CLP equal to 0 and 1 traffic; parameter 2 represents the SCR for 
      CLP equal to 0 traffic with cell discard; parameter 3 represents the 
      MBS for CLP equal to 0 traffic.
      
      When txTrafficDescType is 8, parameter 1 represents the PCR for 
      CLP equal to 0 and 1 traffic; parameter 2 represents the SCR for 
      CLP equal to 0 traffic with cell tagging; parameter 3 represents the 
      MBS for CLP equal to 0 traffic
      
      When txTrafficDescType is 3, 4, 5, 6, 7 or 8, parameter 4 reflects 
      the actual shaping rate in cell/s for this connection. This rate is one 
      of the set of available shaping rates for this type of ATM-FP, based 
      on the number of interfaces doing shaping (attribute 
      perVcQueueInterfaces), the provisioned cell rate, the 
      shapingScalingFactor attribute of the AtmResourceControl 
      component, and whether traffic shaping is enabled. A rate of zero 
      (0) indicates that shaping is not performed. 
      
      When txTrafficDescType is 3, 4, 5, 6, 7 or 8, parameter 5 reflects 
      the equivalent cell rate in cell/s for this connection as determined by 
      the Connection Admission Control (CAC) algorithm. The 
      equivalent cell rate is useful in determining the admission 
      characteristics of this connection."
::= { mscAtmIfVpc 294 }

mscAtmIfVpcTxTdpEntry OBJECT-TYPE
   SYNTAX     MscAtmIfVpcTxTdpEntry
   ACCESS     not-accessible
   STATUS     obsolete
   DESCRIPTION
     "An entry in the mscAtmIfVpcTxTdpTable."
   INDEX {
      mscAtmIfIndex,
      mscAtmIfVpcIndex,
      mscAtmIfVpcTxTdpIndex }
::= { mscAtmIfVpcTxTdpTable 1 }

MscAtmIfVpcTxTdpEntry ::= SEQUENCE {
   mscAtmIfVpcTxTdpIndex
      Integer32,
   mscAtmIfVpcTxTdpValue
      Unsigned32 }

mscAtmIfVpcTxTdpIndex OBJECT-TYPE
   SYNTAX     Integer32 (1..5)
   ACCESS     not-accessible
   STATUS     obsolete
   DESCRIPTION
     "This variable represents the mscAtmIfVpcTxTdpTable
      specific index for the mscAtmIfVpcTxTdpTable."
::= { mscAtmIfVpcTxTdpEntry 1 }

mscAtmIfVpcTxTdpValue OBJECT-TYPE
   SYNTAX     Unsigned32 (0..2147483647)
   ACCESS     read-only
   STATUS     obsolete
   DESCRIPTION
     "This variable represents an individual value for the
      mscAtmIfVpcTxTdpTable."
::= { mscAtmIfVpcTxTdpEntry 2 }

mscAtmIfVpcRxTdpTable OBJECT-TYPE
   SYNTAX     SEQUENCE OF MscAtmIfVpcRxTdpEntry
   ACCESS     not-accessible
   STATUS     obsolete
   DESCRIPTION
     "This attribute is HISTORICAL. Please refer to the attribute of the 
      same name in the group AtmTmOper.
      
      This attribute is a vector of four traffic parameters whose meanings 
      are defined by the rxTrafficDescType attribute. The values of peak 
      cell rate (PCR), sustained cell rate (SCR) are expressed in cells/s. 
      Maximum burst size (MBS) is expressed in cells. Cell Delay 
      Variation Tolerance (CDVT) is expressed in microseconds.
      
      When rxTrafficDescType is 1 or 2, none of the parameters are used.
      
      When rxTrafficDescType is 3, parameter 1 represents the PCR for 
      CLP equal to 0 and 1 traffic; parameter 4 represents the CDVT.
      
      When rxTrafficDescType is 4, parameter 1 represents the PCR for 
      CLP equal to 0 and 1 traffic; parameter 2 represents the PCR for 
      CLP equal to 0 traffic with cell discard; parameter 4 represents the 
      CDVT.
      
      When rxTrafficDescType is 5, parameter 1 represents the PCR for 
      CLP equal to 0 and 1 traffic; parameter 2 represents the PCR for 
      CLP equal to 0 traffic with cell tagging; parameter 4 represents the 
      CDVT.
      
      When rxTrafficDescType is a 6, parameter 1 represents the PCR for 
      CLP equal to 0 and 1 traffic; parameter 2 represents the SCR for 
      CLP equal to 0 and 1 traffic; parameter 3 represents the MBS for 
      CLP equal to 0 and 1 traffic; parameter 4 represents the CDVT. 
      
      When rxTrafficDescType is 7, parameter 1 represents the PCR for 
      CLP equal to 0 and 1 traffic; parameter 2 represents the SCR for 
      CLP equal to 0 traffic with cell discard; parameter 3 represents the 
      MBS for CLP equal to 0 traffic; parameter 4 represents the CDVT.
      
      When rxTrafficDescType is 8, parameter 1 represents the PCR for 
      CLP equal to 0 and 1 traffic; parameter 2 represents the SCR for 
      CLP equal to 0 traffic with cell tagging; parameter 3 represents the 
      MBS for CLP equal to 0 traffic; parameter 4 represents the CDVT. 
      
      If Upc is disabled for this connection, the values of PCR, SCR, 
      MBS and CDVT is a combination of provisioned parameters. If Upc 
      is enabled, the values of PCR, SCR, MBS, and CDVT is exactly the 
      values used by the usage parameter control hardware in policing the 
      arriving traffic. These may vary slightly from the provisioned values 
      due to granularity of the hardware. In the case where the PCR is 
      equal to the SCR, the effective MBS is zero."
::= { mscAtmIfVpc 295 }

mscAtmIfVpcRxTdpEntry OBJECT-TYPE
   SYNTAX     MscAtmIfVpcRxTdpEntry
   ACCESS     not-accessible
   STATUS     obsolete
   DESCRIPTION
     "An entry in the mscAtmIfVpcRxTdpTable."
   INDEX {
      mscAtmIfIndex,
      mscAtmIfVpcIndex,
      mscAtmIfVpcRxTdpIndex }
::= { mscAtmIfVpcRxTdpTable 1 }

MscAtmIfVpcRxTdpEntry ::= SEQUENCE {
   mscAtmIfVpcRxTdpIndex
      Integer32,
   mscAtmIfVpcRxTdpValue
      Unsigned32 }

mscAtmIfVpcRxTdpIndex OBJECT-TYPE
   SYNTAX     Integer32 (1..4)
   ACCESS     not-accessible
   STATUS     obsolete
   DESCRIPTION
     "This variable represents the mscAtmIfVpcRxTdpTable
      specific index for the mscAtmIfVpcRxTdpTable."
::= { mscAtmIfVpcRxTdpEntry 1 }

mscAtmIfVpcRxTdpValue OBJECT-TYPE
   SYNTAX     Unsigned32 (0..2147483647)
   ACCESS     read-only
   STATUS     obsolete
   DESCRIPTION
     "This variable represents an individual value for the
      mscAtmIfVpcRxTdpTable."
::= { mscAtmIfVpcRxTdpEntry 2 }

mscAtmIfVpcTxQThreshTable OBJECT-TYPE
   SYNTAX     SEQUENCE OF MscAtmIfVpcTxQThreshEntry
   ACCESS     not-accessible
   STATUS     obsolete
   DESCRIPTION
     "This attribute is HISTORICAL. Please refer to the attribute of the 
      same name in the group AtmTmOper.
      
      This attribute indicates the queue limit and the discard thresholds 
      for the transmit queue of this connection. 
      
      The first element indicates the queue limit. Depending upon the 
      atmServiceCategory of the connection, the provisioned value of the 
      transmit queue limit is derived from the txQueueLimit attribute 
      under one of the subcomponents of the AtmIf CA component. If the 
      connection has traffic shaping disabled, then this attribute relates to 
      the common queue. If traffic shaping is enabled, then this attribute 
      relates to the per-VC queue.
      
      The second element is the threshold that marks the transition from 
      congestion state 1 to congestion state 0. This is the threshold at 
      which traffic with discard priority (DP) = 1 is discarded. This 
      threshold is set approximately at 90 percent of the first parameter, 
      the operational queue limit.
      
      The third element is the threshold that marks the transition from 
      congestion state 2 to congestion state 1. This is the threshold at 
      which traffic with DP = 2 is discarded. This threshold is set 
      approximately at 75 percent of the first parameter, the operational 
      queue limit.
      
      The fourth element is the threshold that marks the transition from 
      congestion state 3 to congestion state 2. This is the threshold at 
      which traffic with DP = 3 is discarded. This threshold is set 
      approximately at 35 percent of the first parameter, the operational 
      queue limit."
::= { mscAtmIfVpc 352 }

mscAtmIfVpcTxQThreshEntry OBJECT-TYPE
   SYNTAX     MscAtmIfVpcTxQThreshEntry
   ACCESS     not-accessible
   STATUS     obsolete
   DESCRIPTION
     "An entry in the mscAtmIfVpcTxQThreshTable."
   INDEX {
      mscAtmIfIndex,
      mscAtmIfVpcIndex,
      mscAtmIfVpcTxQThreshIndex }
::= { mscAtmIfVpcTxQThreshTable 1 }

MscAtmIfVpcTxQThreshEntry ::= SEQUENCE {
   mscAtmIfVpcTxQThreshIndex
      Integer32,
   mscAtmIfVpcTxQThreshValue
      Unsigned32 }

mscAtmIfVpcTxQThreshIndex OBJECT-TYPE
   SYNTAX     Integer32 (0..3)
   ACCESS     not-accessible
   STATUS     obsolete
   DESCRIPTION
     "This variable represents the mscAtmIfVpcTxQThreshTable
      specific index for the mscAtmIfVpcTxQThreshTable."
::= { mscAtmIfVpcTxQThreshEntry 1 }

mscAtmIfVpcTxQThreshValue OBJECT-TYPE
   SYNTAX     Unsigned32 (0..30720)
   ACCESS     read-only
   STATUS     obsolete
   DESCRIPTION
     "This variable represents an individual value for the
      mscAtmIfVpcTxQThreshTable."
::= { mscAtmIfVpcTxQThreshEntry 2 }

mscAtmIfVpcFqpTable OBJECT-TYPE
   SYNTAX     SEQUENCE OF MscAtmIfVpcFqpEntry
   ACCESS     not-accessible
   STATUS     obsolete
   DESCRIPTION
     "This attribute is HISTORICAL. Please refer to the attribute of the 
      same name in the group AtmTmOper.
      
      This attribute is a vector of three elements that indicate the quality 
      of service parameters for the forward direction for this connection. 
      This attribute is used for SPVC and SVC connections on a PNNI 
      interface.
      
      The cdv element indicates the acceptable peak-to-peak Cell Delay 
      Variation (CDV) of real-time connections (CBR, and rt-VBR). 
      
      The ctd element indicates the acceptable maximum Cell Transfer 
      Delay (maxCtd) of real-time connections (CBR, and rt-VBR). 
      
      The clr element indicates the acceptable Cell Loss Ratio (CLR) of 
      CBR, rt-VBR, and nrt-VBR connections."
::= { mscAtmIfVpc 357 }

mscAtmIfVpcFqpEntry OBJECT-TYPE
   SYNTAX     MscAtmIfVpcFqpEntry
   ACCESS     not-accessible
   STATUS     obsolete
   DESCRIPTION
     "An entry in the mscAtmIfVpcFqpTable."
   INDEX {
      mscAtmIfIndex,
      mscAtmIfVpcIndex,
      mscAtmIfVpcFqpIndex }
::= { mscAtmIfVpcFqpTable 1 }

MscAtmIfVpcFqpEntry ::= SEQUENCE {
   mscAtmIfVpcFqpIndex
      INTEGER,
   mscAtmIfVpcFqpValue
      Unsigned32 }

mscAtmIfVpcFqpIndex OBJECT-TYPE
   SYNTAX     INTEGER  {
                 cdv(0),
                 ctd(1),
                 clr(2) }
   ACCESS     not-accessible
   STATUS     obsolete
   DESCRIPTION
     "This variable represents the mscAtmIfVpcFqpTable
      specific index for the mscAtmIfVpcFqpTable."
::= { mscAtmIfVpcFqpEntry 1 }

mscAtmIfVpcFqpValue OBJECT-TYPE
   SYNTAX     Unsigned32 (0..2147483647)
   ACCESS     read-only
   STATUS     obsolete
   DESCRIPTION
     "This variable represents an individual value for the
      mscAtmIfVpcFqpTable."
::= { mscAtmIfVpcFqpEntry 2 }

mscAtmIfVpcBqpTable OBJECT-TYPE
   SYNTAX     SEQUENCE OF MscAtmIfVpcBqpEntry
   ACCESS     not-accessible
   STATUS     obsolete
   DESCRIPTION
     "This attribute is HISTORICAL. Please refer to the attribute of the 
      same name in the group AtmTmOper.
      
      This attribute is a vector of three elements that indicate the quality 
      of service parameters for the backward direction for this 
      connection. This attribute is used for SPVC and SVC connections 
      on a PNNI interface.
      
      The cdv element indicates the acceptable peak-to-peak Cell Delay 
      Variation (CDV) of real-time connections (CBR, and rt-VBR). 
      
      The ctd element indicates the acceptable maximum Cell Transfer 
      Delay (maxCtd) of real-time connections (CBR, and rt-VBR). 
      
      The clr element indicates the acceptable Cell Loss Ratio (CLR) of 
      CBR, rt-VBR, and nrt-VBR connections."
::= { mscAtmIfVpc 358 }

mscAtmIfVpcBqpEntry OBJECT-TYPE
   SYNTAX     MscAtmIfVpcBqpEntry
   ACCESS     not-accessible
   STATUS     obsolete
   DESCRIPTION
     "An entry in the mscAtmIfVpcBqpTable."
   INDEX {
      mscAtmIfIndex,
      mscAtmIfVpcIndex,
      mscAtmIfVpcBqpIndex }
::= { mscAtmIfVpcBqpTable 1 }

MscAtmIfVpcBqpEntry ::= SEQUENCE {
   mscAtmIfVpcBqpIndex
      INTEGER,
   mscAtmIfVpcBqpValue
      Unsigned32 }

mscAtmIfVpcBqpIndex OBJECT-TYPE
   SYNTAX     INTEGER  {
                 cdv(0),
                 ctd(1),
                 clr(2) }
   ACCESS     not-accessible
   STATUS     obsolete
   DESCRIPTION
     "This variable represents the mscAtmIfVpcBqpTable
      specific index for the mscAtmIfVpcBqpTable."
::= { mscAtmIfVpcBqpEntry 1 }

mscAtmIfVpcBqpValue OBJECT-TYPE
   SYNTAX     Unsigned32 (0..2147483647)
   ACCESS     read-only
   STATUS     obsolete
   DESCRIPTION
     "This variable represents an individual value for the
      mscAtmIfVpcBqpTable."
::= { mscAtmIfVpcBqpEntry 2 }


-- AtmIf/n Vpc/vpi VirtualPathDescriptor
-- The Vpd component contains provisioning information about its 
-- parent Vpc component.

mscAtmIfVpcVpd OBJECT IDENTIFIER ::= { mscAtmIfVpc 2 }



mscAtmIfVpcVpdRowStatusTable OBJECT-TYPE
   SYNTAX     SEQUENCE OF MscAtmIfVpcVpdRowStatusEntry
   ACCESS     not-accessible
   STATUS     mandatory
   DESCRIPTION
     "This entry controls the addition and deletion of 
      mscAtmIfVpcVpd components."
::= { mscAtmIfVpcVpd 1 }

mscAtmIfVpcVpdRowStatusEntry OBJECT-TYPE
   SYNTAX     MscAtmIfVpcVpdRowStatusEntry
   ACCESS     not-accessible
   STATUS     mandatory
   DESCRIPTION
     "A single entry in the table represents a single 
      mscAtmIfVpcVpd component."
   INDEX {
      mscAtmIfIndex,
      mscAtmIfVpcIndex,
      mscAtmIfVpcVpdIndex }
::= { mscAtmIfVpcVpdRowStatusTable 1 }

MscAtmIfVpcVpdRowStatusEntry ::= SEQUENCE {
   mscAtmIfVpcVpdRowStatus
      RowStatus,
   mscAtmIfVpcVpdComponentName
      DisplayString,
   mscAtmIfVpcVpdStorageType
      StorageType,
   mscAtmIfVpcVpdIndex
      NonReplicated }

mscAtmIfVpcVpdRowStatus OBJECT-TYPE
   SYNTAX     RowStatus 
   ACCESS     read-only
   STATUS     mandatory
   DESCRIPTION
     "This variable is used as the basis for SNMP naming of
      mscAtmIfVpcVpd components.
      These components cannot be added nor deleted."
::= { mscAtmIfVpcVpdRowStatusEntry 1 }

mscAtmIfVpcVpdComponentName OBJECT-TYPE
   SYNTAX     DisplayString 
   ACCESS     read-only
   STATUS     mandatory
   DESCRIPTION
     "This variable provides the component's string name for
      use with the ASCII Console Interface"
::= { mscAtmIfVpcVpdRowStatusEntry 2 }

mscAtmIfVpcVpdStorageType OBJECT-TYPE
   SYNTAX     StorageType 
   ACCESS     read-only
   STATUS     mandatory
   DESCRIPTION
     "This variable represents the storage type value for the
      mscAtmIfVpcVpd tables."
::= { mscAtmIfVpcVpdRowStatusEntry 4 }

mscAtmIfVpcVpdIndex OBJECT-TYPE
   SYNTAX     NonReplicated 
   ACCESS     not-accessible
   STATUS     mandatory
   DESCRIPTION
     "This variable represents the index for the mscAtmIfVpcVpd tables."
::= { mscAtmIfVpcVpdRowStatusEntry 10 }

mscAtmIfVpcVpdLbkTable OBJECT-TYPE
   SYNTAX     SEQUENCE OF MscAtmIfVpcVpdLbkEntry
   ACCESS     not-accessible
   STATUS     mandatory
   DESCRIPTION
     "This group contains the provisionable loopback attributes for a Vcc, 
      Vpc, or Vpt component.
      
      Note that certain loopback requests may not be possible on a given 
      connection. In such cases, the corresponding operational loopback 
      attribute in the Status group of the Vcc, Vpc, or Vpt component is 
      set to notApplicable and the requested loopback is not performed.
      
      If loopbacks are provisioned to be on, and for any reason the 
      segment or end-to-end OAM loopback cells are not relayed, the 
      connection component becomes troubled, and user cell traffic may 
      be discarded. If loopbacks are provisioned to be on, all of the nodes 
      in the segment, and external networks which are in the end-to-end 
      connection must relay the OAM loopback cells."
::= { mscAtmIfVpcVpd 100 }

mscAtmIfVpcVpdLbkEntry OBJECT-TYPE
   SYNTAX     MscAtmIfVpcVpdLbkEntry
   ACCESS     not-accessible
   STATUS     mandatory
   DESCRIPTION
     "An entry in the mscAtmIfVpcVpdLbkTable."
   INDEX {
      mscAtmIfIndex,
      mscAtmIfVpcIndex,
      mscAtmIfVpcVpdIndex }
::= { mscAtmIfVpcVpdLbkTable 1 }

MscAtmIfVpcVpdLbkEntry ::= SEQUENCE {
   mscAtmIfVpcVpdSegLinkSideLoopback
      INTEGER,
   mscAtmIfVpcVpdSegSwitchSideLoopback
      INTEGER,
   mscAtmIfVpcVpdEndToEndLoopback
      INTEGER,
   mscAtmIfVpcVpdMCastConnectionType
      INTEGER }

mscAtmIfVpcVpdSegLinkSideLoopback OBJECT-TYPE
   SYNTAX     INTEGER  {
                 on(0),
                 off(1),
                 sameAsInterface(2) }
   ACCESS     read-write
   STATUS     mandatory
   DESCRIPTION
     "This attribute specifies whether link-side segment loopback 
      insertion should be performed on this connection. 
      
      When sameAsInterface is selected, the link-side segment loopback 
      insertion for the connection is based on the segLinkSideLoopback 
      attribute of the connection's parent AtmIf componentif the ATM 
      interface has link-side segment loopback insertion turned on, then 
      link-side segment loopback insertion is also on for the connection. 
      
      When on or off is selected, link-side segment loopback insertion is 
      turned on or off respectively for the connection regardless of the 
      provisioning of the parent AtmIf component.
      
      Note that link-side segment loopback insertion is not possible if the 
      connectionPointType attribute of the Vcc or Vpc component is 
      connectingPoint. Link-side segment loopback insertion is also not 
      possible if the distributionType of the Vcc is pointToMultipoint. In 
      such cases, the associated segLinkSideLoopbackState attribute 
      indicates notApplicable and link-side segment loopback insertion is 
      not performed. Link-side segment loopback insertion is always 
      possible on a Vpt."
   DEFVAL     { sameAsInterface }
::= { mscAtmIfVpcVpdLbkEntry 10 }

mscAtmIfVpcVpdSegSwitchSideLoopback OBJECT-TYPE
   SYNTAX     INTEGER  {
                 on(0),
                 off(1),
                 sameAsInterface(2) }
   ACCESS     read-write
   STATUS     mandatory
   DESCRIPTION
     "This attribute specifies whether switch-side segment loopback 
      insertion should be performed on this connection.
      
      When sameAsInterface is selected, the switch-side segment 
      loopback for the connection is based on the segSwitchSideLoopback 
      attribute of the connection's parent AtmIf componentif the ATM 
      interface has switch-side segment loopback insertion turned on, 
      then switch-side segment loopback insertion is also on for the 
      connection. 
      
      When on or off is selected, switch-side segment loopback insertion 
      is turned on or off respectively for the connection regardless of the 
      provisioning of the parent AtmIf component.
      
      Note that switch-side segment loopback insertion is not possible if 
      the connectionPointType attribute of the Vcc or Vpc component is 
      connectingPoint or connectionEndPoint. Switch-side segment 
      loopback insertion is also not possible if the distributionType of the 
      Vcc is pointToMultipoint In such cases, the associated 
      segSwitchSideLoopbackState attribute indicates notApplicable and 
      switch-side segment loopback insertion is not performed. Switch-
      side segment loopback is never possible on a Vpt."
   DEFVAL     { sameAsInterface }
::= { mscAtmIfVpcVpdLbkEntry 20 }

mscAtmIfVpcVpdEndToEndLoopback OBJECT-TYPE
   SYNTAX     INTEGER  {
                 on(0),
                 off(1),
                 sameAsInterface(2) }
   ACCESS     read-write
   STATUS     mandatory
   DESCRIPTION
     "This attribute specifies whether end-to-end loopback insertion 
      should be performed on this connection.
      
      When sameAsInterface is selected, the end-to-end loopback for the 
      connection is based on the endToEndLoopback attribute of the 
      connection's parent AtmIf componentif the ATM interface has 
      end-to-end loopback insertion turned on, then end-to-end loopback 
      insertion is also on for the connection. 
      
      When on or off is selected, end-to-end loopback insertion is turned 
      on or off respectively for the connection regardless of the 
      provisioning of the parent AtmIf component.
      
      Note that end-to-end loopback insertion is not possible if the 
      connectionPointType attribute of the Vcc or Vpc component is 
      connectingPoint or segmentEndPoint. End-to-end loopback 
      insertion is also not possible if the distributionType of the Vcc is 
      pointToMultipoint. In such cases, the associated 
      endToEndLoopbackState attribute indicates notApplicable and end-
      to-end loopback insertion is not performed. End-to-end loopback 
      insertion is always possible on a Vpt."
   DEFVAL     { sameAsInterface }
::= { mscAtmIfVpcVpdLbkEntry 30 }

mscAtmIfVpcVpdMCastConnectionType OBJECT-TYPE
   SYNTAX     INTEGER  {
                 pointToPoint(0),
                 pointToMultipointRoot(1),
                 pointToMultipointLeaf(2) }
   ACCESS     read-write
   STATUS     mandatory
   DESCRIPTION
     "This attribute is introduced to exist temporarily to pass to AtmIf the 
      connection type defined under Vcc or Vpc. This attribute will be 
      obsoleted once a more elegant solution is available."
   DEFVAL     { pointToPoint }
::= { mscAtmIfVpcVpdLbkEntry 50 }

mscAtmIfVpcVpdTrafficTable OBJECT-TYPE
   SYNTAX     SEQUENCE OF MscAtmIfVpcVpdTrafficEntry
   ACCESS     not-accessible
   STATUS     mandatory
   DESCRIPTION
     "This group contains traffic related provisionable attributes for the 
      Vcc and Vpc components. The attributes' operational values are 
      reflected in the Traffic group for these components. Changing any 
      of the attributes in this group causes a service interruption on the 
      Vcc or Vpc component."
::= { mscAtmIfVpcVpd 110 }

mscAtmIfVpcVpdTrafficEntry OBJECT-TYPE
   SYNTAX     MscAtmIfVpcVpdTrafficEntry
   ACCESS     not-accessible
   STATUS     mandatory
   DESCRIPTION
     "An entry in the mscAtmIfVpcVpdTrafficTable."
   INDEX {
      mscAtmIfIndex,
      mscAtmIfVpcIndex,
      mscAtmIfVpcVpdIndex }
::= { mscAtmIfVpcVpdTrafficTable 1 }

MscAtmIfVpcVpdTrafficEntry ::= SEQUENCE {
   mscAtmIfVpcVpdTxTrafficDescType
      INTEGER,
   mscAtmIfVpcVpdTxQosClass
      INTEGER,
   mscAtmIfVpcVpdFwdQosClass
      INTEGER,
   mscAtmIfVpcVpdHoldingPriority
      INTEGER,
   mscAtmIfVpcVpdRxTrafficDescType
      INTEGER,
   mscAtmIfVpcVpdRxQosClass
      INTEGER,
   mscAtmIfVpcVpdBwdQosClass
      INTEGER,
   mscAtmIfVpcVpdAtmServiceCategory
      INTEGER,
   mscAtmIfVpcVpdTrafficShaping
      INTEGER,
   mscAtmIfVpcVpdUnshapedTransmitQueueing
      INTEGER,
   mscAtmIfVpcVpdUsageParameterControl
      INTEGER,
   mscAtmIfVpcVpdBearerClassBbc
      INTEGER,
   mscAtmIfVpcVpdTransferCapabilityBbc
      INTEGER,
   mscAtmIfVpcVpdClippingBbc
      INTEGER,
   mscAtmIfVpcVpdBestEffort
      INTEGER,
   mscAtmIfVpcVpdFwdFrameDiscard
      INTEGER,
   mscAtmIfVpcVpdBwdFrameDiscard
      INTEGER }

mscAtmIfVpcVpdTxTrafficDescType OBJECT-TYPE
   SYNTAX     INTEGER  {
                 n1(1),
                 n2(2),
                 n3(3),
                 n4(4),
                 n5(5),
                 n6(6),
                 n7(7),
                 n8(8),
                 n9(9) }
   ACCESS     read-write
   STATUS     obsolete
   DESCRIPTION
     "This attribute is migrated to the AtmTmProv group.
      
      This attribute specifies the type of traffic management which is 
      applied to the transmit direction of this connection as defined in the 
      ATM Forum. The txTrafficDescType determines the number and 
      meaning of the parameters in the txTrafficDescParm attribute."
   DEFVAL     { n1 }
::= { mscAtmIfVpcVpdTrafficEntry 10 }

mscAtmIfVpcVpdTxQosClass OBJECT-TYPE
   SYNTAX     INTEGER  {
                 unspecified(0),
                 constantBitRate(1),
                 variableBitRate(2),
                 connectionOriented(3),
                 connectionless(4) }
   ACCESS     read-write
   STATUS     obsolete
   DESCRIPTION
     "This attribute specifies the quality of service for the transmit 
      direction for this connection.
      
      The constantBitRate class refers to traffic offered on services such 
      as a constant bit rate video service. This traffic is highest priority.
      
      The variableBitRate class refers to traffic offered on services such 
      as packetized audio and video.
      
      The connectionOriented class refers to connection-oriented traffic 
      such as Frame Relay or X.25 traffic. 
      
      The connectionless traffic refers to traffic offered through 
      connectionless trunks such as certain LAN protocols.
      
      The unspecified class supports a 'best effort' type of service, where 
      there is a minimum guarantee of bandwidth. This traffic is lowest 
      priority.
      
      This attribute is obsolete. The value is migrated into 
      atmServiceCategory. The atmServiceCategory applies in both 
      transmit and receive directions.
      
      unspecified maps to unspecifiedBitRate;
      constantBitRate maps to constantBitRate;
      variableBitRate maps to variableBitRateRt;
      connectionOriented maps to variableBitRateNrt
      connectionless maps to variableBitRateNrt"
   DEFVAL     { connectionOriented }
::= { mscAtmIfVpcVpdTrafficEntry 20 }

mscAtmIfVpcVpdFwdQosClass OBJECT-TYPE
   SYNTAX     INTEGER  {
                 n0(0),
                 n1(1),
                 n2(2),
                 n3(3),
                 n4(4) }
   ACCESS     read-write
   STATUS     obsolete
   DESCRIPTION
     "This attribute is migrated to the AtmTmProv group.
      
      This attribute specifies the quality of service for the forward 
      direction for this connection. This attribute is only used for SPVC 
      connections.
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified bit rate QOS class; no objective is 
      specified for the performance parameters."
   DEFVAL     { n0 }
::= { mscAtmIfVpcVpdTrafficEntry 21 }

mscAtmIfVpcVpdHoldingPriority OBJECT-TYPE
   SYNTAX     INTEGER  {
                 n0(0),
                 n1(1),
                 n2(2),
                 n3(3),
                 n4(4) }
   ACCESS     read-write
   STATUS     obsolete
   DESCRIPTION
     "This attribute is migrated to the AtmTmProv group.
      
      This attribute specifies the holding priority of this connection. In a 
      situation where the link bandwidth fluctuates, such as over an IMA 
      link, holding priority is used to determine which connections are 
      held and which are released. Holding priority 4 connections are the 
      first to be released. Holding priority 0 connections are the last to be 
      released. This value provisioned in the Vcd or Vpd may be 
      overridden by certain applications, for example Vcc Test, which run 
      over this connection. The default holding priority for a provisioned 
      connection is higher then default holding priorities for dynamic 
      (SVC) connections."
   DEFVAL     { n2 }
::= { mscAtmIfVpcVpdTrafficEntry 25 }

mscAtmIfVpcVpdRxTrafficDescType OBJECT-TYPE
   SYNTAX     INTEGER  {
                 n1(1),
                 n2(2),
                 n3(3),
                 n4(4),
                 n5(5),
                 n6(6),
                 n7(7),
                 n8(8),
                 sameAsTx(15) }
   ACCESS     read-write
   STATUS     obsolete
   DESCRIPTION
     "This attribute is migrated to the AtmTmProv group.
      
      This attribute specifies the type of traffic management which is 
      applied to the receive direction of this connection as defined in the 
      ATM Forum. The rxTrafficDescType determines the number and 
      meaning of the parameters in the rxTrafficDescParm attribute
      
      When sameAsTx is selected, the rxTrafficDescType as well as the 
      rxTrafficDescParm are taken from the transmit values."
   DEFVAL     { sameAsTx }
::= { mscAtmIfVpcVpdTrafficEntry 30 }

mscAtmIfVpcVpdRxQosClass OBJECT-TYPE
   SYNTAX     INTEGER  {
                 unspecified(0),
                 constantBitRate(1),
                 variableBitRate(2),
                 connectionOriented(3),
                 connectionless(4),
                 sameAsTx(15) }
   ACCESS     read-write
   STATUS     obsolete
   DESCRIPTION
     "This attribute specifies the quality of service for the receive 
      direction for this connection.
      
      The constantBitRate class refers to traffic offered on services such 
      as a constant bit rate video service. 
      
      The variableBitRate class refers to traffic offered on services such 
      as packetized audio and video. 
      
      The connectionOriented class refers to connection-oriented traffic.
      
      The connectionless traffic refers to traffic offered through 
      connectionless trunks. 
      
      The unspecified class supports a 'best effort' type of service, where 
      there is a minimum guarantee of bandwidth. 
      
      The sameAsTx selection sets the receive quality of service to be the 
      same as the transmit quality of service.
      
      This attribute is obsolete. The value of txQosClass is migrated into 
      atmServiceCategory. The value of this attribute is ignored. 
      AtmServiceCategory applies in both transmit and receive directions."
   DEFVAL     { sameAsTx }
::= { mscAtmIfVpcVpdTrafficEntry 40 }

mscAtmIfVpcVpdBwdQosClass OBJECT-TYPE
   SYNTAX     INTEGER  {
                 n0(0),
                 n1(1),
                 n2(2),
                 n3(3),
                 n4(4),
                 sameAsFwd(15) }
   ACCESS     read-write
   STATUS     obsolete
   DESCRIPTION
     "This attribute is migrated to the AtmTmProv group.
      
      This attribute specifies the quality of service for the backward 
      direction for this connection. This attribute is only used for SPVC 
      connections.
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified bit rate QOS class; no objective is 
      specified for the performance parameters.
      
      The sameAsFwd selection sets the backward quality of service to 
      be the same as the forward quality of service."
   DEFVAL     { sameAsFwd }
::= { mscAtmIfVpcVpdTrafficEntry 41 }

mscAtmIfVpcVpdAtmServiceCategory OBJECT-TYPE
   SYNTAX     INTEGER  {
                 unspecifiedBitRate(0),
                 constantBitRate(1),
                 rtVariableBitRate(2),
                 nrtVariableBitRate(3),
                 derivedFromBBC(15) }
   ACCESS     read-write
   STATUS     obsolete
   DESCRIPTION
     "This attribute is migrated to the AtmTmProv group.
      
      This attribute specifies the ATM service category for both directions 
      of the connection. 
      
      The value derivedFromBBC may only be used if the SrcPvc 
      component is provisioned under this Vcc.Otherwise a specific ATM 
      service category must be specified. 
      
      If this attribute is set to derivedFromBBC, the Broadband Bearer 
      Capability (BBC) and bestEffort attributes are used to determine the 
      atmServiceCategory of this connection. 
      
      If this attribute is set to other than derivedFromBBC, the value of 
      this attribute is used to override the provisioned BBC Information 
      Element parameters. In those cases, the BBC attributes are not used. 
      
      The constantBitRate service category is intended for real time 
      applications, that is those requiring tightly constrained delay and 
      delay variation, as would be appropriate for voice and video 
      applications. The consistent availability of a fixed quantity of 
      bandwidth is considered appropriate for CBR service. Cells which 
      are delayed beyond the value specified by Cell Transfer Delay are 
      assumed to be of significantly reduce value to the application.
      
      The rtVariableBitRate service category is intended for real time 
      applications, that is those requiring tightly constrained delay and 
      delay variation, as would be appropriate for voice and video 
      applications. Sources are expected to transmit at a rate which varies 
      with time. Equivalently, the source can be described as 'bursty'. 
      Cells which are delayed beyond the value specified by CTD are 
      assumed to be of significantly reduced value to the application. Real 
      time VBR service may support statistical multiplexing of real time 
      sources.
      
      The nrtVariableBitRate service category is intended for non-real 
      time applications which have bursty traffic characteristics and which 
      can be characterized in terms of a PCR, SCR, and MBS. For those 
      cells which are transferred within the traffic contract, the application 
      expects a low cell loss ratio. For all connections, it expects a bound 
      on the mean cell transfer delay. Non-real time VBR service may 
      support statistical multiplexing of connections.
      
      The unspecifiedBitRate service is intended for non-real time 
      applications; that is, those not requiring tightly constrained delay 
      and delay variation. UBR sources are expected to be bursty. UBR 
      service supports a high degree of statistical multiplexing among 
      sources. UBR service does not specify traffic related service 
      guarantees. No numerical commitments are made with respect to 
      the cell loss ratio experienced by a UBR connection, or as to the 
      cell transfer delay experienced by cells on the connection."
   DEFVAL     { unspecifiedBitRate }
::= { mscAtmIfVpcVpdTrafficEntry 42 }

mscAtmIfVpcVpdTrafficShaping OBJECT-TYPE
   SYNTAX     INTEGER  {
                 disabled(1),
                 sameAsInterface(2) }
   ACCESS     read-write
   STATUS     obsolete
   DESCRIPTION
     "This attribute is migrated to the AtmTmProv group.
      
      This attribute specifies whether this connection uses traffic shaping 
      when transmitting traffic to the ATM interface.
      
      When sameAsInterface is selected, traffic shaping for the 
      connection is based on the trafficShaping attribute of the 
      connection's parent AtmIf componentif the ATM interface has 
      traffic shaping enabled, then traffic shaping is enabled for the 
      connection. Note that enabling traffic shaping may have no effect 
      under certain cases. These cases are listed in the description of the 
      trafficShaping operational attribute, which is under the Vcc and Vpc 
      components.
      
      When disabled is selected, traffic shaping for this connection is 
      disabled regardless of the provisioning of the parent AtmIf 
      component."
   DEFVAL     { sameAsInterface }
::= { mscAtmIfVpcVpdTrafficEntry 50 }

mscAtmIfVpcVpdUnshapedTransmitQueueing OBJECT-TYPE
   SYNTAX     INTEGER  {
                 common(1),
                 sameAsInterface(3) }
   ACCESS     read-write
   STATUS     obsolete
   DESCRIPTION
     "This attribute is migrated to the AtmTmProv group.
      
      This attribute only applies when this connection is unshaped. This 
      attribute defines the transmit queueing method for this connection if 
      it is unshaped. Refer to the unshapedTransmitQueueing attribute 
      under the AtmIf for more details on the meaning of this attribute. 
      
      When this attribute is set to sameAsInterface, the value from the 
      AtmIf is used. 
      
      When this attribute is set to common, transmit traffic on this 
      unshaped connection is destined for the common queue."
   DEFVAL     { sameAsInterface }
::= { mscAtmIfVpcVpdTrafficEntry 60 }

mscAtmIfVpcVpdUsageParameterControl OBJECT-TYPE
   SYNTAX     INTEGER  {
                 disabled(1),
                 sameAsInterface(2) }
   ACCESS     read-write
   STATUS     obsolete
   DESCRIPTION
     "This attribute is migrated to the AtmTmProv group.
      
      This attribute specifies whether this connection enforces usage 
      parameter control when receiving traffic from the ATM interface.
      
      When sameAsInterface is selected, UPC for the connection is 
      based on the usageParameterControl attribute of the connection's 
      parent AtmIf componentif the ATM interface has UPC enabled, 
      then UPC is enabled for the connection. Note that enabling UPC 
      may have no effect under certain cases. These cases are listed in the 
      description of the usageParameterControl operational attribute, 
      which is under the Vcc and Vpc components.
      
      When disabled is selected, UPC for this connection is disabled 
      regardless of the provisioning of the parent AtmIf component."
   DEFVAL     { sameAsInterface }
::= { mscAtmIfVpcVpdTrafficEntry 70 }

mscAtmIfVpcVpdBearerClassBbc OBJECT-TYPE
   SYNTAX     INTEGER  {
                 a(1),
                 c(3),
                 x(16),
                 vp(24),
                 derivedFromServiceCategory(31) }
   ACCESS     read-write
   STATUS     obsolete
   DESCRIPTION
     "This attribute is migrated to the AtmTmProv group.
      
      This attribute specifies the bearer capability. This attribute is only 
      used for SPVC and SPVP connections. It is one of the Broadband 
      Bearer Capability (BBC) attributes. The purpose of the BBC 
      information element is to indicate a requested broadband 
      connection-oriented bearer service to be provided by the network.
      
      The value derivedFromServiceCategory specifies that the actual 
      value which is used for this connection is derived from the value of 
      the atmServiceCategory. Either, this attribute must be set to 
      derivedFromServiceCategory, or the atmServiceCategory attribute 
      must be set to derivedFromBBC, but not both.
      
      Class a service is a connection-oriented, constant bit rate ATM 
      transport service. Class a service has end to end timing 
      requirements and may require stringent cell loss, cell delay and cell 
      delay variation performance.When a is set, the user is requesting 
      more than an ATM only service. The network may look at the AAL 
      to provide interworking based upon its contents. 
      
      Class c service is a connection-oriented, variable bit rate ATM 
      transport service. Class c service has no end-to-end timing 
      requirements. When c is set, the user is requesting more than an 
      ATM only service. The network interworking function may look at 
      the AAL and provide service based on it.
      
      Class x service is a connection-oriented ATM transport service 
      where the AAL, trafficType (vbr or cbr) and timing requirements 
      are user defined (that is, transparent to the network).When x is set 
      the user is requesting an ATM only service from the network.
      
      Class vp service is used to specify a transparent VP service. When 
      the value of this attribute is vp, the user is requesting an ATM only 
      service from the network. In this case, the network shall not process 
      any higher layer protocol. This service differs from class x service 
      in that with the class vp service both the VCI field (except or VCI 
      values 0, 3, 4, and 6 through 15) and Payload Type field are 
      transported transparently by the network. This attribute value is 
      only applicable to SPVP connections."
   DEFVAL     { derivedFromServiceCategory }
::= { mscAtmIfVpcVpdTrafficEntry 71 }

mscAtmIfVpcVpdTransferCapabilityBbc OBJECT-TYPE
   SYNTAX     INTEGER  {
                 n0(0),
                 n1(1),
                 n2(2),
                 n5(5),
                 n8(8),
                 n9(9),
                 n10(10),
                 notApplicable(30),
                 derivedFromServiceCategory(31) }
   ACCESS     read-write
   STATUS     obsolete
   DESCRIPTION
     "This attribute is migrated to the AtmTmProv group.
      
      This attribute specifies the transfer capability for this connection. 
      Uni 3.0/3.1 traffic type and end-to-end timing parameters are 
      mapped into this parameter as follows:
      <transferCapability: TrafficType, Timing>
      0: NoIndication, NoIndication
      1: NoIndication, yes
      2: NoIndication, no
      5: CBR, yes
      8: VBR, NoIndication
      9: VBR, yes
      10: VBR, no
      
      NotApplicable specifies that the user does not want to specify the 
      transfer capability.
      
      The CBR traffic type refers to traffic offered on services such as a 
      constant bit rate video service or a circuit emulation.
      
      The VBR traffic type refers to traffic offered on services such as 
      packetized audio and video, or data.
      
      The value no indication for traffic type is used if the user has not set 
      the traffic type; similarly for end-to-end timing.
      
      The value yes for end-to-end timing indicates that end-to-end 
      timing is required.
      
      The value no for end-to-end timing indicates that end-to-end timing 
      is not required.
      
      The value derivedFromServiceCategory specifies that the actual 
      value which is used for this connection is derived from the value of 
      the atmServiceCategory. Either, this attribute must be set to 
      derivedFromServiceCategory, or the atmServiceCategory attribute 
      must be set to derivedFromBBC, but not both."
   DEFVAL     { derivedFromServiceCategory }
::= { mscAtmIfVpcVpdTrafficEntry 72 }

mscAtmIfVpcVpdClippingBbc OBJECT-TYPE
   SYNTAX     INTEGER  {
                 no(0),
                 yes(1) }
   ACCESS     read-write
   STATUS     obsolete
   DESCRIPTION
     "This attribute is migrated to the AtmTmProv group.
      
      This attribute specifies the value for the clipping susceptibility 
      parameter in the BBC Information Element. This attribute is only 
      used for SPVC connections. It is one of the Broadband Bearer 
      Capability attributes.
      
      Clipping is an impairment in which the first fraction of a second of 
      information to be transferred is lost. It occurs after a call is 
      answered and before an associated connection is switched through."
   DEFVAL     { no }
::= { mscAtmIfVpcVpdTrafficEntry 74 }

mscAtmIfVpcVpdBestEffort OBJECT-TYPE
   SYNTAX     INTEGER  {
                 indicated(0),
                 notIndicated(1),
                 derivedFromServiceCategory(15) }
   ACCESS     read-write
   STATUS     obsolete
   DESCRIPTION
     "This attribute is migrated to the AtmTmProv group.
      
      This attribute specifies the value of the best effort parameter in the 
      ATM Traffic Descriptor Information Element. This attribute is only 
      used for Soft PVC connections. It is one of the Broadband Bearer 
      Capability attributes.
      
      The value indicated implies that the quality of service for this 
      connection is not guaranteed.
      
      The value notIndicated implies that the quality of service for this 
      connection is guaranteed.
      
      The value derivedFromServiceCategory specifies that the actual 
      value which is used for this connection is derived from the value of 
      the atmServiceCategory. Either, this attribute must be set to 
      derivedFromServiceCategory, or the atmServiceCategory attribute 
      must be set to derivedFromBBC, but not both."
   DEFVAL     { derivedFromServiceCategory }
::= { mscAtmIfVpcVpdTrafficEntry 75 }

mscAtmIfVpcVpdFwdFrameDiscard OBJECT-TYPE
   SYNTAX     INTEGER  {
                 notIndicated(0),
                 indicated(1) }
   ACCESS     read-write
   STATUS     obsolete
   DESCRIPTION
     "This attribute specifies the activation of frame discard functionality 
      in the forward data direction, at relay points, for this connection. It 
      applies to each hop of the connection. Frame discard functions 
      should not be requested if this connection is not transferring frame 
      (AAL5) traffic. Setting the value to indicated for any other traffic 
      type results in all traffic being discarded.
      
      If this connection point is a permanent (provisioned) VCC mid-
      point, this attribute specifies whether the Partial Packet 
      Discard (PPD) function is to be enabled or disabled in the transmit 
      direction at this connecting point. The PPD function allows the 
      connecting point to discard the remainder of a cell-forwarded AAL5 
      frame if one cell of this frame has been discarded. The PPD 
      function increases the 'goodput' of the link, since cells which are 
      only going to be discarded by the AAL5 reassembly are not 
      transmitted.
      
      At a permanent VCC connecting point which is not a connection 
      endpoint, when this attribute is set to indicated, the PPD function is 
      applied to transmit traffic at this connecting point. It should not be 
      indicated for connections whose end points are not performing 
      AAL5 segmentation and reassembly. When this attribute is set to 
      notIndicated, the PPD feature is not applied to transmit traffic at 
      this connecting point.
      
      At a SPVC origin on a PNNI interface, a value of indicated 
      specifies that frame discard is requested in the forward direction. 
      The frame discard function for SPVCs consists of PPD at the SPVC 
      origin and at all intermediate connecting points. When this attribute 
      is set to notIndicated, forward frame discard is not requested in the 
      SPVC call setup. Thus PPD is not enabled at the SPVC origin nor at 
      any intermediate connecting point.
      
      At all points along a VPC, this setting is ignored.
      
      At a permanent VCC connection endpoint, this value is ignored. If 
      AAL5 segmentation and reassembly has been requested, PPD and 
      Early Packet Discard (EPD) are automatically enabled.
      
      This attribute has been migrated to txFrameDiscard."
   DEFVAL     { notIndicated }
::= { mscAtmIfVpcVpdTrafficEntry 76 }

mscAtmIfVpcVpdBwdFrameDiscard OBJECT-TYPE
   SYNTAX     INTEGER  {
                 notIndicated(0),
                 indicated(1) }
   ACCESS     read-write
   STATUS     obsolete
   DESCRIPTION
     "This attribute specifies the activation of frame discard functionality 
      in the backward data direction, at relay points, for this connection. 
      It applies to each hop of the connection. Frame discard functions 
      should not be requested if this connection is not transferring frame 
      (AAL5) traffic. Setting the value to indicated for any other traffic 
      type results in all traffic being discarded.
      
      If this connection point is a permanent (provisioned) VCC mid-
      point, this attribute specifies whether the Partial Packet Discard 
      (PPD) function is to be enabled or disabled in the receive direction 
      at this connecting point. The PPD function allows the connecting 
      point to discard the remainder of a cell-forwarded AAL5 frame if 
      one cell of this frame has been discarded. The PPD function 
      increases the 'goodput' of the link, since cells which are only going 
      to be discarded by the AAL5 reassembly are not received.
      
      At a permanent VCC connecting point which is not a connection 
      endpoint, when this attribute is set to indicated, the PPD function is 
      applied to receive traffic at this connecting point. It should not be 
      indicated for connections whose end points are not performing 
      AAL5 segmentation and reassembly. When this attribute is set to 
      notIndicated, the PPD feature is not applied to receive traffic at this 
      connecting point.
      
      At a SPVC origin on a PNNI interface, a value of indicated 
      specifies that frame discard is requested in the backward direction. 
      The frame discard function for SPVCs consists of PPD at the SPVC 
      origin and at all intermediate connecting points. When this attribute 
      is set to notIndicated, backwards frame discard is not requested in 
      the SPVC call setup. Thus PPD is not enabled at the SPVC origin 
      nor at any intermediate connecting point.
      
      At all points along a VPC, this setting is ignored.
      
      At a permanent VCC connection endpoint, this value is ignored. If 
      AAL5 segmentation and reassembly has been requested, PPD and 
      Early Packet Discard (EPD) are automatically enabled.
      
      This attribute has been migrated to rxFrameDiscard."
   DEFVAL     { notIndicated }
::= { mscAtmIfVpcVpdTrafficEntry 77 }

mscAtmIfVpcVpdAcctTable OBJECT-TYPE
   SYNTAX     SEQUENCE OF MscAtmIfVpcVpdAcctEntry
   ACCESS     not-accessible
   STATUS     mandatory
   DESCRIPTION
     "This group contains the provisionable ATM accounting attributes 
      for a Vcc, Vpc, or Vpt component."
::= { mscAtmIfVpcVpd 111 }

mscAtmIfVpcVpdAcctEntry OBJECT-TYPE
   SYNTAX     MscAtmIfVpcVpdAcctEntry
   ACCESS     not-accessible
   STATUS     mandatory
   DESCRIPTION
     "An entry in the mscAtmIfVpcVpdAcctTable."
   INDEX {
      mscAtmIfIndex,
      mscAtmIfVpcIndex,
      mscAtmIfVpcVpdIndex }
::= { mscAtmIfVpcVpdAcctTable 1 }

MscAtmIfVpcVpdAcctEntry ::= SEQUENCE {
   mscAtmIfVpcVpdCorrelationTag
      AsciiString }

mscAtmIfVpcVpdCorrelationTag OBJECT-TYPE
   SYNTAX     AsciiString (SIZE (0..32))
   ACCESS     read-write
   STATUS     mandatory
   DESCRIPTION
     "This attribute specifies a unique indentifier for each end of a PVC. It 
      that may be used by downstream processing systems to correlate 
      accounting records issued at different nodes in the network. The 
      attribute can be up to 32 bytes long. If it is less than 32 bytes, it is 
      zero filled on the right to create a 32 byte value. The resulting value 
      is recorded in the attribute callConnId for this PVC's ATM 
      accounting records.
      If the attribute is a null string then this PVC does not have any 
      accounting records generated for it."
   DEFVAL     { ''H }  -- ""
::= { mscAtmIfVpcVpdAcctEntry 10 }

mscAtmIfVpcVpdTxTdpTable OBJECT-TYPE
   SYNTAX     SEQUENCE OF MscAtmIfVpcVpdTxTdpEntry
   ACCESS     not-accessible
   STATUS     obsolete
   DESCRIPTION
     "This attribute is migrated to the AtmTmProv group.
      
      This attribute is a vector of five traffic parameters whose meanings 
      are defined by the txTrafficDescType attribute. The values of peak 
      cell rate (PCR), sustained cell rate (SCR) and requested shaping rate 
      are expressed in cell/s. Maximum burst size (MBS) is expressed in 
      cells. CDVT is expressed in microseconds. The values of PCR, 
      SCR, MBS and CDVT are used for connection admission control 
      (CAC). The value of CDVT is only used for connections where the 
      atmServiceCategory is constantBitRate. For all other values of 
      atmServiceCategory, CDVT is ignored. The values of PCR, SCR 
      and requested shaping rate are used to determine the actual shaping 
      rate where traffic shaping is enabled.
      
      When txTrafficDescType is 1 or 2, all of the parameters must be set 
      to zero.
      
      When txTrafficDescType is 3, parameter 1 represents the PCR for 
      CLP equal to 0 and 1 traffic; parameter 4 represents the CDVT; and 
      parameter 5 represents the requested shaping rate. A non-zero value 
      in parameter 5 overrides any value in parameter 1. This result is 
      used as the PCR. Parameter 1 must be non-zero. Parameters 2 and 3 
      must be zero.
      
      When txTrafficDescType is 4, parameter 1 represents the PCR for 
      CLP equal to 0 and 1 traffic with cell discard; parameter 2 
      represents the PCR for CLP equal to 0 traffic; parameter 4 
      represents the CDVT; and parameter 5 represents the requested 
      shaping rate. A non-zero value in parameter 5 overrides any value in 
      parameter 1. This result is used as the PCR. Parameter 1 must be 
      greater than or equal to parameter 2. Parameters 1 and 2 must be 
      non-zero. Parameter 3 must be zero.
      
      When txTrafficDescType is 5, parameter 1 represents the PCR for 
      CLP equal to 0 and 1 traffic with cell tagging; parameter 2 
      represents the PCR for CLP equal to 0 traffic; parameter 4 
      represents the CDVT; and parameter 5 represents the requested 
      shaping rate. A non-zero value in parameter 5 overrides any value in 
      parameter 1. This result is used as the PCR. Parameter 1 must be 
      greater than or equal to parameter 2. Parameters 1 and 2 must be 
      non-zero. Parameter 3 must be zero.
      
      When txTrafficDescType is 6, parameter 1 represents the PCR for 
      CLP equal to 0 and 1 traffic; parameter 2 represents the SCR for 
      CLP equal to 0 and 1 traffic; parameter 3 represents the MBS for 
      CLP equal to 0 and 1 traffic; parameter 4 represents the CDVT; and 
      parameter 5 represents the requested shaping rate. A non-zero value 
      in parameter 5 overrides any value in parameter 1. This result is 
      used as the PCR. Parameters 1, 2 and 3 must be non-zero. 
      Parameter 1 must be greater than or equal to parameter 2. Parameter 
      5, must either be zero (unused) or greater than or equal to parameter 
      2.
      
      When txTrafficDescType is 7, parameter 1 represents the PCR for 
      CLP equal to 0 and 1 traffic; parameter 2 represents the SCR for 
      CLP equal to 0 with cell discard; parameter 3 represents the MBS 
      for CLP equal to 0 traffic; parameter 4 represents the CDVT; and 
      parameter 5 represents the requested shaping rate. A non-zero value 
      in parameter 5 overrides any value in parameter 1. This result is 
      used as the PCR. Parameters 1, 2 and 3 must be non-zero. 
      Parameter 1 must be greater than or equal to parameter 2. Parameter 
      5, must either be zero (unused) or greater than or equal to parameter 
      2.
      
      When txTrafficDescType is 8, parameter 1 represents the PCR for 
      CLP equal to 0 and 1 traffic; parameter 2 represents the SCR for 
      CLP equal to 0 traffic with cell tagging; parameter 3 represents the 
      MBS for CLP equal to 0 traffic; parameter 4 represents the CDVT; 
      and parameter 5 represents the requested shaping rate. A non-zero 
      value in parameter 5 overrides any value in parameter 1. This result 
      is used as the PCR. Parameters 1, 2 and 3 must be non-zero. 
      Parameter 1 must be greater than or equal to parameter 2. Parameter 
      5, must either be zero (unused) or greater than or equal to parameter 
      2.
      
      Whenever it is valid for PCR to be specified, parameter 5 may also 
      be used to specify a requested shaping rate. A non-zero value in 
      parameter 5 overrides the value in parameter 1 and is used as the 
      peak cell rate in calculations of CAC and shaping rate.
      
      For txTrafficDescType 3, 4 and 5, the transmit traffic is shaped at 
      the next rate less than the PCR. 
      
      For txTrafficDescType 6, 7 and 8, the transmit traffic is shaped at 
      the highest available rate which is between PCR and SCR. 
      However, if there is no available shaping rate between PCR and 
      SCR, traffic is shaped at the next rate above the PCR."
::= { mscAtmIfVpcVpd 297 }

mscAtmIfVpcVpdTxTdpEntry OBJECT-TYPE
   SYNTAX     MscAtmIfVpcVpdTxTdpEntry
   ACCESS     not-accessible
   STATUS     obsolete
   DESCRIPTION
     "An entry in the mscAtmIfVpcVpdTxTdpTable."
   INDEX {
      mscAtmIfIndex,
      mscAtmIfVpcIndex,
      mscAtmIfVpcVpdIndex,
      mscAtmIfVpcVpdTxTdpIndex }
::= { mscAtmIfVpcVpdTxTdpTable 1 }

MscAtmIfVpcVpdTxTdpEntry ::= SEQUENCE {
   mscAtmIfVpcVpdTxTdpIndex
      Integer32,
   mscAtmIfVpcVpdTxTdpValue
      Unsigned32 }

mscAtmIfVpcVpdTxTdpIndex OBJECT-TYPE
   SYNTAX     Integer32 (1..5)
   ACCESS     not-accessible
   STATUS     obsolete
   DESCRIPTION
     "This variable represents the mscAtmIfVpcVpdTxTdpTable
      specific index for the mscAtmIfVpcVpdTxTdpTable."
::= { mscAtmIfVpcVpdTxTdpEntry 1 }

mscAtmIfVpcVpdTxTdpValue OBJECT-TYPE
   SYNTAX     Unsigned32 (0..2147483647)
   ACCESS     read-write
   STATUS     obsolete
   DESCRIPTION
     "This variable represents an individual value for the
      mscAtmIfVpcVpdTxTdpTable."
::= { mscAtmIfVpcVpdTxTdpEntry 2 }

mscAtmIfVpcVpdRxTdpTable OBJECT-TYPE
   SYNTAX     SEQUENCE OF MscAtmIfVpcVpdRxTdpEntry
   ACCESS     not-accessible
   STATUS     obsolete
   DESCRIPTION
     "This attribute is migrated to the AtmTmProv group.
      
      This attribute is a vector of four traffic parameters whose meanings 
      are defined by the rxTrafficDescType attribute. The values of peak 
      cell rate (PCR) and sustained cell rate (SCR) are expressed in 
      cell/s. Maximum burst size (MBS) is expressed in cells. The value 
      of CDVT is expressed in microseconds. The values of PCR, SCR, 
      MBS and CDVT are used for usage parameter control (UPC).
      
      When rxTrafficDescType is 1 or 2, all of the parameters must be set 
      to zero (unused).
      
      When rxTrafficDescType is 3, parameter 1 represents the PCR for 
      CLP equal to 0 and 1 traffic. Parameter 1 must be non-zero. 
      Parameters 2 and 3 must be set to zero (unused).
      
      When rxTrafficDescType is 4, parameter 1 represents the PCR for 
      CLP equal to 0 and 1 traffic; parameter 2 represents the PCR for 
      CLP equal to 0 traffic with cell discard. Parameters 1 and 2 must be 
      non-zero. Parameter 3 must be set to zero (unused). Parameter 1 
      must be greater than or equal to parameter 2.
      
      When rxTrafficDescType is 5, parameter 1 represents the PCR for 
      CLP equal to 0 and 1 traffic; parameter 2 represents the PCR for 
      CLP equal to 0 traffic with cell tagging. Parameters 1 and 2 must be 
      non-zero. Parameter 3 must be set to zero (unused). Parameter 1 
      must be greater than or equal to parameter 2.
      
      When rxTrafficDescType is a 6, parameter 1 represents the PCR for 
      CLP equal to 0 and 1 traffic; parameter 2 represents the SCR for 
      CLP equal to 0 and 1 traffic; parameter 3 represents the MBS for 
      CLP equal to 0 and 1 traffic. Parameters 1, 2 and 3 must be non-
      zero. Parameter 1 must be greater than or equal to Parameter 2. 
      
      When rxTrafficDescType is 7, parameter 1 represents the PCR for 
      CLP equal to 0 and 1 traffic; parameter 2 represents the SCR for 
      CLP equal to 0 traffic with cell discard; parameter 3 represents the 
      MBS for CLP equal to 0 traffic. Parameters 1, 2 and 3 must be non-
      zero. Parameter 1 must be greater than or equal to parameter 2. 
      
      When rxTrafficDescType is 8, parameter 1 represents the PCR for 
      CLP equal to 0 and 1 traffic; parameter 2 represents the SCR for 
      CLP equal to 0 traffic with cell tagging; parameter 3 represents the 
      MBS for CLP equal to 0 traffic. Parameter 1, 2 and 3 must be non-
      zero. Parameter 1 must be greater than or equal to parameter 2.
      
      When rxTrafficDescType is any value from 3 through 8, parameter 
      4 represents the CDVT. If this value is zero, the CDVT is taken 
      from the ConnectionAdministrator defaults for the particular 
      atmServiceCategory of this connection.
      
      When rxTrafficDescriptorType is 3 through 8, there are certain 
      extreme combinations of rxTrafficDescParm which are outside the 
      capabilities of the UPC hardware. The check prov command detects 
      such cases and generates an error message. If this happens, adjust 
      the parameters until they fall within the supported limits. 
      
      To calculate the limits, use the following formulae:
      I1 = 1 000 000 000 / PCR
      L1 = CDVT * 1000
      I2 = 1 000 000 000 / SCR
      L2 = CDVT + (MBS - 1) * (I2 - I1)
      I1 and I2 must be less than or equal to 335 523 840. I1 + L1 must 
      be less than or equal to 1 342 156 800. I2 + L2 must be less than or 
      equal to 1 342 156 800. Note that I2 and L2 only apply when the 
      rxTrafficDescriptorType is 6 through 8.
      
      If the values of I1, L1, I2 or L2 are closer to the limits described 
      above, a further restriction applies. Specifically, if either:
      I1 > 41 940 480 or
      I2 > 41 940 480 or
      I1 + L1 > 167 769 600 or
      I2 + L2 > 167 769 600
      then both I1 and I2 must be greater than 20 480. 
      
      Parameter 5 of the rxTrafficDescParm is always unused. 
      
      If the rxTrafficDescType is sameAsTx, the values in this attribute 
      are taken from the txTrafficDescParm."
::= { mscAtmIfVpcVpd 298 }

mscAtmIfVpcVpdRxTdpEntry OBJECT-TYPE
   SYNTAX     MscAtmIfVpcVpdRxTdpEntry
   ACCESS     not-accessible
   STATUS     obsolete
   DESCRIPTION
     "An entry in the mscAtmIfVpcVpdRxTdpTable."
   INDEX {
      mscAtmIfIndex,
      mscAtmIfVpcIndex,
      mscAtmIfVpcVpdIndex,
      mscAtmIfVpcVpdRxTdpIndex }
::= { mscAtmIfVpcVpdRxTdpTable 1 }

MscAtmIfVpcVpdRxTdpEntry ::= SEQUENCE {
   mscAtmIfVpcVpdRxTdpIndex
      Integer32,
   mscAtmIfVpcVpdRxTdpValue
      Unsigned32 }

mscAtmIfVpcVpdRxTdpIndex OBJECT-TYPE
   SYNTAX     Integer32 (1..5)
   ACCESS     not-accessible
   STATUS     obsolete
   DESCRIPTION
     "This variable represents the mscAtmIfVpcVpdRxTdpTable
      specific index for the mscAtmIfVpcVpdRxTdpTable."
::= { mscAtmIfVpcVpdRxTdpEntry 1 }

mscAtmIfVpcVpdRxTdpValue OBJECT-TYPE
   SYNTAX     Unsigned32 (0..2147483647)
   ACCESS     read-write
   STATUS     obsolete
   DESCRIPTION
     "This variable represents an individual value for the
      mscAtmIfVpcVpdRxTdpTable."
::= { mscAtmIfVpcVpdRxTdpEntry 2 }

mscAtmIfVpcVpdFqpTable OBJECT-TYPE
   SYNTAX     SEQUENCE OF MscAtmIfVpcVpdFqpEntry
   ACCESS     not-accessible
   STATUS     obsolete
   DESCRIPTION
     "This attribute is migrated to the AtmTmProv group.
      
      This attribute is a vector of three elements that specify the quality of 
      service parameters for the forward direction for this connection. 
      This attribute is used for SPVC connections.
      
      The cdv element specifies the acceptable peak-to-peak Cell Delay 
      Variation (CDV) of real-time connections (CBR, and rt-VBR). It is 
      signalled through the extended QoS information element.
      
      The ctd specifies the acceptable maximum Cell Transfer Delay 
      (maxCtd) of real-time connections (CBR, and rt-VBR). 
      It is signalled through the end to end transit delay information 
      element.
      
      The clr specifies the acceptable Cell Loss Ratio (CLR) of CBR, rt-
      VBR, and nrt-VBR connections. It is signalled through the extended 
      QoS information element."
::= { mscAtmIfVpcVpd 359 }

mscAtmIfVpcVpdFqpEntry OBJECT-TYPE
   SYNTAX     MscAtmIfVpcVpdFqpEntry
   ACCESS     not-accessible
   STATUS     obsolete
   DESCRIPTION
     "An entry in the mscAtmIfVpcVpdFqpTable."
   INDEX {
      mscAtmIfIndex,
      mscAtmIfVpcIndex,
      mscAtmIfVpcVpdIndex,
      mscAtmIfVpcVpdFqpIndex }
::= { mscAtmIfVpcVpdFqpTable 1 }

MscAtmIfVpcVpdFqpEntry ::= SEQUENCE {
   mscAtmIfVpcVpdFqpIndex
      INTEGER,
   mscAtmIfVpcVpdFqpValue
      Unsigned32 }

mscAtmIfVpcVpdFqpIndex OBJECT-TYPE
   SYNTAX     INTEGER  {
                 cdv(0),
                 ctd(1),
                 clr(2) }
   ACCESS     not-accessible
   STATUS     obsolete
   DESCRIPTION
     "This variable represents the mscAtmIfVpcVpdFqpTable
      specific index for the mscAtmIfVpcVpdFqpTable."
::= { mscAtmIfVpcVpdFqpEntry 1 }

mscAtmIfVpcVpdFqpValue OBJECT-TYPE
   SYNTAX     Unsigned32 (0..2147483647)
   ACCESS     read-write
   STATUS     obsolete
   DESCRIPTION
     "This variable represents an individual value for the
      mscAtmIfVpcVpdFqpTable."
::= { mscAtmIfVpcVpdFqpEntry 2 }

mscAtmIfVpcVpdBqpTable OBJECT-TYPE
   SYNTAX     SEQUENCE OF MscAtmIfVpcVpdBqpEntry
   ACCESS     not-accessible
   STATUS     obsolete
   DESCRIPTION
     "This attribute is migrated to the AtmTmProv group.
      
      This attribute is a vector of three elements that specify the quality of 
      service parameters for the backward direction for this connection. 
      This attribute is used for SPVC connections.
      
      The cdv element specifies the acceptable peak-to-peak Cell Delay 
      Variation (CDV) of real-time connections (CBR, and rt-VBR). 
      
      It is signalled through the extended QoS information element.
      
      The ctd specifies the acceptable maximum Cell Transfer Delay 
      (maxCtd) of real-time connections (CBR, and rt-VBR). It is 
      signalled through the end to end transit delay information element.
      
      The clr specifies the acceptable Cell Loss Ratio (CLR) of CBR, rt-
      VBR, and nrt-VBR connections. It is signalled through the extended 
      QoS information element."
::= { mscAtmIfVpcVpd 360 }

mscAtmIfVpcVpdBqpEntry OBJECT-TYPE
   SYNTAX     MscAtmIfVpcVpdBqpEntry
   ACCESS     not-accessible
   STATUS     obsolete
   DESCRIPTION
     "An entry in the mscAtmIfVpcVpdBqpTable."
   INDEX {
      mscAtmIfIndex,
      mscAtmIfVpcIndex,
      mscAtmIfVpcVpdIndex,
      mscAtmIfVpcVpdBqpIndex }
::= { mscAtmIfVpcVpdBqpTable 1 }

MscAtmIfVpcVpdBqpEntry ::= SEQUENCE {
   mscAtmIfVpcVpdBqpIndex
      INTEGER,
   mscAtmIfVpcVpdBqpValue
      Unsigned32 }

mscAtmIfVpcVpdBqpIndex OBJECT-TYPE
   SYNTAX     INTEGER  {
                 cdv(0),
                 ctd(1),
                 clr(2) }
   ACCESS     not-accessible
   STATUS     obsolete
   DESCRIPTION
     "This variable represents the mscAtmIfVpcVpdBqpTable
      specific index for the mscAtmIfVpcVpdBqpTable."
::= { mscAtmIfVpcVpdBqpEntry 1 }

mscAtmIfVpcVpdBqpValue OBJECT-TYPE
   SYNTAX     Unsigned32 (0..2147483647)
   ACCESS     read-write
   STATUS     obsolete
   DESCRIPTION
     "This variable represents an individual value for the
      mscAtmIfVpcVpdBqpTable."
::= { mscAtmIfVpcVpdBqpEntry 2 }


-- AtmIf/n Vcc/vpi.vci Vcd TrafficManagement, 
-- AtmIf/n Vpc/vci Vpd TrafficManagement,
-- AtmIf/n Vpt/vpi Vpd TrafficManagement,
-- AtmIf/n Vpt/vpi Vcc/vci Vcd TrafficManagement
-- This component contains provisioned traffic management attributes 
-- of a connection. It is added automatically when a Vcc, Vpc, or Vpt is 
-- added in provisioning mode. It is a mandatory subcomponent of the 
-- Vcd or Vpd component.

mscAtmIfVpcVpdTm OBJECT IDENTIFIER ::= { mscAtmIfVpcVpd 2 }



mscAtmIfVpcVpdTmRowStatusTable OBJECT-TYPE
   SYNTAX     SEQUENCE OF MscAtmIfVpcVpdTmRowStatusEntry
   ACCESS     not-accessible
   STATUS     mandatory
   DESCRIPTION
     "This entry controls the addition and deletion of 
      mscAtmIfVpcVpdTm components."
::= { mscAtmIfVpcVpdTm 1 }

mscAtmIfVpcVpdTmRowStatusEntry OBJECT-TYPE
   SYNTAX     MscAtmIfVpcVpdTmRowStatusEntry
   ACCESS     not-accessible
   STATUS     mandatory
   DESCRIPTION
     "A single entry in the table represents a single 
      mscAtmIfVpcVpdTm component."
   INDEX {
      mscAtmIfIndex,
      mscAtmIfVpcIndex,
      mscAtmIfVpcVpdIndex,
      mscAtmIfVpcVpdTmIndex }
::= { mscAtmIfVpcVpdTmRowStatusTable 1 }

MscAtmIfVpcVpdTmRowStatusEntry ::= SEQUENCE {
   mscAtmIfVpcVpdTmRowStatus
      RowStatus,
   mscAtmIfVpcVpdTmComponentName
      DisplayString,
   mscAtmIfVpcVpdTmStorageType
      StorageType,
   mscAtmIfVpcVpdTmIndex
      NonReplicated }

mscAtmIfVpcVpdTmRowStatus OBJECT-TYPE
   SYNTAX     RowStatus 
   ACCESS     read-only
   STATUS     mandatory
   DESCRIPTION
     "This variable is used as the basis for SNMP naming of
      mscAtmIfVpcVpdTm components.
      These components cannot be added nor deleted."
::= { mscAtmIfVpcVpdTmRowStatusEntry 1 }

mscAtmIfVpcVpdTmComponentName OBJECT-TYPE
   SYNTAX     DisplayString 
   ACCESS     read-only
   STATUS     mandatory
   DESCRIPTION
     "This variable provides the component's string name for
      use with the ASCII Console Interface"
::= { mscAtmIfVpcVpdTmRowStatusEntry 2 }

mscAtmIfVpcVpdTmStorageType OBJECT-TYPE
   SYNTAX     StorageType 
   ACCESS     read-only
   STATUS     mandatory
   DESCRIPTION
     "This variable represents the storage type value for the
      mscAtmIfVpcVpdTm tables."
::= { mscAtmIfVpcVpdTmRowStatusEntry 4 }

mscAtmIfVpcVpdTmIndex OBJECT-TYPE
   SYNTAX     NonReplicated 
   ACCESS     not-accessible
   STATUS     mandatory
   DESCRIPTION
     "This variable represents the index for the mscAtmIfVpcVpdTm tables."
::= { mscAtmIfVpcVpdTmRowStatusEntry 10 }

mscAtmIfVpcVpdTmProvTable OBJECT-TYPE
   SYNTAX     SEQUENCE OF MscAtmIfVpcVpdTmProvEntry
   ACCESS     not-accessible
   STATUS     mandatory
   DESCRIPTION
     "This group contains traffic related provisionable attributes for the 
      Vcc, Vpc, and Vpt components. Changing any of the attributes in 
      this group causes a service interruption on the Vcc, Vpc, or Vpt 
      component."
::= { mscAtmIfVpcVpdTm 100 }

mscAtmIfVpcVpdTmProvEntry OBJECT-TYPE
   SYNTAX     MscAtmIfVpcVpdTmProvEntry
   ACCESS     not-accessible
   STATUS     mandatory
   DESCRIPTION
     "An entry in the mscAtmIfVpcVpdTmProvTable."
   INDEX {
      mscAtmIfIndex,
      mscAtmIfVpcIndex,
      mscAtmIfVpcVpdIndex,
      mscAtmIfVpcVpdTmIndex }
::= { mscAtmIfVpcVpdTmProvTable 1 }

MscAtmIfVpcVpdTmProvEntry ::= SEQUENCE {
   mscAtmIfVpcVpdTmTxTrafficDescType
      INTEGER,
   mscAtmIfVpcVpdTmFwdQosClass
      INTEGER,
   mscAtmIfVpcVpdTmTxQueueLimit
      Unsigned32,
   mscAtmIfVpcVpdTmHoldingPriority
      INTEGER,
   mscAtmIfVpcVpdTmRxTrafficDescType
      INTEGER,
   mscAtmIfVpcVpdTmBwdQosClass
      INTEGER,
   mscAtmIfVpcVpdTmAtmServiceCategory
      INTEGER,
   mscAtmIfVpcVpdTmTrafficShaping
      INTEGER,
   mscAtmIfVpcVpdTmUnshapedTransmitQueueing
      INTEGER,
   mscAtmIfVpcVpdTmWeight
      Unsigned32,
   mscAtmIfVpcVpdTmForceTagging
      INTEGER,
   mscAtmIfVpcVpdTmUsageParameterControl
      INTEGER,
   mscAtmIfVpcVpdTmBearerClassBbc
      INTEGER,
   mscAtmIfVpcVpdTmTransferCapabilityBbc
      INTEGER,
   mscAtmIfVpcVpdTmClippingBbc
      INTEGER,
   mscAtmIfVpcVpdTmBestEffort
      INTEGER,
   mscAtmIfVpcVpdTmTxPacketWiseDiscard
      INTEGER,
   mscAtmIfVpcVpdTmRxPacketWiseDiscard
      INTEGER,
   mscAtmIfVpcVpdTmAbrConnectionType
      INTEGER }

mscAtmIfVpcVpdTmTxTrafficDescType OBJECT-TYPE
   SYNTAX     INTEGER  {
                 n1(1),
                 n2(2),
                 n3(3),
                 n4(4),
                 n5(5),
                 n6(6),
                 n7(7),
                 n8(8),
                 n9(9) }
   ACCESS     read-write
   STATUS     mandatory
   DESCRIPTION
     "This attribute specifies the type of traffic management which is 
      applied to the transmit direction of this connection as defined in the 
      ATM Forum. The txTrafficDescType determines the number and 
      meaning of the parameters in the txTrafficDescParm attribute.
      
      This attribute can have a value of 9 if and only if the 
      atmServiceCategory is availableBitRate."
   DEFVAL     { n1 }
::= { mscAtmIfVpcVpdTmProvEntry 10 }

mscAtmIfVpcVpdTmFwdQosClass OBJECT-TYPE
   SYNTAX     INTEGER  {
                 n0(0),
                 n1(1),
                 n2(2),
                 n3(3),
                 n4(4) }
   ACCESS     read-write
   STATUS     mandatory
   DESCRIPTION
     "This attribute specifies the quality of service for the forward 
      direction for this connection. This attribute is only used for SPVC 
      connections.
      
      Class 1 supports a QOS that meets Service Class A performance 
      requirements (circuit emulation, constant bit rate video).
      
      Class 2 supports a QOS that meets Service Class B performance 
      requirements (variable bit rate audio and video).
      
      Class 3 supports a QOS that meets Service Class C performance 
      requirements (Connection-Oriented Data Transfer).
      
      Class 4 supports a QOS that meets Service Class D performance 
      requirements (Connectionless Data Transfer).
      
      Class 0 is the unspecified bit rate QOS class; no objective is 
      specified for the performance parameters."
   DEFVAL     { n0 }
::= { mscAtmIfVpcVpdTmProvEntry 21 }

mscAtmIfVpcVpdTmTxQueueLimit OBJECT-TYPE
   SYNTAX     Unsigned32 (0 | 5..512000)
   ACCESS     read-write
   STATUS     mandatory
   DESCRIPTION
     "This attribute specifies an override to the default transmit queue 
      limit for this connection. An value other than sameAsCa may be 
      specified only for ATM IP and 1pOC48SmSrAtm cards. This 
      attribute is not applicable for basic Vpts.
      
      A value of sameAsCa means to use the default common or per-VC 
      transmit queue limit as defined by the CA service category for this 
      connection. 
      
      A value from 5 to 63,488 indicates that a specific transmit queue 
      limit is requested which differs from the default which is defined 
      under the CA component for this service category. A specific value 
      is ignored for connections where common queuing is specified for 
      the service category. 
      
      For the 1pOC48SmSrAtm card, this attribute is used to set the per 
      VC utilization limit.
      
      The actual transmit queue limit for a connection is visible in the Vcc 
      Tm, Vpc Tm or Vpt txQueueThresholds attribute.

      VALUES (

      0 = sameAsCa

      )"
   DEFVAL     { 0 }
::= { mscAtmIfVpcVpdTmProvEntry 22 }

mscAtmIfVpcVpdTmHoldingPriority OBJECT-TYPE
   SYNTAX     INTEGER  {
                 n0(0),
                 n1(1),
                 n2(2),
                 n3(3),
                 n4(4) }
   ACCESS     read-write
   STATUS     mandatory
   DESCRIPTION
     "This attribute specifies the holding priority of this connection. In a 
      situation where the link bandwidth fluctuates, such as over an IMA 
      link, holding priority is used to determine which connections are 
      held and which are released. Holding priority 4 connections are the 
      first to be released. Holding priority 0 connections are the last to be 
      released. This value provisioned in the Vcd or Vpd may be 
      overridden by certain applications, for example Vcc Test, which run 
      over this connection. The default holding priority for a provisioned 
      connection is higher then default holding priorities for dynamic 
      (SVC) connections. 
      
      This attribute is not applicable for Vpt Vccs."
   DEFVAL     { n2 }
::= { mscAtmIfVpcVpdTmProvEntry 25 }

mscAtmIfVpcVpdTmRxTrafficDescType OBJECT-TYPE
   SYNTAX     INTEGER  {
                 n1(1),
                 n2(2),
                 n3(3),
                 n4(4),
                 n5(5),
                 n6(6),
                 n7(7),
                 n8(8),
                 n9(9),
                 sameAsTx(15) }
   ACCESS     read-write
   STATUS     mandatory
   DESCRIPTION
     "This attribute specifies the type of traffic management which is 
      applied to the receive direction of this connection as defined in the 
      ATM Forum. The rxTrafficDescType determines the number and 
      meaning of the parameters in the rxTrafficDescParm attribute.
      
      When this attribute is set to sameAsTx, the rxTrafficDescType as 
      well as the rxTrafficDescParm are taken from the 
      txTrafficDescType and txTrafficDescParm values."
   DEFVAL     { sameAsTx }
::= { mscAtmIfVpcVpdTmProvEntry 30 }

mscAtmIfVpcVpdTmBwdQosClass OBJECT-TYPE
   SYNTAX     INTEGER  {
                 n0(0),
                 n1(1),
                 n2(2),
                 n3(3),
                 n4(4),
                 sameAsFwd(15) }
   ACCESS     read-write
   STATUS     mandatory
   DESCRIPTION
     "This attribute specifies the quality of service for the backward 
      direction for this connection. This attribute is only used for SPVC 
      connections.
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified bit rate QOS class; no objective is 
      specified for the performance parameters.
      
      The sameAsFwd selection sets the backward quality of service to 
      be the same as the forward quality of service."
   DEFVAL     { sameAsFwd }
::= { mscAtmIfVpcVpdTmProvEntry 41 }

mscAtmIfVpcVpdTmAtmServiceCategory OBJECT-TYPE
   SYNTAX     INTEGER  {
                 unspecifiedBitRate(0),
                 constantBitRate(1),
                 rtVariableBitRate(2),
                 nrtVariableBitRate(3),
                 availableBitRate(4),
                 derivedFromBBC(15) }
   ACCESS     read-write
   STATUS     mandatory
   DESCRIPTION
     "This attribute specifies the ATM service category for both directions 
      of the connection. 
      
      The value derivedFromBBC may only be used if the SrcPvc 
      component is provisioned under this Vcc. Otherwise a specific 
      ATM service category must be specified. 
      
      If this attribute is set to derivedFromBBC, the Broadband Bearer 
      Capability (BBC) and bestEffort attributes are used to determine the 
      atmServiceCategory of this connection. 
      
      If this attribute is set to other than derivedFromBBC, the value of 
      this attribute is used to override the provisioned BBC Information 
      Element parameters. In those cases, the BBC attributes are not used. 
      
      The constantBitRate service category is intended for real time 
      applications, that is those requiring tightly constrained delay and 
      delay variation, as would be appropriate for voice and video 
      applications. The consistent availability of a fixed quantity of 
      bandwidth is considered appropriate for CBR service. Cells which 
      are delayed beyond the value specified by Cell Transfer Delay are 
      assumed to be of significantly reduced value to the application.
      
      The rtVariableBitRate service category is intended for real time 
      applications, that is those requiring tightly constrained delay and 
      delay variation, as would be appropriate for voice and video 
      applications. Sources are expected to transmit at a rate which varies 
      with time. Equivalently, the source can be described as 'bursty'. 
      Cells which are delayed beyond the value specified by CTD are 
      assumed to be of significantly reduced value to the application. Real 
      time VBR service may support statistical multiplexing of real time 
      sources.
      
      The nrtVariableBitRate service category is intended for non-real 
      time applications which have bursty traffic characteristics and which 
      can be characterized in terms of a PCR, SCR, and MBS. For those 
      cells which are transferred within the traffic contract, the application 
      expects a low cell loss ratio. For all connections, it expects a bound 
      on the mean cell transfer delay. Non-real time VBR service may 
      support statistical multiplexing of connections. 
      
      The availableBitRate service is an ATM layer service category for 
      which the limiting ATM layer transfer characteristics provided by 
      the network may change subsequent to connection establishment. 
      ABR service has a flow control mechanism which supports several 
      types of feedback to control the source rate in response to changing 
      ATM layer transfer characteristics. ABR service is not intended to 
      support real-time applications. 
      
      The unspecifiedBitRate service is intended for non-real time 
      applications; that is, those not requiring tightly constrained delay 
      and delay variation. UBR sources are expected to be bursty. UBR 
      service supports a high degree of statistical multiplexing among 
      sources. UBR service does not specify traffic related service 
      guarantees. No numerical commitments are made with respect to 
      the cell loss ratio experienced by a UBR connection, or as to the 
      cell transfer delay experienced by cells on the connection."
   DEFVAL     { unspecifiedBitRate }
::= { mscAtmIfVpcVpdTmProvEntry 42 }

mscAtmIfVpcVpdTmTrafficShaping OBJECT-TYPE
   SYNTAX     INTEGER  {
                 disabled(1),
                 sameAsCa(2) }
   ACCESS     read-write
   STATUS     mandatory
   DESCRIPTION
     "This attribute specifies whether this connection uses traffic shaping 
      when transmitting traffic to the ATM interface.
      
      This attribute is ignored if the atmServiceCategory is 
      availableBitRate.
      
      Traffic shaping is not available on the 1pOC12SmLrAtm card, 
      therefore this attribute is ignored.
      
      When sameAsCa is selected, traffic shaping for the connection is 
      based on the trafficShaping attribute of the connection's service 
      category component under the CA. If the service category has 
      trafficShaping set to enabled or inverseUpc, then traffic shaping is 
      enabled for the connection. Note that enabling traffic shaping may 
      have no effect under certain cases. These cases are listed in the 
      description of the trafficShaping operational attribute, which is 
      under the Vcc Tm, Vpc Tm, or Vpt Tm components.
      
      When disabled is selected, traffic shaping for this connection is 
      disabled regardless of the provisioning of the connection's service 
      category component."
   DEFVAL     { sameAsCa }
::= { mscAtmIfVpcVpdTmProvEntry 50 }

mscAtmIfVpcVpdTmUnshapedTransmitQueueing OBJECT-TYPE
   SYNTAX     INTEGER  {
                 common(1),
                 sameAsCa(3) }
   ACCESS     read-write
   STATUS     mandatory
   DESCRIPTION
     "This attribute only applies when this connection is unshaped. This 
      attribute specifies the transmit queueing method for this connection 
      if it is unshaped. The two possible methods are per-VC queuing and 
      common queuing. 
      
      On ATM IP FPs, this attribute must be set to sameAsCa. 
      
      This attribute is ignored in the following situations:
      - if the connection has trafficShaping enabled or inverseUpc, or 
      - if the atmServiceCategory is availableBitRate, or
      - if the atmServiceCategory is constantBitRate and this is a CQC-
      based ATM FP.
      - for basic Vpts and standard Vpt Vccs
      
      When this attribute is set to sameAsCa, the transmit queueing 
      method for the connection is based on the 
      unshapedTransmitQueueing attribute of the connection's service 
      category component under the CA. 
      
      When this attribute is set to common, transmit traffic on this 
      unshaped connection is destined for the common queue."
   DEFVAL     { sameAsCa }
::= { mscAtmIfVpcVpdTmProvEntry 60 }

mscAtmIfVpcVpdTmWeight OBJECT-TYPE
   SYNTAX     Unsigned32 (0 | 1..4095 | 65535)
   ACCESS     read-write
   STATUS     mandatory
   DESCRIPTION
     "This attribute specifies an override for the weight of this unshaped 
      connection. This attribute is ignored for shaped connections, for 
      ABR connections, for connections on a CQC-based ATM FP and 
      basic Vpts.
      
      When the value is set to sameAsCa, the weight is determined by the 
      fairnessWeight attribute under the CA service category component 
      for all but standard Vpt Vccs. For standard Vpt Vccs, the weight is 
      determined by the Vcc's service category, when the value is set to 
      sameAsCa.
      
      When this attribute is set to a value from 1 to 4095, that value is 
      used for the fairness weight of this connection relative to other 
      connections. For all but standard Vpt Vccs, fairness weight 
      determines the proportion of transmit cell opportunities which are 
      allocated to this connection, compared to other connections in the 
      same service category. For standard Vpt Vccs, fairness weight 
      determines the proportion of transmit cell opportunities which are 
      allocated to this connection, compared to other connections 
      associated with the Vpt.
      
      When the value is set to upToQueueLimit, the fairness weight is 
      limited only by the txQueueLimit.

      VALUES (

      0 = upToQueueLimit

      65535 = sameAsCa

      )"
   DEFVAL     { 65535 }
::= { mscAtmIfVpcVpdTmProvEntry 61 }

mscAtmIfVpcVpdTmForceTagging OBJECT-TYPE
   SYNTAX     INTEGER  {
                 enabled(0),
                 disabled(1),
                 sameAsCa(2) }
   ACCESS     read-write
   STATUS     mandatory
   DESCRIPTION
     "This attribute specifies whether force tagging is enforced for this 
      connection for cells in the transmit direction. 
      
      On CQC-based ATM cards and for Vpts, this attribute is not 
      applicable and is ignored. 
      
      When the value is set to sameAsCa, the force tagging functionality 
      is determined by the forceTagging attribute under the CA service 
      category component. 
      
      When the value is set to enabled, force tagging is enabled for cells 
      in the transmit direction on this connection. When this option is 
      selected, the CLP bit is set to 1 for all cells in the transmit direction. 
      Cells which are tagged are counted in the txCellClp attribute. 
      
      When the value is set to disabled, force tagging is disabled for cells 
      in the transmit direction on this connection. When this option is 
      selected, the CLP bit is unchanged for cells in the transmit 
      direction."
   DEFVAL     { sameAsCa }
::= { mscAtmIfVpcVpdTmProvEntry 62 }

mscAtmIfVpcVpdTmUsageParameterControl OBJECT-TYPE
   SYNTAX     INTEGER  {
                 enforced(0),
                 disabled(1),
                 sameAsCa(2),
                 monitored(4) }
   ACCESS     read-write
   STATUS     mandatory
   DESCRIPTION
     "This attribute specifies whether this connection enforces usage 
      parameter control when receiving traffic from the ATM interface.
      
      When sameAsCa is selected, UPC for the connection is based on 
      the usageParameterControl attribute of the service category 
      component under the AtmIf CA. If the service category has UPC 
      enforced or monitored, then UPC is set to that value for the 
      connection. 
      
      When disabled is selected, UPC for this connection is disabled 
      regardless of the provisioning of the service category. 
      
      When enforced is selected, UPC for this connection is enforced 
      regardless of the provisioning of the service category. 
      
      Note that setting UPC to enforced or monitored may have no effect 
      under certain cases. These cases are listed in the description of the 
      usageParameterControl operational attribute, which is under the 
      Vcc, Vpc, and Vpt components."
   DEFVAL     { sameAsCa }
::= { mscAtmIfVpcVpdTmProvEntry 70 }

mscAtmIfVpcVpdTmBearerClassBbc OBJECT-TYPE
   SYNTAX     INTEGER  {
                 a(1),
                 c(3),
                 x(16),
                 vp(24),
                 derivedFromServiceCategory(31) }
   ACCESS     read-write
   STATUS     mandatory
   DESCRIPTION
     "This attribute specifies the bearer capability. This attribute is only 
      used for SPVC and SPVP connections. It is one of the Broadband 
      Bearer Capability (BBC) attributes. The purpose of the BBC 
      information element is to indicate a requested broadband 
      connection-oriented bearer service to be provided by the network.
      
      The value derivedFromServiceCategory specifies that the actual 
      value which is used for this connection is derived from the value of 
      the atmServiceCategory. Either, this attribute must be set to 
      derivedFromServiceCategory, or the atmServiceCategory attribute 
      must be set to derivedFromBBC, but not both.
      
      Class a service is a connection-oriented, constant bit rate ATM 
      transport service. Class a service has end to end timing 
      requirements and may require stringent cell loss, cell delay and cell 
      delay variation performance.When a is set, the user is requesting 
      more than an ATM only service. The network may look at the AAL 
      to provide interworking based upon its contents. 
      
      Class c service is a connection-oriented, variable bit rate ATM 
      transport service. Class c service has no end-to-end timing 
      requirements. When c is set, the user is requesting more than an 
      ATM only service. The network interworking function may look at 
      the AAL and provide service based on it.
      
      Class x service is a connection-oriented ATM transport service 
      where the AAL, trafficType (vbr or cbr) and timing requirements 
      are user defined (that is, transparent to the network).When x is set 
      the user is requesting an ATM only service from the network. In this 
      case, the network shall not process any higher layer protocol.
      
      Class vp service is used to specify a transparent VP service. When 
      the value of this attribute is vp, the user is requesting an ATM only 
      service from the network. In this case, the network shall not process 
      any higher layer protocol. This service differs from class x service 
      in that with the class vp service both the VCI field (except or VCI 
      values 0, 3, 4, and 6 through 15) and Payload Type field are 
      transported transparently by the network. This attribute value is 
      only applicable to SPVP connections."
   DEFVAL     { derivedFromServiceCategory }
::= { mscAtmIfVpcVpdTmProvEntry 71 }

mscAtmIfVpcVpdTmTransferCapabilityBbc OBJECT-TYPE
   SYNTAX     INTEGER  {
                 n0(0),
                 n1(1),
                 n2(2),
                 n5(5),
                 n8(8),
                 n9(9),
                 n10(10),
                 notApplicable(30),
                 derivedFromServiceCategory(31) }
   ACCESS     read-write
   STATUS     mandatory
   DESCRIPTION
     "This attribute specifies the transfer capability for this connection. 
      Uni 3.0/3.1 traffic type and end-to-end timing parameters are 
      mapped into this parameter as follows:
      <transferCapability: TrafficType, Timing>
      0: NoIndication, NoIndication
      1: NoIndication, yes
      2: NoIndication, no
      5: CBR, yes
      8: VBR, NoIndication
      9: VBR, yes
      10: VBR, no
      
      notApplicable specifies that the user does not want to specify the 
      transfer capability.
      
      The CBR traffic type refers to traffic offered on services such as a 
      constant bit rate video service or a circuit emulation.
      The VBR traffic type refers to traffic offered on services such as 
      packetized audio and video, or data.
      
      The value no indication for traffic type is used if the user has not set 
      the traffic type; similarly for end-to-end timing.
      
      The value yes for end-to-end timing indicates that end-to-end 
      timing is required.
      
      The value no for end-to-end timing indicates that end-to-end timing 
      is not required.
      
      The value derivedFromServiceCategory specifies that the actual 
      value which is used for this connection is derived from the value of 
      the atmServiceCategory. Either, this attribute must be set to 
      derivedFromServiceCategory, or the atmServiceCategory attribute 
      must be set to derivedFromBBC, but not both."
   DEFVAL     { derivedFromServiceCategory }
::= { mscAtmIfVpcVpdTmProvEntry 72 }

mscAtmIfVpcVpdTmClippingBbc OBJECT-TYPE
   SYNTAX     INTEGER  {
                 no(0),
                 yes(1) }
   ACCESS     read-write
   STATUS     mandatory
   DESCRIPTION
     "This attribute specifies the value for the clipping susceptibility 
      parameter in the BBC Information Element. This attribute is only 
      used for SPVC connections. It is one of the Broadband Bearer 
      Capability attributes.
      
      Clipping is an impairment in which the first fraction of a second of 
      information to be transferred is lost. It occurs after a call is 
      answered and before an associated connection is switched through."
   DEFVAL     { no }
::= { mscAtmIfVpcVpdTmProvEntry 74 }

mscAtmIfVpcVpdTmBestEffort OBJECT-TYPE
   SYNTAX     INTEGER  {
                 indicated(0),
                 notIndicated(1),
                 derivedFromServiceCategory(15) }
   ACCESS     read-write
   STATUS     mandatory
   DESCRIPTION
     "This attribute specifies the value of the best effort parameter in the 
      ATM Traffic Descriptor Information Element. This attribute is only 
      used for Soft PVC connections. It is one of the Broadband Bearer 
      Capability attributes.
      
      The value indicated implies that the quality of service for this 
      connection is not guaranteed.
      
      The value notIndicated implies that the quality of service for this 
      connection is guaranteed.
      
      The value derivedFromServiceCategory specifies that the actual 
      value which is used for this connection is derived from the value of 
      the atmServiceCategory. Either, this attribute must be set to 
      derivedFromServiceCategory, or the atmServiceCategory attribute 
      must be set to derivedFromBBC, but not both."
   DEFVAL     { derivedFromServiceCategory }
::= { mscAtmIfVpcVpdTmProvEntry 75 }

mscAtmIfVpcVpdTmTxPacketWiseDiscard OBJECT-TYPE
   SYNTAX     INTEGER  {
                 disabled(0),
                 enabled(1) }
   ACCESS     read-write
   STATUS     mandatory
   DESCRIPTION
     "This attribute specifies whether packet-wise discard functions are to 
      be enabled or disabled in the transmit data direction for this 
      connection. Packet-wise discard functions should only be requested 
      if this connection is transferring AAL5 frame traffic. This attribute 
      is not applicable for Vpts.
      
      Packet-wise functions increase the 'goodput' of the link. The 
      transmit packet-wise functions are Early Packet Discard (EPD) and 
      Partial Packet Discard (PPD). 
      
      EPD allows the connection to discard an entire frame once the 
      transmit queue has reached the EPD threshold. EPD increases the 
      'goodput' of a link, since discarding an entire frame means that 
      some queue capacity is guarded for some other frame which is 
      already partially transmitted. All cells of the frame are discarded 
      from the Beginning of Message (BOM) cell up to and including the 
      End of Message (EOM) cell. 
      
      PPD allows the connection to discard the remainder of a cell-
      forwarded AAL5 frame if one cell of this frame has been discarded. 
      All cells are discarded up to but not including the EOM cell. The 
      PPD function increases the 'goodput' of the link, since cells which 
      are only going to be discarded at the AAL5 reassembly point are 
      not transmitted.
      
      On CQC-based ATM cards, the packet-wise discard functions are 
      PPD and EPD. PPD is available at VCC cell-transfer points. PPD is 
      not applicable at frame-cell conversion points, and is not applicable 
      for Vpcs. PPD is configured by this attribute. Packet-wise discard 
      should only be enabled for connections carrying AAL5 
      segmentation traffic. Setting the value to enabled for any other 
      traffic type may result in all traffic being discarded. On CQC-based 
      ATM FPs, EPD is automatically enabled at frame-to-cell conversion 
      points, independent of the setting of this attribute. 
      
      On CQC-based ATM cards, at a permanent VCC connection 
      endpoint, this attribute is not applicable and is ignored. If AAL5 
      segmentation and reassembly has been requested, PPD and Early 
      Packet Discard (EPD) are automatically enabled.
      
      On ATM IP cards, packet-wise discard functions include EPD and 
      PPD. PPD and EPD apply to individual VCCs and VCCs within 
      VPCs at all connection points, including tandem VPC connections. 
      Both PPD and EPD are controlled by this attribute. This attribute 
      may safely be set to enabled for any connection (Vcc or Vpc) on 
      ATM IP FPs since they have the ability to automatically detect 
      AAL5-segmented traffic on a connection, and only enable packet-
      wise discards if AAL5-segmented traffic is detected.
      
      When this attribute is set to enabled, packet-wise discard functions 
      are applied to transmit traffic at this connection point. When this 
      attribute is set to disabled, packet-wise discard functions are not 
      applied to transmit traffic at this connection point.
      
      At a SPVC origin on a PNNI interface, a value of enabled specifies 
      that frame discard is requested in the backward direction. When this 
      attribute is set to disabled, backward frame discard is not requested 
      in the SPVC call setup. 
      
      The transmit packet-wise discard functions that are active are 
      visible in the Vcc/Vpc Tm txPacketWiseDiscard operational 
      attribute."
   DEFVAL     { disabled }
::= { mscAtmIfVpcVpdTmProvEntry 76 }

mscAtmIfVpcVpdTmRxPacketWiseDiscard OBJECT-TYPE
   SYNTAX     INTEGER  {
                 disabled(0),
                 enabled(1) }
   ACCESS     read-write
   STATUS     mandatory
   DESCRIPTION
     "This attribute specifies whether packet-wise discard functions are to 
      be enabled or disabled in the receive data direction for this 
      connection. Packet-wise discard functions should only be requested 
      if this connection is transferring AAL5 frame traffic. This attribute 
      is not applicable for Vpts.
      
      Packet-wise functions increase the 'goodput' of the link. The 
      receive packet-wise function is Partial Packet Discard (PPD). 
      
      PPD allows the connection to discard the remainder of a cell-
      forwarded AAL5 frame if one cell of this frame has been discarded, 
      for example due to UPC. All cells are discarded up to but not 
      including the EOM cell. The PPD function increases the 'goodput' 
      of the link, since cells which are only going to be discarded at the 
      AAL5 reassembly point are not transmitted.
      
      PPD is available at all VCC connection points where UPC may be 
      activated. PPD is not applicable for Vpcs. 
      
      On CQC-based ATM FPs, packet-wise discards should only be 
      enabled for connections carrying AAL5 segmentation traffic. 
      Setting the value to enabled for any other traffic type may result in 
      traffic being discarded. 
      
      On CQC-based ATM cards, at a permanent VCC connection 
      endpoint, this attribute is not applicable and is ignored. If AAL5 
      segmentation and reassembly has been requested, PPD and Early 
      Packet Discard (EPD) are automatically enabled.
      
      On ATM IP cards, this attribute may safely be set to enabled for any 
      connection (Vcc or Vpc) since they have the ability to automatically 
      detect AAL5-segmented traffic on a connection, and only enables 
      packet-wise discards if AAL5-segmented traffic is detected.
      
      When this attribute is set to enabled, packet-wise discard functions 
      are applied to receive traffic at this connection point. When this 
      attribute is set to disabled, packet-wise discard functions are not 
      applied to receive traffic at this connection point.
      
      At a SPVC origin on a PNNI interface, a value of enabled specifies 
      that frame discard is requested in the forward direction. When this 
      attribute is set to disabled, forward frame discard is not requested in 
      the SPVC call setup. 
      
      The receive packet-wise discard functions that are active are visible 
      in the Vcc/Vpc Tm rxPacketWiseDiscard operational attribute."
   DEFVAL     { disabled }
::= { mscAtmIfVpcVpdTmProvEntry 78 }

mscAtmIfVpcVpdTmAbrConnectionType OBJECT-TYPE
   SYNTAX     INTEGER  {
                 abrSwitch(0),
                 virtualSourceDest(3),
                 sourceDest(4),
                 nonAbrInterworking(5),
                 sameAsCa(14) }
   ACCESS     read-write
   STATUS     mandatory
   DESCRIPTION
     "This attribute specifies the type of ABR behavior which is to be 
      enforced at this connection. This attribute is only applicable if the 
      atmServiceCategory attribute is availableBitRate. If the 
      atmServicecategory attribute is not availableBitRate, this attribute 
      value is ignored.
      
      The actual ABR functionality which is in effect is visible in the 
      Vcc/Vpc/Vpt Tm abrConnectionType operational attribute.
      
      For CQC-based ATM cards, the only allowable values are 
      sameAsCa, nonAbrInterworking or abrSwitch. If abrSwitch is 
      selected, the CQC implements EFCI marking behavior.
      
      For the 1pOC12SmLrAtm card, the only allowable values are 
      sameAsCa or abrSwitch. If abrSwitch is selected, EFCI marking 
      behavior is implemented.
      
      sameAsCa is used to request the default behavior as specified in the 
      CA Abr component for this Vcc. Otherwise, this attribute overrides 
      the default behavior. 
      
      virtualSourceDest is used to request that this connection point 
      function as a virtual source/virtual destination. VS/VD functionality 
      is only supported on ATM IP FPs.
      
      sourceDest requires that this connection point function as a S/D for 
      RM cells. S/D mode is automatically invoked at this connection 
      point either if this is a connection end point, or if the next hop 
      connection point is configured as nonAbrInterworking.
      
      nonAbrInterworking is used to request that this connection point 
      function as an interworking between ABR and non-ABR service 
      categories. This means that there are no RM cells on the link side of 
      this connection, and that the next hop connection point is 
      performing as an ABR sourceDest.
      
      abrSwitch is used to request ABR switch behavior for this 
      connection point. The ABR switch behavior is first, to confirm to 
      virtualSourceDest or nonAbrInterworking setting on the next hop, 
      and otherwise to implement ABR ER switch behavior. For CQC-
      based FPs, ABR switch behavior is implemented as EFCI marking."
   DEFVAL     { sameAsCa }
::= { mscAtmIfVpcVpdTmProvEntry 90 }

mscAtmIfVpcVpdTmTxTdpTable OBJECT-TYPE
   SYNTAX     SEQUENCE OF MscAtmIfVpcVpdTmTxTdpEntry
   ACCESS     not-accessible
   STATUS     mandatory
   DESCRIPTION
     "This attribute is a vector of five traffic parameters whose meanings 
      are defined by the txTrafficDescType attribute. 
      
      The values of peak cell rate (PCR), sustained cell rate (SCR), 
      Minimum Cell Rate (MCR) and requested shaping rate are 
      expressed in cell/s. Maximum burst size (MBS) is expressed in 
      cells. CDVT is expressed in microseconds. The values of PCR, 
      SCR, MCR, MBS and CDVT are used for connection admission 
      control (CAC). The value of CDVT is only used for connections 
      where the atmServiceCategory is constantBitRate. For all other 
      values of atmServiceCategory, CDVT is ignored. The values of 
      PCR, SCR, MCR and requested shaping rate are used to determine 
      the actual shaping rate where traffic shaping is enabled.
      
      When txTrafficDescType is 1 or 2, all of the parameters must be set 
      to zero.
      
      When txTrafficDescType is 3, parameter 1 represents the PCR for 
      CLP equal to 0 and 1 traffic; parameter 4 represents the CDVT; and 
      parameter 5 represents the requested shaping rate. A non-zero value 
      in parameter 5 overrides any value in parameter 1. This result is 
      used as the PCR. Parameter 1 must be non-zero. Parameters 2 and 3 
      must be zero.
      
      When txTrafficDescType is 4, parameter 1 represents the PCR for 
      CLP equal to 0 and 1 traffic with cell discard; parameter 2 
      represents the PCR for CLP equal to 0 traffic; parameter 4 
      represents the CDVT; and parameter 5 represents the requested 
      shaping rate. A non-zero value in parameter 5 overrides any value in 
      parameter 1. This result is used as the PCR. Parameter 1 must be 
      greater than or equal to parameter 2. Parameters 1 and 2 must be 
      non-zero. Parameter 3 must be zero.
      
      When txTrafficDescType is 5, parameter 1 represents the PCR for 
      CLP equal to 0 and 1 traffic with cell tagging; parameter 2 
      represents the PCR for CLP equal to 0 traffic; parameter 4 
      represents the CDVT; and parameter 5 represents the requested 
      shaping rate. A non-zero value in parameter 5 overrides any value in 
      parameter 1. This result is used as the PCR. Parameter 1 must be 
      greater than or equal to parameter 2. Parameters 1 and 2 must be 
      non-zero. Parameter 3 must be zero.
      
      When txTrafficDescType is 6, parameter 1 represents the PCR for 
      CLP equal to 0 and 1 traffic; parameter 2 represents the SCR for 
      CLP equal to 0 and 1 traffic; parameter 3 represents the MBS for 
      CLP equal to 0 and 1 traffic; parameter 4 represents the CDVT; and 
      parameter 5 represents the requested shaping rate. A non-zero value 
      in parameter 5 overrides any value in parameter 1. This result is 
      used as the PCR. Parameters 1, 2 and 3 must be non-zero. 
      Parameter 1 must be greater than or equal to parameter 2. Parameter 
      5, must either be zero (unused) or greater than or equal to parameter 
      2.
      
      When txTrafficDescType is 7, parameter 1 represents the PCR for 
      CLP equal to 0 and 1 traffic; parameter 2 represents the SCR for 
      CLP equal to 0 with cell discard; parameter 3 represents the MBS 
      for CLP equal to 0 traffic; parameter 4 represents the CDVT; and 
      parameter 5 represents the requested shaping rate. A non-zero value 
      in parameter 5 overrides any value in parameter 1. This result is 
      used as the PCR. Parameters 1, 2 and 3 must be non-zero. 
      Parameter 1 must be greater than or equal to parameter 2. Parameter 
      5, must either be zero (unused) or greater than or equal to parameter 
      2.
      
      When txTrafficDescType is 8, parameter 1 represents the PCR for 
      CLP equal to 0 and 1 traffic; parameter 2 represents the SCR for 
      CLP equal to 0 traffic with cell tagging; parameter 3 represents the 
      MBS for CLP equal to 0 traffic; parameter 4 represents the CDVT; 
      and parameter 5 represents the requested shaping rate. A non-zero 
      value in parameter 5 overrides any value in parameter 1. This result 
      is used as the PCR. Parameters 1, 2 and 3 must be non-zero. 
      Parameter 1 must be greater than or equal to parameter 2. Parameter 
      5, must either be zero (unused) or greater than or equal to parameter 
      2.
      
      When txTrafficDescType is 9, parameter 1 represents the PCR; 
      parameter 2 represents the CDVT; parameter 3 represents the MCR; 
      parameter 4 and parameter 5 represent are not used and must be 
      zero. Parameter 1 must be non-zero and must be greater than or 
      equal to parameter 3. Parameter 3 may be optionally zero.
      
      Whenever it is valid for PCR to be specified, parameter 5 may also 
      be used to specify a requested shaping rate. A non-zero value in 
      parameter 5 overrides the value in parameter 1 and is used as the 
      peak cell rate in calculations of CAC and shaping rate. When the 
      atmServiceCategory is availableBitRate (ABR), the shaping rate is 
      dynamically chosen, based on the ABR flow control mechanism, as 
      a value between the MCR and the PCR or the requested shaping 
      rate if applicable.
      
      For txTrafficDescType 3, 4 and 5, the transmit traffic is shaped at 
      the next available shaping rate less than the PCR. 
      
      For txTrafficDescType 6, 7 and 8 if linear traffic shaping is selected, 
      the transmit traffic is shaped at the highest available rate which is 
      between PCR and SCR. However, if there is no available shaping 
      rate between PCR and SCR, traffic is shaped at the next rate above 
      the PCR. 
      
      For txTrafficDescType 6, 7 and 8 if inverse-UPC traffic shaping is 
      selected, the transmit traffic is shaped at a variable rate which 
      conforms to the PCR, SCR and MBS of the connection traffic 
      descriptor. Inverse-UPC traffic shaping is available only on ATM IP 
      cards."
::= { mscAtmIfVpcVpdTm 456 }

mscAtmIfVpcVpdTmTxTdpEntry OBJECT-TYPE
   SYNTAX     MscAtmIfVpcVpdTmTxTdpEntry
   ACCESS     not-accessible
   STATUS     mandatory
   DESCRIPTION
     "An entry in the mscAtmIfVpcVpdTmTxTdpTable."
   INDEX {
      mscAtmIfIndex,
      mscAtmIfVpcIndex,
      mscAtmIfVpcVpdIndex,
      mscAtmIfVpcVpdTmIndex,
      mscAtmIfVpcVpdTmTxTdpIndex }
::= { mscAtmIfVpcVpdTmTxTdpTable 1 }

MscAtmIfVpcVpdTmTxTdpEntry ::= SEQUENCE {
   mscAtmIfVpcVpdTmTxTdpIndex
      Integer32,
   mscAtmIfVpcVpdTmTxTdpValue
      Unsigned32 }

mscAtmIfVpcVpdTmTxTdpIndex OBJECT-TYPE
   SYNTAX     Integer32 (1..5)
   ACCESS     not-accessible
   STATUS     mandatory
   DESCRIPTION
     "This variable represents the mscAtmIfVpcVpdTmTxTdpTable
      specific index for the mscAtmIfVpcVpdTmTxTdpTable."
::= { mscAtmIfVpcVpdTmTxTdpEntry 1 }

mscAtmIfVpcVpdTmTxTdpValue OBJECT-TYPE
   SYNTAX     Unsigned32 (0..2147483647)
   ACCESS     read-write
   STATUS     mandatory
   DESCRIPTION
     "This variable represents an individual value for the
      mscAtmIfVpcVpdTmTxTdpTable."
::= { mscAtmIfVpcVpdTmTxTdpEntry 2 }

mscAtmIfVpcVpdTmRxTdpTable OBJECT-TYPE
   SYNTAX     SEQUENCE OF MscAtmIfVpcVpdTmRxTdpEntry
   ACCESS     not-accessible
   STATUS     mandatory
   DESCRIPTION
     "This attribute is a vector of four traffic parameters whose meanings 
      are defined by the rxTrafficDescType attribute. The values of peak 
      cell rate (PCR), sustained cell rate (SCR) and Minimum Cell Rate 
      (MCR) are expressed in cell/s. Maximum burst size (MBS) is 
      expressed in cells. The value of CDVT is expressed in 
      microseconds. The values of PCR, SCR, MCR, MBS and CDVT 
      are used for usage parameter control (UPC).
      
      When rxTrafficDescType is 1 or 2, all of the parameters must be set 
      to zero (unused).
      
      When rxTrafficDescType is 3, parameter 1 represents the PCR for 
      CLP equal to 0 and 1 traffic. Parameter 1 must be non-zero. 
      Parameters 2 and 3 must be set to zero (unused).
      
      When rxTrafficDescType is 4, parameter 1 represents the PCR 
      for CLP equal to 0 and 1 traffic; parameter 2 represents the PCR for 
      CLP equal to 0 traffic with cell discard. Parameters 1 and 2 must be 
      non-zero. Parameter 3 must be set to zero (unused). Parameter 1 
      must be greater than or equal to parameter 2.
      
      When rxTrafficDescType is 5, parameter 1 represents the PCR for 
      CLP equal to 0 and 1 traffic; parameter 2 represents the PCR for 
      CLP equal to 0 traffic with cell tagging. Parameters 1 and 2 must be 
      non-zero. Parameter 3 must be set to zero (unused). Parameter 1 
      must be greater than or equal to parameter 2.
      
      When rxTrafficDescType is a 6, parameter 1 represents the PCR for 
      CLP equal to 0 and 1 traffic; parameter 2 represents the SCR for 
      CLP equal to 0 and 1 traffic; parameter 3 represents the MBS for 
      CLP equal to 0 and 1 traffic. Parameters 1, 2 and 3 must be non-
      zero. Parameter 1 must be greater than or equal to Parameter 2. 
      
      When rxTrafficDescType is 7, parameter 1 represents the PCR for 
      CLP equal to 0 and 1 traffic; parameter 2 represents the SCR for 
      CLP equal to 0 traffic with cell discard; parameter 3 represents the 
      MBS for CLP equal to 0 traffic. Parameters 1, 2 and 3 must be non-
      zero. Parameter 1 must be greater than or equal to parameter 2. 
      
      When rxTrafficDescType is 8, parameter 1 represents the PCR for 
      CLP equal to 0 and 1 traffic; parameter 2 represents the SCR for 
      CLP equal to 0 traffic with cell tagging; parameter 3 represents the 
      MBS for CLP equal to 0 traffic. Parameter 1, 2 and 3 must be non-
      zero. Parameter 1 must be greater than or equal to parameter 2.
      
      When rxTrafficDescType is 9, parameter 1 represents the PCR; 
      parameter 2 represents the CDVT; parameter 3 represents the MCR. 
      Parameter 4 is not used and must be zero. Parameter 1,must be non-
      zero and must be greater than or equal to parameter 3. Parameter 3 
      may optionally be zero.
      
      When rxTrafficDescType is any value from 3 through 8, parameter 
      4 represents the CDVT. 
      
      If the value of CDVT either in parameter 2 or in parameter 4 is zero, 
      the CDVT is taken from the CA defaults for the particular 
      atmServiceCategory of this connection.
      
      On a CQC-based ATM card, when rxTrafficDescriptorType is 3 
      through 8, there are certain extreme combinations of 
      rxTrafficDescParm which are outside the capabilities of the UPC 
      hardware. The check prov command detects such cases and 
      generates an error message. If this happens, adjust the parameters 
      until they fall within the supported limits. 
      
      To calculate the limits, use the following formulae:
      I1 = 1 000 000 000 / PCR
      L1 = CDVT * 1000
      I2 = 1,000,000,000 / SCR
      L2 = CDVT + (MBS - 1) * (I2 - I1)
      I1 and I2 must be less than or equal to 335,523,840. I1 + L1 must 
      be less than or equal to 1,342,156,800. I2 + L2 must be less than or 
      equal to 1,342,156,800. Note that I2 and L2 only apply when the 
      rxTrafficDescriptorType is 6 through 8.
      
      If the values of I1, L1, I2 or L2 are closer to the limits described 
      above, a further restriction applies. Specifically, if either:
      I1 > 41,940,480 or
      I2 > 41,940,480 or
      I1 + L1 > 167,769,600 or
      I2 + L2 > 167,769,600
      then both I1 and I2 must be greater than 20,480. 
      
      Parameter 5 of the rxTrafficDescParm is always unused. 
      
      If the rxTrafficDescType is sameAsTx, the values provisioned in 
      this attribute are ignored. The traffic parameters for the receive 
      direction are taken from the txTrafficDescParm."
::= { mscAtmIfVpcVpdTm 457 }

mscAtmIfVpcVpdTmRxTdpEntry OBJECT-TYPE
   SYNTAX     MscAtmIfVpcVpdTmRxTdpEntry
   ACCESS     not-accessible
   STATUS     mandatory
   DESCRIPTION
     "An entry in the mscAtmIfVpcVpdTmRxTdpTable."
   INDEX {
      mscAtmIfIndex,
      mscAtmIfVpcIndex,
      mscAtmIfVpcVpdIndex,
      mscAtmIfVpcVpdTmIndex,
      mscAtmIfVpcVpdTmRxTdpIndex }
::= { mscAtmIfVpcVpdTmRxTdpTable 1 }

MscAtmIfVpcVpdTmRxTdpEntry ::= SEQUENCE {
   mscAtmIfVpcVpdTmRxTdpIndex
      Integer32,
   mscAtmIfVpcVpdTmRxTdpValue
      Unsigned32 }

mscAtmIfVpcVpdTmRxTdpIndex OBJECT-TYPE
   SYNTAX     Integer32 (1..5)
   ACCESS     not-accessible
   STATUS     mandatory
   DESCRIPTION
     "This variable represents the mscAtmIfVpcVpdTmRxTdpTable
      specific index for the mscAtmIfVpcVpdTmRxTdpTable."
::= { mscAtmIfVpcVpdTmRxTdpEntry 1 }

mscAtmIfVpcVpdTmRxTdpValue OBJECT-TYPE
   SYNTAX     Unsigned32 (0..2147483647)
   ACCESS     read-write
   STATUS     mandatory
   DESCRIPTION
     "This variable represents an individual value for the
      mscAtmIfVpcVpdTmRxTdpTable."
::= { mscAtmIfVpcVpdTmRxTdpEntry 2 }

mscAtmIfVpcVpdTmFqpTable OBJECT-TYPE
   SYNTAX     SEQUENCE OF MscAtmIfVpcVpdTmFqpEntry
   ACCESS     not-accessible
   STATUS     mandatory
   DESCRIPTION
     "This attribute is a vector of three elements that specify the quality of 
      service parameters for the forward direction for this connection. 
      This attribute is used for SPVC connections.
      
      The cdv element specifies the acceptable peak-to-peak Cell Delay 
      Variation (CDV) of real-time connections (CBR and rt-VBR). It is 
      signalled through the extended QoS information element.
      
      The ctd specifies the acceptable maximum Cell Transfer Delay 
      (maxCtd) of real-time connections (CBR and rt-VBR). 
      It is signalled through the end to end transit delay information 
      element.
      
      The clr specifies the acceptable Cell Loss Ratio (CLR) of CBR, rt-
      VBR, and nrt-VBR connections. It is signalled through the extended 
      QoS information element."
::= { mscAtmIfVpcVpdTm 458 }

mscAtmIfVpcVpdTmFqpEntry OBJECT-TYPE
   SYNTAX     MscAtmIfVpcVpdTmFqpEntry
   ACCESS     not-accessible
   STATUS     mandatory
   DESCRIPTION
     "An entry in the mscAtmIfVpcVpdTmFqpTable."
   INDEX {
      mscAtmIfIndex,
      mscAtmIfVpcIndex,
      mscAtmIfVpcVpdIndex,
      mscAtmIfVpcVpdTmIndex,
      mscAtmIfVpcVpdTmFqpIndex }
::= { mscAtmIfVpcVpdTmFqpTable 1 }

MscAtmIfVpcVpdTmFqpEntry ::= SEQUENCE {
   mscAtmIfVpcVpdTmFqpIndex
      INTEGER,
   mscAtmIfVpcVpdTmFqpValue
      Unsigned32 }

mscAtmIfVpcVpdTmFqpIndex OBJECT-TYPE
   SYNTAX     INTEGER  {
                 cdv(0),
                 ctd(1),
                 clr(2) }
   ACCESS     not-accessible
   STATUS     mandatory
   DESCRIPTION
     "This variable represents the mscAtmIfVpcVpdTmFqpTable
      specific index for the mscAtmIfVpcVpdTmFqpTable."
::= { mscAtmIfVpcVpdTmFqpEntry 1 }

mscAtmIfVpcVpdTmFqpValue OBJECT-TYPE
   SYNTAX     Unsigned32 (0..2147483647)
   ACCESS     read-write
   STATUS     mandatory
   DESCRIPTION
     "This variable represents an individual value for the
      mscAtmIfVpcVpdTmFqpTable."
::= { mscAtmIfVpcVpdTmFqpEntry 2 }

mscAtmIfVpcVpdTmBqpTable OBJECT-TYPE
   SYNTAX     SEQUENCE OF MscAtmIfVpcVpdTmBqpEntry
   ACCESS     not-accessible
   STATUS     mandatory
   DESCRIPTION
     "This attribute is a vector of three elements that specify the quality of 
      service parameters for the backward direction for this connection. 
      This attribute is used for SPVC connections.
      
      The cdv element specifies the acceptable peak-to-peak Cell Delay 
      Variation (CDV) of real-time connections (CBR and rt-VBR).
      It is signalled through the extended QoS information element.
      
      The ctd specifies the acceptable maximum Cell Transfer Delay 
      (maxCtd) of real-time connections (CBR and rt-VBR). It is 
      signalled through the end to end transit delay information element.
      
      The clr specifies the acceptable Cell Loss Ratio (CLR) of CBR, rt-
      VBR, and nrt-VBR connections. It is signalled through the extended 
      QoS information element."
::= { mscAtmIfVpcVpdTm 459 }

mscAtmIfVpcVpdTmBqpEntry OBJECT-TYPE
   SYNTAX     MscAtmIfVpcVpdTmBqpEntry
   ACCESS     not-accessible
   STATUS     mandatory
   DESCRIPTION
     "An entry in the mscAtmIfVpcVpdTmBqpTable."
   INDEX {
      mscAtmIfIndex,
      mscAtmIfVpcIndex,
      mscAtmIfVpcVpdIndex,
      mscAtmIfVpcVpdTmIndex,
      mscAtmIfVpcVpdTmBqpIndex }
::= { mscAtmIfVpcVpdTmBqpTable 1 }

MscAtmIfVpcVpdTmBqpEntry ::= SEQUENCE {
   mscAtmIfVpcVpdTmBqpIndex
      INTEGER,
   mscAtmIfVpcVpdTmBqpValue
      Unsigned32 }

mscAtmIfVpcVpdTmBqpIndex OBJECT-TYPE
   SYNTAX     INTEGER  {
                 cdv(0),
                 ctd(1),
                 clr(2) }
   ACCESS     not-accessible
   STATUS     mandatory
   DESCRIPTION
     "This variable represents the mscAtmIfVpcVpdTmBqpTable
      specific index for the mscAtmIfVpcVpdTmBqpTable."
::= { mscAtmIfVpcVpdTmBqpEntry 1 }

mscAtmIfVpcVpdTmBqpValue OBJECT-TYPE
   SYNTAX     Unsigned32 (0..2147483647)
   ACCESS     read-write
   STATUS     mandatory
   DESCRIPTION
     "This variable represents an individual value for the
      mscAtmIfVpcVpdTmBqpTable."
::= { mscAtmIfVpcVpdTmBqpEntry 2 }


-- AtmIf/n Vcc/vpi.vci Vcd Tm AvailableBitRate, 
-- AtmIf/n Vpc/vci Vpd Tm AvailableBitRate,
-- AtmIf/n Vpt/vpi Vpd Tm AvailableBitRate,
-- AtmIf/n Vpt/vpi Vcc/vci Vcd Tm AvailableBitRate
-- This component contains provisioned ABR-related attributes of a 
-- connection. It is an optional subcomponent of the Vcd Tm and Vpd 
-- Tm component. It is used to override DGCRA-related defaults in 
-- the CA Abr component. It contains the specific configuration for the 
-- ABR connection at this connection point. If this is the source of an 
-- SPVC connection, this component also contains the ABR 
-- parameters required for the SPVC call request.

mscAtmIfVpcVpdTmAbr OBJECT IDENTIFIER ::= { mscAtmIfVpcVpdTm 2 }



mscAtmIfVpcVpdTmAbrRowStatusTable OBJECT-TYPE
   SYNTAX     SEQUENCE OF MscAtmIfVpcVpdTmAbrRowStatusEntry
   ACCESS     not-accessible
   STATUS     mandatory
   DESCRIPTION
     "This entry controls the addition and deletion of 
      mscAtmIfVpcVpdTmAbr components."
::= { mscAtmIfVpcVpdTmAbr 1 }

mscAtmIfVpcVpdTmAbrRowStatusEntry OBJECT-TYPE
   SYNTAX     MscAtmIfVpcVpdTmAbrRowStatusEntry
   ACCESS     not-accessible
   STATUS     mandatory
   DESCRIPTION
     "A single entry in the table represents a single 
      mscAtmIfVpcVpdTmAbr component."
   INDEX {
      mscAtmIfIndex,
      mscAtmIfVpcIndex,
      mscAtmIfVpcVpdIndex,
      mscAtmIfVpcVpdTmIndex,
      mscAtmIfVpcVpdTmAbrIndex }
::= { mscAtmIfVpcVpdTmAbrRowStatusTable 1 }

MscAtmIfVpcVpdTmAbrRowStatusEntry ::= SEQUENCE {
   mscAtmIfVpcVpdTmAbrRowStatus
      RowStatus,
   mscAtmIfVpcVpdTmAbrComponentName
      DisplayString,
   mscAtmIfVpcVpdTmAbrStorageType
      StorageType,
   mscAtmIfVpcVpdTmAbrIndex
      NonReplicated }

mscAtmIfVpcVpdTmAbrRowStatus OBJECT-TYPE
   SYNTAX     RowStatus 
   ACCESS     read-write
   STATUS     mandatory
   DESCRIPTION
     "This variable is used as the basis for SNMP naming of
      mscAtmIfVpcVpdTmAbr components.
      These components can be added and deleted."
::= { mscAtmIfVpcVpdTmAbrRowStatusEntry 1 }

mscAtmIfVpcVpdTmAbrComponentName OBJECT-TYPE
   SYNTAX     DisplayString 
   ACCESS     read-only
   STATUS     mandatory
   DESCRIPTION
     "This variable provides the component's string name for
      use with the ASCII Console Interface"
::= { mscAtmIfVpcVpdTmAbrRowStatusEntry 2 }

mscAtmIfVpcVpdTmAbrStorageType OBJECT-TYPE
   SYNTAX     StorageType 
   ACCESS     read-only
   STATUS     mandatory
   DESCRIPTION
     "This variable represents the storage type value for the
      mscAtmIfVpcVpdTmAbr tables."
::= { mscAtmIfVpcVpdTmAbrRowStatusEntry 4 }

mscAtmIfVpcVpdTmAbrIndex OBJECT-TYPE
   SYNTAX     NonReplicated 
   ACCESS     not-accessible
   STATUS     mandatory
   DESCRIPTION
     "This variable represents the index for the mscAtmIfVpcVpdTmAbr tables."
::= { mscAtmIfVpcVpdTmAbrRowStatusEntry 10 }

mscAtmIfVpcVpdTmAbrProvTable OBJECT-TYPE
   SYNTAX     SEQUENCE OF MscAtmIfVpcVpdTmAbrProvEntry
   ACCESS     not-accessible
   STATUS     mandatory
   DESCRIPTION
     "This group contains provisioned attributes for the ABR ATM 
      connections configured on an ATM interface."
::= { mscAtmIfVpcVpdTmAbr 110 }

mscAtmIfVpcVpdTmAbrProvEntry OBJECT-TYPE
   SYNTAX     MscAtmIfVpcVpdTmAbrProvEntry
   ACCESS     not-accessible
   STATUS     mandatory
   DESCRIPTION
     "An entry in the mscAtmIfVpcVpdTmAbrProvTable."
   INDEX {
      mscAtmIfIndex,
      mscAtmIfVpcIndex,
      mscAtmIfVpcVpdIndex,
      mscAtmIfVpcVpdTmIndex,
      mscAtmIfVpcVpdTmAbrIndex }
::= { mscAtmIfVpcVpdTmAbrProvTable 1 }

MscAtmIfVpcVpdTmAbrProvEntry ::= SEQUENCE {
   mscAtmIfVpcVpdTmAbrInitialCellRate
      Unsigned32,
   mscAtmIfVpcVpdTmAbrTransientBufferExposure
      Unsigned32,
   mscAtmIfVpcVpdTmAbrFixedRoundTripTime
      Unsigned32,
   mscAtmIfVpcVpdTmAbrRateDecreaseFactor
      Unsigned32,
   mscAtmIfVpcVpdTmAbrRateIncreaseFactor
      Unsigned32,
   mscAtmIfVpcVpdTmAbrMaxCellPerRmCell
      Unsigned32,
   mscAtmIfVpcVpdTmAbrMaxTimeBetweenRmCells
      Unsigned32,
   mscAtmIfVpcVpdTmAbrCutoffDecreaseFactor
      Unsigned32,
   mscAtmIfVpcVpdTmAbrAcrDecreaseTimeFactor
      Unsigned32,
   mscAtmIfVpcVpdTmAbrDgcraMaximumDelay
      Unsigned32,
   mscAtmIfVpcVpdTmAbrDgcraMinimumDelay
      Unsigned32,
   mscAtmIfVpcVpdTmAbrFarEndAcrDecreaseTimeFactor
      Unsigned32,
   mscAtmIfVpcVpdTmAbrFarEndInitialCellRate
      Unsigned32 }

mscAtmIfVpcVpdTmAbrInitialCellRate OBJECT-TYPE
   SYNTAX     Unsigned32 (0..16777215 | 16777216 | 16777217 | 16777218)
   ACCESS     read-write
   STATUS     mandatory
   DESCRIPTION
     "This attribute specifies the Initial Cell Rate (ICR) parameter for this 
      connection. ICR is the rate at which a source should send initially 
      and after an idle period.
      
      When this attribute is set to sameAsCa, the initial cell rate is 
      determined by the AtmIf CA Abr/0 icr attribute. When the value of 
      this attribute is set to useMcr, ICR is set to the same value as the 
      Minimum Cell Rate (MCR) for the connection.
      
      When the value of this attribute is set to usePcr, ICR is set to the 
      same value as the Peak Cell Rate (PCR) for the connection.
      
      If this attribute is specified less than the MCR of the connection, 
      then the MCR is used as the ICR. If this attribute is specified more 
      than PCR of the connection, then PCR is used as the ICR.
      
      This attribute is ignored under all conditions where the operational 
      attribute abrConnectionType indicates erSwitch or efciSwitch.

      VALUES (

      16777216 = sameAsCa

      16777217 = useMcr

      16777218 = usePcr

      )"
   DEFVAL     { 16777216 }
::= { mscAtmIfVpcVpdTmAbrProvEntry 10 }

mscAtmIfVpcVpdTmAbrTransientBufferExposure OBJECT-TYPE
   SYNTAX     Unsigned32 (0..16777215)
   ACCESS     read-write
   STATUS     mandatory
   DESCRIPTION
     "This attribute specifies the Transient Buffer Exposure (TBE) for this 
      connection. TBE is the negotiated number of cells that the network 
      would like to limit the source to send during start-up periods, before 
      the first Resource Management (RM) cell returns.
      
      TBE divided by fixedRoundTripTime determines an upper bound 
      for the operational value of initialCellRate, the rate at which a 
      source should send initially and after an idle period.
      
      TBE divided by maxCellsPerRmCell specifies the operational value 
      of forwardRmCellLimit, the limit of the number of forward 
      Resource Management (RM) cells which may be sent in the 
      absence of received backward RM cells.
      
      This attribute is ignored under all conditions where the operational 
      attribute abrConnectionType is set to erSwitch."
   DEFVAL     { 16777215 }
::= { mscAtmIfVpcVpdTmAbrProvEntry 11 }

mscAtmIfVpcVpdTmAbrFixedRoundTripTime OBJECT-TYPE
   SYNTAX     Unsigned32 (0..16700000)
   ACCESS     read-write
   STATUS     mandatory
   DESCRIPTION
     "This attribute specifies the Fixed Round-Trip Time (FRTT) 
      parameter for this connection. FRTT is the sum of the fixed and 
      propagation delays from the source to a destination and back.
      
      The value of transientBufferExposure divided by the value of FRTT 
      (in seconds) determines an upper bound for the operational value of 
      initialCellRate, the rate at which a source should send initially and 
      after an idle period.
      
      This attribute is ignored under all conditions where the operational 
      attribute abrConnectionType indicates erSwitch or efciSwitch."
   DEFVAL     { 5000000 }
::= { mscAtmIfVpcVpdTmAbrProvEntry 12 }

mscAtmIfVpcVpdTmAbrRateDecreaseFactor OBJECT-TYPE
   SYNTAX     Unsigned32 (0..15 | 16777216)
   ACCESS     read-write
   STATUS     mandatory
   DESCRIPTION
     "This attribute specifies the Rate Decrease Factor (RDF) for this 
      connection. The RDF value is computed by using the provisioned 
      value of this attribute, n, as 2 to the inverse power n. For example, if 
      the value of this attribute is 8, RDF is 2E-8 = 1/256.
      
      RDF controls the amount by which the cell transmission rate may 
      decrease upon receipt of a backward Resource Management (RM) 
      cell. For example, if a backward RM cell is received with the 
      Congestion Indication (CI) field set to 1, the Allowed Cell Rate 
      (ACR) value would be reduced by the amount (RDF*ACR). The 
      ACR is not allowed to fall below the Minimum Cell Rate (MCR), in 
      which case the ACR is set to MCR.
      
      This attribute is ignored under all conditions where the operational 
      attribute abrConnectionType has the value erSwitch.

      VALUES (

      16777216 = sameAsCa

      )"
   DEFVAL     { 16777216 }
::= { mscAtmIfVpcVpdTmAbrProvEntry 13 }

mscAtmIfVpcVpdTmAbrRateIncreaseFactor OBJECT-TYPE
   SYNTAX     Unsigned32 (0..15 | 16777216)
   ACCESS     read-write
   STATUS     mandatory
   DESCRIPTION
     "This attribute specifies the Rate Increase Factor (RIF) for this 
      connection. The RIF value is computed by using the provisioned 
      value of this attribute, n, as 2 to the inverse power n. For example, if 
      the value of this attribute is 6, RIF is 2E-6 = 1/64.
      
      RIF controls the amount by which the cell transmission rate may 
      increase upon receipt of a backward Resource Management (RM) 
      cell. For example, if a backward RM cell is received with the 
      Congestion Indication (CI) and the No Increase (NI) fields both set 
      to 0, the Allowed Cell Rate (ACR) value would be increased by the 
      amount (RIF*ACR). The ACR is not allowed to exceed the Peak 
      Cell Rate (PCR), in which case the ACR is set to PCR.
      
      This attribute is ignored under all conditions where the operational 
      attribute abrConnectionType has the value erSwitch.

      VALUES (

      16777216 = sameAsCa

      )"
   DEFVAL     { 16777216 }
::= { mscAtmIfVpcVpdTmAbrProvEntry 14 }

mscAtmIfVpcVpdTmAbrMaxCellPerRmCell OBJECT-TYPE
   SYNTAX     Unsigned32 (2 | 4 | 8 | 16 | 32 | 64 | 128 | 256 | 16777216)
   ACCESS     read-write
   STATUS     mandatory
   DESCRIPTION
     "This attribute specifies the maximum number of cells an ABR 
      source may transmit for each forward Resource Management (RM) 
      cell. The count of the cells transmitted includes data cells, OAM 
      cells, backward RM cells, and the forward RM cell.
      
      A value of 2 is not recommended although it is permitted according 
      to the ATM Forum standard. When this attribute is set to a value of 
      2, it is possible that only one forward and one backward RM cell 
      are repeatedly transmitted, and all data traffic is queued up 
      indefinitely.
      
      This attribute is ignored under all conditions where the operational 
      attribute abrConnectionType has the value erSwitch.

      VALUES (

      16777216 = sameAsCa

      )"
   DEFVAL     { 16777216 }
::= { mscAtmIfVpcVpdTmAbrProvEntry 15 }

mscAtmIfVpcVpdTmAbrMaxTimeBetweenRmCells OBJECT-TYPE
   SYNTAX     Unsigned32 (781 | 1563 | 3125 | 6250 | 12500 | 25000 | 50000 | 100000 | 16777216)
   ACCESS     read-write
   STATUS     mandatory
   DESCRIPTION
     "This attribute specifies the TRM parameter for this connection.
      
      TRM provides an lower bound on the time interval between forward 
      Resource Management (RM) cells for an ABR source. Since the last 
      forward RM cell was sent, if at least TRM time has elapsed since 
      and at least two other cells have been sent, then the next cell to be 
      transmitted would be a forward RM cell.
      
      This attribute is ignored under all conditions where the operational 
      attribute abrConnectionType has the value erSwitch.
      
      The provisioned value of 781 is signalled as TRM = 0, in the ABR 
      Additional Parameters Information Element. 
      1563 is signalled as TRM = 1. 
      3125 is signalled as TRM = 2. 
      6250 is signalled as TRM = 3. 
      12500 is signalled as TRM = 4 
      25000 is signalled as TRM = 5. 
      50000 is signalled as TRM = 6. 
      100000 is signalled as TRM = 7.

      VALUES (

      16777216 = sameAsCa

      )"
   DEFVAL     { 16777216 }
::= { mscAtmIfVpcVpdTmAbrProvEntry 16 }

mscAtmIfVpcVpdTmAbrCutoffDecreaseFactor OBJECT-TYPE
   SYNTAX     Unsigned32 (0 | 1 | 2 | 4 | 8 | 16 | 32 | 64 | 16777216)
   ACCESS     read-write
   STATUS     mandatory
   DESCRIPTION
     "This attribute specifies the Cutoff Decrease Factor (CDF) parameter 
      for this connection. When the value of this attribute is non-zero, 
      CDF is computed as the inverse of the value. For example, if the 
      value is 32, the value of CDF is 1/32. When the value of this 
      attribute is 0, CDF is also zero.
      
      CDF controls the decrease in the Allowed Cell Rate (ACR) 
      associated with the CRM parameter, the limit of the number of 
      forward Resource Management (RM) cells which may be sent in 
      the absence of received backward RM cells. When this limit is 
      crossed, the ACR value would be decreased by the amount 
      (CDF*ACR). The ACR is not allowed to fall below the Minimum 
      Cell Rate (MCR), in which case the ACR is set to MCR.
      
      The value of CRM is indicated by the forwardRmCellLimit 
      attribute.
      
      This attribute is ignored under all conditions where the operational 
      attribute abrConnectionType indicates erSwitch or efciSwitch.

      VALUES (

      16777216 = sameAsCa

      )"
   DEFVAL     { 16777216 }
::= { mscAtmIfVpcVpdTmAbrProvEntry 17 }

mscAtmIfVpcVpdTmAbrAcrDecreaseTimeFactor OBJECT-TYPE
   SYNTAX     Unsigned32 (0..1023 | 16777216)
   ACCESS     read-write
   STATUS     mandatory
   DESCRIPTION
     "This attribute specifies the Allowed Cell Rate Decrease Time Factor 
      (ADTF) parameter for this connection.
      
      ADTF is the maximum time interval permitted between sending 
      forward Resource Management (RM) cells before the Allowed Cell 
      Rate (ACR) is decreased to initialCellRate. In other words, if the 
      source does not transit a forward RM cell for the period specified by 
      adtf, it reduces its ACR to the value of its initialCellRate.
      
      This attribute is ignored under all conditions where the operational 
      attribute abrConnectionType indicates erSwitch or efciSwitch.

      VALUES (

      16777216 = sameAsCa

      )"
   DEFVAL     { 16777216 }
::= { mscAtmIfVpcVpdTmAbrProvEntry 18 }

mscAtmIfVpcVpdTmAbrDgcraMaximumDelay OBJECT-TYPE
   SYNTAX     Unsigned32 (1..16700000 | 16777216)
   ACCESS     read-write
   STATUS     mandatory
   DESCRIPTION
     "This attribute specifies an upper bound on the delay after which the 
      rate change induced by a backward Resource Management (RM) 
      cell departing from this connection point (in the backward 
      direction) is expected to be observed at this connection point (in the 
      forward direction).
      
      This upper bound may be approximated as the sum of the round trip 
      fixed and propagation delays and the maximum queuing delays 
      between the ABR source and this interface.
      
      The value of this attribute is used in policing an ABR connection 
      using the Dynamic General Cell Rate Algorithm (DGCRA). A 
      larger value for this attribute implies a more lenient policer. When 
      there is a reduction in the Allowed Cell Rate (ACR), the policer 
      waits for a correspondingly longer period of time before it enforces 
      at the new cell rate.
      
      The value of this attribute must not be less than the 
      dgcraMinimumDelay attribute.

      VALUES (

      16777216 = sameAsCa

      )"
   DEFVAL     { 16777216 }
::= { mscAtmIfVpcVpdTmAbrProvEntry 19 }

mscAtmIfVpcVpdTmAbrDgcraMinimumDelay OBJECT-TYPE
   SYNTAX     Unsigned32 (1..16700000 | 16777216)
   ACCESS     read-write
   STATUS     mandatory
   DESCRIPTION
     "This attribute specifies a lower bound on the delay after which the 
      rate change induced by a backward Resource Management (RM) 
      cell departing from this connection point (in the backward 
      direction) is expected to be observed at this connection point (in the 
      forward connection).
      
      This lower bound may be approximated as the sum of the round trip 
      fixed and propagation delays between the ABR source and this 
      interface.
      
      The value of this attribute is used in policing an ABR connection 
      using the Dynamic General Cell Rate Algorithm (DGCRA). A 
      smaller value for this attribute implies a more lenient policer. When 
      there is a increase in the Allowed Cell Rate (ACR), the policer waits 
      for a correspondingly shorter period of time before it enforces at the 
      new cell rate.

      VALUES (

      16777216 = sameAsCa

      )"
   DEFVAL     { 16777216 }
::= { mscAtmIfVpcVpdTmAbrProvEntry 20 }

mscAtmIfVpcVpdTmAbrFarEndAcrDecreaseTimeFactor OBJECT-TYPE
   SYNTAX     Unsigned32 (0..1023)
   ACCESS     read-write
   STATUS     mandatory
   DESCRIPTION
     "This attribute specifies the Allowed Cell Rate Decrease Time Factor 
      (ADTF) of the far end ABR source. The value specified should be 
      the same as the ADTF parameter at the far end of this ABR 
      connection. 
      
      The value of this attribute is used in policing an ABR connection 
      using the Dynamic Generic Cell Rate Algorithm (DGCRA). A 
      larger value for this attribute implies a more lenient policer. When 
      the delay between two consecutive forward Resource Management 
      (RM) cells received at this interface corresponds to a value greater 
      than the value of this attribute, the policer begins to limit enforce 
      the incoming traffic at the initial cell rate (ICR) of the far end, as 
      specified by the farEndInitialCellRate attribute."
   DEFVAL     { 50 }
::= { mscAtmIfVpcVpdTmAbrProvEntry 21 }

mscAtmIfVpcVpdTmAbrFarEndInitialCellRate OBJECT-TYPE
   SYNTAX     Unsigned32 (0..16777215)
   ACCESS     read-write
   STATUS     mandatory
   DESCRIPTION
     "This attribute specifies the Initial Cell Rate (ICR) of the far end 
      ABR source. The value specified should be the same as the ICR 
      parameter at the far end of this ABR connection. 
      
      The value of this attribute is used in policing an ABR connection 
      using the Dynamic Generic Cell Rate Algorithm (DGCRA). A 
      larger value for this attribute implies a more lenient policer. When 
      the delay between two consecutive forward Resource Management 
      (RM) cells received at this interface corresponds to a value greater 
      than the farEndAcrDecreaseTimeFactor attribute, the policer begins 
      to enforce the incoming traffic at the value of this attribute.
      
      If this attribute is specified less than the MCR of the connection, 
      then the MCR is used as the feIcr. If this attribute is more than the 
      PCR of the connection, then PCR is used as the feIcr."
   DEFVAL     { 0 }
::= { mscAtmIfVpcVpdTmAbrProvEntry 22 }


-- AtmIf/n Vcc/x.y Vcd PerformanceMonitoring
-- AtmIf/n Vpc/x Vpd PerformanceMonitoring
-- This component represents the Performance Monitoring (Pm) 
-- function on a provisioned connection. No Performane Monitoring is 
-- done unless this component is present. The attribute values override 
-- corresponding values in the AtmIf Pm settings. There can be a 
-- maximum of 255 Pms on one LP.

mscAtmIfVpcVpdPm OBJECT IDENTIFIER ::= { mscAtmIfVpcVpd 3 }



mscAtmIfVpcVpdPmRowStatusTable OBJECT-TYPE
   SYNTAX     SEQUENCE OF MscAtmIfVpcVpdPmRowStatusEntry
   ACCESS     not-accessible
   STATUS     mandatory
   DESCRIPTION
     "This entry controls the addition and deletion of 
      mscAtmIfVpcVpdPm components."
::= { mscAtmIfVpcVpdPm 1 }

mscAtmIfVpcVpdPmRowStatusEntry OBJECT-TYPE
   SYNTAX     MscAtmIfVpcVpdPmRowStatusEntry
   ACCESS     not-accessible
   STATUS     mandatory
   DESCRIPTION
     "A single entry in the table represents a single 
      mscAtmIfVpcVpdPm component."
   INDEX {
      mscAtmIfIndex,
      mscAtmIfVpcIndex,
      mscAtmIfVpcVpdIndex,
      mscAtmIfVpcVpdPmIndex }
::= { mscAtmIfVpcVpdPmRowStatusTable 1 }

MscAtmIfVpcVpdPmRowStatusEntry ::= SEQUENCE {
   mscAtmIfVpcVpdPmRowStatus
      RowStatus,
   mscAtmIfVpcVpdPmComponentName
      DisplayString,
   mscAtmIfVpcVpdPmStorageType
      StorageType,
   mscAtmIfVpcVpdPmIndex
      NonReplicated }

mscAtmIfVpcVpdPmRowStatus OBJECT-TYPE
   SYNTAX     RowStatus 
   ACCESS     read-write
   STATUS     mandatory
   DESCRIPTION
     "This variable is used as the basis for SNMP naming of
      mscAtmIfVpcVpdPm components.
      These components can be added and deleted."
::= { mscAtmIfVpcVpdPmRowStatusEntry 1 }

mscAtmIfVpcVpdPmComponentName OBJECT-TYPE
   SYNTAX     DisplayString 
   ACCESS     read-only
   STATUS     mandatory
   DESCRIPTION
     "This variable provides the component's string name for
      use with the ASCII Console Interface"
::= { mscAtmIfVpcVpdPmRowStatusEntry 2 }

mscAtmIfVpcVpdPmStorageType OBJECT-TYPE
   SYNTAX     StorageType 
   ACCESS     read-only
   STATUS     mandatory
   DESCRIPTION
     "This variable represents the storage type value for the
      mscAtmIfVpcVpdPm tables."
::= { mscAtmIfVpcVpdPmRowStatusEntry 4 }

mscAtmIfVpcVpdPmIndex OBJECT-TYPE
   SYNTAX     NonReplicated 
   ACCESS     not-accessible
   STATUS     mandatory
   DESCRIPTION
     "This variable represents the index for the mscAtmIfVpcVpdPm tables."
::= { mscAtmIfVpcVpdPmRowStatusEntry 10 }

mscAtmIfVpcVpdPmProvTable OBJECT-TYPE
   SYNTAX     SEQUENCE OF MscAtmIfVpcVpdPmProvEntry
   ACCESS     not-accessible
   STATUS     mandatory
   DESCRIPTION
     "This group contains provisioned attributes which specify 
      Performance Monitoring (PM) measurements, namely, Availability 
      Ratio (AR) and Cell Loss Ratio (CLR), and control modes for the 
      connection. The values specified in this group override those 
      specified by AtmIf Pm settings."
::= { mscAtmIfVpcVpdPm 100 }

mscAtmIfVpcVpdPmProvEntry OBJECT-TYPE
   SYNTAX     MscAtmIfVpcVpdPmProvEntry
   ACCESS     not-accessible
   STATUS     mandatory
   DESCRIPTION
     "An entry in the mscAtmIfVpcVpdPmProvTable."
   INDEX {
      mscAtmIfIndex,
      mscAtmIfVpcIndex,
      mscAtmIfVpcVpdIndex,
      mscAtmIfVpcVpdPmIndex }
::= { mscAtmIfVpcVpdPmProvTable 1 }

MscAtmIfVpcVpdPmProvEntry ::= SEQUENCE {
   mscAtmIfVpcVpdPmSegSwitchSideMeasurement
      OCTET STRING,
   mscAtmIfVpcVpdPmSegLinkSideMeasurement
      OCTET STRING,
   mscAtmIfVpcVpdPmControlMode
      INTEGER }

mscAtmIfVpcVpdPmSegSwitchSideMeasurement OBJECT-TYPE
   SYNTAX     OCTET STRING (SIZE (1))
   ACCESS     read-write
   STATUS     mandatory
   DESCRIPTION
     "This attribute specifies the set of Performance Monitoring (PM) 
      measurements on the switch side configuration for the connection.
      
      sameAsInterface means that the measurements specified by the 
      segSwitchSideMeasurement attribute of the AtmIf Pm component 
      will be performed. No other values may be specified if 
      sameAsInterface is selected. If the value is empty, no switch side 
      PM measurements are done.

      Description of bits:
      availabilityRatio(0)
      cellLossRatio(1)
      sameAsInterface(2)"
   DEFVAL     { '20'H }
::= { mscAtmIfVpcVpdPmProvEntry 1 }

mscAtmIfVpcVpdPmSegLinkSideMeasurement OBJECT-TYPE
   SYNTAX     OCTET STRING (SIZE (1))
   ACCESS     read-write
   STATUS     mandatory
   DESCRIPTION
     "This attribute specifies the set of Performance Monitoring (PM) 
      measurements on the link side configuration for the connection.
      
      sameAsInterface means that the measurements specified by the 
      segLinkSideMeasurement attribute of the AtmIf Pm component will 
      be performed. No other values may be specified if sameAsInterface 
      is selected. If the value is empty, no link side PM measurements are 
      done.
      
      The following are valid sets:
      (~sameAsInterface ~availabilityRatio ~cellLossRatio)
      (~sameAsInterface ~availabilityRatio cellLossRatio)
      (~sameAsInterface availabilityRatio ~cellLossRatio)
      (~sameAsInterface availabilityRatio cellLossRatio)
      (sameAsInterface ~availabilityRatio ~cellLossRatio)

      Description of bits:
      availabilityRatio(0)
      cellLossRatio(1)
      sameAsInterface(2)"
   DEFVAL     { '20'H }
::= { mscAtmIfVpcVpdPmProvEntry 2 }

mscAtmIfVpcVpdPmControlMode OBJECT-TYPE
   SYNTAX     INTEGER  {
                 autoStart(0),
                 onDemand(1),
                 sameAsInterface(2) }
   ACCESS     read-write
   STATUS     mandatory
   DESCRIPTION
     "This attribute specifies the control mode of Performance Monitoring 
      (PM) measurements for the connection.
      
      autoStart means that PM activation procedures will start when the 
      provisioned data is activated.
      
      onDemand means that PM activation procedures will start when the 
      operator issues the START command. The PM measurements in this 
      mode will continue until the operator issues the STOP command.
      
      sameAsInterface means that the behavior will be as specified by the 
      controlMode attribute of the AtmIf Pm component."
   DEFVAL     { sameAsInterface }
::= { mscAtmIfVpcVpdPmProvEntry 3 }


-- AtmIf/n Vcc/vpi.vci Loop
-- The Loop component configures an ATM connection so that cells 
-- received from the ATM interface are retransmitted back to the 
-- interface through that connection. The Loop component requires 
-- exclusive use of its parent Vcc or Vpc and cannot co-exist with other 
-- ATM service components (such as Nep, Nrp, and Test).

mscAtmIfVpcLoop OBJECT IDENTIFIER ::= { mscAtmIfVpc 3 }



mscAtmIfVpcLoopRowStatusTable OBJECT-TYPE
   SYNTAX     SEQUENCE OF MscAtmIfVpcLoopRowStatusEntry
   ACCESS     not-accessible
   STATUS     mandatory
   DESCRIPTION
     "This entry controls the addition and deletion of 
      mscAtmIfVpcLoop components."
::= { mscAtmIfVpcLoop 1 }

mscAtmIfVpcLoopRowStatusEntry OBJECT-TYPE
   SYNTAX     MscAtmIfVpcLoopRowStatusEntry
   ACCESS     not-accessible
   STATUS     mandatory
   DESCRIPTION
     "A single entry in the table represents a single 
      mscAtmIfVpcLoop component."
   INDEX {
      mscAtmIfIndex,
      mscAtmIfVpcIndex,
      mscAtmIfVpcLoopIndex }
::= { mscAtmIfVpcLoopRowStatusTable 1 }

MscAtmIfVpcLoopRowStatusEntry ::= SEQUENCE {
   mscAtmIfVpcLoopRowStatus
      RowStatus,
   mscAtmIfVpcLoopComponentName
      DisplayString,
   mscAtmIfVpcLoopStorageType
      StorageType,
   mscAtmIfVpcLoopIndex
      NonReplicated }

mscAtmIfVpcLoopRowStatus OBJECT-TYPE
   SYNTAX     RowStatus 
   ACCESS     read-write
   STATUS     mandatory
   DESCRIPTION
     "This variable is used as the basis for SNMP naming of
      mscAtmIfVpcLoop components.
      These components can be added and deleted."
::= { mscAtmIfVpcLoopRowStatusEntry 1 }

mscAtmIfVpcLoopComponentName OBJECT-TYPE
   SYNTAX     DisplayString 
   ACCESS     read-only
   STATUS     mandatory
   DESCRIPTION
     "This variable provides the component's string name for
      use with the ASCII Console Interface"
::= { mscAtmIfVpcLoopRowStatusEntry 2 }

mscAtmIfVpcLoopStorageType OBJECT-TYPE
   SYNTAX     StorageType 
   ACCESS     read-only
   STATUS     mandatory
   DESCRIPTION
     "This variable represents the storage type value for the
      mscAtmIfVpcLoop tables."
::= { mscAtmIfVpcLoopRowStatusEntry 4 }

mscAtmIfVpcLoopIndex OBJECT-TYPE
   SYNTAX     NonReplicated 
   ACCESS     not-accessible
   STATUS     mandatory
   DESCRIPTION
     "This variable represents the index for the mscAtmIfVpcLoop tables."
::= { mscAtmIfVpcLoopRowStatusEntry 10 }


-- AtmIf/n Vpc/vpi TrafficManagement, 
-- AtmIf/n Vcc/vpi.vci TrafficManagement,
-- AtmIf/n Vpt/vpi TrafficManagement,
-- AtmIf/n Vpt/vpi Vcc/vci TrafficManagement
-- The Tm subcomponent contains the operational traffic management 
-- attributes of a connection. It is created dynamically for each 
-- activated Vcc, Vpc, or Vpt component.

mscAtmIfVpcTm OBJECT IDENTIFIER ::= { mscAtmIfVpc 9 }



mscAtmIfVpcTmRowStatusTable OBJECT-TYPE
   SYNTAX     SEQUENCE OF MscAtmIfVpcTmRowStatusEntry
   ACCESS     not-accessible
   STATUS     mandatory
   DESCRIPTION
     "This entry controls the addition and deletion of 
      mscAtmIfVpcTm components."
::= { mscAtmIfVpcTm 1 }

mscAtmIfVpcTmRowStatusEntry OBJECT-TYPE
   SYNTAX     MscAtmIfVpcTmRowStatusEntry
   ACCESS     not-accessible
   STATUS     mandatory
   DESCRIPTION
     "A single entry in the table represents a single 
      mscAtmIfVpcTm component."
   INDEX {
      mscAtmIfIndex,
      mscAtmIfVpcIndex,
      mscAtmIfVpcTmIndex }
::= { mscAtmIfVpcTmRowStatusTable 1 }

MscAtmIfVpcTmRowStatusEntry ::= SEQUENCE {
   mscAtmIfVpcTmRowStatus
      RowStatus,
   mscAtmIfVpcTmComponentName
      DisplayString,
   mscAtmIfVpcTmStorageType
      StorageType,
   mscAtmIfVpcTmIndex
      NonReplicated }

mscAtmIfVpcTmRowStatus OBJECT-TYPE
   SYNTAX     RowStatus 
   ACCESS     read-only
   STATUS     mandatory
   DESCRIPTION
     "This variable is used as the basis for SNMP naming of
      mscAtmIfVpcTm components.
      These components cannot be added nor deleted."
::= { mscAtmIfVpcTmRowStatusEntry 1 }

mscAtmIfVpcTmComponentName OBJECT-TYPE
   SYNTAX     DisplayString 
   ACCESS     read-only
   STATUS     mandatory
   DESCRIPTION
     "This variable provides the component's string name for
      use with the ASCII Console Interface"
::= { mscAtmIfVpcTmRowStatusEntry 2 }

mscAtmIfVpcTmStorageType OBJECT-TYPE
   SYNTAX     StorageType 
   ACCESS     read-only
   STATUS     mandatory
   DESCRIPTION
     "This variable represents the storage type value for the
      mscAtmIfVpcTm tables."
::= { mscAtmIfVpcTmRowStatusEntry 4 }

mscAtmIfVpcTmIndex OBJECT-TYPE
   SYNTAX     NonReplicated 
   ACCESS     not-accessible
   STATUS     mandatory
   DESCRIPTION
     "This variable represents the index for the mscAtmIfVpcTm tables."
::= { mscAtmIfVpcTmRowStatusEntry 10 }

mscAtmIfVpcTmOperTable OBJECT-TYPE
   SYNTAX     SEQUENCE OF MscAtmIfVpcTmOperEntry
   ACCESS     not-accessible
   STATUS     mandatory
   DESCRIPTION
     "This group contains attributes for the Tm component to reflect 
      operational traffic attributes."
::= { mscAtmIfVpcTm 100 }

mscAtmIfVpcTmOperEntry OBJECT-TYPE
   SYNTAX     MscAtmIfVpcTmOperEntry
   ACCESS     not-accessible
   STATUS     mandatory
   DESCRIPTION
     "An entry in the mscAtmIfVpcTmOperTable."
   INDEX {
      mscAtmIfIndex,
      mscAtmIfVpcIndex,
      mscAtmIfVpcTmIndex }
::= { mscAtmIfVpcTmOperTable 1 }

MscAtmIfVpcTmOperEntry ::= SEQUENCE {
   mscAtmIfVpcTmTxTrafficDescType
      INTEGER,
   mscAtmIfVpcTmTxQosClass
      INTEGER,
   mscAtmIfVpcTmTxQueueLength
      Unsigned32,
   mscAtmIfVpcTmTxQueueCongestionState
      Unsigned32,
   mscAtmIfVpcTmHoldingPriority
      INTEGER,
   mscAtmIfVpcTmRxTrafficDescType
      INTEGER,
   mscAtmIfVpcTmRxQosClass
      INTEGER,
   mscAtmIfVpcTmAtmServiceCategory
      INTEGER,
   mscAtmIfVpcTmTrafficShaping
      INTEGER,
   mscAtmIfVpcTmBearerClassBbc
      INTEGER,
   mscAtmIfVpcTmTransferCapabilityBbc
      INTEGER,
   mscAtmIfVpcTmClippingBbc
      INTEGER,
   mscAtmIfVpcTmUnshapedTransmitQueueing
      INTEGER,
   mscAtmIfVpcTmBestEffort
      INTEGER,
   mscAtmIfVpcTmForceTagging
      INTEGER,
   mscAtmIfVpcTmWeight
      Unsigned32,
   mscAtmIfVpcTmUsageParameterControl
      INTEGER,
   mscAtmIfVpcTmTxPacketWiseDiscard
      OCTET STRING,
   mscAtmIfVpcTmRxPacketWiseDiscard
      OCTET STRING,
   mscAtmIfVpcTmBandwidthElastic
      INTEGER,
   mscAtmIfVpcTmBandwidthReduction
      Unsigned32,
   mscAtmIfVpcTmAbrConnectionType
      INTEGER }

mscAtmIfVpcTmTxTrafficDescType OBJECT-TYPE
   SYNTAX     INTEGER  {
                 n1(1),
                 n2(2),
                 n3(3),
                 n4(4),
                 n5(5),
                 n6(6),
                 n7(7),
                 n8(8),
                 n9(9) }
   ACCESS     read-only
   STATUS     mandatory
   DESCRIPTION
     "T his attribute indicates the type of traffic management which is 
      applied to the transmit direction of this connection as defined in the 
      ATM Forum. The txTrafficDescType determines the number and 
      meaning of the parameters in the txTrafficDescParm attribute."
::= { mscAtmIfVpcTmOperEntry 10 }

mscAtmIfVpcTmTxQosClass OBJECT-TYPE
   SYNTAX     INTEGER  {
                 n0(0),
                 n1(1),
                 n2(2),
                 n3(3),
                 n4(4),
                 notApplicable(14) }
   ACCESS     read-only
   STATUS     mandatory
   DESCRIPTION
     "This attribute indicates the quality of service for the calling to called 
      direction for this connection. This is only applicable to Soft PVC 
      and SVC connections. 
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified QOS class; no objective is specified for 
      the performance parameters.
      
      A value of notApplicable is displayed in the case of nailed-up PVCs 
      for which this attribute has no significance."
::= { mscAtmIfVpcTmOperEntry 31 }

mscAtmIfVpcTmTxQueueLength OBJECT-TYPE
   SYNTAX     Unsigned32 (0..30720)
   ACCESS     read-only
   STATUS     mandatory
   DESCRIPTION
     "This attribute indicates the current number of cells in the transmit 
      queue for this connection. 
      
      If this connection has unshapedTransmitQueueing attribute 
      displayed as common, this attribute displays the length of the 
      common queue which is used for this atm service category. 
      
      If this connection has unshapedTransmitQueueing attribute 
      displayed as fifo, this attribute indicates the number of cells for this 
      connection which are enqueued in a first-in-first-out queuing 
      method for this atm service category. This will only occur for 
      connections on ATM IP cards with atmServiceCategory of nrtVbr 
      or ubr. 
      
      If this connection has unshapedTransmitQueueing attribute 
      displayed as perVc or as notApplicable, this attribute displays the 
      length of the per-VC queue.
      
      For the 1pOC48SmSrAtm card, this attribute displays the current 
      number of cells in the link class queue used by this connection to 
      buffer its traffic.
      
      
      This attribute does not apply to basic Vpts."
::= { mscAtmIfVpcTmOperEntry 32 }

mscAtmIfVpcTmTxQueueCongestionState OBJECT-TYPE
   SYNTAX     Unsigned32 (0..3)
   ACCESS     read-only
   STATUS     mandatory
   DESCRIPTION
     "This attribute indicates the congestion state of the transmit queue 
      for this connection. 
      
      If this connection has unshapedTransmitQueueing attribute 
      displayed as common, this attribute displays the congestion state of 
      the common queue. If this connection has 
      unshapedTransmitQueueing attribute displayed as perVc or as 
      notApplicable, this attribute displays the congestion state of the per-
      VC queue.
      
      For the 1pOC48SmSrAtm card, this attribute displays the current 
      congestion state of the link class queue used by this connection to 
      buffer its traffic.
      
      The congestion state of a queue is indicated by a numeric value 
      ranging from 0 to 3. When a queue is in a congested state x, only 
      traffic with discard priority (DP) 0 to x are enqueued. Traffic with 
      DP > x is discarded. 
      
      For example, if the congestion state is 3, there is no congestion and 
      all traffic is enqueued. Likewise, when the congestion state is 0, 
      there is maximum congestion and only traffic with DP=0 is 
      enqueued on that queue.
      
      This attribute does not apply to basic Vpts."
::= { mscAtmIfVpcTmOperEntry 33 }

mscAtmIfVpcTmHoldingPriority OBJECT-TYPE
   SYNTAX     INTEGER  {
                 n0(0),
                 n1(1),
                 n2(2),
                 n3(3),
                 n4(4),
                 notApplicable(6) }
   ACCESS     read-only
   STATUS     mandatory
   DESCRIPTION
     "This attribute indicates the actual holding priority in effect for this 
      connection. In a situation where the link bandwidth fluctuates, such 
      as over an IMA link, holding priority is used to determine which 
      connections are held and which are released. Holding priority 4 
      connections are the first to be released. Holding priority 0 
      connections are the last to be released. Some applications, for 
      example Vcc Test, may override the provisioned holding priority. 
      
      A value of notApplicable is displayed when this is an elastic 
      connection. Holding priority does not apply to bandwidth elastic 
      connections.
      
      Holding priority has no effect if the equivalent cell rate (ECR) for a 
      connection is zero.
      
      This attribute does not apply to Vpt Vccs."
::= { mscAtmIfVpcTmOperEntry 35 }

mscAtmIfVpcTmRxTrafficDescType OBJECT-TYPE
   SYNTAX     INTEGER  {
                 n1(1),
                 n2(2),
                 n3(3),
                 n4(4),
                 n5(5),
                 n6(6),
                 n7(7),
                 n8(8),
                 n9(9) }
   ACCESS     read-only
   STATUS     mandatory
   DESCRIPTION
     "This attribute indicates the type of traffic management which is 
      applied to the receive direction of this connection as defined in the 
      ATM Forum. The rxTrafficDescType determines the number and 
      meaning of the parameters in the rxTrafficDescParm attribute."
::= { mscAtmIfVpcTmOperEntry 40 }

mscAtmIfVpcTmRxQosClass OBJECT-TYPE
   SYNTAX     INTEGER  {
                 n0(0),
                 n1(1),
                 n2(2),
                 n3(3),
                 n4(4),
                 notApplicable(14),
                 sameAsFwd(15) }
   ACCESS     read-only
   STATUS     mandatory
   DESCRIPTION
     "This attribute indicates the quality of service for the called to calling 
      direction for this connection. This is only applicable to Soft PVC 
      and SVC connections. 
      
      Class 1 supports a QOS that meets Service Class A performance 
      requirements (circuit emulation, constant bit rate video).
      
      Class 2 supports a QOS that meets Service Class B performance 
      requirements (variable bit rate audio and video).
      
      Class 3 supports a QOS that meets Service Class C performance 
      requirements (Connection-Oriented Data Transfer).
      
      Class 4 supports a QOS that meets Service Class D performance 
      requirements (Connectionless Data Transfer).
      
      Class 0 is the unspecified QOS class; no objective is specified for 
      the performance parameters.
      
      A value of notApplicable is displayed in the case of nailed-up PVCs 
      for which this attribute has no significance."
::= { mscAtmIfVpcTmOperEntry 61 }

mscAtmIfVpcTmAtmServiceCategory OBJECT-TYPE
   SYNTAX     INTEGER  {
                 unspecifiedBitRate(0),
                 constantBitRate(1),
                 rtVariableBitRate(2),
                 nrtVariableBitRate(3),
                 availableBitRate(4) }
   ACCESS     read-only
   STATUS     mandatory
   DESCRIPTION
     "This attribute indicates the ATM service category used for traffic in 
      both directions of the connection. 
      
      The constantBitRate service category is intended for real time 
      applications, that is, those requiring tightly constrained delay and 
      delay variation, as would be appropriate for voice and video 
      applications. The consistent availability of a fixed quantity of 
      bandwidth is considered appropriate for CBR service. Cells which 
      are delayed beyond the value specified by Cell Transfer Delay are 
      assumed to have significantly reduced value for the application.
      
      The rtVariableBitRate service category is intended for real time 
      applications; that is those requiring tightly constrained delay and 
      delay variation, as would be appropriate for voice and video 
      applications. Sources are expected to transmit at a rate which varies 
      with time. Equivalently, the source can be described as 'bursty'. 
      Cells which are delayed beyond the value specified by Cell Transfer 
      Delay are assumed to be of significantly reduced value to the 
      application. Real time VBR service may support statistical 
      multiplexing of real time sources.
      
      The nrtVariableBitRate service category is intended for non-real 
      time applications which have bursty traffic characteristics and which 
      can be characterized in terms of a PCR, SCR, and MBS. For those 
      cells which are transferred within the traffic contract, the application 
      expects a low cell loss ratio. For all connections, it expects a bound 
      on the mean cell transfer delay. Non-real time VBR service may 
      support statistical multiplexing of connections.
      
      The availableBitRate service is an ATM layer service category for 
      which the limiting ATM layer transfer characteristics provided by 
      the network may change subsequent to connection establishment. 
      ABR service has a flow control mechanism which supports several 
      types of feedback to control the source rate in response to changing 
      ATM layer transfer characteristics. ABR service is not intended to 
      support real-time applications.
      
      The unspecifiedBitRate service is intended for non-real time 
      applications, that is those not requiring tightly constrained delay 
      and delay variation. UBR sources are expected to be bursty. UBR 
      service supports a high degree of statistical multiplexing among 
      sources. UBR service does not specify traffic related service 
      guarantees. No numerical commitments are made with respect to 
      the cell loss ratio experienced by a UBR connection, or as to the 
      cell transfer delay experienced by cells on the connection."
::= { mscAtmIfVpcTmOperEntry 62 }

mscAtmIfVpcTmTrafficShaping OBJECT-TYPE
   SYNTAX     INTEGER  {
                 disabled(1),
                 notApplicable(4),
                 linear(5),
                 inverseUpc(6) }
   ACCESS     read-only
   STATUS     mandatory
   DESCRIPTION
     "This attribute indicates the traffic shaping state of the connection.
      
      A value of notApplicable indicates that traffic shaping is not 
      applicable or not supported for this connection. This is the case:
      - when the txTrafficDescType is 1 or 2.
      - for standard Vpt Vccs and basic Vpts.
      - for CQC-based ATM cards, when the atmServiceCategory is 
      constantBitRate.
      
      In these cases, the value of notApplicable is set regardless of 
      whether traffic shaping is enabled or disabled in the provisioning 
      data.
      
      For the 1pOC12SmLrAtm card, traffic shaping is not available, 
      therefore this attribute is always notApplicable.
      
      A value of disabled indicates that traffic shaping is applicable and 
      supported for the type of connection but has been turned off in the 
      provisioning data.
      
      A value of linear or inverseUpc indicates that traffic shaping is 
      applicable and supported for the type of connection and has been 
      turned on in the provisioning data. This is the only case that 
      indicates that traffic shaping is performed on the connection. In this 
      case, the actual shaping rate is reflected in the txTrafficDescParm 
      attribute, parameter number 4. A value of linear indicates that 
      traffic is being shaped at the constant rate indicated in 
      txTrafficDescParm 4.
      
      A value of inverseUpc is possible only on ATM IP cards. This value 
      indicates that the shaper strictly conforms to the requirements of a 
      dual leaky bucket UPC enforcer. This value is indicated if traffic 
      shaping is enabled, and the txTrafficDescType for this connection is 
      6, 7 or 8.
      
      Traffic shaping for connections with atmServiceCategory as 
      availableBitRate (txTrafficDescType 9) depends upon the 
      abrConnectionType attribute. If abrConnectionType is sourceDest 
      or virtualSourceDest, the value of this attribute is linear. If 
      abrConnectionType is erSwitch or efciSwitch, this attribute is 
      notApplicable."
::= { mscAtmIfVpcTmOperEntry 70 }

mscAtmIfVpcTmBearerClassBbc OBJECT-TYPE
   SYNTAX     INTEGER  {
                 a(1),
                 c(3),
                 x(16),
                 vp(24),
                 notApplicable(30) }
   ACCESS     read-only
   STATUS     mandatory
   DESCRIPTION
     "This attribute indicates the bearer capability for this connection.
      
      Class a service is a connection-oriented, constant bit rate ATM 
      transport service. Class a service has end to end timing 
      requirements and may require stringent cell loss, cell delay and cell 
      delay variation performance.When a is displayed, the user is 
      requesting more than an ATM only service. The network may look 
      at the AAL to provide interworking based upon its contents. 
      
      Class c service is a connection-oriented, variable bit rate ATM 
      transport service. Class c service has no end-to-end timing 
      requirements.When c is displayed, the user is requesting more than 
      an ATM only service. The network interworking function may look 
      at the AAL and provide service based on it.
      
      Class x service is a connection-oriented ATM transport service 
      where the AAL, trafficType (cbr or vbr), and timing requirements 
      are user defined (that is, transparent to the network). When the 
      value of this attribute is x, the user is requesting an ATM only 
      service from the network. In this case, the network shall not process 
      any higher layer protocol.
      
      Class vp service is used to indicate a transparent VP service when 
      the user is requesting an ATM only service from the network. In this 
      case, the network does not process any higher layer protocol. This 
      service differs from class x service in that with the class vp service 
      both the VCI field (except for VCI values 0, 3, 4, and 6 through 15) 
      and Payload Type field are transported transparently by the network. 
      This attribute value is only applicable to SPVP and SVP 
      connections.
      
      A value of notApplicable is displayed in the case of nailed-up PVCs 
      for which this attribute has no significance."
::= { mscAtmIfVpcTmOperEntry 71 }

mscAtmIfVpcTmTransferCapabilityBbc OBJECT-TYPE
   SYNTAX     INTEGER  {
                 n0(0),
                 n1(1),
                 n2(2),
                 n5(5),
                 n8(8),
                 n9(9),
                 n10(10),
                 notApplicable(30) }
   ACCESS     read-only
   STATUS     mandatory
   DESCRIPTION
     "This attribute indicates the transfer capability for this connection. 
      Uni 3.0/3.1 traffic type and end-to-end timing parameters are 
      mapped into this parameter as follows:
      <transferCapability: TrafficType, Timing>
      0: NoIndication, NoIndication
      1: NoIndication, yes
      2: NoIndication, no
      5: CBR, yes
      8: VBR, NoIndication
      9: VBR, yes
      10: VBR, no
      
      A value of notApplicable is displayed in the case of nailed-up PVCs 
      for which this attribute has no significance, or in the case that the 
      transfer capability in the call request was set to NoIndication.
      
      The CBR traffic type refers to traffic offered on services such as a 
      constant bit rate video service or a circuit emulation.
      
      The VBR traffic type refers to traffic offered on services such as 
      packetized audio and video, or data.
      
      The value NoIndication for traffic type is used if the user has not set 
      the traffic type; similarly for end-to-end timing.
      
      The value yes for end-to-end timing indicates that end-to-end 
      timing is required for the connection.
      
      The value no for end-to-end timing indicates that end-to-end timing 
      is not required for the connection."
::= { mscAtmIfVpcTmOperEntry 72 }

mscAtmIfVpcTmClippingBbc OBJECT-TYPE
   SYNTAX     INTEGER  {
                 no(0),
                 yes(1),
                 notApplicable(14) }
   ACCESS     read-only
   STATUS     mandatory
   DESCRIPTION
     "This attribute indicates the value of the clipping susceptibility 
      parameter in the broadband bearer capability (BBC) Information 
      Element.
      
      Clipping is an impairment in which the first fraction of a second of 
      information to be transferred is lost. It occurs after a call is 
      answered and before an associated connection is switched through.
      
      A value of notApplicable is displayed in the case of nailed-up PVCs 
      for which this attribute has no significance."
::= { mscAtmIfVpcTmOperEntry 74 }

mscAtmIfVpcTmUnshapedTransmitQueueing OBJECT-TYPE
   SYNTAX     INTEGER  {
                 perVc(0),
                 common(1),
                 notApplicable(4),
                 fifo(5) }
   ACCESS     read-only
   STATUS     mandatory
   DESCRIPTION
     "This attribute indicates the unshaped transmit queuing state of the 
      connection.
      
      A value of common indicates that transmit traffic is being enqueued 
      onto the common transmit queue for this service category. 
      The txQueueLength attribute indicates the current length of the 
      common transmit queue.
      
      A value of fifo indicates that transmit traffic is being queued in a 
      first-in-first-out basis for this service category. This is similar to 
      common queueing, but the txQueueLength attribute indicates the 
      number of cells in this connection queue. A value of fifo will only 
      be indicated for connections on ATM IP cards with 
      atmServiceCategory of nrtVbr or ubr. 
      
      A value of perVc indicates that transmit traffic is being enqueued 
      onto a per-VC queue for this connection. 
      
      A value of notApplicable indicates that transmit traffic is being 
      shaped for this connection, or that unshaped transmit queuing is not 
      applicable for this type of connection. Transmit traffic for a shaped 
      connection is enqueued onto a per-VC queue, but this attribute is 
      only applicable for unshaped connections. Unshaped transmit 
      queuing is not applicable for basic Vpts.
      
      For 1pOC12SmLrAtm cards, perVc queueing is not available thus 
      this attribute only indicates common or notApplicable."
::= { mscAtmIfVpcTmOperEntry 75 }

mscAtmIfVpcTmBestEffort OBJECT-TYPE
   SYNTAX     INTEGER  {
                 indicated(0),
                 notIndicated(1),
                 notApplicable(14) }
   ACCESS     read-only
   STATUS     mandatory
   DESCRIPTION
     "This attribute indicates value of best effort parameter in the ATM 
      Traffic Descriptor Information Element.
      
      The value indicated implies that the quality of service for this 
      connection is not guaranteed.
      
      The value notIndicated implies that the quality of service for this 
      connection is guaranteed.
      
      A value of notApplicable is displayed in the case of nailed-up PVCs 
      for which this attribute has no significance."
::= { mscAtmIfVpcTmOperEntry 76 }

mscAtmIfVpcTmForceTagging OBJECT-TYPE
   SYNTAX     INTEGER  {
                 enabled(0),
                 disabled(1) }
   ACCESS     read-only
   STATUS     mandatory
   DESCRIPTION
     "This attribute indicates the state of force tagging option for this 
      connection. Force tagging refers to setting the CLP bit for all cells 
      on a connection. 
      
      For CQC-based ATM cards, this attribute is not applicable and is 
      not displayed.
      
      A value of enabled indicates that the CLP bit is being set to 1 for all 
      cells in the transmit direction on this connection. 
      
      A value of disabled indicates that the CLP bit is unchanged for cells 
      in the transmit direction on this connection. disabled is always 
      displayed for Vpts since forced tagging is applied on a per Vpt Vcc 
      basis."
::= { mscAtmIfVpcTmOperEntry 78 }

mscAtmIfVpcTmWeight OBJECT-TYPE
   SYNTAX     Unsigned32 (0 | 1..4095 | 65534)
   ACCESS     read-only
   STATUS     mandatory
   DESCRIPTION
     "This attribute indicates the relative weight of this unshaped 
      connection. Connections with a larger weight get a larger proportion 
      of the link bandwidth or in the case of standard Vpt Vccs, the Vpt 
      bandwidth.
      
      For all but standard Vpt Vccs, the default connection weight is 
      determined by the weight policy for a service category and the 
      traffic descriptor for a connection. For standard Vpt Vccs, the 
      default connection weight is determined by the Vcc's service 
      category.
      
      For CQC-based ATM cards, this attribute is not applicable and is 
      not displayed.
      
      A value from 1 to 4095 indicates an actual weight. The value 
      upToQueueLimit indicates that the weight of a connection is up to 
      the transmit queue limit for this connection. upToQueueLimit is 
      used with common (first-in-first-out) queueing. 
      
      This attribute is displayed as notApplicable if:
      - this connection has trafficShaping displayed as linear or 
      inverseUpc.
      - this is a basic Vpt.

      VALUES (

      0 = upToQueueLimit

      65534 = notApplicable

      )"
::= { mscAtmIfVpcTmOperEntry 79 }

mscAtmIfVpcTmUsageParameterControl OBJECT-TYPE
   SYNTAX     INTEGER  {
                 enforced(0),
                 disabled(1),
                 notApplicable(3),
                 monitored(4) }
   ACCESS     read-only
   STATUS     mandatory
   DESCRIPTION
     "This attribute indicates the UPC state of the connection.
      
      A value of notApplicable indicates that UPC is not applicable or not 
      supported for the connection. This is the case:
      - when the connection's rxTrafficDescType is 1 or 2. 
      - for standard Vpt Vccs and basic Vpts.
      
      A value of notApplicable is set regardless of whether UPC is 
      disabled or enabled in provisioning data.
      
      A value of disabled indicates that UPC is applicable and supported 
      for the type of connection but has been turned off in the 
      provisioning data.
      
      A value of enforced indicates that UPC is actively checking 
      conformance for the connection and is discarding or tagging cells 
      which do not conform to the connection traffic contract. The traffic 
      descriptor parameters used for UPC conformance are reflected in 
      the rxTrafficDescParms of the connection. On ATM IP cards, the 
      counts of UPC violations are visible in the Vcc, Vpc or Vpt 
      rxUpcViolationsOnEnforcer1 or rxUpcViolationsOnEnforcer2 
      attributes. 
      
      ATM IP cards provide the ability to monitor UPC violations without 
      tagging or discarding. A value of monitored indicates that UPC is 
      actively checking conformance for the connection and counting the 
      violations, but is not discarding or tagging cells which do not 
      conform to the connection traffic contract. The traffic descriptor 
      parameters used for UPC conformance are reflected in the 
      rxTrafficDescParms of the connection. The counts of UPC 
      violations are visible in the Vcc, Vpc or Vpt. 
      rxUpcViolationsOnEnforcer1 or rxUpcViolationsOnEnforcer2 
      attributes. The value of monitored appears only on ATM IP cards. 
      
      If the atmServiceCategory for this connection is availableBitRate, a 
      value of enforced indicates that Dynamic Generic Cell Rate 
      Algorithm (DGCRA) is active for the connection. The traffic 
      descriptor parameters used for DGCRA enforcement are reflected in 
      the rxTrafficDescParm of the connection."
::= { mscAtmIfVpcTmOperEntry 80 }

mscAtmIfVpcTmTxPacketWiseDiscard OBJECT-TYPE
   SYNTAX     OCTET STRING (SIZE (1))
   ACCESS     read-only
   STATUS     mandatory
   DESCRIPTION
     "This attribute indicates the current set of packet-wise discard 
      functions in effect in the transmit data direction at this connection 
      point.
      
      A value of ppd indicates that the Partial Packet Discard (PPD) 
      function is in effect. PPD may be applied at an intermediate 
      connecting point for a connection which is transporting frame traffic 
      (AAL5 at the endpoint). PPD is controlled by provisioning for 
      PVCs and SPVCs, and by call setup parameters in the AAL and 
      Traffic Descriptor Information Elements.
      
      A value of epd indicates that the Early Packet Discard (EPD) 
      function is in effect at this connection endpoint. On CQC-based 
      ATM cards, PPD and EPD are enabled by default at a connection 
      endpoint which is performing AAL5 segmentation and assembly.
      
      A value of wred indicates that Weighted Random Early Detection is 
      in effect at this connection point. W-RED can be enabled by 
      provisioning for PVCs and SPVCs.
      
      On ATM IP cards, all packet-wise discard functions also apply to 
      provisioned virtual path connections (VPCs). On CQC-based ATM 
      cards, packet-wise functions are not applicable for VPCs.
      
      This attribute is not applicable for Vpts.

      Description of bits:
      ppd(0)
      epd(1)
      wred(2)"
::= { mscAtmIfVpcTmOperEntry 85 }

mscAtmIfVpcTmRxPacketWiseDiscard OBJECT-TYPE
   SYNTAX     OCTET STRING (SIZE (1))
   ACCESS     read-only
   STATUS     mandatory
   DESCRIPTION
     "This attribute indicates the current set of packet-wise discard 
      functions in effect in the receive data direction at this connection 
      point.
      
      A value of ppd indicates that the Partial Packet Discard (PPD) 
      function is in effect. PPD may be applied at an intermediate 
      connecting point for a connection which is transporting frame traffic 
      (AAL5 at the endpoint). PPD is controlled by provisioning for 
      PVCs and SPVCs, and by call setup parameters in the AAL and 
      Traffic Descriptor Information Elements.
      
      A value of epd indicates that the Early Packet Discard (EPD) 
      function is in effect at this connection endpoint. PPD and EPD are 
      enabled by default at a connection endpoint which is performing 
      AAL5 segmentation and assembly.
      
      On ATM IP cards, all packet-wise discard functions also apply to 
      provisioned virtual path connections (VPCs). On CQC-based ATM 
      cards, packet-wise functions are not applicable for VPCs.
      
      This attribute is not applicable for Vpts.

      Description of bits:
      ppd(0)
      epd(1)"
::= { mscAtmIfVpcTmOperEntry 86 }

mscAtmIfVpcTmBandwidthElastic OBJECT-TYPE
   SYNTAX     INTEGER  {
                 no(0),
                 yes(1) }
   ACCESS     read-only
   STATUS     mandatory
   DESCRIPTION
     "This attribute is only of importance for connections which are 
      carried on a link with a variable bandwidth. For example, the 
      bandwidth may be reduced in the event that one or more physical 
      links in the IMA group fail, such that the originally requested 
      bandwidth cannot be maintained. This attribute shows whether the 
      application (for example, Trunk) running on this connection can 
      continue to operate if the bandwidth is reduced. If the bandwidth is 
      reduced, the amount by which it is reduced is displayed in the 
      bandwidthReduction attribute. 
      
      A value of yes, indicates that this connection is elastic, and the 
      bandwidth may be reduced but the connection is not released. 
      
      A value of no indicates that the bandwidth for this connection is not 
      reduced in the event of link bandwidth reduction. However, this 
      connection may be released based on its holdingPriority.
      
      Bandwidth elasticity has no effect for connections which have an 
      equivalent cell rate (ECR) of zero. 
      
      This attribute is not applicable for Vpts and Vpt Vccs."
::= { mscAtmIfVpcTmOperEntry 90 }

mscAtmIfVpcTmBandwidthReduction OBJECT-TYPE
   SYNTAX     Unsigned32 (0..2147483647)
   ACCESS     read-only
   STATUS     mandatory
   DESCRIPTION
     "This attribute shows the amount by which the bandwidth has been 
      reduced for this connection. This value is non-zero only for 
      connections which have bandwidthElastic displayed as yes, and 
      which are also operating in a reduced bandwidth mode. This is 
      typically the case for selected connections running over an IMA 
      link. This attribute takes a value from 0 (no reduction) up to the 
      ECR. For all connections which are running at their full allocated 
      bandwidth, bwReduction has the value 0. Connections which have 
      been reduced in allocated bandwidth have a positive number for this 
      attribute. The bwReduction may be subtracted from the ECR (which 
      is displayed as txTrafficDescParm 5) to determine the actual 
      bandwidth allocated to this connection."
::= { mscAtmIfVpcTmOperEntry 100 }

mscAtmIfVpcTmAbrConnectionType OBJECT-TYPE
   SYNTAX     INTEGER  {
                 erSwitch(1),
                 efciSwitch(2),
                 virtualSourceDest(3),
                 sourceDest(4),
                 nonAbrInterworking(5),
                 notApplicable(15) }
   ACCESS     read-only
   STATUS     mandatory
   DESCRIPTION
     "This attribute indicates the type of ABR behavior which is in effect 
      at this connection. This attribute is only applicable if the 
      atmServiceCategory attribute is availableBitRate. If the 
      atmServiceCategory attribute is not availableBitRate, this attribute 
      value is set to notApplicable.
      
      For CQC-based ATM cards and the 1pOC12SmLrAtm card, the 
      notApplicable, efciSwitch or nonAbrInterworking. In EFCI 
      marking mode, the Explicit Forward Congestion Indication (EFCI) 
      field in the data cell headers is used to indicate transmit queue 
      congestion. 
      
      For ATM IP cards other than 1pOC12SmLrAtm, if the displayed as 
      connectionEndPoint, this attribute has the value sourceDest. In this 
      mode, the ABR Source and Destination behavior is in effect at this 
      connection. This attribute is also sourceDest in the case where the 
      next hop connection is specified as nonAbrInterworking. The next 
      hop connection is the Vcc or Vpc identified by the nextHop attribute 
      of the Nrp or Rp component. 
      
      If the connectionPointType is not connectionEndPoint, the value of 
      this attribute depends upon the abrConnectionType provisioning 
      and the card type to which the traffic is forwarded on the backplane. 
      The default abrConnectionType is provisioned at the CA Abr 
      abrConnectionType attribute, and may be overridden for a 
      provisioned connection in the Vcd Tm abrConnectionType or Vpd 
      Tm abrConnectionType attribute. If the CA Abr abrConnectionType 
      attribute is virtualSourceDest at either one of the two connection 
      points, and if both the connection points are defined on ATM IP 
      cards, virtual source and destination behavior is applied to the 
      connection. In this instance, the attribute displays the value 
      virtualSourceDest.
      
      This attribute has the value erSwitch if ABR explicit rate 
      functionality is in effect at this connection. In this mode, the switch 
      may modify the Explicit Rate (ER) field of backward Resource 
      Management (RM) cells to indicate the status of congestion at this 
      connection point.
      
      This attribute has the value nonAbrInterworking in the case where 
      this connection point is functioning as an SPVC origin for an ABR 
      connection where the link side of this connection is configured as a 
      non-ABR ATM service category. This means that there are no RM 
      cells on the link side of this connection, and that the next hop 
      connection point is performing as an ABR sourceDest."
::= { mscAtmIfVpcTmOperEntry 110 }

mscAtmIfVpcTmTxTdpTable OBJECT-TYPE
   SYNTAX     SEQUENCE OF MscAtmIfVpcTmTxTdpEntry
   ACCESS     not-accessible
   STATUS     mandatory
   DESCRIPTION
     "This attribute is a vector of five transmit traffic parameters whose 
      mapping is defined by the txTrafficDescType attribute. 
      
      The values of peak cell rate (PCR), sustained cell rate (SCR), 
      Minimum Cell Rate (MCR), actual cell rate (ACR), explicit rate 
      (ER), equivalent cell rate (ECR), and actual shaping rate are 
      expressed in cell/s. Maximum burst size (MBS) is expressed in 
      cells. CDVT is expressed in microseconds. 
      
      When txTrafficDescType is 1 or 2, parameters 1 through 5 are 
      unused.
      
      In this description, PCR is the greater of either the PCR or the 
      requested shaping rate (parameter 1 or parameter 5) specified in the 
      txTrafficDescParm attribute under the Vcd Tm or Vpd Tm 
      component.
      
      When txTrafficDescType is 3, parameter 1 represents the PCR for 
      CLP equal to 0 or 1 traffic; parameters 2 and 3 are unused.
      
      When txTrafficDescType is 4, parameter 1 represents the PCR for 
      CLP equal to 0 and 1 traffic; parameter 2 represents the PCR for 
      CLP equal to 0 traffic with cell discard.
      
      When txTrafficDescType is 5, parameter 1 represents the PCR for 
      CLP equal to 0 and 1 traffic; parameter 2 represents the PCR for 
      CLP equal to 0 traffic with cell tagging.
      
      When txTrafficDescType is 6, parameter 1 represents the PCR for 
      CLP equal to 0 and 1 traffic; parameter 2 represents the SCR for 
      CLP equal to 0 and 1 traffic; parameter 3 represents the MBS for 
      CLP equal to 0 and 1 traffic.
      
      When txTrafficDescType is 7, parameter 1 represents the PCR for 
      CLP equal to 0 and 1 traffic; parameter 2 represents the SCR for 
      CLP equal to 0 traffic with cell discard; parameter 3 represents the 
      MBS for CLP equal to 0 traffic.
      
      When txTrafficDescType is 8, parameter 1 represents the PCR for 
      CLP equal to 0 and 1 traffic; parameter 2 represents the SCR for 
      CLP equal to 0 traffic with cell tagging; parameter 3 represents the 
      MBS for CLP equal to 0 traffic.
      
      When txTrafficDescType is 3, 4, 5, 6, 7, or 8, parameter 4 reflects 
      the actual shaping rate in cell/s for this connection. For CQC-based 
      ATM cards, the set of available shaping rates is based on the 
      number of interfaces doing shaping (attribute 
      perVcQueueInterfaces), and the shapingScalingFactor attribute of 
      the Arc Cqc Override component. A rate of zero (0) indicates that 
      shaping is not performed, or that the interface is down. 
      
      When txTrafficDescType is 9, parameter 1 represents the PCR; 
      parameter 2 represents the Cell Delay Variation Toleration (CDVT); 
      parameter 3 represents the Minimum Cell Rate (MCR); the meaning 
      of parameter 4 depends upon the value of the abrConnectionType 
      attribute. if abrConnectionType is sourceDest or 
      virtualSourceDest, parameter 4 represents the Allowed Cell Rate 
      (ACR); If abrConnectionType is erSwitch, parameter 4 represents 
      the Explicit Rate (ER); and if abrConnectionType is efciSwitch, 
      parameter 4 reflects the actual shaping rate in cell/s for this 
      connection.
      
      When txTrafficDescType is 3, 4, 5, 6, 7, 8, or 9, parameter 5 reflects 
      the equivalent cell rate in cell/s for this connection as determined by 
      the Connection Admission Control (CAC) algorithm. The 
      equivalent cell rate is useful in determining the admission 
      characteristics of this connection."
::= { mscAtmIfVpcTm 451 }

mscAtmIfVpcTmTxTdpEntry OBJECT-TYPE
   SYNTAX     MscAtmIfVpcTmTxTdpEntry
   ACCESS     not-accessible
   STATUS     mandatory
   DESCRIPTION
     "An entry in the mscAtmIfVpcTmTxTdpTable."
   INDEX {
      mscAtmIfIndex,
      mscAtmIfVpcIndex,
      mscAtmIfVpcTmIndex,
      mscAtmIfVpcTmTxTdpIndex }
::= { mscAtmIfVpcTmTxTdpTable 1 }

MscAtmIfVpcTmTxTdpEntry ::= SEQUENCE {
   mscAtmIfVpcTmTxTdpIndex
      Integer32,
   mscAtmIfVpcTmTxTdpValue
      Unsigned32 }

mscAtmIfVpcTmTxTdpIndex OBJECT-TYPE
   SYNTAX     Integer32 (1..5)
   ACCESS     not-accessible
   STATUS     mandatory
   DESCRIPTION
     "This variable represents the mscAtmIfVpcTmTxTdpTable
      specific index for the mscAtmIfVpcTmTxTdpTable."
::= { mscAtmIfVpcTmTxTdpEntry 1 }

mscAtmIfVpcTmTxTdpValue OBJECT-TYPE
   SYNTAX     Unsigned32 (0..2147483647)
   ACCESS     read-only
   STATUS     mandatory
   DESCRIPTION
     "This variable represents an individual value for the
      mscAtmIfVpcTmTxTdpTable."
::= { mscAtmIfVpcTmTxTdpEntry 2 }

mscAtmIfVpcTmTxQThreshTable OBJECT-TYPE
   SYNTAX     SEQUENCE OF MscAtmIfVpcTmTxQThreshEntry
   ACCESS     not-accessible
   STATUS     mandatory
   DESCRIPTION
     "This attribute indicates the queue limit and the discard thresholds 
      for the transmit queue of this connection. 
      
      If this connection has unshapedTransmitQueueing attribute 
      displayed as common, this attribute displays the thresholds of the 
      common queue. If this connection has unshapedTransmitQueueing 
      attribute displayed as perVc or as notApplicable, this attribute 
      displays the thresholds of the per-VC queue.
      
      The first element indicates the queue limit. The provisioned value of 
      the transmit queue limit is derived from the txQueueLimit attribute 
      under the service category subcomponents of the CA component for 
      the service category of this connection. 
      
      The second element is the threshold that marks the transition from 
      congestion state 1 to congestion state 0. This is the threshold at 
      which traffic with discard priority (DP) = 1 is discarded. This 
      threshold is set at approximately 90 percent of the first parameter, 
      the operational queue limit.
      
      The third element is the threshold that marks the transition from 
      congestion state 2 to congestion state 1. This is the threshold at 
      which traffic with DP = 2 is discarded. This threshold is set at 
      approximately 75 percent of the first parameter, the operational 
      queue limit.
      
      The fourth element is the threshold that marks the transition from 
      congestion state 3 to congestion state 2. This is the threshold at 
      which traffic with DP = 3 is discarded. This threshold is set at 
      approximately 35 percent of the first parameter, the operational 
      queue limit.
      
      This attribute does not apply to basic Vpts."
::= { mscAtmIfVpcTm 452 }

mscAtmIfVpcTmTxQThreshEntry OBJECT-TYPE
   SYNTAX     MscAtmIfVpcTmTxQThreshEntry
   ACCESS     not-accessible
   STATUS     mandatory
   DESCRIPTION
     "An entry in the mscAtmIfVpcTmTxQThreshTable."
   INDEX {
      mscAtmIfIndex,
      mscAtmIfVpcIndex,
      mscAtmIfVpcTmIndex,
      mscAtmIfVpcTmTxQThreshIndex }
::= { mscAtmIfVpcTmTxQThreshTable 1 }

MscAtmIfVpcTmTxQThreshEntry ::= SEQUENCE {
   mscAtmIfVpcTmTxQThreshIndex
      Integer32,
   mscAtmIfVpcTmTxQThreshValue
      Unsigned32 }

mscAtmIfVpcTmTxQThreshIndex OBJECT-TYPE
   SYNTAX     Integer32 (0..3)
   ACCESS     not-accessible
   STATUS     mandatory
   DESCRIPTION
     "This variable represents the mscAtmIfVpcTmTxQThreshTable
      specific index for the mscAtmIfVpcTmTxQThreshTable."
::= { mscAtmIfVpcTmTxQThreshEntry 1 }

mscAtmIfVpcTmTxQThreshValue OBJECT-TYPE
   SYNTAX     Unsigned32 (0..512000)
   ACCESS     read-only
   STATUS     mandatory
   DESCRIPTION
     "This variable represents an individual value for the
      mscAtmIfVpcTmTxQThreshTable."
::= { mscAtmIfVpcTmTxQThreshEntry 2 }

mscAtmIfVpcTmRxTdpTable OBJECT-TYPE
   SYNTAX     SEQUENCE OF MscAtmIfVpcTmRxTdpEntry
   ACCESS     not-accessible
   STATUS     mandatory
   DESCRIPTION
     "This attribute is a vector of four traffic parameters whose meanings 
      are defined by the rxTrafficDescType attribute. The values of peak 
      cell rate (PCR), sustained cell rate (SCR), minimum cell rate 
      (MCR) are expressed in cell/s. Maximum burst size (MBS) is 
      expressed in cells. Cell delay variation tolerance (CDVT) is 
      expressed in microseconds.
      
      When rxTrafficDescType is 1 or 2, none of the parameters are used.
      
      When rxTrafficDescType is 3, parameter 1 represents the PCR for 
      CLP equal to 0 and 1 traffic; parameter 4 represents the CDVT.
      
      When rxTrafficDescType is 4, parameter 1 represents the PCR for 
      CLP equal to 0 and 1 traffic; parameter 2 represents the PCR for 
      CLP equal to 0 traffic with cell discard; parameter 4 represents the 
      CDVT.
      
      When rxTrafficDescType is 5, parameter 1 represents the PCR for 
      CLP equal to 0 and 1 traffic; parameter 2 represents the PCR for 
      CLP equal to 0 traffic with cell tagging; parameter 4 represents the 
      CDVT.
      
      When rxTrafficDescType is 6, parameter 1 represents the PCR for 
      CLP equal to 0 and 1 traffic; parameter 2 represents the SCR for 
      CLP equal to 0 and 1 traffic; parameter 3 represents the MBS for 
      CLP equal to 0 and 1 traffic; parameter 4 represents the CDVT. 
      
      When rxTrafficDescType is 7, parameter 1 represents the PCR for 
      CLP equal to 0 and 1 traffic; parameter 2 represents the SCR for 
      CLP equal to 0 traffic with cell discard; parameter 3 represents the 
      MBS for CLP equal to 0 traffic; parameter 4 represents the CDVT.
      
      When rxTrafficDescType is 8, parameter 1 represents the PCR for 
      CLP equal to 0 and 1 traffic; parameter 2 represents the SCR for 
      CLP equal to 0 traffic with cell tagging; parameter 3 represents the 
      MBS for CLP equal to 0 traffic; parameter 4 represents the CDVT. 
      
      When rxTrafficDescType is 9, parameter 1 represents the PCR; 
      parameter 2 represents CDVT; parameter 3 represents the MCR; 
      parameter 4 is not used.
      
      If upc is disabled for this connection, the values of PCR, SCR, 
      MBS and CDVT are the provisioned parameters.
      
      If upc is enabled, the values of PCR, SCR, MBS, and CDVT are 
      exactly the values used by the usage parameter control hardware in 
      policing the arriving traffic. These may vary slightly from the 
      provisioned values due to granularity of the hardware. In the case 
      where the PCR is equal to the SCR, the effective MBS is zero."
::= { mscAtmIfVpcTm 453 }

mscAtmIfVpcTmRxTdpEntry OBJECT-TYPE
   SYNTAX     MscAtmIfVpcTmRxTdpEntry
   ACCESS     not-accessible
   STATUS     mandatory
   DESCRIPTION
     "An entry in the mscAtmIfVpcTmRxTdpTable."
   INDEX {
      mscAtmIfIndex,
      mscAtmIfVpcIndex,
      mscAtmIfVpcTmIndex,
      mscAtmIfVpcTmRxTdpIndex }
::= { mscAtmIfVpcTmRxTdpTable 1 }

MscAtmIfVpcTmRxTdpEntry ::= SEQUENCE {
   mscAtmIfVpcTmRxTdpIndex
      Integer32,
   mscAtmIfVpcTmRxTdpValue
      Unsigned32 }

mscAtmIfVpcTmRxTdpIndex OBJECT-TYPE
   SYNTAX     Integer32 (1..4)
   ACCESS     not-accessible
   STATUS     mandatory
   DESCRIPTION
     "This variable represents the mscAtmIfVpcTmRxTdpTable
      specific index for the mscAtmIfVpcTmRxTdpTable."
::= { mscAtmIfVpcTmRxTdpEntry 1 }

mscAtmIfVpcTmRxTdpValue OBJECT-TYPE
   SYNTAX     Unsigned32 (0..2147483647)
   ACCESS     read-only
   STATUS     mandatory
   DESCRIPTION
     "This variable represents an individual value for the
      mscAtmIfVpcTmRxTdpTable."
::= { mscAtmIfVpcTmRxTdpEntry 2 }

mscAtmIfVpcTmTqpTable OBJECT-TYPE
   SYNTAX     SEQUENCE OF MscAtmIfVpcTmTqpEntry
   ACCESS     not-accessible
   STATUS     mandatory
   DESCRIPTION
     "This attribute is a vector of three elements that indicate the quality 
      of service parameters for the forward direction for this connection. 
      This attribute is used for SPVC and SVC connections on a PNNI 
      interface.
      
      The cdv element indicates the acceptable peak-to-peak Cell Delay 
      Variation (CDV) of real-time connections (CBR and rt-VBR). 
      
      The ctd element indicates the acceptable maximum Cell Transfer 
      Delay (maxCtd) of real-time connections (CBR and rt-VBR). 
      
      The clr element indicates the acceptable Cell Loss Ratio (CLR) of 
      CBR, rt-VBR, and nrt-VBR connections."
::= { mscAtmIfVpcTm 454 }

mscAtmIfVpcTmTqpEntry OBJECT-TYPE
   SYNTAX     MscAtmIfVpcTmTqpEntry
   ACCESS     not-accessible
   STATUS     mandatory
   DESCRIPTION
     "An entry in the mscAtmIfVpcTmTqpTable."
   INDEX {
      mscAtmIfIndex,
      mscAtmIfVpcIndex,
      mscAtmIfVpcTmIndex,
      mscAtmIfVpcTmTqpIndex }
::= { mscAtmIfVpcTmTqpTable 1 }

MscAtmIfVpcTmTqpEntry ::= SEQUENCE {
   mscAtmIfVpcTmTqpIndex
      INTEGER,
   mscAtmIfVpcTmTqpValue
      Unsigned32 }

mscAtmIfVpcTmTqpIndex OBJECT-TYPE
   SYNTAX     INTEGER  {
                 cdv(0),
                 ctd(1),
                 clr(2) }
   ACCESS     not-accessible
   STATUS     mandatory
   DESCRIPTION
     "This variable represents the mscAtmIfVpcTmTqpTable
      specific index for the mscAtmIfVpcTmTqpTable."
::= { mscAtmIfVpcTmTqpEntry 1 }

mscAtmIfVpcTmTqpValue OBJECT-TYPE
   SYNTAX     Unsigned32 (0..2147483647)
   ACCESS     read-only
   STATUS     mandatory
   DESCRIPTION
     "This variable represents an individual value for the
      mscAtmIfVpcTmTqpTable."
::= { mscAtmIfVpcTmTqpEntry 2 }

mscAtmIfVpcTmRqpTable OBJECT-TYPE
   SYNTAX     SEQUENCE OF MscAtmIfVpcTmRqpEntry
   ACCESS     not-accessible
   STATUS     mandatory
   DESCRIPTION
     "This attribute is a vector of three elements that indicate the quality 
      of service parameters for the backward direction for this 
      connection. This attribute is used for SPVC and SVC connections 
      on a PNNI interface.
      
      The cdv element indicates the acceptable peak-to-peak Cell Delay 
      Variation (CDV) of real-time connections (CBR and rt-VBR). 
      
      The ctd element indicates the acceptable maximum Cell Transfer 
      Delay (maxCtd) of real-time connections (CBR and rt-VBR). 
      
      The clr element indicates the acceptable Cell Loss Ratio (CLR) of 
      CBR, rt-VBR, and nrt-VBR connections."
::= { mscAtmIfVpcTm 455 }

mscAtmIfVpcTmRqpEntry OBJECT-TYPE
   SYNTAX     MscAtmIfVpcTmRqpEntry
   ACCESS     not-accessible
   STATUS     mandatory
   DESCRIPTION
     "An entry in the mscAtmIfVpcTmRqpTable."
   INDEX {
      mscAtmIfIndex,
      mscAtmIfVpcIndex,
      mscAtmIfVpcTmIndex,
      mscAtmIfVpcTmRqpIndex }
::= { mscAtmIfVpcTmRqpTable 1 }

MscAtmIfVpcTmRqpEntry ::= SEQUENCE {
   mscAtmIfVpcTmRqpIndex
      INTEGER,
   mscAtmIfVpcTmRqpValue
      Unsigned32 }

mscAtmIfVpcTmRqpIndex OBJECT-TYPE
   SYNTAX     INTEGER  {
                 cdv(0),
                 ctd(1),
                 clr(2) }
   ACCESS     not-accessible
   STATUS     mandatory
   DESCRIPTION
     "This variable represents the mscAtmIfVpcTmRqpTable
      specific index for the mscAtmIfVpcTmRqpTable."
::= { mscAtmIfVpcTmRqpEntry 1 }

mscAtmIfVpcTmRqpValue OBJECT-TYPE
   SYNTAX     Unsigned32 (0..2147483647)
   ACCESS     read-only
   STATUS     mandatory
   DESCRIPTION
     "This variable represents an individual value for the
      mscAtmIfVpcTmRqpTable."
::= { mscAtmIfVpcTmRqpEntry 2 }


-- AtmIf/n Vpc/vpi Tm AvailableBitRate, 
-- AtmIf/n Vcc/vpi.vci Tm AvailableBitRate,
-- AtmIf/n Vpt/vpi Tm AvailableBitRate,
-- AtmIf/n Vpt/vpi Vcc/vci Tm AvailableBitRate
-- This component contains ABR-related operational attributes of a 
-- connection. It is dynamically created for connections where the 
-- atmServiceCategory is availableBitRate, and where 
-- abrConnectionType is sourceDest or virtualSourceDest.

mscAtmIfVpcTmAbr OBJECT IDENTIFIER ::= { mscAtmIfVpcTm 2 }



mscAtmIfVpcTmAbrRowStatusTable OBJECT-TYPE
   SYNTAX     SEQUENCE OF MscAtmIfVpcTmAbrRowStatusEntry
   ACCESS     not-accessible
   STATUS     mandatory
   DESCRIPTION
     "This entry controls the addition and deletion of 
      mscAtmIfVpcTmAbr components."
::= { mscAtmIfVpcTmAbr 1 }

mscAtmIfVpcTmAbrRowStatusEntry OBJECT-TYPE
   SYNTAX     MscAtmIfVpcTmAbrRowStatusEntry
   ACCESS     not-accessible
   STATUS     mandatory
   DESCRIPTION
     "A single entry in the table represents a single 
      mscAtmIfVpcTmAbr component."
   INDEX {
      mscAtmIfIndex,
      mscAtmIfVpcIndex,
      mscAtmIfVpcTmIndex,
      mscAtmIfVpcTmAbrIndex }
::= { mscAtmIfVpcTmAbrRowStatusTable 1 }

MscAtmIfVpcTmAbrRowStatusEntry ::= SEQUENCE {
   mscAtmIfVpcTmAbrRowStatus
      RowStatus,
   mscAtmIfVpcTmAbrComponentName
      DisplayString,
   mscAtmIfVpcTmAbrStorageType
      StorageType,
   mscAtmIfVpcTmAbrIndex
      NonReplicated }

mscAtmIfVpcTmAbrRowStatus OBJECT-TYPE
   SYNTAX     RowStatus 
   ACCESS     read-only
   STATUS     mandatory
   DESCRIPTION
     "This variable is used as the basis for SNMP naming of
      mscAtmIfVpcTmAbr components.
      These components cannot be added nor deleted."
::= { mscAtmIfVpcTmAbrRowStatusEntry 1 }

mscAtmIfVpcTmAbrComponentName OBJECT-TYPE
   SYNTAX     DisplayString 
   ACCESS     read-only
   STATUS     mandatory
   DESCRIPTION
     "This variable provides the component's string name for
      use with the ASCII Console Interface"
::= { mscAtmIfVpcTmAbrRowStatusEntry 2 }

mscAtmIfVpcTmAbrStorageType OBJECT-TYPE
   SYNTAX     StorageType 
   ACCESS     read-only
   STATUS     mandatory
   DESCRIPTION
     "This variable represents the storage type value for the
      mscAtmIfVpcTmAbr tables."
::= { mscAtmIfVpcTmAbrRowStatusEntry 4 }

mscAtmIfVpcTmAbrIndex OBJECT-TYPE
   SYNTAX     NonReplicated 
   ACCESS     not-accessible
   STATUS     mandatory
   DESCRIPTION
     "This variable represents the index for the mscAtmIfVpcTmAbr tables."
::= { mscAtmIfVpcTmAbrRowStatusEntry 10 }

mscAtmIfVpcTmAbrOperTable OBJECT-TYPE
   SYNTAX     SEQUENCE OF MscAtmIfVpcTmAbrOperEntry
   ACCESS     not-accessible
   STATUS     mandatory
   DESCRIPTION
     "This group contains operational attributes for connections using 
      ABR service category."
::= { mscAtmIfVpcTmAbr 110 }

mscAtmIfVpcTmAbrOperEntry OBJECT-TYPE
   SYNTAX     MscAtmIfVpcTmAbrOperEntry
   ACCESS     not-accessible
   STATUS     mandatory
   DESCRIPTION
     "An entry in the mscAtmIfVpcTmAbrOperTable."
   INDEX {
      mscAtmIfIndex,
      mscAtmIfVpcIndex,
      mscAtmIfVpcTmIndex,
      mscAtmIfVpcTmAbrIndex }
::= { mscAtmIfVpcTmAbrOperTable 1 }

MscAtmIfVpcTmAbrOperEntry ::= SEQUENCE {
   mscAtmIfVpcTmAbrInitialCellRate
      Unsigned32,
   mscAtmIfVpcTmAbrTransientBufferExposure
      Unsigned32,
   mscAtmIfVpcTmAbrFixedRoundTripTime
      Unsigned32,
   mscAtmIfVpcTmAbrRateDecreaseFactor
      Unsigned32,
   mscAtmIfVpcTmAbrRateIncreaseFactor
      Unsigned32,
   mscAtmIfVpcTmAbrMaxCellPerRmCell
      Unsigned32,
   mscAtmIfVpcTmAbrMaxTimeBetweenRmCell
      Unsigned32,
   mscAtmIfVpcTmAbrCutoffDecreaseFactor
      Unsigned32,
   mscAtmIfVpcTmAbrAcrDecreaseTimeFactor
      Unsigned32,
   mscAtmIfVpcTmAbrForwardRmCellLimit
      Unsigned32,
   mscAtmIfVpcTmAbrTxRateChangeInfo
      INTEGER,
   mscAtmIfVpcTmAbrAcrRateChangeInfo
      INTEGER,
   mscAtmIfVpcTmAbrTxFwdRmCells
      Unsigned32,
   mscAtmIfVpcTmAbrRxEfci
      INTEGER }

mscAtmIfVpcTmAbrInitialCellRate OBJECT-TYPE
   SYNTAX     Unsigned32 (0..16777215)
   ACCESS     read-only
   STATUS     mandatory
   DESCRIPTION
     "This attribute indicates the Initial Cell Rate (ICR) parameter for this 
      connection. ICR is the rate at which a source should send initially 
      and after an idle period.
      
      For nailed-up connections, this attribute is determined by the 
      provisioned value of the initialCellRate attribute. For signalled 
      connections, it is indicated in the ABR Setup Parameters 
      Information Element.
      
      The ICR for a connection is a value between the MCR and the PCR. 
      Furthermore, ICR has an upper bound determined by the 
      transientBufferExposure divided by fixedRoundTripTime."
::= { mscAtmIfVpcTmAbrOperEntry 10 }

mscAtmIfVpcTmAbrTransientBufferExposure OBJECT-TYPE
   SYNTAX     Unsigned32 (0..16777215)
   ACCESS     read-only
   STATUS     mandatory
   DESCRIPTION
     "This attribute indicates the Transient Buffer Exposure (TBE) for 
      this connection. TBE is the negotiated number of cells that the 
      network would like to limit the resource to send during start-up 
      periods, before the first Resource Management (RM) cell returns.
      
      For nailed-up connections, this attribute is determined by the 
      provisioned value of the transientBufferExposure attribute. For 
      signalled connections, it is indicated in the ABR Setup Parameters 
      Information Element."
::= { mscAtmIfVpcTmAbrOperEntry 11 }

mscAtmIfVpcTmAbrFixedRoundTripTime OBJECT-TYPE
   SYNTAX     Unsigned32 (0..16700000)
   ACCESS     read-only
   STATUS     mandatory
   DESCRIPTION
     "This attribute indicates the Fixed Round-Trip Time (FRTT) 
      parameter for this connection. FRTT is the sum of the fixed and 
      propagation delays from the source to a destination and back.
      
      For nailed-up connections, this attribute is determined by the 
      provisioned value of the fixedRoundTripTime attribute. For 
      signalled connections, it is indicated in the ABR Setup Parameters 
      Information Element."
::= { mscAtmIfVpcTmAbrOperEntry 12 }

mscAtmIfVpcTmAbrRateDecreaseFactor OBJECT-TYPE
   SYNTAX     Unsigned32 (0..15)
   ACCESS     read-only
   STATUS     mandatory
   DESCRIPTION
     "This attribute indicates the Rate Decrease Factor (RDF) for this 
      connection. The RDF value is computed by using the operational 
      value of this attribute, n, as 2 to the inverse power n. For example, if 
      the value of this attribute is 8, RDF is 2E-8 = 1/256.
      
      RDF controls the amount by which the cell transmission rate may 
      decrease upon receipt of a backward Resource Management (RM) 
      cell. For example, if a backward RM cell is received with the 
      Congestion Indication (CI) field set to 1, the Allowed Cell Rate 
      (ACR) value would be reduced by the amount (RDF*ACR). The 
      ACR is not allowed to fall below the Minimum Cell Rate (MCR), in 
      which case the ACR is set to MCR.
      
      For nailed-up connections, this attribute is determined by the 
      provisioned value of the rateDecreaseFactor attribute. For signalled 
      connections, it is indicated in the ABR Setup Parameters 
      Information Element."
::= { mscAtmIfVpcTmAbrOperEntry 13 }

mscAtmIfVpcTmAbrRateIncreaseFactor OBJECT-TYPE
   SYNTAX     Unsigned32 (0..15)
   ACCESS     read-only
   STATUS     mandatory
   DESCRIPTION
     "This attribute indicates the Rate Increase Factor (RIF) for this 
      connection. The RIF value is computed by using the operational 
      value of this attribute, n, as 2 to the inverse power n. For example, if 
      the value of this attribute is 6, RIF is 2E-6 = 1/64.
      
      RIF controls the amount by which the cell transmission rate may 
      increase upon receipt of a backward Resource Management (RM) 
      cell. For example, if a backward RM cell is received with the 
      Congestion Indication (CI) and the No Increase (NI) fields both set 
      to 0, the Allowed Cell Rate (ACR) value would be increased by the 
      amount (RIF*ACR). The ACR is not allowed to exceed the Peak 
      Cell Rate (PCR), in which case the ACR is set to PCR.
      
      For nailed-up connections, this attribute is determined by the 
      provisioned value of the rateIncreaseFactor attribute. For signalled 
      connections, it is indicated in the ABR Setup Parameters 
      Information Element."
::= { mscAtmIfVpcTmAbrOperEntry 14 }

mscAtmIfVpcTmAbrMaxCellPerRmCell OBJECT-TYPE
   SYNTAX     Unsigned32 (2 | 4 | 8 | 16 | 32 | 64 | 128 | 256)
   ACCESS     read-only
   STATUS     mandatory
   DESCRIPTION
     "This attribute indicates the maximum number of cells an ABR 
      source may transmit for each forward Resource Management (RM) 
      cell. The count of the cells transmitted includes data cells, OAM 
      cells, backward RM cells, and the forward RM cell.
      
      For nailed-up connections, this attribute is determined by the 
      provisioned value of the maxCellsPerRmCell attribute. For 
      signalled connections, it is indicated in the ABR Additional 
      Parameters Information Element."
::= { mscAtmIfVpcTmAbrOperEntry 15 }

mscAtmIfVpcTmAbrMaxTimeBetweenRmCell OBJECT-TYPE
   SYNTAX     Unsigned32 (781 | 1563 | 3125 | 6250 | 12500 | 25000 | 50000 | 100000)
   ACCESS     read-only
   STATUS     mandatory
   DESCRIPTION
     "This attribute indicates the TRM parameter for this connection.
      
      TRM provides an upper bound on the time interval between forward 
      Resource Management (RM) cells for an ABR source. Since the last 
      forward RM cell was sent, if at least TRM time has elapsed since 
      and at least 2 other cells have been sent, the next cell to be 
      transmitted would be a forward RM cell.
      
      For nailed-up connections, this attribute is determined by the 
      provisioned value of the maxTimeBetweenRmCell attribute. For 
      signalled connections, it is indicated in the ABR Additional 
      Parameters Information Element."
::= { mscAtmIfVpcTmAbrOperEntry 16 }

mscAtmIfVpcTmAbrCutoffDecreaseFactor OBJECT-TYPE
   SYNTAX     Unsigned32 (0 | 1 | 2 | 4 | 8 | 16 | 32 | 64)
   ACCESS     read-only
   STATUS     mandatory
   DESCRIPTION
     "This attribute indicates the Cutoff Decrease Factor (CDF) parameter 
      for this connection. When the value of this attribute is non-zero, 
      CDF is computed as the inverse of the value. For example, if the 
      value is 32, the value of CDF is 1/32. When the value of this 
      attribute is 0, CDF is also zero.
      
      CDF controls the decrease in the Allowed Cell Rate (ACR) 
      associated with the forwardRmCellLimit attribute, the limit of the 
      number of forward Resource Management (RM) cells which may 
      be sent in the absence of received backward RM cells. When this 
      limit is crossed, the ACR value would be decreased by the amount 
      (CDF*ACR). The ACR is not allowed to fall below the Minimum 
      Cell Rate (MCR), in which case the ACR is set to MCR.
      
      For nailed-up connections, this attribute is determined by the 
      provisioned value of the cutoffDecreaseFactor attribute. For 
      signalled connections, it is indicated in the ABR Additional 
      Parameters Information Element."
::= { mscAtmIfVpcTmAbrOperEntry 17 }

mscAtmIfVpcTmAbrAcrDecreaseTimeFactor OBJECT-TYPE
   SYNTAX     Unsigned32 (0..1023)
   ACCESS     read-only
   STATUS     mandatory
   DESCRIPTION
     "This attribute indicates the Allowed Cell Rate Decrease Time Factor 
      (ADTF) parameter for this connection.
      
      ADTF is the time interval permitted between sending forward 
      Resource Management (RM) cells before the Allowed Cell Rate 
      (ACR) is decreased to initialCellRate. In other words, if the source 
      does not transit a forward RM cell for the period specified by adtf, it 
      reduces its ACR to the value of its initialCellRate.
      
      For nailed-up connections, this attribute is determined by the 
      provisioned value of the acrDecreaseTimeFactor attribute. For 
      signalled connections, it is indicated in the ABR Additional 
      Parameters Information Element."
::= { mscAtmIfVpcTmAbrOperEntry 18 }

mscAtmIfVpcTmAbrForwardRmCellLimit OBJECT-TYPE
   SYNTAX     Unsigned32 (1 | 3 | 7 | 15 | 31 | 63 | 127 | 255 | 511 | 1023 | 2047 | 4095)
   ACCESS     read-only
   STATUS     mandatory
   DESCRIPTION
     "This attribute indicates the CRM parameter for this connection.
      
      CRM is the limit of the number of forward Resource Management 
      (RM) cells which may be sent in the absence of received backward 
      RM cells. When this limit is crossed, the Allowed Cell Rate (ACR) 
      value would be decreased by the amount (CDF*ACR), where CDF 
      is determined by the cutoffDecreaseFactor. The ACR is not allowed 
      to fall below the Minimum Cell Rate (MCR), in which case the 
      ACR is set to MCR.
      
      The value of CRM is obtained as transientBufferExposure divided 
      by maxCellsPerRmCell."
::= { mscAtmIfVpcTmAbrOperEntry 19 }

mscAtmIfVpcTmAbrTxRateChangeInfo OBJECT-TYPE
   SYNTAX     INTEGER  {
                 congestionIndicated(0),
                 noIncreaseIndicated(1),
                 explicitRateIndicated(2) }
   ACCESS     read-only
   STATUS     mandatory
   DESCRIPTION
     "This attribute indicates the rate change information put into the last 
      forward Resource Management (RM) cell turned around as a 
      backward-RM cell. For connections configured as an ABR Source 
      or Destination, the turned around backward-RM cell is sent over the 
      interface. For connections configured as an ABR Virtual Source or 
      Virtual Destination, the turned around backward-RM cell is sent 
      over the backplane."
::= { mscAtmIfVpcTmAbrOperEntry 20 }

mscAtmIfVpcTmAbrAcrRateChangeInfo OBJECT-TYPE
   SYNTAX     INTEGER  {
                 noChange(0),
                 decreasedByRdf(1),
                 increasedByRif(2),
                 setToExplicitRate(3),
                 notApplicable(15) }
   ACCESS     read-only
   STATUS     mandatory
   DESCRIPTION
     "This attribute indicates the type of change in the Allowed Cell Rate 
      (ACR) as a result of the information in the last backward Resource 
      Management (B-RM) cell received from the interface.
      
      This attribute value is only applicable when the Vcc Tm or Vpc Tm 
      abrConnectionType attribute is sourceDest or VirtualSourceDest. 
      In all other cases, this attribute value is notApplicable.
      
      A value of noChange indicates that the rate did not change as a 
      result of the last backward RM cell received.
      
      A value of decreasedByRdf or increasedByRif indicates that the 
      ACR was increased or decreased by the corresponding factor. This 
      change is as a result of the CI or NI bit setting in the last backward 
      RM cell, or an ADTF timeout.
      
      A value of setToExplicitRate indicates that the ACR was set to the 
      ER value in the last backward RM cell."
::= { mscAtmIfVpcTmAbrOperEntry 21 }

mscAtmIfVpcTmAbrTxFwdRmCells OBJECT-TYPE
   SYNTAX     Unsigned32 (0..4095)
   ACCESS     read-only
   STATUS     mandatory
   DESCRIPTION
     "This attribute counts the number of forward Resource Management 
      (RM) cells sent over the interface since the last backward RM-cell 
      was received from the interface. If the value of this attribute is 
      greater than or equal to the value of forwardRmCellLimit, the 
      Allowed Cell Rate (ACR) value would be decreased by the amount 
      (CDF*ACR), where CDF is determined by the 
      cutoffDecreaseFactor.
      
      This counter is reset to zero each time a backward-RM cell is 
      received.
      
      This counter does not wrap to zero if it reaches its maximum value 
      of 4095 in order to indicate that no backward RM cell has been 
      received."
::= { mscAtmIfVpcTmAbrOperEntry 22 }

mscAtmIfVpcTmAbrRxEfci OBJECT-TYPE
   SYNTAX     INTEGER  {
                 notIndicated(0),
                 indicated(1) }
   ACCESS     read-only
   STATUS     mandatory
   DESCRIPTION
     "This attribute indicates the value of the Explicit Forward 
      Congestion Indication (EFCI) bit of the last data cell received from 
      the interface.
      
      When a forward Resource Management (RM) cell is turned around 
      as a backward-RM cell, the Congestion Indication (CI) field of the 
      backward-RM cell is set to 1, if the value of this attribute is 
      indicated.
      
      This attribute is set to notIndicated each time a backward-RM cell 
      is transmitted."
::= { mscAtmIfVpcTmAbrOperEntry 23 }

-- 
-- *** THIS SUBTREE CURRENTLY NOT IMPLEMENTED ***
-- 

-- AtmIf/n Vcc/x.y PerformanceMonitoring
-- AtmIf/n Vpc/x PerformanceMonitoring
-- This component contains operational attributes for Performance 
-- Monitoring (PM) measurements on the connection. It also allows 
-- starting and stopping PM measurements when the controlMode 
-- attribute in the AtmIf Pm or AtmIf Vcc Vcd Pm or AtmIf Vpc Vpd 
-- Pm component is set to onDemand.

mscAtmIfVpcPm OBJECT IDENTIFIER ::= { mscAtmIfVpc 13 }



mscAtmIfVpcPmRowStatusTable OBJECT-TYPE
   SYNTAX     SEQUENCE OF MscAtmIfVpcPmRowStatusEntry
   ACCESS     not-accessible
   STATUS     mandatory
   DESCRIPTION
     "*** THIS TABLE CURRENTLY NOT IMPLEMENTED ***

      This entry controls the addition and deletion of 
      mscAtmIfVpcPm components."
::= { mscAtmIfVpcPm 1 }

mscAtmIfVpcPmRowStatusEntry OBJECT-TYPE
   SYNTAX     MscAtmIfVpcPmRowStatusEntry
   ACCESS     not-accessible
   STATUS     mandatory
   DESCRIPTION
     "A single entry in the table represents a single 
      mscAtmIfVpcPm component."
   INDEX {
      mscAtmIfIndex,
      mscAtmIfVpcIndex,
      mscAtmIfVpcPmIndex }
::= { mscAtmIfVpcPmRowStatusTable 1 }

MscAtmIfVpcPmRowStatusEntry ::= SEQUENCE {
   mscAtmIfVpcPmRowStatus
      RowStatus,
   mscAtmIfVpcPmComponentName
      DisplayString,
   mscAtmIfVpcPmStorageType
      StorageType,
   mscAtmIfVpcPmIndex
      INTEGER }

mscAtmIfVpcPmRowStatus OBJECT-TYPE
   SYNTAX     RowStatus 
   ACCESS     read-only
   STATUS     mandatory
   DESCRIPTION
     "This variable is used as the basis for SNMP naming of
      mscAtmIfVpcPm components.
      These components cannot be added nor deleted."
::= { mscAtmIfVpcPmRowStatusEntry 1 }

mscAtmIfVpcPmComponentName OBJECT-TYPE
   SYNTAX     DisplayString 
   ACCESS     read-only
   STATUS     mandatory
   DESCRIPTION
     "This variable provides the component's string name for
      use with the ASCII Console Interface"
::= { mscAtmIfVpcPmRowStatusEntry 2 }

mscAtmIfVpcPmStorageType OBJECT-TYPE
   SYNTAX     StorageType 
   ACCESS     read-only
   STATUS     mandatory
   DESCRIPTION
     "This variable represents the storage type value for the
      mscAtmIfVpcPm tables."
::= { mscAtmIfVpcPmRowStatusEntry 4 }

mscAtmIfVpcPmIndex OBJECT-TYPE
   SYNTAX     INTEGER  {
                 linkSide(0),
                 switchSide(1) }
   ACCESS     not-accessible
   STATUS     mandatory
   DESCRIPTION
     "This variable represents the index for the mscAtmIfVpcPm tables."
::= { mscAtmIfVpcPmRowStatusEntry 10 }

mscAtmIfVpcPmStatusTable OBJECT-TYPE
   SYNTAX     SEQUENCE OF MscAtmIfVpcPmStatusEntry
   ACCESS     not-accessible
   STATUS     mandatory
   DESCRIPTION
     "*** THIS TABLE CURRENTLY NOT IMPLEMENTED ***

      This group contains attributes indicating the status of each 
      Performance Monitoring (PM) measurement."
::= { mscAtmIfVpcPm 10 }

mscAtmIfVpcPmStatusEntry OBJECT-TYPE
   SYNTAX     MscAtmIfVpcPmStatusEntry
   ACCESS     not-accessible
   STATUS     mandatory
   DESCRIPTION
     "An entry in the mscAtmIfVpcPmStatusTable."
   INDEX {
      mscAtmIfIndex,
      mscAtmIfVpcIndex,
      mscAtmIfVpcPmIndex }
::= { mscAtmIfVpcPmStatusTable 1 }

MscAtmIfVpcPmStatusEntry ::= SEQUENCE {
   mscAtmIfVpcPmClrMeasurementStatus
      INTEGER,
   mscAtmIfVpcPmArMeasurementStatus
      INTEGER,
   mscAtmIfVpcPmFailureCause
      INTEGER }

mscAtmIfVpcPmClrMeasurementStatus OBJECT-TYPE
   SYNTAX     INTEGER  {
                 inactive(0),
                 activating(1),
                 active(2),
                 activationFailed(3) }
   ACCESS     read-only
   STATUS     mandatory
   DESCRIPTION
     "This attribute displays the Cell Loss Ratio (CLR) measurement 
      status of the connection.
      
      inactive indicates the test is inactive.
      activating indicates the test is activating.
      active indicates the test is in progress
      activationFailed indicates the test failed to be activated. Refer to 
      the failureCause attribute for failure cause."
   DEFVAL     { inactive }
::= { mscAtmIfVpcPmStatusEntry 1 }

mscAtmIfVpcPmArMeasurementStatus OBJECT-TYPE
   SYNTAX     INTEGER  {
                 inactive(0),
                 activating(1),
                 active(2),
                 activationFailed(3) }
   ACCESS     read-only
   STATUS     mandatory
   DESCRIPTION
     "This attribute indicates the Availability Ratio (AR) measurement 
      status of the connection.
      
      inactive indicates the test is inactive.
      activating indicates the test is activating.
      active indicates the test is in progress
      activationFailed indicates the test failed to be activated. Refer to 
      the failureCause attribute for the failure cause."
   DEFVAL     { inactive }
::= { mscAtmIfVpcPmStatusEntry 2 }

mscAtmIfVpcPmFailureCause OBJECT-TYPE
   SYNTAX     INTEGER  {
                 noError(0),
                 unknownCause(1),
                 softwareResourcesUnavailable(2),
                 hardwareResourcesUnavailable(3),
                 remoteEndNoResponse(4),
                 activationCollision(5),
                 remoteEndRejectedActivation(6),
                 pcrUnsupported(7),
                 nextHopCardUnsupported(8) }
   ACCESS     read-only
   STATUS     mandatory
   DESCRIPTION
     "This attribute indicates the failure cause of Performance Monitoring 
      (PM) measurements. The following are possible causes:
      
      noError indicates no error.
      unknownCause indicates unknown failure cause.
      softwareResourcesUnavailable indicates software resources 
      reserved for a maximum of 255 active PMs on the local FP card 
      have been used up.
      hardwareResourcesUnavailable indicates hardware resources 
      reserved for a maximum of 512 active PMs CLR have been used up 
      on the Link Side local card.
      remoteEndNoResponse indicates no response from remote end.
      activationCollision indicates activation collision was detected. 
      Usually this is caused by both ends of the connection being 
      provisioned to request PM. Only one end should be so provisioned.
      remoteEndRejectedActivation indicates the remote end has rejected 
      an activation request. Usually this is due to the remote end reaching 
      a resource limit.
      pcrUnsupported indicates the Tx or Rx PCR was out of range 
      between 0 and 409600.
      nextHopCardUnsupported indicates the next hop card type is not 
      supported."
   DEFVAL     { noError }
::= { mscAtmIfVpcPmStatusEntry 3 }

mscAtmIfVpcPmFwdClrTable OBJECT-TYPE
   SYNTAX     SEQUENCE OF MscAtmIfVpcPmFwdClrEntry
   ACCESS     not-accessible
   STATUS     mandatory
   DESCRIPTION
     "*** THIS TABLE CURRENTLY NOT IMPLEMENTED ***

      This group contains Cell Loss Ratio (CLR) measurements for the 
      forward direction of the connection. The local end is always the 
      provisioned end which sends the activation request, and the remote 
      end is the end which receives the activation request."
::= { mscAtmIfVpcPm 11 }

mscAtmIfVpcPmFwdClrEntry OBJECT-TYPE
   SYNTAX     MscAtmIfVpcPmFwdClrEntry
   ACCESS     not-accessible
   STATUS     mandatory
   DESCRIPTION
     "An entry in the mscAtmIfVpcPmFwdClrTable."
   INDEX {
      mscAtmIfIndex,
      mscAtmIfVpcIndex,
      mscAtmIfVpcPmIndex }
::= { mscAtmIfVpcPmFwdClrTable 1 }

MscAtmIfVpcPmFwdClrEntry ::= SEQUENCE {
   mscAtmIfVpcPmFwdLastSampleUserCellsRx0
      PassportCounter64,
   mscAtmIfVpcPmFwdLastSampleUserCellsTx0
      PassportCounter64,
   mscAtmIfVpcPmFwdLastSampleClr0
      FixedPoint9,
   mscAtmIfVpcPmFwdLastSampleUserCellsRx01
      PassportCounter64,
   mscAtmIfVpcPmFwdLastSampleUserCellsTx01
      PassportCounter64,
   mscAtmIfVpcPmFwdLastSampleClr01
      FixedPoint9,
   mscAtmIfVpcPmFwdTotalClrInterval
      Unsigned32,
   mscAtmIfVpcPmFwdTotalUserCellsRx0
      PassportCounter64,
   mscAtmIfVpcPmFwdTotalUserCellsTx0
      PassportCounter64,
   mscAtmIfVpcPmFwdAverageClr0
      FixedPoint9,
   mscAtmIfVpcPmFwdMaximumClr0
      FixedPoint9,
   mscAtmIfVpcPmFwdMinimumClr0
      FixedPoint9,
   mscAtmIfVpcPmFwdTotalUserCellsRx01
      PassportCounter64,
   mscAtmIfVpcPmFwdTotalUserCellsTx01
      PassportCounter64,
   mscAtmIfVpcPmFwdAverageClr01
      FixedPoint9,
   mscAtmIfVpcPmFwdMaximumClr01
      FixedPoint9,
   mscAtmIfVpcPmFwdMinimumClr01
      FixedPoint9,
   mscAtmIfVpcPmFwdPmCellDiscardCount
      Unsigned32 }

mscAtmIfVpcPmFwdLastSampleUserCellsRx0 OBJECT-TYPE
   SYNTAX     PassportCounter64 
   ACCESS     read-only
   STATUS     mandatory
   DESCRIPTION
     "This attribute displays the number of cells with CLP=0 received at 
      the remote end over the last sample period."
::= { mscAtmIfVpcPmFwdClrEntry 1 }

mscAtmIfVpcPmFwdLastSampleUserCellsTx0 OBJECT-TYPE
   SYNTAX     PassportCounter64 
   ACCESS     read-only
   STATUS     mandatory
   DESCRIPTION
     "This attribute displays the number of cells with CLP=0 transmitted 
      from the local end over the last sample period."
::= { mscAtmIfVpcPmFwdClrEntry 2 }

mscAtmIfVpcPmFwdLastSampleClr0 OBJECT-TYPE
   SYNTAX     FixedPoint9 (0..1000000000)
   ACCESS     read-only
   STATUS     mandatory
   DESCRIPTION
     "This attribute displays CLR for CLP=0 traffic over the last sample 
      period."
::= { mscAtmIfVpcPmFwdClrEntry 3 }

mscAtmIfVpcPmFwdLastSampleUserCellsRx01 OBJECT-TYPE
   SYNTAX     PassportCounter64 
   ACCESS     read-only
   STATUS     mandatory
   DESCRIPTION
     "This attribute indicates the number of cells with CLP=0+1 received 
      at the remote end over the last sample period."
::= { mscAtmIfVpcPmFwdClrEntry 4 }

mscAtmIfVpcPmFwdLastSampleUserCellsTx01 OBJECT-TYPE
   SYNTAX     PassportCounter64 
   ACCESS     read-only
   STATUS     mandatory
   DESCRIPTION
     "This attribute indicates the number of cells with CLP=0+1 
      transmitted from the local end over the last sample period."
::= { mscAtmIfVpcPmFwdClrEntry 5 }

mscAtmIfVpcPmFwdLastSampleClr01 OBJECT-TYPE
   SYNTAX     FixedPoint9 (0..1000000000)
   ACCESS     read-only
   STATUS     mandatory
   DESCRIPTION
     "This attribute indicates CLR for CLP=0+1 traffic over the last 
      sample period."
::= { mscAtmIfVpcPmFwdClrEntry 6 }

mscAtmIfVpcPmFwdTotalClrInterval OBJECT-TYPE
   SYNTAX     Unsigned32 (0..4294967295)
   ACCESS     read-only
   STATUS     mandatory
   DESCRIPTION
     "This attribute indicates the total time duration over which Cell Loss 
      Ratio (CLR) has been calculated."
::= { mscAtmIfVpcPmFwdClrEntry 7 }

mscAtmIfVpcPmFwdTotalUserCellsRx0 OBJECT-TYPE
   SYNTAX     PassportCounter64 
   ACCESS     read-only
   STATUS     mandatory
   DESCRIPTION
     "This attribute indicates the number of cells with CLP=0 received at 
      the remote end over the total Cell Loss Ratio (CLR) measurement 
      interval."
::= { mscAtmIfVpcPmFwdClrEntry 8 }

mscAtmIfVpcPmFwdTotalUserCellsTx0 OBJECT-TYPE
   SYNTAX     PassportCounter64 
   ACCESS     read-only
   STATUS     mandatory
   DESCRIPTION
     "This attribute indicates the number of cells with CLP=0 transmitted 
      from the local end over the total Cell Loss Ratio (CLR) 
      measurement interval."
::= { mscAtmIfVpcPmFwdClrEntry 9 }

mscAtmIfVpcPmFwdAverageClr0 OBJECT-TYPE
   SYNTAX     FixedPoint9 (0..1000000000)
   ACCESS     read-only
   STATUS     mandatory
   DESCRIPTION
     "This attribute indicates the average CLR for CLP=0 traffic 
      calculated for the total measurement interval."
::= { mscAtmIfVpcPmFwdClrEntry 10 }

mscAtmIfVpcPmFwdMaximumClr0 OBJECT-TYPE
   SYNTAX     FixedPoint9 (0..1000000000)
   ACCESS     read-only
   STATUS     mandatory
   DESCRIPTION
     "This attribute indicates the maximum CLR for CLP=0 traffic 
      calculated for the total measurement interval."
::= { mscAtmIfVpcPmFwdClrEntry 11 }

mscAtmIfVpcPmFwdMinimumClr0 OBJECT-TYPE
   SYNTAX     FixedPoint9 (0..1000000000)
   ACCESS     read-only
   STATUS     mandatory
   DESCRIPTION
     "This attribute indicates the minimum CLR for CLP=0 traffic 
      calculated for the total measurement interval."
::= { mscAtmIfVpcPmFwdClrEntry 12 }

mscAtmIfVpcPmFwdTotalUserCellsRx01 OBJECT-TYPE
   SYNTAX     PassportCounter64 
   ACCESS     read-only
   STATUS     mandatory
   DESCRIPTION
     "This attribute indicates the number of cells with CLP=0+1 received 
      at the remote end over the total Cell Loss Ratio (CLR) measurement 
      interval."
::= { mscAtmIfVpcPmFwdClrEntry 13 }

mscAtmIfVpcPmFwdTotalUserCellsTx01 OBJECT-TYPE
   SYNTAX     PassportCounter64 
   ACCESS     read-only
   STATUS     mandatory
   DESCRIPTION
     "This attribute indicates the number of cells with CLP=0+1 
      transmitted from the local end over the total CLR measurement 
      interval."
::= { mscAtmIfVpcPmFwdClrEntry 14 }

mscAtmIfVpcPmFwdAverageClr01 OBJECT-TYPE
   SYNTAX     FixedPoint9 (0..1000000000)
   ACCESS     read-only
   STATUS     mandatory
   DESCRIPTION
     "This attribute displays the average CLR for CLP=0+1 traffic 
      calculated for the total measurement interval."
::= { mscAtmIfVpcPmFwdClrEntry 15 }

mscAtmIfVpcPmFwdMaximumClr01 OBJECT-TYPE
   SYNTAX     FixedPoint9 (0..1000000000)
   ACCESS     read-only
   STATUS     mandatory
   DESCRIPTION
     "This attribute indicates the maximum CLR for CLP=0+1 traffic 
      calculated for the total measurement interval."
::= { mscAtmIfVpcPmFwdClrEntry 16 }

mscAtmIfVpcPmFwdMinimumClr01 OBJECT-TYPE
   SYNTAX     FixedPoint9 (0..1000000000)
   ACCESS     read-only
   STATUS     mandatory
   DESCRIPTION
     "This attribute indicates the minimum CLR for CLP=0+1 traffic 
      calculated for the total measurement interval."
::= { mscAtmIfVpcPmFwdClrEntry 17 }

mscAtmIfVpcPmFwdPmCellDiscardCount OBJECT-TYPE
   SYNTAX     Unsigned32 (0..4294967295)
   ACCESS     read-only
   STATUS     mandatory
   DESCRIPTION
     "This attribute indicates the total number of Performance Monitoring 
      (PM) cells discarded."
::= { mscAtmIfVpcPmFwdClrEntry 18 }

mscAtmIfVpcPmBwdClrTable OBJECT-TYPE
   SYNTAX     SEQUENCE OF MscAtmIfVpcPmBwdClrEntry
   ACCESS     not-accessible
   STATUS     mandatory
   DESCRIPTION
     "*** THIS TABLE CURRENTLY NOT IMPLEMENTED ***

      This group contains Cell Loss Ratio (CLR) measurements for the 
      backward direction of the connection. The local end is always the 
      provisioned end which sends the activation request, and the remote 
      end is the end which receives the activation request."
::= { mscAtmIfVpcPm 12 }

mscAtmIfVpcPmBwdClrEntry OBJECT-TYPE
   SYNTAX     MscAtmIfVpcPmBwdClrEntry
   ACCESS     not-accessible
   STATUS     mandatory
   DESCRIPTION
     "An entry in the mscAtmIfVpcPmBwdClrTable."
   INDEX {
      mscAtmIfIndex,
      mscAtmIfVpcIndex,
      mscAtmIfVpcPmIndex }
::= { mscAtmIfVpcPmBwdClrTable 1 }

MscAtmIfVpcPmBwdClrEntry ::= SEQUENCE {
   mscAtmIfVpcPmBwdLastSampleUserCellsRx0
      PassportCounter64,
   mscAtmIfVpcPmBwdLastSampleUserCellsTx0
      PassportCounter64,
   mscAtmIfVpcPmBwdLastSampleClr0
      FixedPoint9,
   mscAtmIfVpcPmBwdLastSampleUserCellsRx01
      PassportCounter64,
   mscAtmIfVpcPmBwdLastSampleUserCellsTx01
      PassportCounter64,
   mscAtmIfVpcPmBwdLastSampleClr01
      FixedPoint9,
   mscAtmIfVpcPmBwdTotalClrInterval
      Unsigned32,
   mscAtmIfVpcPmBwdTotalUserCellsRx0
      PassportCounter64,
   mscAtmIfVpcPmBwdTotalUserCellsTx0
      PassportCounter64,
   mscAtmIfVpcPmBwdAverageClr0
      FixedPoint9,
   mscAtmIfVpcPmBwdMaximumClr0
      FixedPoint9,
   mscAtmIfVpcPmBwdMinimumClr0
      FixedPoint9,
   mscAtmIfVpcPmBwdTotalUserCellsRx01
      PassportCounter64,
   mscAtmIfVpcPmBwdTotalUserCellsTx01
      PassportCounter64,
   mscAtmIfVpcPmBwdAverageClr01
      FixedPoint9,
   mscAtmIfVpcPmBwdMaximumClr01
      FixedPoint9,
   mscAtmIfVpcPmBwdMinimumClr01
      FixedPoint9,
   mscAtmIfVpcPmBwdPmCellDiscardCount
      Unsigned32 }

mscAtmIfVpcPmBwdLastSampleUserCellsRx0 OBJECT-TYPE
   SYNTAX     PassportCounter64 
   ACCESS     read-only
   STATUS     mandatory
   DESCRIPTION
     "This attribute indicates the number of cells with CLP=0 received at 
      the local end over the last sample period."
::= { mscAtmIfVpcPmBwdClrEntry 1 }

mscAtmIfVpcPmBwdLastSampleUserCellsTx0 OBJECT-TYPE
   SYNTAX     PassportCounter64 
   ACCESS     read-only
   STATUS     mandatory
   DESCRIPTION
     "This attribute indicates the number of cells with CLP=0 transmitted 
      from the remote end over the last sample period."
::= { mscAtmIfVpcPmBwdClrEntry 2 }

mscAtmIfVpcPmBwdLastSampleClr0 OBJECT-TYPE
   SYNTAX     FixedPoint9 (0..1000000000)
   ACCESS     read-only
   STATUS     mandatory
   DESCRIPTION
     "This attribute indicates CLR for CLP=0 traffic over the last sample 
      period."
::= { mscAtmIfVpcPmBwdClrEntry 3 }

mscAtmIfVpcPmBwdLastSampleUserCellsRx01 OBJECT-TYPE
   SYNTAX     PassportCounter64 
   ACCESS     read-only
   STATUS     mandatory
   DESCRIPTION
     "This attribute indicates the number of cells with CLP=0+1 received 
      at the local end over the last sample period."
::= { mscAtmIfVpcPmBwdClrEntry 4 }

mscAtmIfVpcPmBwdLastSampleUserCellsTx01 OBJECT-TYPE
   SYNTAX     PassportCounter64 
   ACCESS     read-only
   STATUS     mandatory
   DESCRIPTION
     "This attribute indicates the number of cells with CLP=0+1 
      transmitted from the remote end over the last sample period."
::= { mscAtmIfVpcPmBwdClrEntry 5 }

mscAtmIfVpcPmBwdLastSampleClr01 OBJECT-TYPE
   SYNTAX     FixedPoint9 (0..1000000000)
   ACCESS     read-only
   STATUS     mandatory
   DESCRIPTION
     "This attribute display CLRfor CLP=0+1 traffic over the last sample 
      period."
::= { mscAtmIfVpcPmBwdClrEntry 6 }

mscAtmIfVpcPmBwdTotalClrInterval OBJECT-TYPE
   SYNTAX     Unsigned32 (0..4294967295)
   ACCESS     read-only
   STATUS     mandatory
   DESCRIPTION
     "This attribute indicates the total time duration over which Cell Loss 
      Ratio (CLR) measurement has been calculated."
::= { mscAtmIfVpcPmBwdClrEntry 7 }

mscAtmIfVpcPmBwdTotalUserCellsRx0 OBJECT-TYPE
   SYNTAX     PassportCounter64 
   ACCESS     read-only
   STATUS     mandatory
   DESCRIPTION
     "This attribute indicates the number of cells with CLP=0 received at 
      the local end over the total Cell Loss Ratio (CLR) measurement 
      interval in the backward direction."
::= { mscAtmIfVpcPmBwdClrEntry 8 }

mscAtmIfVpcPmBwdTotalUserCellsTx0 OBJECT-TYPE
   SYNTAX     PassportCounter64 
   ACCESS     read-only
   STATUS     mandatory
   DESCRIPTION
     "This attribute indicates the number of cells with CLP=0 transmitted 
      from the remote end over the total Cell Loss Ratio (CLR) 
      measurement interval."
::= { mscAtmIfVpcPmBwdClrEntry 9 }

mscAtmIfVpcPmBwdAverageClr0 OBJECT-TYPE
   SYNTAX     FixedPoint9 (0..1000000000)
   ACCESS     read-only
   STATUS     mandatory
   DESCRIPTION
     "This attribute indicates the average CLR for CLP=0 traffic 
      calculated for the total measurement interval."
::= { mscAtmIfVpcPmBwdClrEntry 10 }

mscAtmIfVpcPmBwdMaximumClr0 OBJECT-TYPE
   SYNTAX     FixedPoint9 (0..1000000000)
   ACCESS     read-only
   STATUS     mandatory
   DESCRIPTION
     "This attribute indicates the maximum CLR for CLP=0 traffi 
      calculated for the total measurement interval."
::= { mscAtmIfVpcPmBwdClrEntry 11 }

mscAtmIfVpcPmBwdMinimumClr0 OBJECT-TYPE
   SYNTAX     FixedPoint9 (0..1000000000)
   ACCESS     read-only
   STATUS     mandatory
   DESCRIPTION
     "This attribute indicates the minimum CLR for CLP=0 traffic 
      calculated for the total measurement interval."
::= { mscAtmIfVpcPmBwdClrEntry 12 }

mscAtmIfVpcPmBwdTotalUserCellsRx01 OBJECT-TYPE
   SYNTAX     PassportCounter64 
   ACCESS     read-only
   STATUS     mandatory
   DESCRIPTION
     "This attribute indicates the number of cells with CLP=0 received at 
      the local end over the total Cell Loss Ratio (CLR) measurement 
      interval."
::= { mscAtmIfVpcPmBwdClrEntry 13 }

mscAtmIfVpcPmBwdTotalUserCellsTx01 OBJECT-TYPE
   SYNTAX     PassportCounter64 
   ACCESS     read-only
   STATUS     mandatory
   DESCRIPTION
     "This attribute indicates the number of cells with CLP=0+1 
      transmitted from the remote end over the total Cell Loss Ratio 
      (CLR) measurement interval ."
::= { mscAtmIfVpcPmBwdClrEntry 14 }

mscAtmIfVpcPmBwdAverageClr01 OBJECT-TYPE
   SYNTAX     FixedPoint9 (0..1000000000)
   ACCESS     read-only
   STATUS     mandatory
   DESCRIPTION
     "This attribute displays the average CLR for CLP=0+1 traffic 
      calculated for the total measurement interval."
::= { mscAtmIfVpcPmBwdClrEntry 15 }

mscAtmIfVpcPmBwdMaximumClr01 OBJECT-TYPE
   SYNTAX     FixedPoint9 (0..1000000000)
   ACCESS     read-only
   STATUS     mandatory
   DESCRIPTION
     "This attribute indicates the maximum CLR for CLP=0+1 traffic 
      calculated for the total measurement interval."
::= { mscAtmIfVpcPmBwdClrEntry 16 }

mscAtmIfVpcPmBwdMinimumClr01 OBJECT-TYPE
   SYNTAX     FixedPoint9 (0..1000000000)
   ACCESS     read-only
   STATUS     mandatory
   DESCRIPTION
     "This attribute indicates the minimum CLR for CLP=0+1 traffic 
      calculated for the total measurement interval."
::= { mscAtmIfVpcPmBwdClrEntry 17 }

mscAtmIfVpcPmBwdPmCellDiscardCount OBJECT-TYPE
   SYNTAX     Unsigned32 (0..4294967295)
   ACCESS     read-only
   STATUS     mandatory
   DESCRIPTION
     "This attribute indicates the total number of Performance Monitoring 
      (PM) cells discarded."
::= { mscAtmIfVpcPmBwdClrEntry 18 }

mscAtmIfVpcPmArTable OBJECT-TYPE
   SYNTAX     SEQUENCE OF MscAtmIfVpcPmArEntry
   ACCESS     not-accessible
   STATUS     mandatory
   DESCRIPTION
     "*** THIS TABLE CURRENTLY NOT IMPLEMENTED ***

      This group contains Availability Ratio (AR) measurements of the 
      connection."
::= { mscAtmIfVpcPm 13 }

mscAtmIfVpcPmArEntry OBJECT-TYPE
   SYNTAX     MscAtmIfVpcPmArEntry
   ACCESS     not-accessible
   STATUS     mandatory
   DESCRIPTION
     "An entry in the mscAtmIfVpcPmArTable."
   INDEX {
      mscAtmIfIndex,
      mscAtmIfVpcIndex,
      mscAtmIfVpcPmIndex }
::= { mscAtmIfVpcPmArTable 1 }

MscAtmIfVpcPmArEntry ::= SEQUENCE {
   mscAtmIfVpcPmCurrentAvailabilityStatus
      INTEGER,
   mscAtmIfVpcPmArTotalTime
      Unsigned32,
   mscAtmIfVpcPmArAvailableTime
      Unsigned32,
   mscAtmIfVpcPmArAvailabilityRatio
      FixedPoint7 }

mscAtmIfVpcPmCurrentAvailabilityStatus OBJECT-TYPE
   SYNTAX     INTEGER  {
                 notApplicable(0),
                 available(1),
                 unavailable(2) }
   ACCESS     read-only
   STATUS     mandatory
   DESCRIPTION
     "This attribute indicates the current status of the bidirectional 
      connection for purposes of Availability Ratio (AR) computation.
      
      notApplicable means AR measurement was not requested on this 
      connection.
      available means AR is running and considers the connection 
      available (that is, the arAvailableTime attribute is being 
      incremented).
      unavailable means AR measurement was requested but the 
      connection is currently unavailable."
::= { mscAtmIfVpcPmArEntry 1 }

mscAtmIfVpcPmArTotalTime OBJECT-TYPE
   SYNTAX     Unsigned32 (0..4294967295)
   ACCESS     read-only
   STATUS     mandatory
   DESCRIPTION
     "This attribute indicates the total time used for calculating 
      Availability Ratio (AR) of the bi-directional connection."
::= { mscAtmIfVpcPmArEntry 2 }

mscAtmIfVpcPmArAvailableTime OBJECT-TYPE
   SYNTAX     Unsigned32 (0..4294967295)
   ACCESS     read-only
   STATUS     mandatory
   DESCRIPTION
     "This attribute indicates the total time the connection was available."
::= { mscAtmIfVpcPmArEntry 3 }

mscAtmIfVpcPmArAvailabilityRatio OBJECT-TYPE
   SYNTAX     FixedPoint7 (0..10000000)
   ACCESS     read-only
   STATUS     mandatory
   DESCRIPTION
     "This attribute indicates the ratio of network availability representing 
      the time to the total time of the connection."
::= { mscAtmIfVpcPmArEntry 4 }


-- AtmIf/n VirtualChannelConnection/vpi.vci 
-- This component represents a virtual channel connection (VCC).
-- 
-- For Vccs directly beneath the AtmIf, the instance value defines the 
-- VPI and VCI values for this connectionfor example, Vcc/16.32 
-- would define a connection with a VPI of 16 and a VCI of 32.
-- 
-- The VPI can be in the range of 0 to 4095 and the VCI can be in the 
-- range of 0 to 65535. Note that a Vcc instance of 0.0 is invalid as 
-- defined in the ATM Forum.

mscAtmIfVcc OBJECT IDENTIFIER ::= { mscAtmIf 5 }



mscAtmIfVccRowStatusTable OBJECT-TYPE
   SYNTAX     SEQUENCE OF MscAtmIfVccRowStatusEntry
   ACCESS     not-accessible
   STATUS     mandatory
   DESCRIPTION
     "This entry controls the addition and deletion of 
      mscAtmIfVcc components."
::= { mscAtmIfVcc 1 }

mscAtmIfVccRowStatusEntry OBJECT-TYPE
   SYNTAX     MscAtmIfVccRowStatusEntry
   ACCESS     not-accessible
   STATUS     mandatory
   DESCRIPTION
     "A single entry in the table represents a single 
      mscAtmIfVcc component."
   INDEX {
      mscAtmIfIndex,
      mscAtmIfVccIndex }
::= { mscAtmIfVccRowStatusTable 1 }

MscAtmIfVccRowStatusEntry ::= SEQUENCE {
   mscAtmIfVccRowStatus
      RowStatus,
   mscAtmIfVccComponentName
      DisplayString,
   mscAtmIfVccStorageType
      StorageType,
   mscAtmIfVccIndex
      AsciiStringIndex }

mscAtmIfVccRowStatus OBJECT-TYPE
   SYNTAX     RowStatus 
   ACCESS     read-write
   STATUS     mandatory
   DESCRIPTION
     "This variable is used as the basis for SNMP naming of
      mscAtmIfVcc components.
      These components can be added and deleted."
::= { mscAtmIfVccRowStatusEntry 1 }

mscAtmIfVccComponentName OBJECT-TYPE
   SYNTAX     DisplayString 
   ACCESS     read-only
   STATUS     mandatory
   DESCRIPTION
     "This variable provides the component's string name for
      use with the ASCII Console Interface"
::= { mscAtmIfVccRowStatusEntry 2 }

mscAtmIfVccStorageType OBJECT-TYPE
   SYNTAX     StorageType 
   ACCESS     read-only
   STATUS     mandatory
   DESCRIPTION
     "This variable represents the storage type value for the
      mscAtmIfVcc tables."
::= { mscAtmIfVccRowStatusEntry 4 }

mscAtmIfVccIndex OBJECT-TYPE
   SYNTAX     AsciiStringIndex (SIZE (3..10))
   ACCESS     not-accessible
   STATUS     mandatory
   DESCRIPTION
     "This variable represents the index for the mscAtmIfVcc tables."
::= { mscAtmIfVccRowStatusEntry 10 }

mscAtmIfVccStateTable OBJECT-TYPE
   SYNTAX     SEQUENCE OF MscAtmIfVccStateEntry
   ACCESS     not-accessible
   STATUS     mandatory
   DESCRIPTION
     "This group contains the three OSI State attributes. The descriptions 
      generically indicate what each state attribute implies about the 
      component. Note that not all the values and state combinations 
      described here are supported by every component which reuses this 
      group. For component-specific information and the valid state 
      combinations, refer to the appropriate NTP."
::= { mscAtmIfVcc 100 }

mscAtmIfVccStateEntry OBJECT-TYPE
   SYNTAX     MscAtmIfVccStateEntry
   ACCESS     not-accessible
   STATUS     mandatory
   DESCRIPTION
     "An entry in the mscAtmIfVccStateTable."
   INDEX {
      mscAtmIfIndex,
      mscAtmIfVccIndex }
::= { mscAtmIfVccStateTable 1 }

MscAtmIfVccStateEntry ::= SEQUENCE {
   mscAtmIfVccAdminState
      INTEGER,
   mscAtmIfVccOperationalState
      INTEGER,
   mscAtmIfVccUsageState
      INTEGER }

mscAtmIfVccAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock -force or 
      Lock command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscAtmIfVccStateEntry 1 }

mscAtmIfVccOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscAtmIfVccStateEntry 2 }

mscAtmIfVccUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscAtmIfVccStateEntry 3 }

mscAtmIfVccOperTable OBJECT-TYPE
   SYNTAX     SEQUENCE OF MscAtmIfVccOperEntry
   ACCESS     not-accessible
   STATUS     mandatory
   DESCRIPTION
     "This group contains operational information for a Vcc, Vpc, or Vpt 
      component."
::= { mscAtmIfVcc 110 }

mscAtmIfVccOperEntry OBJECT-TYPE
   SYNTAX     MscAtmIfVccOperEntry
   ACCESS     not-accessible
   STATUS     mandatory
   DESCRIPTION
     "An entry in the mscAtmIfVccOperTable."
   INDEX {
      mscAtmIfIndex,
      mscAtmIfVccIndex }
::= { mscAtmIfVccOperTable 1 }

MscAtmIfVccOperEntry ::= SEQUENCE {
   mscAtmIfVccConnectionPointType
      INTEGER }

mscAtmIfVccConnectionPointType OBJECT-TYPE
   SYNTAX     INTEGER  {
                 connectionEndPoint(0),
                 segmentEndPoint(1),
                 connectingPoint(2),
                 unknown(3) }
   ACCESS     read-only
   STATUS     mandatory
   DESCRIPTION
     "This attribute reflects the role of the connection component at this 
      interface.
      
      A value of connectionEndPoint indicates that user cells, end-to-end 
      OAM cells, and segment OAM cells are processed by the 
      connection component.
      
      A value of segmentEndPoint indicates that user cells and end-to-
      end OAM cells are relayed by the connection component, while 
      segment OAM cells are processed by the connection component.
      
      A value of connectingPoint indicates that user cells, end-to-end 
      OAM cells, and segment OAM cells are relayed by the connection 
      component.
      
      A value of unknown indicates that the connection component is 
      inactive."
::= { mscAtmIfVccOperEntry 10 }

mscAtmIfVccConnInfoTable OBJECT-TYPE
   SYNTAX     SEQUENCE OF MscAtmIfVccConnInfoEntry
   ACCESS     not-accessible
   STATUS     mandatory
   DESCRIPTION
     "This group contains operational connection characteristics 
      information for a Vcc component."
::= { mscAtmIfVcc 115 }

mscAtmIfVccConnInfoEntry OBJECT-TYPE
   SYNTAX     MscAtmIfVccConnInfoEntry
   ACCESS     not-accessible
   STATUS     mandatory
   DESCRIPTION
     "An entry in the mscAtmIfVccConnInfoTable."
   INDEX {
      mscAtmIfIndex,
      mscAtmIfVccIndex }
::= { mscAtmIfVccConnInfoTable 1 }

MscAtmIfVccConnInfoEntry ::= SEQUENCE {
   mscAtmIfVccDistributionType
      INTEGER,
   mscAtmIfVccNumLeaves
      Gauge32,
   mscAtmIfVccCallDirection
      INTEGER }

mscAtmIfVccDistributionType OBJECT-TYPE
   SYNTAX     INTEGER  {
                 pointToPoint(0),
                 pointToMultipoint(1) }
   ACCESS     read-only
   STATUS     mandatory
   DESCRIPTION
     "This attribute indicates the way data is distributed in the connection.
      
      A value of pointToPoint indicates this connection point is part of a 
      point-to-point connection.
      
      A value of pointToMultipoint indicates this connection point is part 
      of a point-to-multipoint connection."
   DEFVAL     { pointToPoint }
::= { mscAtmIfVccConnInfoEntry 11 }

mscAtmIfVccNumLeaves OBJECT-TYPE
   SYNTAX     Gauge32 (0..2147483647)
   ACCESS     read-only
   STATUS     mandatory
   DESCRIPTION
     "This attribute indicates the number of destination leaves of the 
      connection. If the distributionType is pointToPoint the value of this 
      attribute is 0."
   DEFVAL     { 0 }
::= { mscAtmIfVccConnInfoEntry 12 }

mscAtmIfVccCallDirection OBJECT-TYPE
   SYNTAX     INTEGER  {
                 fromLink(0),
                 toLink(1),
                 notApplicable(2) }
   ACCESS     read-only
   STATUS     mandatory
   DESCRIPTION
     "This attribute indicates the direction of the call setup request for an 
      SVC.
      
      A value of fromLink means that the call setup originated from the 
      link.
      
      A value of toLink means that the call setup was directed to the link.
      
      For PVC connections, the value of this attribute is notApplicable.
      
      For SPVC connections, the value of this attribute is notApplicable 
      for Vccs with the SourcePVC and DestinationPVC subcomponents.
      
      For Signalling channels, the value of this attribute is notApplicable."
   DEFVAL     { notApplicable }
::= { mscAtmIfVccConnInfoEntry 13 }

mscAtmIfVccStatusTable OBJECT-TYPE
   SYNTAX     SEQUENCE OF MscAtmIfVccStatusEntry
   ACCESS     not-accessible
   STATUS     mandatory
   DESCRIPTION
     "This group contains operational status information for a Vcc, Vpc or 
      Vpt component."
::= { mscAtmIfVcc 120 }

mscAtmIfVccStatusEntry OBJECT-TYPE
   SYNTAX     MscAtmIfVccStatusEntry
   ACCESS     not-accessible
   STATUS     mandatory
   DESCRIPTION
     "An entry in the mscAtmIfVccStatusTable."
   INDEX {
      mscAtmIfIndex,
      mscAtmIfVccIndex }
::= { mscAtmIfVccStatusTable 1 }

MscAtmIfVccStatusEntry ::= SEQUENCE {
   mscAtmIfVccOperStatus
      INTEGER,
   mscAtmIfVccLocalFailureCause
      INTEGER,
   mscAtmIfVccTroubled
      INTEGER,
   mscAtmIfVccSegLinkSideLoopbackState
      INTEGER,
   mscAtmIfVccSegSwitchSideLoopbackState
      INTEGER,
   mscAtmIfVccEndToEndLoopbackState
      INTEGER,
   mscAtmIfVccRxOamCellCongestionState
      INTEGER,
   mscAtmIfVccAisState
      INTEGER,
   mscAtmIfVccRdiState
      INTEGER }

mscAtmIfVccOperStatus OBJECT-TYPE
   SYNTAX     INTEGER  {
                 unknown(0),
                 end2endUp(1),
                 end2endDown(2),
                 localUpEnd2endUnknown(3),
                 localDown(4) }
   ACCESS     read-only
   STATUS     mandatory
   DESCRIPTION
     "This attribute indicates the present operational status of the Vcc, 
      Vpc or Vpt component. Its value is dependent upon the current state 
      of the segLinkSideLoopbackState and endToEndLoopbackState 
      attributes.
      
      The value is end2endUp when the endToEndLoopbackState is good 
      and the segLinkSideLoopbackState is either good or unknown.
      
      The value is end2endDown when the endToEndLoopbackState is 
      bad and the segLinkSideLoopbackState is either good or unknown.
      
      The value is localUpEnd2endUnknown when the 
      endToEndLoopbackState is unknown and the 
      segLinkSideLoopbackState is good.
      
      The value is localDown when segLinkSideLoopbackState is bad.
      
      The value is localUpEnd2endUnknown when the 
      endToEndLoopbackState is notApplicable and the 
      segLinkSideLoopbackState is good.
      
      The value is unknown when the endToEndLoopbackState is either 
      unknown or notApplicable and the segLinkSideLoopbackState is 
      unknown."
::= { mscAtmIfVccStatusEntry 20 }

mscAtmIfVccLocalFailureCause OBJECT-TYPE
   SYNTAX     INTEGER  {
                 noFailure(0),
                 localBwLoss(1),
                 portDown(2),
                 notAdmitted(3),
                 appNotRegistered(4),
                 disabledByApp(5),
                 bwReduced(6),
                 vpDown(7) }
   ACCESS     read-only
   STATUS     mandatory
   DESCRIPTION
     "This attribute indicates the failure cause of the Vcc, Vpc or Vpt 
      component. noFailure indicates that there is currently no 
      bandwidth related failure for this connection. 
      
      portDown indicates that the interface corresponding to the parent 
      AtmIf is down. 
      
      localBwLoss indicates that the Ima corresponding to this AtmIf has 
      lost some, but not all bandwidth, and as a result, this connection has 
      been released.
      
      notAdmitted indicates that this connection has failed to be admitted 
      by the Connection Admission Control (CAC) algorithm.
      
      appNotRegistered indicates that there is no application registered to 
      use this connection. This may be the case, for example when there 
      is a Vcc Test application, but the test has not been started. Check the 
      status of the application to determine why it is not functional.
      
      disabledByApp indicates that the application using this connection 
      has requested that the connection be disabled. An example is a 
      connection used by a trunk application where the trunk has timed 
      out on an attempt to stage. Check the application to determine why 
      it is not fully functional.
      
      bwReduced indicates that this connection is operating in a reduced 
      bandwidth state. It is a bandwidth elastic connection which 
      currently has been allocated less than the requested (equivalent) 
      bandwidth.
      
      vpDown indicates that this connection has been notified of a fault 
      detected at the associated VP-layer. vpDown is applicable for Vpt 
      Vccs only."
::= { mscAtmIfVccStatusEntry 25 }

mscAtmIfVccTroubled OBJECT-TYPE
   SYNTAX     INTEGER  {
                 no(0),
                 yes(1) }
   ACCESS     read-only
   STATUS     mandatory
   DESCRIPTION
     "This attribute indicates whether or not the connection is in a 
      troubled state. Connections become troubled because of OAM 
      failures; when one of the attributes segLinkSideLoopbackState, 
      segSwitchSideLoopbackState, endToEndLoopbackState, aisState 
      (when receiving AIS cells only) or rdiState go bad, this attribute is 
      set to yes; otherwise it is set to no."
   DEFVAL     { no }
::= { mscAtmIfVccStatusEntry 28 }

mscAtmIfVccSegLinkSideLoopbackState OBJECT-TYPE
   SYNTAX     INTEGER  {
                 good(0),
                 bad(1),
                 unknown(2),
                 notApplicable(3) }
   ACCESS     read-only
   STATUS     mandatory
   DESCRIPTION
     "This attribute contains the current state of the link-side segment 
      loopback for this connection. Link-side segment loopback cells are 
      transmitted (inserted) by a connection component in the direction of 
      the link (port). The value of this attribute is dependent upon the 
      current setting of the segLinkSideLoopback provisionable attribute, 
      the connection point type as specified by the connectionPointType 
      attribute, and the current loopback state (if applicable).
      
      The value is notApplicable when the connectionPointType is a 
      connectingPoint. 
      
      The value is notApplicable when the distributionType is 
      pointToMultipoint.
      
      The value is good when the segLinkSideLoopback is on, the 
      connectionPointType is a segmentEndPoint or a 
      connectionEndPoint, and the segment link side loopback is 
      working.
      
      The value is bad when the segLinkSideLoopback is on, the 
      connectionPointType is a segmentEndPoint or a 
      connectionEndPoint, and the link side segment loopback is not 
      working.
      
      The value is unknown when the segLinkSideLoopback is off.
      
      The value is unknown when the segLinkSideLoopback is on, the 
      connectionPointType is a segmentEndPoint and the segment switch 
      side loopback has not yet been determined.
      
      The state of this attribute determines, in part, the value of the 
      operStatus attribute."
::= { mscAtmIfVccStatusEntry 30 }

mscAtmIfVccSegSwitchSideLoopbackState OBJECT-TYPE
   SYNTAX     INTEGER  {
                 good(0),
                 bad(1),
                 unknown(2),
                 notApplicable(3) }
   ACCESS     read-only
   STATUS     mandatory
   DESCRIPTION
     "This attribute contains the current state of the switch-side segment 
      loopback for this connection. Switch-side segment loopback cells 
      are transmitted (inserted) by a connection component in the 
      direction of the bus. The value of this attribute is dependent upon 
      the current setting of the segSwitchSideLoopback provisionable 
      attribute, the connection point type as specified by the 
      connectionPointType attribute, and the current loopback state (if 
      applicable).
      
      The value is only applicable when the connectionPointType is a 
      segmentEndPoint. 
      
      The value is notApplicable when the connectionPointType is a 
      connectingPoint or connectionEndPoint. 
      
      The value is notApplicable when the distributionType is 
      pointToMultipoint.
      
      The value is good when the segSwitchSideLoopback is on, the 
      connectionPointType is a segmentEndPoint and the segment switch 
      side loopback is working.
      
      The value is bad when the segSwitchSideLoopback is on, the 
      connectionPointType is a segmentEndPoint and the switch side 
      segment loopback is not working.
      
      The value is unknown when the segSwitchSideLoopback is off.
      
      The value is unknown when the segSwitchSideLoopback is on, the 
      connectionPointType is a segmentEndPoint and the segment switch 
      side loopback has not been determined."
::= { mscAtmIfVccStatusEntry 40 }

mscAtmIfVccEndToEndLoopbackState OBJECT-TYPE
   SYNTAX     INTEGER  {
                 good(0),
                 bad(1),
                 unknown(2),
                 notApplicable(3) }
   ACCESS     read-only
   STATUS     mandatory
   DESCRIPTION
     "This attribute contains the current state of the end-to-end loopback 
      for this connection. Its value is dependent upon the current setting 
      of the endToEndLoopback provisionable attribute and the 
      connection point type as specified by the connectionPointType 
      attribute.
      
      The value is only applicable when the connectionPointType is a 
      connectionEndPoint. 
      
      The value is notApplicable when the connectionPointType is a 
      connectingPoint or segmentEndPoint. 
      
      The value is notApplicable when the distributionType is a 
      pointToMultipoint.
      
      The value is good when the endToEndLoopback is on, the 
      connectionPointType is a connectionEndPoint and the end-to-end 
      loopback is working.
      
      The value is bad when the endToEndLoopback is on, the 
      connectionPointType is a connectionEndPoint and the end-to-end 
      loopback is not working.
      
      The value is unknown when the endToEndLoopback is off.
      
      The value is unknown when the endToEndLoopback is on, the 
      connectionPointType is a connectionEndPoint and the end-to-end 
      loopback status has not been determined.
      
      The state of this attribute determines, in part, the value of the 
      operStatus attribute."
::= { mscAtmIfVccStatusEntry 50 }

mscAtmIfVccRxOamCellCongestionState OBJECT-TYPE
   SYNTAX     INTEGER  {
                 good(0),
                 bad(1),
                 unknown(2),
                 notApplicable(3) }
   ACCESS     read-only
   STATUS     mandatory
   DESCRIPTION
     "This attribute contains the current state of the receive side OAM cell 
      congestion for this connection. Its value reflects whether the rate of 
      received OAM cells for this connection is below a specified 
      threshold. The connection maintains a count of the number of OAM 
      cells which are terminated per second. Once that count exceeds the 
      specified threshold, extraction of all OAM cells for this connection 
      is disabled for a period of one minute. This is a congestion 
      management mechanism to prevent the processor from being 
      overloaded with handling OAM cells for a particular connection. 
      This mechanism ensures that tasks, such as trunks obtain enough 
      processor cycles to remain in service, and are not adversely affected 
      by excessive rate of OAM cells on a particular connection.
      
      The value is good when the rate of received OAM cells is less than 
      the allowed threshold.
      
      The value is bad when the arrival rate has exceeded the allowed 
      threshold. It remains bad for one minute, before returning to good 
      again. During this timeout, extraction of all OAM cells is disabled 
      for this connection. As a result, other loopback failure conditions 
      may occur.
      
      The value is unknown when the application has not yet begun to 
      use this connection. An example is the Test component before a test 
      has been started.
      
      Each type of OAM cell is counted separately. The threshold for AIS 
      cells is three cells per second. If more than three AIS cells are 
      received within a one second interval, this attribute is set to bad. 
      The threshold for RDI cells and each loopback type is also three, 
      but the threshold for trace cells is 250 per second.
      
      The state of this attribute has no direct effect on the value of the 
      operStatus attribute or on the number of troubled connections."
::= { mscAtmIfVccStatusEntry 55 }

mscAtmIfVccAisState OBJECT-TYPE
   SYNTAX     INTEGER  {
                 good(0),
                 bad(1),
                 unknown(2),
                 notApplicable(3) }
   ACCESS     read-only
   STATUS     mandatory
   DESCRIPTION
     "This attribute contains the current state of the Alarm Indication 
      Signal for this connection.
      
      A value of good indicates that the connection's application is active 
      and no alarm has occurred.
      
      A value of bad indicates that the connection's application is active 
      and an alarm has occurred.
      
      A value of unknown indicates that the connection's application is 
      inactive.
      
      A value of notApplicable occurs when the connectionPointType is 
      either a segmentEndPoint or a connectingPoint."
::= { mscAtmIfVccStatusEntry 60 }

mscAtmIfVccRdiState OBJECT-TYPE
   SYNTAX     INTEGER  {
                 good(0),
                 bad(1),
                 unknown(2),
                 notApplicable(3) }
   ACCESS     read-only
   STATUS     mandatory
   DESCRIPTION
     "This attribute indicates the current state of the Remote Defect 
      Indication for this connection.
      
      A value of good indicates that the connection's application is active 
      and no alarm has occurred.
      
      A value of bad indicates that the connection's application is active 
      and an alarm has occurred.
      
      A value of unknown indicates that the connection's application is 
      inactive.
      
      A value of notApplicable occurs when the connectionPointType is 
      either a segmentEndPoint or a connectingPoint."
::= { mscAtmIfVccStatusEntry 70 }

mscAtmIfVccTrafficTable OBJECT-TYPE
   SYNTAX     SEQUENCE OF MscAtmIfVccTrafficEntry
   ACCESS     not-accessible
   STATUS     mandatory
   DESCRIPTION
     "This group is HISTORICAL. Please refer to the group AtmTmOper;
      
      This attribute group contains attributes for the Vcc and Vpc 
      components to reflect operational traffic attributes."
::= { mscAtmIfVcc 130 }

mscAtmIfVccTrafficEntry OBJECT-TYPE
   SYNTAX     MscAtmIfVccTrafficEntry
   ACCESS     not-accessible
   STATUS     mandatory
   DESCRIPTION
     "An entry in the mscAtmIfVccTrafficTable."
   INDEX {
      mscAtmIfIndex,
      mscAtmIfVccIndex }
::= { mscAtmIfVccTrafficTable 1 }

MscAtmIfVccTrafficEntry ::= SEQUENCE {
   mscAtmIfVccTxTrafficDescType
      INTEGER,
   mscAtmIfVccTxQosClass
      INTEGER,
   mscAtmIfVccFwdQosClass
      INTEGER,
   mscAtmIfVccTxQueueLength
      INTEGER,
   mscAtmIfVccTxQueueCongestionState
      INTEGER,
   mscAtmIfVccHoldingPriority
      INTEGER,
   mscAtmIfVccRxTrafficDescType
      INTEGER,
   mscAtmIfVccRxQosClass
      INTEGER,
   mscAtmIfVccBwdQosClass
      INTEGER,
   mscAtmIfVccAtmServiceCategory
      INTEGER,
   mscAtmIfVccTrafficShaping
      INTEGER,
   mscAtmIfVccBearerClassBbc
      INTEGER,
   mscAtmIfVccTransferCapabilityBbc
      INTEGER,
   mscAtmIfVccClippingBbc
      INTEGER,
   mscAtmIfVccUnshapedTransmitQueueing
      INTEGER,
   mscAtmIfVccBestEffort
      INTEGER,
   mscAtmIfVccUsageParameterControl
      INTEGER,
   mscAtmIfVccTxFrameDiscard
      OCTET STRING,
   mscAtmIfVccRxFrameDiscard
      OCTET STRING,
   mscAtmIfVccBandwidthElastic
      INTEGER,
   mscAtmIfVccBandwidthReduction
      INTEGER }

mscAtmIfVccTxTrafficDescType OBJECT-TYPE
   SYNTAX     INTEGER  {
                 n1(1),
                 n2(2),
                 n3(3),
                 n4(4),
                 n5(5),
                 n6(6),
                 n7(7),
                 n8(8) }
   ACCESS     read-only
   STATUS     obsolete
   DESCRIPTION
     "This attribute is HISTORICAL. Please refer to the attribute of the 
      same name in the group AtmTmOper.
      
      This attribute indicates the type of traffic management which is 
      applied to the transmit direction of this connection as defined in the 
      ATM Forum. The txTrafficDescType determines the number and 
      meaning of the parameters in the txTrafficDescParm attribute."
::= { mscAtmIfVccTrafficEntry 10 }

mscAtmIfVccTxQosClass OBJECT-TYPE
   SYNTAX     INTEGER  {
                 unspecified(0),
                 constantBitRate(1),
                 variableBitRate(2),
                 connectionOriented(3),
                 connectionless(4) }
   ACCESS     read-only
   STATUS     obsolete
   DESCRIPTION
     "This attribute indicates the quality of service for the transmit 
      direction for this connection.
      
      The constantBitRate class refers to traffic offered on services such 
      as a constant bit rate video service. This traffic is highest priority.
      
      The variableBitRate class refers to traffic offered on services such 
      as packetized audio and video.
      
      The connectionOriented class refers to connection-oriented traffic 
      such as Frame Relay or X.25 traffic. 
      
      The connectionless traffic refers to traffic offered through 
      connectionless trunks such as certain LAN protocols.
      
      The unspecified class supports a 'best effort' type of service, where 
      there is a minimum guarantee of bandwidth. This traffic is lowest 
      priority.
      
      This attribute is obsolete, replaced by the UNI 4.0 attribute 
      atmServiceCategory."
::= { mscAtmIfVccTrafficEntry 30 }

mscAtmIfVccFwdQosClass OBJECT-TYPE
   SYNTAX     INTEGER  {
                 n0(0),
                 n1(1),
                 n2(2),
                 n3(3),
                 n4(4),
                 notApplicable(14) }
   ACCESS     read-only
   STATUS     obsolete
   DESCRIPTION
     "This attribute is HISTORICAL. Please refer to the attribute of the 
      same name in the group AtmTmOper.
      
      This attribute indicates the quality of service for the calling to called 
      direction for this connection. This is only applicable to Soft PVC 
      and SVC connections. 
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified QOS class; no objective is specified for 
      the performance parameters.
      
      A value of notApplicable is displayed in the case of nailed-up PVCs 
      for which this attribute has no significance."
::= { mscAtmIfVccTrafficEntry 31 }

mscAtmIfVccTxQueueLength OBJECT-TYPE
   SYNTAX     INTEGER (0..30720)
   ACCESS     read-only
   STATUS     obsolete
   DESCRIPTION
     "This attribute is HISTORICAL. Please refer to the attribute of the 
      same name in the group AtmTmOper.
      
      This attribute indicates the current length of the transmit queue for 
      this connection. If this connection has traffic shaping disabled, then 
      this attribute displays the common queue length. If traffic shaping is 
      enabled, then this attribute displays the per-VC queue length."
::= { mscAtmIfVccTrafficEntry 32 }

mscAtmIfVccTxQueueCongestionState OBJECT-TYPE
   SYNTAX     INTEGER (0..3)
   ACCESS     read-only
   STATUS     obsolete
   DESCRIPTION
     "This attribute is HISTORICAL. Please refer to the attribute of the 
      same name in the group AtmTmOper.
      
      This attribute indicates the congestion state of the transmit queue 
      for this connection. If the connection has traffic shaping disabled, 
      then this attribute displays the common queue congestion state. If 
      traffic shaping is enabled, then this attribute displays the per-VC 
      queue congestion state.
      
      The congestion state of a queue is indicated by a numeric value 
      ranging from 0 to 3. When a queue is in a congested state x, only 
      traffic with discard priority (DP) 0 to x are enqueued. Traffic with 
      DP > x is discarded. 
      
      Therefore, if the congestion state is 3, there is no congestion and all 
      traffic is enqueued. Likewise, when the congestion state is 0, there 
      is maximum congestion and only traffic with DP=0 is enqueued on 
      that queue."
::= { mscAtmIfVccTrafficEntry 33 }

mscAtmIfVccHoldingPriority OBJECT-TYPE
   SYNTAX     INTEGER  {
                 n0(0),
                 n1(1),
                 n2(2),
                 n3(3),
                 n4(4),
                 notApplicable(6) }
   ACCESS     read-only
   STATUS     obsolete
   DESCRIPTION
     "This attribute is HISTORICAL. Please refer to the attribute of the 
      same name in the group AtmTmOper.
      
      This attribute indicates the actual holding priority in effect for this 
      connection. In a situation where the link bandwidth fluctuates, such 
      as over an IMA link, holding priority is used to determine which 
      connections are held and which are released. Holding priority 4 
      connections are the first to be released. Holding priority 0 
      connections are the last to be released. Some applications, for 
      example Vcc Test, may override the provisioned holding priority. 
      
      A value of notApplicable is displayed when this is an elastic 
      connection. Holding priority does not apply to bandwidth elastic 
      connections.
      
      Holding priority has no effect for ubr atmServiceCategory or 
      txTrafficDescriptorType 1 or 2 connections."
::= { mscAtmIfVccTrafficEntry 35 }

mscAtmIfVccRxTrafficDescType OBJECT-TYPE
   SYNTAX     INTEGER  {
                 n1(1),
                 n2(2),
                 n3(3),
                 n4(4),
                 n5(5),
                 n6(6),
                 n7(7),
                 n8(8) }
   ACCESS     read-only
   STATUS     obsolete
   DESCRIPTION
     "This attribute is HISTORICAL. Please refer to the attribute of the 
      same name in the group AtmTmOper.
      
      This attribute indicates the type of traffic management which is 
      applied to the receive direction of this connection as defined in the 
      ATM Forum. The rxTrafficDescType determines the number and 
      meaning of the parameters in the rxTrafficDescParm attribute."
::= { mscAtmIfVccTrafficEntry 40 }

mscAtmIfVccRxQosClass OBJECT-TYPE
   SYNTAX     INTEGER  {
                 unspecified(0),
                 constantBitRate(1),
                 variableBitRate(2),
                 connectionOriented(3),
                 connectionless(4) }
   ACCESS     read-only
   STATUS     obsolete
   DESCRIPTION
     "This attribute reflects the value of the provisioned attribute in the 
      Vcd or Vpd. Refer to that attribute for more detailed explanation. 
      
      This attribute is obsolete replaced by the UNI 4.0 attribute 
      atmServiceCategory."
::= { mscAtmIfVccTrafficEntry 60 }

mscAtmIfVccBwdQosClass OBJECT-TYPE
   SYNTAX     INTEGER  {
                 n0(0),
                 n1(1),
                 n2(2),
                 n3(3),
                 n4(4),
                 notApplicable(14) }
   ACCESS     read-only
   STATUS     obsolete
   DESCRIPTION
     "This attribute is HISTORICAL. Please refer to the attribute of the 
      same name in the group AtmTmOper.
      
      This attribute indicates the quality of service for the called to calling 
      direction for this connection. This is only applicable to Soft PVC 
      and SVC connections. 
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified QOS class; no objective is specified for 
      the performance parameters.
      
      A value of notApplicable is displayed in the case of nailed-up PVCs 
      for which this attribute has no significance."
::= { mscAtmIfVccTrafficEntry 61 }

mscAtmIfVccAtmServiceCategory OBJECT-TYPE
   SYNTAX     INTEGER  {
                 unspecifiedBitRate(0),
                 constantBitRate(1),
                 rtVariableBitRate(2),
                 nrtVariableBitRate(3) }
   ACCESS     read-only
   STATUS     obsolete
   DESCRIPTION
     "This attribute is HISTORICAL. Please refer to the attribute of the 
      same name in the group AtmTmOper.
      
      This attribute indicates the ATM service category used for traffic in 
      both directions of the connection. 
      
      The constantBitRate service category is intended for real time 
      applications, that is, those requiring tightly constrained delay and 
      delay variation, as would be appropriate for voice and video 
      applications. The consistent availability of a fixed quantity of 
      bandwidth is considered appropriate for CBR service. Cells which 
      are delayed beyond the value specified by Cell Transfer Delay are 
      assumed to have significantly reduced value of the application.
      
      The rtVariableBitRate service category is intended for real time 
      applications; that is those requiring tightly constrained delay and 
      delay variation, as would be appropriate for voice and video 
      applications. Sources are expected to transmit at a rate which varies 
      with time. Equivalently, the source can be described as 'bursty'. 
      Cells which are delayed beyond the value specified by Cell Transfer 
      Delay are assumed to be of significantly reduced value to the 
      application. Real time VBR service may support statistical 
      multiplexing of real time sources.
      
      The nrtVariableBitRate service category is intended for non-real 
      time applications which have bursty traffic characteristics and which 
      can be characterized in terms of a PCR, SCR, and MBS. For those 
      cells which are transferred within the traffic contract, the application 
      expects a low cell loss ratio. For all connections, it expects a bound 
      on the mean cell transfer delay. Non-real time VBR service may 
      support statistical multiplexing of connections.
      
      The unspecifiedBitRate service is intended for non-real time 
      applications, that is those not requiring tightly constrained delay 
      and delay variation. UBR sources are expected to be bursty. UBR 
      service supports a high degree of statistical multiplexing among 
      sources. UBR service does not specify traffic related service 
      guarantees. No numerical commitments are made with respect to 
      the cell loss ratio experienced by a UBR connection, or as to the 
      cell transfer delay experienced by cells on the connection."
::= { mscAtmIfVccTrafficEntry 62 }

mscAtmIfVccTrafficShaping OBJECT-TYPE
   SYNTAX     INTEGER  {
                 enabled(0),
                 disabled(1),
                 notApplicable(4) }
   ACCESS     read-only
   STATUS     obsolete
   DESCRIPTION
     "This attribute is HISTORICAL. Please refer to the attribute of the 
      same name in the group AtmTmOper.
      
      This attribute indicates the traffic shaping state of the connection.
      
      A value of notApplicable indicates that traffic shaping is not 
      applicable or not supported for this connection. This is the case 
      when the atmServiceCategory is constantBitRate, or when the 
      txTrafficDescType is 1 or 2. In these cases, the value of 
      notApplicable is set regardless of whether traffic shaping is enabled 
      or disabled in the provisioning data.
      
      A value of disabled indicates that traffic shaping is applicable and 
      supported for the type of connection but has been turned off in the 
      provisioning data.
      
      A value of enabled indicates that traffic shaping is applicable and 
      supported for the type of connection and has been turned on in the 
      provisioning data. This is the only case that indicates that traffic 
      shaping is performed on the connection. In this case, the actual 
      shaping rate is reflected in the txTrafficDescParm attribute, 
      parameter number 4."
::= { mscAtmIfVccTrafficEntry 70 }

mscAtmIfVccBearerClassBbc OBJECT-TYPE
   SYNTAX     INTEGER  {
                 a(1),
                 c(3),
                 x(16),
                 vp(24),
                 notApplicable(30) }
   ACCESS     read-only
   STATUS     obsolete
   DESCRIPTION
     "This attribute is HISTORICAL. Please refer to the attribute of the 
      same name in the group AtmTmOper.
      
      This attribute indicates the bearer capability for this connection.
      
      Class a service is a connection-oriented, constant bit rate ATM 
      transport service. Class a service has end to end timing 
      requirements and may require stringent cell loss, cell delay and cell 
      delay variation performance.When a is displayed, the user is 
      requesting more than an ATM only service. The network may look 
      at the AAL to provide interworking based upon its contents. 
      
      Class c service is a connection-oriented, variable bit rate ATM 
      transport service. Class c service has no end-to-end timing 
      requirements.When c is displayed, the user is requesting more than 
      an ATM only service. The network interworking function may look 
      at the AAL and provide service based on it.
      
      Class x service is a connection-oriented ATM transport service 
      where the AAL, trafficType (cbr or vbr) and timing requirements 
      are user defined (that is, transparent to the network). When the 
      value of this attribute is x, the user is requesting an ATM only 
      service from the network. In this case, the network shall not process 
      any higher layer protocol.
      
      Class vp service is used to indicate a transparent VP service when 
      the user is requesting an ATM only service from the network. In this 
      case, the network does not process any higher layer protocol. This 
      service differs from class x service in that with the class vp service 
      both the VCI field (except for VCI values 0, 3, 4, and 6 through 15) 
      and Payload Type field are transported transparently by the network. 
      This attribute value is only applicable to SPVP and SVP 
      connections.
      
      A value of notApplicable is displayed in the case of nailed-up PVCs 
      for which this attribute has no significance."
::= { mscAtmIfVccTrafficEntry 71 }

mscAtmIfVccTransferCapabilityBbc OBJECT-TYPE
   SYNTAX     INTEGER  {
                 n0(0),
                 n1(1),
                 n2(2),
                 n5(5),
                 n8(8),
                 n9(9),
                 n10(10),
                 notApplicable(30) }
   ACCESS     read-only
   STATUS     obsolete
   DESCRIPTION
     "This attribute is HISTORICAL. Please refer to the attribute of the 
      same name in the group AtmTmOper.
      
      This attribute indicates the transfer capability for this connection. 
      Uni 3.0/3.1 traffic type and end-to-end timing parameters are 
      mapped into this parameter as follows:
      <transferCapability: TrafficType, Timing>
      0: NoIndication, NoIndication
      1: NoIndication, yes
      2: NoIndication, no
      5: CBR, yes
      8: VBR, NoIndication
      9: VBR, yes
      10: VBR, no
      
      A value of notApplicable is displayed in the case of nailed-up PVCs 
      for which this attribute has no significance, or in the case that the 
      transfer capability in the call request was set to NoIndication.
      
      The CBR traffic type refers to traffic offered on services such as a 
      constant bit rate video service or a circuit emulation.
      
      The VBR traffic type refers to traffic offered on services such as 
      packetized audio and video, or data.
      
      The value NoIndication for traffic type is used if the user has not set 
      the traffic type; similarly for end-to-end timing.
      
      The value yes for end-to-end timing indicates that end-to-end 
      timing is required for the connection.
      
      The value no for end-to-end timing indicates that end-to-end timing 
      is not required for the connection."
::= { mscAtmIfVccTrafficEntry 72 }

mscAtmIfVccClippingBbc OBJECT-TYPE
   SYNTAX     INTEGER  {
                 no(0),
                 yes(1),
                 notApplicable(14) }
   ACCESS     read-only
   STATUS     obsolete
   DESCRIPTION
     "This attribute is HISTORICAL. Please refer to the attribute of the 
      same name in the group AtmTmOper.
      
      This attribute indicates the value of the clipping susceptibility 
      parameter in the BBC Information Element.
      
      Clipping is an impairment in which the first fraction of a second of 
      information to be transferred is lost. It occurs after a call is 
      answered and before an associated connection is switched through.
      
      A value of notApplicable is displayed in the case of nailed-up PVCs 
      for which this attribute has no significance."
::= { mscAtmIfVccTrafficEntry 74 }

mscAtmIfVccUnshapedTransmitQueueing OBJECT-TYPE
   SYNTAX     INTEGER  {
                 perVc(0),
                 common(1),
                 notApplicable(4) }
   ACCESS     read-only
   STATUS     obsolete
   DESCRIPTION
     "This attribute is HISTORICAL. Please refer to the attribute of the 
      same name in the group AtmTmOper.
      
      This attribute indicates the unshaped transmit queuing state of the 
      connection.
      
      A value of common indicates that transmit traffic is being enqueued 
      onto common transmit queues. 
      
      A value of perVc indicates that transmit traffic is being enqueued 
      onto a per-VC queue for this connection. This is the case when 
      trafficShaping is disabled, but per-VC queueing has been 
      configured for this connection. 
      
      A value of notApplicable indicates that transmit traffic is being 
      shaped for this connection. Transmit traffic for a shaped connection 
      is enqueued onto a per-VC queue, but this attribute is only 
      applicable for unshaped connections."
::= { mscAtmIfVccTrafficEntry 75 }

mscAtmIfVccBestEffort OBJECT-TYPE
   SYNTAX     INTEGER  {
                 indicated(0),
                 notIndicated(1),
                 notApplicable(14) }
   ACCESS     read-only
   STATUS     obsolete
   DESCRIPTION
     "This attribute is HISTORICAL. Please refer to the attribute of the 
      same name in the group AtmTmOper.
      
      This attribute indicates value of best effort parameter in the ATM 
      Traffic Descriptor Information Element.
      
      The value indicated implies that the quality of service for this 
      connection is not guaranteed.
      
      The value notIndicated implies that the quality of service for this 
      connection is guaranteed.
      
      A value of notApplicable is displayed in the case of nailed-up PVCs 
      for which this attribute has no significance."
::= { mscAtmIfVccTrafficEntry 76 }

mscAtmIfVccUsageParameterControl OBJECT-TYPE
   SYNTAX     INTEGER  {
                 enabled(0),
                 disabled(1),
                 notApplicable(3) }
   ACCESS     read-only
   STATUS     obsolete
   DESCRIPTION
     "This attribute is HISTORICAL. Please refer to the attribute of the 
      same name in the group AtmTmOper.
      
      This attribute indicates the UPC state of the connection.
      
      A value of notApplicable indicates that UPC is not applicable or not 
      supported for the connection. This is the case when the connection's 
      rxTrafficDescType is 1 or 2. A value of notApplicable is set 
      regardless of whether UPC is disabled or enabled in provisioning 
      data.
      
      A value of disabled indicates that UPC is applicable and supported 
      for the type of connection but has been turned off in the 
      provisioning data.
      
      A value of enabled indicates that UPC is applicable and supported 
      for the type of connection and has been turned on in the 
      provisioning data. This is the only case that indicates that UPC is 
      enforced on the connection. In this case the traffic descriptor 
      parameters used for UPC enforcement are reflected in the 
      rxTrafficDescParms of the connection."
::= { mscAtmIfVccTrafficEntry 80 }

mscAtmIfVccTxFrameDiscard OBJECT-TYPE
   SYNTAX     OCTET STRING (SIZE (1))
   ACCESS     read-only
   STATUS     obsolete
   DESCRIPTION
     "This attribute is HISTORICAL. Please refer to the attribute of the 
      same name in the group AtmTmOper.
      
      This attribute indicates the set of current frame discard functions in 
      effect in the transmit data direction at this connection point.
      
      A value of ppd indicates that the Partial Packet Discard (PPD) 
      function is in effect. PPD may be applied at an interim connecting 
      point for a connection which is transporting frame traffic (AAL5 at 
      the endpoint). PPD is controlled by provisioning for PVCs and 
      SPVCs, and by call setup parameters in the AAL and Traffic 
      Descriptor Information Elements.
      
      A value of epd indicates that the Early Packet Discard (EPD) 
      function is in effect at this connection endpoint. PPD and EPD are 
      enabled by default at a connection endpoint which is performing 
      AAL5 segmentation and assembly.
      
      Frame discard functions are not applicable for Virtual Path 
      Connections (VPCs).

      Description of bits:
      ppd(0)
      epd(1)"
::= { mscAtmIfVccTrafficEntry 85 }

mscAtmIfVccRxFrameDiscard OBJECT-TYPE
   SYNTAX     OCTET STRING (SIZE (1))
   ACCESS     read-only
   STATUS     obsolete
   DESCRIPTION
     "This attribute is HISTORICAL. Please refer to the attribute of the 
      same name in the group AtmTmOper.
      
      This attribute indicates the set of current frame discard functions in 
      effect in the receive data direction at this connection point.
      
      A value of ppd indicates that the Partial Packet Discard (PPD) 
      function is in effect. PPD may be applied at an interim connecting 
      point for a connection which is transporting frame traffic (AAL5 at 
      the endpoint). PPD is controlled by provisioning for PVCs and 
      SPVCs, and by call setup parameters in the AAL and Traffic 
      Descriptor Information Elements.
      
      A value of epd indicates that the Early Packet Discard (EPD) 
      function is in effect at this connection endpoint. PPD and EPD are 
      enabled by default at a connection endpoint which is performing 
      AAL5 segmentation and assembly.
      
      Frame discard functions are not applicable for Virtual Path 
      Connections (VPCs).

      Description of bits:
      ppd(0)
      epd(1)"
::= { mscAtmIfVccTrafficEntry 86 }

mscAtmIfVccBandwidthElastic OBJECT-TYPE
   SYNTAX     INTEGER  {
                 no(0),
                 yes(1) }
   ACCESS     read-only
   STATUS     obsolete
   DESCRIPTION
     "This attribute is HISTORICAL. Please refer to the attribute of the 
      same name in the group AtmTmOper.
      
      This attribute is only of importance for connections which are 
      carried on a link with a variable bandwidth. For example, the 
      bandwidth may be reduced in the event that one or more physical 
      links in the IMA group fail, such that the originally requested 
      bandwidth cannot be maintained. This attribute shows whether the 
      application (for example, Trunk) running on this connection can 
      continue to operate if the bandwidth is reduced. If the bandwidth is 
      reduced, the amount by which it is reduced is displayed in the 
      bandwidthReduction attribute. 
      
      A value of yes, indicates that this connection is elastic, and the 
      bandwidth may be reduced but the connection is not released. 
      
      A value of no indicates that the bandwidth for this connection is not 
      reduced in the event of link bandwidth reduction. However, this 
      connection may be released based on its holdingPriority.
      
      Bandwidth elasticity has no effect for ubr atmServiceCategory or 
      txTrafficDescriptorType 1 or 2 connections."
::= { mscAtmIfVccTrafficEntry 90 }

mscAtmIfVccBandwidthReduction OBJECT-TYPE
   SYNTAX     INTEGER (0..2147483647)
   ACCESS     read-only
   STATUS     obsolete
   DESCRIPTION
     "This attribute is HISTORICAL. Please refer to the attribute of the 
      same name in the group AtmTmOper.
      
      This attribute shows the amount by which the bandwidth has been 
      reduced for this connection. This value is non-zero only for 
      connections which have bandwidthElastic displayed as yes, and 
      which are also operating in a reduced bandwidth mode. This is 
      typically be the case for selected connections running over an IMA 
      link. This attribute takes a value from 0 (no reduction) up to the 
      ECR. All connections which are running at their full allocated 
      bandwidth, bwReduction have the value 0. Connections which have 
      been reduced in allocated bandwidth have a positive number for this 
      attribute. The bwReduction may be subtracted from the ECR (which 
      is displayed as txTrafficDescParm 5) to determine the actual 
      bandwidth allocated to this connection."
::= { mscAtmIfVccTrafficEntry 100 }

mscAtmIfVccStatsTable OBJECT-TYPE
   SYNTAX     SEQUENCE OF MscAtmIfVccStatsEntry
   ACCESS     not-accessible
   STATUS     mandatory
   DESCRIPTION
     "This group contains traffic statistics for a Vcc, Vpc, or Vpt 
      component."
::= { mscAtmIfVcc 140 }

mscAtmIfVccStatsEntry OBJECT-TYPE
   SYNTAX     MscAtmIfVccStatsEntry
   ACCESS     not-accessible
   STATUS     mandatory
   DESCRIPTION
     "An entry in the mscAtmIfVccStatsTable."
   INDEX {
      mscAtmIfIndex,
      mscAtmIfVccIndex }
::= { mscAtmIfVccStatsTable 1 }

MscAtmIfVccStatsEntry ::= SEQUENCE {
   mscAtmIfVccStatsTxCell
      PassportCounter64,
   mscAtmIfVccStatsTxCellClp
      PassportCounter64,
   mscAtmIfVccTxDiscard
      PassportCounter64,
   mscAtmIfVccTxDiscardClp
      PassportCounter64,
   mscAtmIfVccStatsTxCellDiscard
      PassportCounter64,
   mscAtmIfVccStatsTxCellDiscardClp
      PassportCounter64,
   mscAtmIfVccStatsTxFrameDiscard
      PassportCounter64,
   mscAtmIfVccStatsTxFrameDiscardClp
      PassportCounter64,
   mscAtmIfVccStatsRxCell
      PassportCounter64,
   mscAtmIfVccStatsRxCellClp
      PassportCounter64,
   mscAtmIfVccRxDiscard
      PassportCounter64,
   mscAtmIfVccRxDiscardClp
      PassportCounter64,
   mscAtmIfVccStatsRxCellDiscard
      PassportCounter64,
   mscAtmIfVccStatsRxCellDiscardClp
      PassportCounter64,
   mscAtmIfVccStatsRxFrameDiscard
      PassportCounter64,
   mscAtmIfVccStatsRxFrameDiscardClp
      PassportCounter64,
   mscAtmIfVccStatsRxUpcViolationOnEnforcer1
      PassportCounter64,
   mscAtmIfVccStatsRxUpcViolationOnEnforcer2
      PassportCounter64,
   mscAtmIfVccStatsRxAal5FrameError
      PassportCounter64,
   mscAtmIfVccStatsRxAal5FrameAbort
      PassportCounter64 }

mscAtmIfVccStatsTxCell OBJECT-TYPE
   SYNTAX     PassportCounter64 
   ACCESS     read-only
   STATUS     mandatory
   DESCRIPTION
     "This attribute counts the number of cells that have been transmitted 
      from the interface on this connection. The counter wraps to zero if it 
      exceeds its maximum value of (2**64)-1."
::= { mscAtmIfVccStatsEntry 10 }

mscAtmIfVccStatsTxCellClp OBJECT-TYPE
   SYNTAX     PassportCounter64 
   ACCESS     read-only
   STATUS     mandatory
   DESCRIPTION
     "This attribute counts the number of cells that have been transmitted 
      from the interface on this connection with the CLP=1. The counter 
      wraps to zero if it exceeds its maximum value of (2**64)-1."
::= { mscAtmIfVccStatsEntry 20 }

mscAtmIfVccTxDiscard OBJECT-TYPE
   SYNTAX     PassportCounter64 
   ACCESS     read-only
   STATUS     obsolete
   DESCRIPTION
     "This attribute is replaced by new attributes txCellDiscard and 
      txFrameDiscard.
      
      This attribute counts the number of cells or frames received from 
      the bus on this connection that have been discarded.
      
      If the connection segments frames into cells, the counter indicates 
      the number of frames discarded. Connections which segment 
      frames into cells have a connectionPointType of 
      connectionEndPoint.
      
      If the connection relays cells without adaptation, the counter 
      indicates the number of cells discarded. Connections which relay 
      cells without adaptation have a connectionPointType of 
      segmentEndPoint or connectingPoint.
      
      AAL1 connections are an exception to this rule; although they have 
      a connectionPointType of connectionEndPoint, they do not do 
      adaptation at this point. Thus, in the AAL1 case, this attribute 
      counts discarded cells.
      
      Discards are done due to congestion or when the connection's 
      interface is disabled.
      
      The counter wraps to zero if it exceeds its maximum value of 
      (2**64)-1."
::= { mscAtmIfVccStatsEntry 30 }

mscAtmIfVccTxDiscardClp OBJECT-TYPE
   SYNTAX     PassportCounter64 
   ACCESS     read-only
   STATUS     obsolete
   DESCRIPTION
     "This attribute is replaced by new attributes txCellDiscardClp and 
      txFrameDiscardClp.
      
      This attribute counts the number of cells or frames received from 
      the bus on this connection with CLP=1 that have been discarded.
      
      If the connection segments frames into cells, the counter indicates 
      the number of frames discarded. Connections which segment 
      frames into cells have a connectionPointType of 
      connectionEndPoint.
      
      If the connection relays cells without adaptation, the counter 
      indicates the number of cells discarded. Connections which relay 
      cells without adaptation have a connectionPointType of 
      segmentEndPoint or connectingPoint.
      
      AAL1 connections are an exception to this rule; although they have 
      a connectionPointType of connectionEndPoint, they do not do 
      adaptation at this point. Thus, in the AAL1 case, this attribute 
      counts discarded cells.
      
      Discards are done due to congestion or when the connection's 
      interface is disabled.
      
      The counter wraps to zero if it exceeds its maximum value of 
      (2**64)-1."
::= { mscAtmIfVccStatsEntry 40 }

mscAtmIfVccStatsTxCellDiscard OBJECT-TYPE
   SYNTAX     PassportCounter64 
   ACCESS     read-only
   STATUS     mandatory
   DESCRIPTION
     "This attribute counts the number of cells received from the bus on 
      this connection that have been discarded.
      
      Discarded cells are not counted in the txCell attribute.
      
      Cells are discarded due to transmit congestion, Partial Packet 
      Discard (PPD), Early Packet Discard (EPD), and Weighted Random 
      Early Detection (W-RED) mechanisms, or when the connection's 
      interface is disabled.
      
      For CQC-based ATM cards, this attribute is applicable only to 
      connections that relay cells without adaptation. Such connections 
      usually have a connectionPointType of segmentEndPoint or 
      connectingPoint. AAL1 connections are an exception to this rule; 
      although they have a connectionPointType of connectionEndPoint, 
      they do not do adaptation at this point. For Vpts, this attribute 
      provides an aggregated total of all txCellDiscard values for all such 
      connections associated with the Vpt.
      
      For Vccs on CQC-based ATM cards, if the connection segments 
      frames into cells, this attribute is not applicable and is not 
      displayed.
      
      The counter wraps to zero if it exceeds its maximum value of 
      (2**64)-1."
::= { mscAtmIfVccStatsEntry 42 }

mscAtmIfVccStatsTxCellDiscardClp OBJECT-TYPE
   SYNTAX     PassportCounter64 
   ACCESS     read-only
   STATUS     mandatory
   DESCRIPTION
     "This attribute counts the number of cells received from the bus on 
      this connection with CLP=1 that have been discarded.
      
      This count is included in the txCellDiscard attribute. Discarded 
      cells are not counted in the txCellClp attribute.
      
      Cells are discarded due to transmit congestion, Partial Packet 
      Discard (PPD), Early Packet Discard (EPD), and Weighted Random 
      Early Detection (W-RED) mechanisms, or when the connection's 
      interface is disabled.
      
      For CQC-based ATM cards, this attribute is applicable only to 
      connections that relay cells without adaptation. Such connections 
      have a connectionPointType of segmentEndPoint or 
      connectingPoint. AAL1 connections are an exception to this rule; 
      although they have a connectionPointType of connectionEndPoint, 
      they do not do adaptation at this point. For Vpts, this attribute 
      provides an aggregated total of all txCellDiscardClp values for all 
      such connections associated with the Vpt.
      
      For Vccs on CQC-based ATM cards, if the connection segments 
      frames into cells, this attribute is not applicable and is not 
      displayed.
      
      The counter wraps to zero if it exceeds its maximum value of 
      (2**64)-1."
::= { mscAtmIfVccStatsEntry 43 }

mscAtmIfVccStatsTxFrameDiscard OBJECT-TYPE
   SYNTAX     PassportCounter64 
   ACCESS     read-only
   STATUS     mandatory
   DESCRIPTION
     "This attribute counts the number of frames received from the bus on 
      this connection that have been discarded.
      
      Frames are discarded due to congestion, Partial Packet Discard 
      (PPD), Early Packet Discard (EPD), and Weighted Random Early 
      Detection (W-RED) mechanisms, or when the connection interface 
      is disabled.
      
      This count is independent of the txCell or txCellDiscard attribute.
      
      For CQC-based ATM cards, this attribute is applicable only to 
      connections that segment frames into cells. Such connections have a 
      connectionPointType of connectionEndPoint. AAL1 connections 
      are an exception to this rule; although they have a 
      connectionPointType of connectionEndPoint, they do not do 
      adaptation at this point. For Vpts, this attribute provides an 
      aggregated total of all txFrameDiscard values for all such 
      connections associated with the Vpt.
      
      For CQC-based ATM cards, for Vpcs, and Vccs that relay cells 
      without adaptation, this attribute is not applicable and is not 
      displayed.
      
      Discards due to EPD, PPD, and W-RED for a standard Vpt Vcc are 
      not included in this attribute. These discards are counted in the 
      Vcc's parent Vpt txFrameDiscard attribute.
      
      The counter wraps to zero if it exceeds its maximum value of 
      (2**64)-1."
::= { mscAtmIfVccStatsEntry 46 }

mscAtmIfVccStatsTxFrameDiscardClp OBJECT-TYPE
   SYNTAX     PassportCounter64 
   ACCESS     read-only
   STATUS     mandatory
   DESCRIPTION
     "This attribute counts the number of discarded frames on this 
      connection that were received from the bus and composed of one or 
      more CLP=1 cells.
      
      Frames are discarded due to congestion, Partial Packet Discard 
      (PPD), Early Packet Discard (EPD), and Weighted Random Early 
      Detection (W-RED) mechanisms, or when the connection interface 
      is disabled.
      
      This count is included in the txFrameDiscard attribute.
      
      For CQC-based ATM cards, this attribute is applicable only to 
      connections that segment frames into cells. Such connections have a 
      connectionPointType of connectionEndPoint. AAL1 connections 
      are an exception to this rule; although they have a 
      connectionPointType of connectionEndPoint, they do not do 
      adaptation at this point. For Vpts, this attribute provides an 
      aggregated total of all txFrameDiscardClp values for all such 
      connections associated with the Vpt.
      
      For CQC-based ATM cards, for Vpcs and Vccs that relay cells 
      without adaptation, this attribute is not applicable and is not 
      displayed.
      
      
      Discards due to EPD, PPD, and W-RED for a standard Vpt Vcc are 
      not included in this attribute. These discards are counted in the 
      Vcc's parent Vpt txFrameDiscardClp attribute.
      
      The counter wraps to zero if it exceeds its maximum value of 
      (2**64)-1."
::= { mscAtmIfVccStatsEntry 47 }

mscAtmIfVccStatsRxCell OBJECT-TYPE
   SYNTAX     PassportCounter64 
   ACCESS     read-only
   STATUS     mandatory
   DESCRIPTION
     "This attribute counts the number of cells that have been received 
      from the interface on this connection. The counter wraps to zero if it 
      exceeds its maximum value of (2**64)-1."
::= { mscAtmIfVccStatsEntry 50 }

mscAtmIfVccStatsRxCellClp OBJECT-TYPE
   SYNTAX     PassportCounter64 
   ACCESS     read-only
   STATUS     mandatory
   DESCRIPTION
     "This attribute counts the number of cells that have been received 
      from the interface on this connection with the CLP=1. The counter 
      wraps to zero if it exceeds its maximum value of (2**64)-1."
::= { mscAtmIfVccStatsEntry 60 }

mscAtmIfVccRxDiscard OBJECT-TYPE
   SYNTAX     PassportCounter64 
   ACCESS     read-only
   STATUS     obsolete
   DESCRIPTION
     "This attribute is replaced by new attributes rxCellDiscard and 
      rxFrameDiscard.
      
      This attribute counts the number of cells or frames received from 
      the interface on this connection that have been discarded.
      
      If the connection segments frames into cells, the counter indicates 
      the number of frames discarded. Connections which segment 
      frames into cells have a connectionPointType of 
      connectionEndPoint.
      
      If the connection relays cells without adaptation, the counter 
      indicates the number of cells discarded. Connections which relay 
      cells without adaptation have a connectionPointType of 
      segmentEndPoint or connectingPoint.
      
      AAL1 connections are an exception to this rule; although they have 
      a connectionPointType of connectionEndPoint, they do not do 
      adaptation at this point. Thus, in the AAL1 case, this attribute 
      counts discarded cells.
      
      Discards are done due to congestion, non-conformance with UPC or 
      AAL reassembly problems.
      
      The counter wraps to zero if it exceeds its maximum value of 
      (2**64)-1."
::= { mscAtmIfVccStatsEntry 70 }

mscAtmIfVccRxDiscardClp OBJECT-TYPE
   SYNTAX     PassportCounter64 
   ACCESS     read-only
   STATUS     obsolete
   DESCRIPTION
     "This attribute is replaced by new attributes rxCellDiscardClp and 
      rxFrameDiscardClp.
      
      This attribute counts the number of cells or frames received from 
      the interface on this connection with CLP=1 that have been 
      discarded.
      
      If the connection segments frames into cells, the counter indicates 
      the number of frames discarded. Connections which segment 
      frames into cells have a connectionPointType of 
      connectionEndPoint.
      
      If the connection relays cells without adaptation, the counter 
      indicates the number of cells discarded. Connections which relay 
      cells without adaptation have a connectionPointType of 
      segmentEndPoint or connectingPoint.
      
      AAL1 connections are an exception to this rule; although they have 
      a connectionPointType of connectionEndPoint, they do not do 
      adaptation at this point. Thus, in the AAL1 case, this attribute 
      counts discarded cells.
      
      Discards are done due to congestion, non-conformance with UPC or 
      AAL reassembly problems.
      
      The counter wraps to zero if it exceeds its maximum value of 
      (2**64)-1."
::= { mscAtmIfVccStatsEntry 80 }

mscAtmIfVccStatsRxCellDiscard OBJECT-TYPE
   SYNTAX     PassportCounter64 
   ACCESS     read-only
   STATUS     mandatory
   DESCRIPTION
     "This attribute counts the number of cells received from the interface 
      on this connection that have been discarded. This count is included 
      in the rxCell attribute.
      
      This count includes cells discarded due to non-conformance with 
      UPC, cells which are part of a frame which has been discarded due 
      to an AAL5 frame reassembly error, cells which are discarded due 
      to congestion, or cells which are received while the next hop 
      connection to which the traffic is directed across the backplane is 
      down. The next hop connection is the Vcc or Vpc identified by the 
      nextHop attribute of the Nrp or Rp component. 
      
      For CQC-based ATM cards, this attribute is applicable only to 
      connections that relay cells without adaptation. Such connections 
      have a connectionPointType of connectionEndPoint or 
      connectingPoint. AAL1 connections are an exception to this rule; 
      although they have a connectionPointType of connectionEndPoint, 
      they do not do adaptation at this point. For Vpts, this attribute 
      provides an aggregated total of all rxCellDiscard values for all such 
      connections associated with the Vpt.
      
      For CQC-based ATM cards, for Vpcs, and Vccs that relay cells 
      without adaptation, this attribute is not applicable and is not 
      displayed.
      
      Discards due to non-conformance with UPC at the VP layer, for a 
      standard Vpt Vcc, are not included in this attribute. These discards 
      are counted in the Vcc's parent Vpt rxCellDiscard attribute. 
      
      The counter wraps to zero if it exceeds its maximum value of 
      (2**64)-1."
::= { mscAtmIfVccStatsEntry 82 }

mscAtmIfVccStatsRxCellDiscardClp OBJECT-TYPE
   SYNTAX     PassportCounter64 
   ACCESS     read-only
   STATUS     mandatory
   DESCRIPTION
     "This attribute counts the number of cells received from the interface 
      on this connection with CLP=1 that have been discarded. This count 
      is included in the rxCell and rxCellDiscard attributes.
      
      This count includes cells discarded due to non-conformance with 
      UPC, cells which are part of a frame which has been discarded due 
      to an AAL5 frame reassembly error, cells which are discarded due 
      to congestion, or cells which are received while the next hop 
      connection to which the traffic is directed across the backplane is 
      down. The next hop connection is the Vcc or Vpc identified by the 
      nextHop attribute of the Nrp or Rp component. 
      
      For CQC-based ATM cards, this attribute is applicable only to 
      connections that relay cells without adaptation. Such connections 
      have a connectionPointType of connectionEndPoint or 
      connectingPoint. AAL1 connections are an exception to this rule; 
      although they have a connectionPointType of connectionEndPoint, 
      they do not do adaptation at this point. For Vpts, this attribute 
      provides an aggregated total of all rxCellDiscard values for all such 
      connections associated with the Vpt.
      
      For CQC-based ATM cards, for Vpcs, and Vccs that relay cells 
      without adaptation, this attribute is not applicable and is not 
      displayed.
      
      Discards due to non-conformance with UPC at the VP layer, for a 
      standard Vpt Vcc, are not included in this attribute. These discards 
      are counted in the Vcc's parent Vpt rxCellDiscard attribute.
      
      The counter wraps to zero if it exceeds its maximum value of 
      (2**64)-1."
::= { mscAtmIfVccStatsEntry 83 }

mscAtmIfVccStatsRxFrameDiscard OBJECT-TYPE
   SYNTAX     PassportCounter64 
   ACCESS     read-only
   STATUS     mandatory
   DESCRIPTION
     "This attribute counts the number of frames received from the 
      interface on this connection that have been discarded. This count is 
      independent of the rxCellDiscard attribute.
      
      This count includes frames discarded due to an AAL5 frame 
      reassembly error, frames discarded due to early packet discard 
      (EPD), and frames discarded due to processor (CPU) congestion. 
      This attribute is applicable only to connections that reassemble 
      incoming cells into frames. Connections which reassemble cells 
      into frames have a connectionPointType of connectionEndPoint. 
      AAL1 connections are an exception to this rule; even though they 
      have a connectionPointType of connectionEndPoint, they do not 
      do adaptation at this point. For Vpts, this attribute provides an 
      aggregated total of all rxFrameDiscard values for all applicable 
      connections associated with the Vpt.
      
      For Vpcs and for Vccs that relay cells without adaptation, this 
      attribute is not applicable and is not displayed.
      
      The counter wraps to zero if it exceeds its maximum value of 
      (2**64)-1."
::= { mscAtmIfVccStatsEntry 86 }

mscAtmIfVccStatsRxFrameDiscardClp OBJECT-TYPE
   SYNTAX     PassportCounter64 
   ACCESS     read-only
   STATUS     mandatory
   DESCRIPTION
     "This attribute counts the number of discarded frames on this 
      connection that were received from the interface and composed of 
      one or more CLP1 cells. This count is included in the 
      rxFrameDiscard attribute. It is independent of the rxCellDiscard 
      attribute.
      
      This count includes frames discarded due to an AAL5 frame 
      reassembly error, frames discarded due to early packet discard 
      (EPD), and frames discarded due to processor (CPU) congestion. 
      This attribute is applicable only to connections that reassemble 
      incoming cells into frames. Such connections have a 
      connectionPointType of connectionEndPoint. AAL1 connections 
      are an exception to this rule; although they have a 
      connectionPointType of connectionEndPoint, they do not do 
      adaptation at this point. For Vpts, this attribute provides an 
      aggregated total of all rxFrameDiscardClp values for all applicable 
      connections associated with the Vpt.
      
      For Vpcs and for Vccs that relay cells without adaptation, this 
      attribute is not applicable and is not displayed.
      
      The counter wraps to zero if it exceeds its maximum value of 
      (2**64)-1."
::= { mscAtmIfVccStatsEntry 88 }

mscAtmIfVccStatsRxUpcViolationOnEnforcer1 OBJECT-TYPE
   SYNTAX     PassportCounter64 
   ACCESS     read-only
   STATUS     mandatory
   DESCRIPTION
     "This attribute counts the number of UPC violations observed by the 
      Generic Cell Rate Algorithm (GCRA) Enforcer 1. This attribute is 
      only applicable if UPC is enforced or monitored. This attribute is 
      not applicable for standard Vpt Vccs. This attribute is not applicable 
      and is not displayed on CQC-based ATM cards.
      
      When the value of rxTrafficDescType for this connection is 3, 4, 5, 
      6, 7 or 8, Enforcer 1 enforces conformance of traffic received from 
      the interface to PCR CLP0+1.
      
      When the value of rxTrafficDescType for this connection is 9, 
      Enforcer 1 performs the Dynamic Generic Cell Rate Algorithm 
      (DGCRA) used for the Available Bit Rate (ABR) service category.
      
      If UPC is enforced all non-conforming cells are discarded by this 
      enforcer. These discarded cells are included in rxCellDiscard. 
      
      For basic Vpts, this attribute provides an aggregated total of all 
      rxUpcViolationOnEnforcer1 values for the Vccs associated with the 
      Vpt.
      
      The counter wraps to zero if it exceeds its maximum value of 
      (2**64)-1."
::= { mscAtmIfVccStatsEntry 90 }

mscAtmIfVccStatsRxUpcViolationOnEnforcer2 OBJECT-TYPE
   SYNTAX     PassportCounter64 
   ACCESS     read-only
   STATUS     mandatory
   DESCRIPTION
     "This attribute counts the number of UPC violations observed by the 
      Generic Cell Rate Algorithm (GCRA) Enforcer 2. This attribute is 
      only applicable if UPC is enforced or monitored. This attribute is 
      not applicable for standard Vpt Vccs. This attribute is not applicable 
      and is not displayed on CQC-based ATM cards.
      
      Enforcer2 is applicable only if the rxTrafficDescType for this 
      connection is 4, 5, 6, 7 or 8.
      
      When the value of rxTrafficDescType 4 or 5, Enforcer 2 enforces 
      conformance of traffic received from the interface to PCR CLP0.
      
      When the value of rxTrafficDescType 6, Enforcer 2 enforces 
      conformance of traffic received from the interface to SCR CLP0+1.
      
      When the value of rxTrafficDescType 7 or 8, Enforcer 2 enforces 
      conformance of traffic received from the interface to SCR CLP0.
      
      If UPC is enforced, enforcer 2 discards non-conforming cells for 
      rxTrafficDescType values of 4, 6 and 7. It tags non-conforming cells 
      for rxTrafficDescType values of 5 and 8. Discarded cells are 
      counted in the rxCellDiscard attribute. 
      
      For basic Vpts, this attribute provides an aggregated total of all 
      rxUpcViolationOnEnforcer2 values for the Vccs associated with 
      the Vpt.
      
      The counter wraps to zero if it exceeds its maximum value of 
      (2**64)-1."
::= { mscAtmIfVccStatsEntry 92 }

mscAtmIfVccStatsRxAal5FrameError OBJECT-TYPE
   SYNTAX     PassportCounter64 
   ACCESS     read-only
   STATUS     mandatory
   DESCRIPTION
     "This attribute counts the number of frames received from the 
      interface on this connection that have AAL5 length errors or AAL5 
      CRC errors. 
      
      This attribute is not applicable and is not displayed on CQC-based 
      ATM cards.
      
      AAL5 length or CRC errors typically occur because of cell discards 
      due to congestion, UPC, or due to corruption of data between the 
      AAL5 segmentation and reassembly end points.
      
      This attribute is applicable only to connections that reassemble 
      incoming cells into frames. Such connections have a 
      connectionPointType of connectionEndPoint. AAL1 connections 
      are an exception to this rule; although they have a 
      connectionPointType of connectionEndPoint, they do not do 
      adaptation at this point. For Vpts, this attribute provides an 
      aggregated total of all rxAal5FrameError values for all applicable 
      connections associated with the Vpt.
      
      For Vpcs and for Vccs that relay cells without adaptation, this 
      attribute is not applicable and is not displayed.
      
      The counter wraps to zero if it exceeds its maximum value of 
      (2**64)-1."
::= { mscAtmIfVccStatsEntry 100 }

mscAtmIfVccStatsRxAal5FrameAbort OBJECT-TYPE
   SYNTAX     PassportCounter64 
   ACCESS     read-only
   STATUS     mandatory
   DESCRIPTION
     "This attribute counts the number of frames received from the 
      interface on this connection that have the AAL5 length field set to 
      zero. 
      
      This attribute is not applicable and is not displayed for CQC-based 
      ATM cards.
      
      An AAL5 length of zero is an indication by the far end 
      segmentation point to this reassembly point that the frame is to be 
      discarded without reassembly. This mechanism is typically used by 
      a segmentation point if it detects an error in a frame after some of 
      the cells belonging to that frame have already been transmitted.
      
      This attribute is applicable only to connections that reassemble 
      incoming cells into frames. Such connections have a 
      connectionPointType of connectionEndPoint. AAL1 connections 
      are an exception to this rule; although they have a 
      connectionPointType of connectionEndPoint, they do not do 
      adaptation at this point. For Vpts, this attribute provides an 
      aggregated total of all rxAal5FrameAbort values for all applicable 
      connections associated with the Vpt.
      
      For Vpcs and for Vccs that relay cells without adaptation, this 
      attribute is not applicable and is not displayed.
      
      The counter wraps to zero if it exceeds its maximum value of 
      (2**64)-1."
::= { mscAtmIfVccStatsEntry 102 }

mscAtmIfVccPerfTable OBJECT-TYPE
   SYNTAX     SEQUENCE OF MscAtmIfVccPerfEntry
   ACCESS     not-accessible
   STATUS     mandatory
   DESCRIPTION
     "This group contains operational attributes which keep performance 
      statistics about the behavior of the AtmIf component."
::= { mscAtmIfVcc 150 }

mscAtmIfVccPerfEntry OBJECT-TYPE
   SYNTAX     MscAtmIfVccPerfEntry
   ACCESS     not-accessible
   STATUS     mandatory
   DESCRIPTION
     "An entry in the mscAtmIfVccPerfTable."
   INDEX {
      mscAtmIfIndex,
      mscAtmIfVccIndex }
::= { mscAtmIfVccPerfTable 1 }

MscAtmIfVccPerfEntry ::= SEQUENCE {
   mscAtmIfVccLastMinimumCtd
      Unsigned32,
   mscAtmIfVccLastMaximumCtd
      Unsigned32,
   mscAtmIfVccLastAverageCtd
      Unsigned32,
   mscAtmIfVccCurrentCtd
      Unsigned32,
   mscAtmIfVccLastCtdSampleSize
      Unsigned32 }

mscAtmIfVccLastMinimumCtd OBJECT-TYPE
   SYNTAX     Unsigned32 (0 | 1..2147483647)
   ACCESS     read-only
   STATUS     mandatory
   DESCRIPTION
     "This attribute indicates the minimum calculated cell transfer delay 
      value for this connection from the previous TODA (time of day 
      accounting) interval if TODA is enabled; or for the previous 12 hour 
      interval if TODA is disabled. Cell transfer delay is calculated as half 
      of the measured segment round trip delay of a loopback cell.
      
      The value is noMeasurement when the ctdCalculation attribute of 
      the AtmIf component is off.
      
      The value is noMeasurement when the accountCollection attribute 
      of the AtmIf Uni or AtmIf Iisp component has a non-empty reason.
      
      The value is noMeasurement when the segSwitchSideLoopback 
      attribute value is off for the connection.
      
      The value is noMeasurement when the switch-side loopback is not 
      working.
      
      The value is noMeasurement when the switch-side loopback status 
      cannot be determined.

      VALUES (

      0 = noMeasurement

      )"
::= { mscAtmIfVccPerfEntry 10 }

mscAtmIfVccLastMaximumCtd OBJECT-TYPE
   SYNTAX     Unsigned32 (0 | 1..2147483647)
   ACCESS     read-only
   STATUS     mandatory
   DESCRIPTION
     "This attribute indicates the maximum calculated cell transfer delay 
      value for this connection from the previous TODA (time of day 
      accounting) interval if TODA is enabled; or for the previous 12 hour 
      interval if TODA is disabled. Cell transfer delay is calculated as half 
      of the measured segment round trip delay of a loopback cell.
      
      The value is noMeasurement when the ctdCalculation attribute of 
      the AtmIf component is off.
      
      The value is noMeasurement when the accountCollection attribute 
      of the AtmIf Uni or AtmIf Iisp component has a non-empty reason.
      
      The value is noMeasurement when the segSwitchSideLoopback 
      attribute value is off for the connection.
      
      The value is noMeasurement when the switch-side loopback is not 
      working.
      
      The value is noMeasurement when the switch-side loopback status 
      cannot be determined.

      VALUES (

      0 = noMeasurement

      )"
::= { mscAtmIfVccPerfEntry 20 }

mscAtmIfVccLastAverageCtd OBJECT-TYPE
   SYNTAX     Unsigned32 (0 | 1..2147483647)
   ACCESS     read-only
   STATUS     mandatory
   DESCRIPTION
     "This attribute indicates the average of all calculated cell transfer 
      delay values for this connection from the previous TODA (time of 
      day accounting) interval if TODA is enabled; or for the previous 12 
      hour interval if TODA is disabled. Cell transfer delay is calculated 
      as half of the measured segment round trip delay of a loopback cell.
      
      The value is noMeasurement when the ctdCalculation attribute of 
      the AtmIf component is off.
      
      The value is noMeasurement when the accountCollection attribute 
      of the AtmIf Uni or AtmIf Iisp component has a non-empty reason.
      
      The value is noMeasurement when the segSwitchSideLoopback 
      attribute value is off for the connection.
      
      The value is noMeasurement when the switch-side loopback is not 
      working.
      
      The value is noMeasurement when the switch-side loopback status 
      cannot be determined.

      VALUES (

      0 = noMeasurement

      )"
::= { mscAtmIfVccPerfEntry 30 }

mscAtmIfVccCurrentCtd OBJECT-TYPE
   SYNTAX     Unsigned32 (0 | 1..2147483647)
   ACCESS     read-only
   STATUS     mandatory
   DESCRIPTION
     "This attribute indicates the most recent cell transfer delay value 
      calculated for this connection. Cell transfer delay is calculated as 
      half of the measured segment round trip delay of a loopback cell.
      
      The value is noMeasurement when the ctdCalculation attribute of 
      the AtmIf component is off.
      
      The value is noMeasurement when the segSwitchSideLoopback 
      attribute value is off for the connection.
      
      The value is noMeasurement when the switch-side loopback is not 
      working.
      
      The value is noMeasurement when the switch-side loopback status 
      cannot be determined.

      VALUES (

      0 = noMeasurement

      )"
::= { mscAtmIfVccPerfEntry 40 }

mscAtmIfVccLastCtdSampleSize OBJECT-TYPE
   SYNTAX     Unsigned32 (0..16384)
   ACCESS     read-only
   STATUS     mandatory
   DESCRIPTION
     "This attribute indicates the number of loopback cells sampled for 
      cell transfer delay calculations during the previous TODA (time of 
      day accounting) interval if TODA is enabled; or for the previous 12 
      hour interval of TODA is disabled."
::= { mscAtmIfVccPerfEntry 50 }

mscAtmIfVccTxTdpTable OBJECT-TYPE
   SYNTAX     SEQUENCE OF MscAtmIfVccTxTdpEntry
   ACCESS     not-accessible
   STATUS     obsolete
   DESCRIPTION
     "This attribute is HISTORICAL. Please refer to the attribute of the 
      same name in the group AtmTmOper.
      
      This attribute is a vector of five transmit traffic parameters. The first 
      three elements reflect the settings of the first three elements of the 
      txTrafficDescParm attribute in the AtmTrafficProv group. 
      
      When txTrafficDescType is 1 or 2, parameters 1 through 5 are 
      unused.
      
      In this description, PCR is the greater of either the PCR or the 
      requested shaping rate (parameter 1 or parameter 5) specified in the 
      Traffic group under the Vcd or Vpd.
      
      When txTrafficDescType is 3, parameter 1 represents the PCR for 
      CLP equal to 0 or 1 traffic; parameters 2 and 3 are unused.
      
      When txTrafficDescType is 4, parameter 1 represents the PCR for 
      CLP equal to 0 and 1 traffic; parameter 2 represents the PCR for 
      CLP equal to 0 traffic with cell discard.
      
      When txTrafficDescType is 5, parameter 1 represents the PCR for 
      CLP equal to 0 and 1 traffic; parameter 2 represents the PCR for 
      CLP equal to 0 traffic with cell tagging.
      
      When txTrafficDescType is 6, parameter 1 represents the PCR for 
      CLP equal to 0 and 1 traffic; parameter 2 represents the SCR for 
      CLP equal to 0 and 1 traffic; parameter 3 represents the MBS for 
      CLP equal to 0 and 1 traffic.
      
      When txTrafficDescType is 7, parameter 1 represents the PCR for 
      CLP equal to 0 and 1 traffic; parameter 2 represents the SCR for 
      CLP equal to 0 traffic with cell discard; parameter 3 represents the 
      MBS for CLP equal to 0 traffic.
      
      When txTrafficDescType is 8, parameter 1 represents the PCR for 
      CLP equal to 0 and 1 traffic; parameter 2 represents the SCR for 
      CLP equal to 0 traffic with cell tagging; parameter 3 represents the 
      MBS for CLP equal to 0 traffic
      
      When txTrafficDescType is 3, 4, 5, 6, 7 or 8, parameter 4 reflects 
      the actual shaping rate in cell/s for this connection. This rate is one 
      of the set of available shaping rates for this type of ATM-FP, based 
      on the number of interfaces doing shaping (attribute 
      perVcQueueInterfaces), the provisioned cell rate, the 
      shapingScalingFactor attribute of the AtmResourceControl 
      component, and whether traffic shaping is enabled. A rate of zero 
      (0) indicates that shaping is not performed. 
      
      When txTrafficDescType is 3, 4, 5, 6, 7 or 8, parameter 5 reflects 
      the equivalent cell rate in cell/s for this connection as determined by 
      the Connection Admission Control (CAC) algorithm. The 
      equivalent cell rate is useful in determining the admission 
      characteristics of this connection."
::= { mscAtmIfVcc 294 }

mscAtmIfVccTxTdpEntry OBJECT-TYPE
   SYNTAX     MscAtmIfVccTxTdpEntry
   ACCESS     not-accessible
   STATUS     obsolete
   DESCRIPTION
     "An entry in the mscAtmIfVccTxTdpTable."
   INDEX {
      mscAtmIfIndex,
      mscAtmIfVccIndex,
      mscAtmIfVccTxTdpIndex }
::= { mscAtmIfVccTxTdpTable 1 }

MscAtmIfVccTxTdpEntry ::= SEQUENCE {
   mscAtmIfVccTxTdpIndex
      Integer32,
   mscAtmIfVccTxTdpValue
      Unsigned32 }

mscAtmIfVccTxTdpIndex OBJECT-TYPE
   SYNTAX     Integer32 (1..5)
   ACCESS     not-accessible
   STATUS     obsolete
   DESCRIPTION
     "This variable represents the mscAtmIfVccTxTdpTable
      specific index for the mscAtmIfVccTxTdpTable."
::= { mscAtmIfVccTxTdpEntry 1 }

mscAtmIfVccTxTdpValue OBJECT-TYPE
   SYNTAX     Unsigned32 (0..2147483647)
   ACCESS     read-only
   STATUS     obsolete
   DESCRIPTION
     "This variable represents an individual value for the
      mscAtmIfVccTxTdpTable."
::= { mscAtmIfVccTxTdpEntry 2 }

mscAtmIfVccRxTdpTable OBJECT-TYPE
   SYNTAX     SEQUENCE OF MscAtmIfVccRxTdpEntry
   ACCESS     not-accessible
   STATUS     obsolete
   DESCRIPTION
     "This attribute is HISTORICAL. Please refer to the attribute of the 
      same name in the group AtmTmOper.
      
      This attribute is a vector of four traffic parameters whose meanings 
      are defined by the rxTrafficDescType attribute. The values of peak 
      cell rate (PCR), sustained cell rate (SCR) are expressed in cells/s. 
      Maximum burst size (MBS) is expressed in cells. Cell Delay 
      Variation Tolerance (CDVT) is expressed in microseconds.
      
      When rxTrafficDescType is 1 or 2, none of the parameters are used.
      
      When rxTrafficDescType is 3, parameter 1 represents the PCR for 
      CLP equal to 0 and 1 traffic; parameter 4 represents the CDVT.
      
      When rxTrafficDescType is 4, parameter 1 represents the PCR for 
      CLP equal to 0 and 1 traffic; parameter 2 represents the PCR for 
      CLP equal to 0 traffic with cell discard; parameter 4 represents the 
      CDVT.
      
      When rxTrafficDescType is 5, parameter 1 represents the PCR for 
      CLP equal to 0 and 1 traffic; parameter 2 represents the PCR for 
      CLP equal to 0 traffic with cell tagging; parameter 4 represents the 
      CDVT.
      
      When rxTrafficDescType is a 6, parameter 1 represents the PCR for 
      CLP equal to 0 and 1 traffic; parameter 2 represents the SCR for 
      CLP equal to 0 and 1 traffic; parameter 3 represents the MBS for 
      CLP equal to 0 and 1 traffic; parameter 4 represents the CDVT. 
      
      When rxTrafficDescType is 7, parameter 1 represents the PCR for 
      CLP equal to 0 and 1 traffic; parameter 2 represents the SCR for 
      CLP equal to 0 traffic with cell discard; parameter 3 represents the 
      MBS for CLP equal to 0 traffic; parameter 4 represents the CDVT.
      
      When rxTrafficDescType is 8, parameter 1 represents the PCR for 
      CLP equal to 0 and 1 traffic; parameter 2 represents the SCR for 
      CLP equal to 0 traffic with cell tagging; parameter 3 represents the 
      MBS for CLP equal to 0 traffic; parameter 4 represents the CDVT. 
      
      If Upc is disabled for this connection, the values of PCR, SCR, 
      MBS and CDVT is a combination of provisioned parameters. If Upc 
      is enabled, the values of PCR, SCR, MBS, and CDVT is exactly the 
      values used by the usage parameter control hardware in policing the 
      arriving traffic. These may vary slightly from the provisioned values 
      due to granularity of the hardware. In the case where the PCR is 
      equal to the SCR, the effective MBS is zero."
::= { mscAtmIfVcc 295 }

mscAtmIfVccRxTdpEntry OBJECT-TYPE
   SYNTAX     MscAtmIfVccRxTdpEntry
   ACCESS     not-accessible
   STATUS     obsolete
   DESCRIPTION
     "An entry in the mscAtmIfVccRxTdpTable."
   INDEX {
      mscAtmIfIndex,
      mscAtmIfVccIndex,
      mscAtmIfVccRxTdpIndex }
::= { mscAtmIfVccRxTdpTable 1 }

MscAtmIfVccRxTdpEntry ::= SEQUENCE {
   mscAtmIfVccRxTdpIndex
      Integer32,
   mscAtmIfVccRxTdpValue
      Unsigned32 }

mscAtmIfVccRxTdpIndex OBJECT-TYPE
   SYNTAX     Integer32 (1..4)
   ACCESS     not-accessible
   STATUS     obsolete
   DESCRIPTION
     "This variable represents the mscAtmIfVccRxTdpTable
      specific index for the mscAtmIfVccRxTdpTable."
::= { mscAtmIfVccRxTdpEntry 1 }

mscAtmIfVccRxTdpValue OBJECT-TYPE
   SYNTAX     Unsigned32 (0..2147483647)
   ACCESS     read-only
   STATUS     obsolete
   DESCRIPTION
     "This variable represents an individual value for the
      mscAtmIfVccRxTdpTable."
::= { mscAtmIfVccRxTdpEntry 2 }

mscAtmIfVccTxQThreshTable OBJECT-TYPE
   SYNTAX     SEQUENCE OF MscAtmIfVccTxQThreshEntry
   ACCESS     not-accessible
   STATUS     obsolete
   DESCRIPTION
     "This attribute is HISTORICAL. Please refer to the attribute of the 
      same name in the group AtmTmOper.
      
      This attribute indicates the queue limit and the discard thresholds 
      for the transmit queue of this connection. 
      
      The first element indicates the queue limit. Depending upon the 
      atmServiceCategory of the connection, the provisioned value of the 
      transmit queue limit is derived from the txQueueLimit attribute 
      under one of the subcomponents of the AtmIf CA component. If the 
      connection has traffic shaping disabled, then this attribute relates to 
      the common queue. If traffic shaping is enabled, then this attribute 
      relates to the per-VC queue.
      
      The second element is the threshold that marks the transition from 
      congestion state 1 to congestion state 0. This is the threshold at 
      which traffic with discard priority (DP) = 1 is discarded. This 
      threshold is set approximately at 90 percent of the first parameter, 
      the operational queue limit.
      
      The third element is the threshold that marks the transition from 
      congestion state 2 to congestion state 1. This is the threshold at 
      which traffic with DP = 2 is discarded. This threshold is set 
      approximately at 75 percent of the first parameter, the operational 
      queue limit.
      
      The fourth element is the threshold that marks the transition from 
      congestion state 3 to congestion state 2. This is the threshold at 
      which traffic with DP = 3 is discarded. This threshold is set 
      approximately at 35 percent of the first parameter, the operational 
      queue limit."
::= { mscAtmIfVcc 352 }

mscAtmIfVccTxQThreshEntry OBJECT-TYPE
   SYNTAX     MscAtmIfVccTxQThreshEntry
   ACCESS     not-accessible
   STATUS     obsolete
   DESCRIPTION
     "An entry in the mscAtmIfVccTxQThreshTable."
   INDEX {
      mscAtmIfIndex,
      mscAtmIfVccIndex,
      mscAtmIfVccTxQThreshIndex }
::= { mscAtmIfVccTxQThreshTable 1 }

MscAtmIfVccTxQThreshEntry ::= SEQUENCE {
   mscAtmIfVccTxQThreshIndex
      Integer32,
   mscAtmIfVccTxQThreshValue
      Unsigned32 }

mscAtmIfVccTxQThreshIndex OBJECT-TYPE
   SYNTAX     Integer32 (0..3)
   ACCESS     not-accessible
   STATUS     obsolete
   DESCRIPTION
     "This variable represents the mscAtmIfVccTxQThreshTable
      specific index for the mscAtmIfVccTxQThreshTable."
::= { mscAtmIfVccTxQThreshEntry 1 }

mscAtmIfVccTxQThreshValue OBJECT-TYPE
   SYNTAX     Unsigned32 (0..30720)
   ACCESS     read-only
   STATUS     obsolete
   DESCRIPTION
     "This variable represents an individual value for the
      mscAtmIfVccTxQThreshTable."
::= { mscAtmIfVccTxQThreshEntry 2 }

mscAtmIfVccFqpTable OBJECT-TYPE
   SYNTAX     SEQUENCE OF MscAtmIfVccFqpEntry
   ACCESS     not-accessible
   STATUS     obsolete
   DESCRIPTION
     "This attribute is HISTORICAL. Please refer to the attribute of the 
      same name in the group AtmTmOper.
      
      This attribute is a vector of three elements that indicate the quality 
      of service parameters for the forward direction for this connection. 
      This attribute is used for SPVC and SVC connections on a PNNI 
      interface.
      
      The cdv element indicates the acceptable peak-to-peak Cell Delay 
      Variation (CDV) of real-time connections (CBR, and rt-VBR). 
      
      The ctd element indicates the acceptable maximum Cell Transfer 
      Delay (maxCtd) of real-time connections (CBR, and rt-VBR). 
      
      The clr element indicates the acceptable Cell Loss Ratio (CLR) of 
      CBR, rt-VBR, and nrt-VBR connections."
::= { mscAtmIfVcc 357 }

mscAtmIfVccFqpEntry OBJECT-TYPE
   SYNTAX     MscAtmIfVccFqpEntry
   ACCESS     not-accessible
   STATUS     obsolete
   DESCRIPTION
     "An entry in the mscAtmIfVccFqpTable."
   INDEX {
      mscAtmIfIndex,
      mscAtmIfVccIndex,
      mscAtmIfVccFqpIndex }
::= { mscAtmIfVccFqpTable 1 }

MscAtmIfVccFqpEntry ::= SEQUENCE {
   mscAtmIfVccFqpIndex
      INTEGER,
   mscAtmIfVccFqpValue
      Unsigned32 }

mscAtmIfVccFqpIndex OBJECT-TYPE
   SYNTAX     INTEGER  {
                 cdv(0),
                 ctd(1),
                 clr(2) }
   ACCESS     not-accessible
   STATUS     obsolete
   DESCRIPTION
     "This variable represents the mscAtmIfVccFqpTable
      specific index for the mscAtmIfVccFqpTable."
::= { mscAtmIfVccFqpEntry 1 }

mscAtmIfVccFqpValue OBJECT-TYPE
   SYNTAX     Unsigned32 (0..2147483647)
   ACCESS     read-only
   STATUS     obsolete
   DESCRIPTION
     "This variable represents an individual value for the
      mscAtmIfVccFqpTable."
::= { mscAtmIfVccFqpEntry 2 }

mscAtmIfVccBqpTable OBJECT-TYPE
   SYNTAX     SEQUENCE OF MscAtmIfVccBqpEntry
   ACCESS     not-accessible
   STATUS     obsolete
   DESCRIPTION
     "This attribute is HISTORICAL. Please refer to the attribute of the 
      same name in the group AtmTmOper.
      
      This attribute is a vector of three elements that indicate the quality 
      of service parameters for the backward direction for this 
      connection. This attribute is used for SPVC and SVC connections 
      on a PNNI interface.
      
      The cdv element indicates the acceptable peak-to-peak Cell Delay 
      Variation (CDV) of real-time connections (CBR, and rt-VBR). 
      
      The ctd element indicates the acceptable maximum Cell Transfer 
      Delay (maxCtd) of real-time connections (CBR, and rt-VBR). 
      
      The clr element indicates the acceptable Cell Loss Ratio (CLR) of 
      CBR, rt-VBR, and nrt-VBR connections."
::= { mscAtmIfVcc 358 }

mscAtmIfVccBqpEntry OBJECT-TYPE
   SYNTAX     MscAtmIfVccBqpEntry
   ACCESS     not-accessible
   STATUS     obsolete
   DESCRIPTION
     "An entry in the mscAtmIfVccBqpTable."
   INDEX {
      mscAtmIfIndex,
      mscAtmIfVccIndex,
      mscAtmIfVccBqpIndex }
::= { mscAtmIfVccBqpTable 1 }

MscAtmIfVccBqpEntry ::= SEQUENCE {
   mscAtmIfVccBqpIndex
      INTEGER,
   mscAtmIfVccBqpValue
      Unsigned32 }

mscAtmIfVccBqpIndex OBJECT-TYPE
   SYNTAX     INTEGER  {
                 cdv(0),
                 ctd(1),
                 clr(2) }
   ACCESS     not-accessible
   STATUS     obsolete
   DESCRIPTION
     "This variable represents the mscAtmIfVccBqpTable
      specific index for the mscAtmIfVccBqpTable."
::= { mscAtmIfVccBqpEntry 1 }

mscAtmIfVccBqpValue OBJECT-TYPE
   SYNTAX     Unsigned32 (0..2147483647)
   ACCESS     read-only
   STATUS     obsolete
   DESCRIPTION
     "This variable represents an individual value for the
      mscAtmIfVccBqpTable."
::= { mscAtmIfVccBqpEntry 2 }


-- AtmIf/n Vcc/vpi.vci VirtualChannelDescriptor,
-- AtmIf/n Vpt/vpi Vcc/vci VirtualChannelDescriptor
-- The Vcd component contains provisioning information about its 
-- parent Vcc component.

mscAtmIfVccVcd OBJECT IDENTIFIER ::= { mscAtmIfVcc 2 }



mscAtmIfVccVcdRowStatusTable OBJECT-TYPE
   SYNTAX     SEQUENCE OF MscAtmIfVccVcdRowStatusEntry
   ACCESS     not-accessible
   STATUS     mandatory
   DESCRIPTION
     "This entry controls the addition and deletion of 
      mscAtmIfVccVcd components."
::= { mscAtmIfVccVcd 1 }

mscAtmIfVccVcdRowStatusEntry OBJECT-TYPE
   SYNTAX     MscAtmIfVccVcdRowStatusEntry
   ACCESS     not-accessible
   STATUS     mandatory
   DESCRIPTION
     "A single entry in the table represents a single 
      mscAtmIfVccVcd component."
   INDEX {
      mscAtmIfIndex,
      mscAtmIfVccIndex,
      mscAtmIfVccVcdIndex }
::= { mscAtmIfVccVcdRowStatusTable 1 }

MscAtmIfVccVcdRowStatusEntry ::= SEQUENCE {
   mscAtmIfVccVcdRowStatus
      RowStatus,
   mscAtmIfVccVcdComponentName
      DisplayString,
   mscAtmIfVccVcdStorageType
      StorageType,
   mscAtmIfVccVcdIndex
      NonReplicated }

mscAtmIfVccVcdRowStatus OBJECT-TYPE
   SYNTAX     RowStatus 
   ACCESS     read-only
   STATUS     mandatory
   DESCRIPTION
     "This variable is used as the basis for SNMP naming of
      mscAtmIfVccVcd components.
      These components cannot be added nor deleted."
::= { mscAtmIfVccVcdRowStatusEntry 1 }

mscAtmIfVccVcdComponentName OBJECT-TYPE
   SYNTAX     DisplayString 
   ACCESS     read-only
   STATUS     mandatory
   DESCRIPTION
     "This variable provides the component's string name for
      use with the ASCII Console Interface"
::= { mscAtmIfVccVcdRowStatusEntry 2 }

mscAtmIfVccVcdStorageType OBJECT-TYPE
   SYNTAX     StorageType 
   ACCESS     read-only
   STATUS     mandatory
   DESCRIPTION
     "This variable represents the storage type value for the
      mscAtmIfVccVcd tables."
::= { mscAtmIfVccVcdRowStatusEntry 4 }

mscAtmIfVccVcdIndex OBJECT-TYPE
   SYNTAX     NonReplicated 
   ACCESS     not-accessible
   STATUS     mandatory
   DESCRIPTION
     "This variable represents the index for the mscAtmIfVccVcd tables."
::= { mscAtmIfVccVcdRowStatusEntry 10 }

mscAtmIfVccVcdLbkTable OBJECT-TYPE
   SYNTAX     SEQUENCE OF MscAtmIfVccVcdLbkEntry
   ACCESS     not-accessible
   STATUS     mandatory
   DESCRIPTION
     "This group contains the provisionable loopback attributes for a Vcc, 
      Vpc, or Vpt component.
      
      Note that certain loopback requests may not be possible on a given 
      connection. In such cases, the corresponding operational loopback 
      attribute in the Status group of the Vcc, Vpc, or Vpt component is 
      set to notApplicable and the requested loopback is not performed.
      
      If loopbacks are provisioned to be on, and for any reason the 
      segment or end-to-end OAM loopback cells are not relayed, the 
      connection component becomes troubled, and user cell traffic may 
      be discarded. If loopbacks are provisioned to be on, all of the nodes 
      in the segment, and external networks which are in the end-to-end 
      connection must relay the OAM loopback cells."
::= { mscAtmIfVccVcd 100 }

mscAtmIfVccVcdLbkEntry OBJECT-TYPE
   SYNTAX     MscAtmIfVccVcdLbkEntry
   ACCESS     not-accessible
   STATUS     mandatory
   DESCRIPTION
     "An entry in the mscAtmIfVccVcdLbkTable."
   INDEX {
      mscAtmIfIndex,
      mscAtmIfVccIndex,
      mscAtmIfVccVcdIndex }
::= { mscAtmIfVccVcdLbkTable 1 }

MscAtmIfVccVcdLbkEntry ::= SEQUENCE {
   mscAtmIfVccVcdSegLinkSideLoopback
      INTEGER,
   mscAtmIfVccVcdSegSwitchSideLoopback
      INTEGER,
   mscAtmIfVccVcdEndToEndLoopback
      INTEGER,
   mscAtmIfVccVcdMCastConnectionType
      INTEGER }

mscAtmIfVccVcdSegLinkSideLoopback OBJECT-TYPE
   SYNTAX     INTEGER  {
                 on(0),
                 off(1),
                 sameAsInterface(2) }
   ACCESS     read-write
   STATUS     mandatory
   DESCRIPTION
     "This attribute specifies whether link-side segment loopback 
      insertion should be performed on this connection. 
      
      When sameAsInterface is selected, the link-side segment loopback 
      insertion for the connection is based on the segLinkSideLoopback 
      attribute of the connection's parent AtmIf componentif the ATM 
      interface has link-side segment loopback insertion turned on, then 
      link-side segment loopback insertion is also on for the connection. 
      
      When on or off is selected, link-side segment loopback insertion is 
      turned on or off respectively for the connection regardless of the 
      provisioning of the parent AtmIf component.
      
      Note that link-side segment loopback insertion is not possible if the 
      connectionPointType attribute of the Vcc or Vpc component is 
      connectingPoint. Link-side segment loopback insertion is also not 
      possible if the distributionType of the Vcc is pointToMultipoint. In 
      such cases, the associated segLinkSideLoopbackState attribute 
      indicates notApplicable and link-side segment loopback insertion is 
      not performed. Link-side segment loopback insertion is always 
      possible on a Vpt."
   DEFVAL     { sameAsInterface }
::= { mscAtmIfVccVcdLbkEntry 10 }

mscAtmIfVccVcdSegSwitchSideLoopback OBJECT-TYPE
   SYNTAX     INTEGER  {
                 on(0),
                 off(1),
                 sameAsInterface(2) }
   ACCESS     read-write
   STATUS     mandatory
   DESCRIPTION
     "This attribute specifies whether switch-side segment loopback 
      insertion should be performed on this connection.
      
      When sameAsInterface is selected, the switch-side segment 
      loopback for the connection is based on the segSwitchSideLoopback 
      attribute of the connection's parent AtmIf componentif the ATM 
      interface has switch-side segment loopback insertion turned on, 
      then switch-side segment loopback insertion is also on for the 
      connection. 
      
      When on or off is selected, switch-side segment loopback insertion 
      is turned on or off respectively for the connection regardless of the 
      provisioning of the parent AtmIf component.
      
      Note that switch-side segment loopback insertion is not possible if 
      the connectionPointType attribute of the Vcc or Vpc component is 
      connectingPoint or connectionEndPoint. Switch-side segment 
      loopback insertion is also not possible if the distributionType of the 
      Vcc is pointToMultipoint In such cases, the associated 
      segSwitchSideLoopbackState attribute indicates notApplicable and 
      switch-side segment loopback insertion is not performed. Switch-
      side segment loopback is never possible on a Vpt."
   DEFVAL     { sameAsInterface }
::= { mscAtmIfVccVcdLbkEntry 20 }

mscAtmIfVccVcdEndToEndLoopback OBJECT-TYPE
   SYNTAX     INTEGER  {
                 on(0),
                 off(1),
                 sameAsInterface(2) }
   ACCESS     read-write
   STATUS     mandatory
   DESCRIPTION
     "This attribute specifies whether end-to-end loopback insertion 
      should be performed on this connection.
      
      When sameAsInterface is selected, the end-to-end loopback for the 
      connection is based on the endToEndLoopback attribute of the 
      connection's parent AtmIf componentif the ATM interface has 
      end-to-end loopback insertion turned on, then end-to-end loopback 
      insertion is also on for the connection. 
      
      When on or off is selected, end-to-end loopback insertion is turned 
      on or off respectively for the connection regardless of the 
      provisioning of the parent AtmIf component.
      
      Note that end-to-end loopback insertion is not possible if the 
      connectionPointType attribute of the Vcc or Vpc component is 
      connectingPoint or segmentEndPoint. End-to-end loopback 
      insertion is also not possible if the distributionType of the Vcc is 
      pointToMultipoint. In such cases, the associated 
      endToEndLoopbackState attribute indicates notApplicable and end-
      to-end loopback insertion is not performed. End-to-end loopback 
      insertion is always possible on a Vpt."
   DEFVAL     { sameAsInterface }
::= { mscAtmIfVccVcdLbkEntry 30 }

mscAtmIfVccVcdMCastConnectionType OBJECT-TYPE
   SYNTAX     INTEGER  {
                 pointToPoint(0),
                 pointToMultipointRoot(1),
                 pointToMultipointLeaf(2) }
   ACCESS     read-write
   STATUS     mandatory
   DESCRIPTION
     "This attribute is introduced to exist temporarily to pass to AtmIf the 
      connection type defined under Vcc or Vpc. This attribute will be 
      obsoleted once a more elegant solution is available."
   DEFVAL     { pointToPoint }
::= { mscAtmIfVccVcdLbkEntry 50 }

mscAtmIfVccVcdTrafficTable OBJECT-TYPE
   SYNTAX     SEQUENCE OF MscAtmIfVccVcdTrafficEntry
   ACCESS     not-accessible
   STATUS     mandatory
   DESCRIPTION
     "This group contains traffic related provisionable attributes for the 
      Vcc and Vpc components. The attributes' operational values are 
      reflected in the Traffic group for these components. Changing any 
      of the attributes in this group causes a service interruption on the 
      Vcc or Vpc component."
::= { mscAtmIfVccVcd 110 }

mscAtmIfVccVcdTrafficEntry OBJECT-TYPE
   SYNTAX     MscAtmIfVccVcdTrafficEntry
   ACCESS     not-accessible
   STATUS     mandatory
   DESCRIPTION
     "An entry in the mscAtmIfVccVcdTrafficTable."
   INDEX {
      mscAtmIfIndex,
      mscAtmIfVccIndex,
      mscAtmIfVccVcdIndex }
::= { mscAtmIfVccVcdTrafficTable 1 }

MscAtmIfVccVcdTrafficEntry ::= SEQUENCE {
   mscAtmIfVccVcdTxTrafficDescType
      INTEGER,
   mscAtmIfVccVcdTxQosClass
      INTEGER,
   mscAtmIfVccVcdFwdQosClass
      INTEGER,
   mscAtmIfVccVcdHoldingPriority
      INTEGER,
   mscAtmIfVccVcdRxTrafficDescType
      INTEGER,
   mscAtmIfVccVcdRxQosClass
      INTEGER,
   mscAtmIfVccVcdBwdQosClass
      INTEGER,
   mscAtmIfVccVcdAtmServiceCategory
      INTEGER,
   mscAtmIfVccVcdTrafficShaping
      INTEGER,
   mscAtmIfVccVcdUnshapedTransmitQueueing
      INTEGER,
   mscAtmIfVccVcdUsageParameterControl
      INTEGER,
   mscAtmIfVccVcdBearerClassBbc
      INTEGER,
   mscAtmIfVccVcdTransferCapabilityBbc
      INTEGER,
   mscAtmIfVccVcdClippingBbc
      INTEGER,
   mscAtmIfVccVcdBestEffort
      INTEGER,
   mscAtmIfVccVcdFwdFrameDiscard
      INTEGER,
   mscAtmIfVccVcdBwdFrameDiscard
      INTEGER }

mscAtmIfVccVcdTxTrafficDescType OBJECT-TYPE
   SYNTAX     INTEGER  {
                 n1(1),
                 n2(2),
                 n3(3),
                 n4(4),
                 n5(5),
                 n6(6),
                 n7(7),
                 n8(8),
                 n9(9) }
   ACCESS     read-write
   STATUS     obsolete
   DESCRIPTION
     "This attribute is migrated to the AtmTmProv group.
      
      This attribute specifies the type of traffic management which is 
      applied to the transmit direction of this connection as defined in the 
      ATM Forum. The txTrafficDescType determines the number and 
      meaning of the parameters in the txTrafficDescParm attribute."
   DEFVAL     { n1 }
::= { mscAtmIfVccVcdTrafficEntry 10 }

mscAtmIfVccVcdTxQosClass OBJECT-TYPE
   SYNTAX     INTEGER  {
                 unspecified(0),
                 constantBitRate(1),
                 variableBitRate(2),
                 connectionOriented(3),
                 connectionless(4) }
   ACCESS     read-write
   STATUS     obsolete
   DESCRIPTION
     "This attribute specifies the quality of service for the transmit 
      direction for this connection.
      
      The constantBitRate class refers to traffic offered on services such 
      as a constant bit rate video service. This traffic is highest priority.
      
      The variableBitRate class refers to traffic offered on services such 
      as packetized audio and video.
      
      The connectionOriented class refers to connection-oriented traffic 
      such as Frame Relay or X.25 traffic. 
      
      The connectionless traffic refers to traffic offered through 
      connectionless trunks such as certain LAN protocols.
      
      The unspecified class supports a 'best effort' type of service, where 
      there is a minimum guarantee of bandwidth. This traffic is lowest 
      priority.
      
      This attribute is obsolete. The value is migrated into 
      atmServiceCategory. The atmServiceCategory applies in both 
      transmit and receive directions.
      
      unspecified maps to unspecifiedBitRate;
      constantBitRate maps to constantBitRate;
      variableBitRate maps to variableBitRateRt;
      connectionOriented maps to variableBitRateNrt
      connectionless maps to variableBitRateNrt"
   DEFVAL     { connectionOriented }
::= { mscAtmIfVccVcdTrafficEntry 20 }

mscAtmIfVccVcdFwdQosClass OBJECT-TYPE
   SYNTAX     INTEGER  {
                 n0(0),
                 n1(1),
                 n2(2),
                 n3(3),
                 n4(4) }
   ACCESS     read-write
   STATUS     obsolete
   DESCRIPTION
     "This attribute is migrated to the AtmTmProv group.
      
      This attribute specifies the quality of service for the forward 
      direction for this connection. This attribute is only used for SPVC 
      connections.
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified bit rate QOS class; no objective is 
      specified for the performance parameters."
   DEFVAL     { n0 }
::= { mscAtmIfVccVcdTrafficEntry 21 }

mscAtmIfVccVcdHoldingPriority OBJECT-TYPE
   SYNTAX     INTEGER  {
                 n0(0),
                 n1(1),
                 n2(2),
                 n3(3),
                 n4(4) }
   ACCESS     read-write
   STATUS     obsolete
   DESCRIPTION
     "This attribute is migrated to the AtmTmProv group.
      
      This attribute specifies the holding priority of this connection. In a 
      situation where the link bandwidth fluctuates, such as over an IMA 
      link, holding priority is used to determine which connections are 
      held and which are released. Holding priority 4 connections are the 
      first to be released. Holding priority 0 connections are the last to be 
      released. This value provisioned in the Vcd or Vpd may be 
      overridden by certain applications, for example Vcc Test, which run 
      over this connection. The default holding priority for a provisioned 
      connection is higher then default holding priorities for dynamic 
      (SVC) connections."
   DEFVAL     { n2 }
::= { mscAtmIfVccVcdTrafficEntry 25 }

mscAtmIfVccVcdRxTrafficDescType OBJECT-TYPE
   SYNTAX     INTEGER  {
                 n1(1),
                 n2(2),
                 n3(3),
                 n4(4),
                 n5(5),
                 n6(6),
                 n7(7),
                 n8(8),
                 sameAsTx(15) }
   ACCESS     read-write
   STATUS     obsolete
   DESCRIPTION
     "This attribute is migrated to the AtmTmProv group.
      
      This attribute specifies the type of traffic management which is 
      applied to the receive direction of this connection as defined in the 
      ATM Forum. The rxTrafficDescType determines the number and 
      meaning of the parameters in the rxTrafficDescParm attribute
      
      When sameAsTx is selected, the rxTrafficDescType as well as the 
      rxTrafficDescParm are taken from the transmit values."
   DEFVAL     { sameAsTx }
::= { mscAtmIfVccVcdTrafficEntry 30 }

mscAtmIfVccVcdRxQosClass OBJECT-TYPE
   SYNTAX     INTEGER  {
                 unspecified(0),
                 constantBitRate(1),
                 variableBitRate(2),
                 connectionOriented(3),
                 connectionless(4),
                 sameAsTx(15) }
   ACCESS     read-write
   STATUS     obsolete
   DESCRIPTION
     "This attribute specifies the quality of service for the receive 
      direction for this connection.
      
      The constantBitRate class refers to traffic offered on services such 
      as a constant bit rate video service. 
      
      The variableBitRate class refers to traffic offered on services such 
      as packetized audio and video. 
      
      The connectionOriented class refers to connection-oriented traffic.
      
      The connectionless traffic refers to traffic offered through 
      connectionless trunks. 
      
      The unspecified class supports a 'best effort' type of service, where 
      there is a minimum guarantee of bandwidth. 
      
      The sameAsTx selection sets the receive quality of service to be the 
      same as the transmit quality of service.
      
      This attribute is obsolete. The value of txQosClass is migrated into 
      atmServiceCategory. The value of this attribute is ignored. 
      AtmServiceCategory applies in both transmit and receive directions."
   DEFVAL     { sameAsTx }
::= { mscAtmIfVccVcdTrafficEntry 40 }

mscAtmIfVccVcdBwdQosClass OBJECT-TYPE
   SYNTAX     INTEGER  {
                 n0(0),
                 n1(1),
                 n2(2),
                 n3(3),
                 n4(4),
                 sameAsFwd(15) }
   ACCESS     read-write
   STATUS     obsolete
   DESCRIPTION
     "This attribute is migrated to the AtmTmProv group.
      
      This attribute specifies the quality of service for the backward 
      direction for this connection. This attribute is only used for SPVC 
      connections.
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified bit rate QOS class; no objective is 
      specified for the performance parameters.
      
      The sameAsFwd selection sets the backward quality of service to 
      be the same as the forward quality of service."
   DEFVAL     { sameAsFwd }
::= { mscAtmIfVccVcdTrafficEntry 41 }

mscAtmIfVccVcdAtmServiceCategory OBJECT-TYPE
   SYNTAX     INTEGER  {
                 unspecifiedBitRate(0),
                 constantBitRate(1),
                 rtVariableBitRate(2),
                 nrtVariableBitRate(3),
                 derivedFromBBC(15) }
   ACCESS     read-write
   STATUS     obsolete
   DESCRIPTION
     "This attribute is migrated to the AtmTmProv group.
      
      This attribute specifies the ATM service category for both directions 
      of the connection. 
      
      The value derivedFromBBC may only be used if the SrcPvc 
      component is provisioned under this Vcc.Otherwise a specific ATM 
      service category must be specified. 
      
      If this attribute is set to derivedFromBBC, the Broadband Bearer 
      Capability (BBC) and bestEffort attributes are used to determine the 
      atmServiceCategory of this connection. 
      
      If this attribute is set to other than derivedFromBBC, the value of 
      this attribute is used to override the provisioned BBC Information 
      Element parameters. In those cases, the BBC attributes are not used. 
      
      The constantBitRate service category is intended for real time 
      applications, that is those requiring tightly constrained delay and 
      delay variation, as would be appropriate for voice and video 
      applications. The consistent availability of a fixed quantity of 
      bandwidth is considered appropriate for CBR service. Cells which 
      are delayed beyond the value specified by Cell Transfer Delay are 
      assumed to be of significantly reduce value to the application.
      
      The rtVariableBitRate service category is intended for real time 
      applications, that is those requiring tightly constrained delay and 
      delay variation, as would be appropriate for voice and video 
      applications. Sources are expected to transmit at a rate which varies 
      with time. Equivalently, the source can be described as 'bursty'. 
      Cells which are delayed beyond the value specified by CTD are 
      assumed to be of significantly reduced value to the application. Real 
      time VBR service may support statistical multiplexing of real time 
      sources.
      
      The nrtVariableBitRate service category is intended for non-real 
      time applications which have bursty traffic characteristics and which 
      can be characterized in terms of a PCR, SCR, and MBS. For those 
      cells which are transferred within the traffic contract, the application 
      expects a low cell loss ratio. For all connections, it expects a bound 
      on the mean cell transfer delay. Non-real time VBR service may 
      support statistical multiplexing of connections.
      
      The unspecifiedBitRate service is intended for non-real time 
      applications; that is, those not requiring tightly constrained delay 
      and delay variation. UBR sources are expected to be bursty. UBR 
      service supports a high degree of statistical multiplexing among 
      sources. UBR service does not specify traffic related service 
      guarantees. No numerical commitments are made with respect to 
      the cell loss ratio experienced by a UBR connection, or as to the 
      cell transfer delay experienced by cells on the connection."
   DEFVAL     { unspecifiedBitRate }
::= { mscAtmIfVccVcdTrafficEntry 42 }

mscAtmIfVccVcdTrafficShaping OBJECT-TYPE
   SYNTAX     INTEGER  {
                 disabled(1),
                 sameAsInterface(2) }
   ACCESS     read-write
   STATUS     obsolete
   DESCRIPTION
     "This attribute is migrated to the AtmTmProv group.
      
      This attribute specifies whether this connection uses traffic shaping 
      when transmitting traffic to the ATM interface.
      
      When sameAsInterface is selected, traffic shaping for the 
      connection is based on the trafficShaping attribute of the 
      connection's parent AtmIf componentif the ATM interface has 
      traffic shaping enabled, then traffic shaping is enabled for the 
      connection. Note that enabling traffic shaping may have no effect 
      under certain cases. These cases are listed in the description of the 
      trafficShaping operational attribute, which is under the Vcc and Vpc 
      components.
      
      When disabled is selected, traffic shaping for this connection is 
      disabled regardless of the provisioning of the parent AtmIf 
      component."
   DEFVAL     { sameAsInterface }
::= { mscAtmIfVccVcdTrafficEntry 50 }

mscAtmIfVccVcdUnshapedTransmitQueueing OBJECT-TYPE
   SYNTAX     INTEGER  {
                 common(1),
                 sameAsInterface(3) }
   ACCESS     read-write
   STATUS     obsolete
   DESCRIPTION
     "This attribute is migrated to the AtmTmProv group.
      
      This attribute only applies when this connection is unshaped. This 
      attribute defines the transmit queueing method for this connection if 
      it is unshaped. Refer to the unshapedTransmitQueueing attribute 
      under the AtmIf for more details on the meaning of this attribute. 
      
      When this attribute is set to sameAsInterface, the value from the 
      AtmIf is used. 
      
      When this attribute is set to common, transmit traffic on this 
      unshaped connection is destined for the common queue."
   DEFVAL     { sameAsInterface }
::= { mscAtmIfVccVcdTrafficEntry 60 }

mscAtmIfVccVcdUsageParameterControl OBJECT-TYPE
   SYNTAX     INTEGER  {
                 disabled(1),
                 sameAsInterface(2) }
   ACCESS     read-write
   STATUS     obsolete
   DESCRIPTION
     "This attribute is migrated to the AtmTmProv group.
      
      This attribute specifies whether this connection enforces usage 
      parameter control when receiving traffic from the ATM interface.
      
      When sameAsInterface is selected, UPC for the connection is 
      based on the usageParameterControl attribute of the connection's 
      parent AtmIf componentif the ATM interface has UPC enabled, 
      then UPC is enabled for the connection. Note that enabling UPC 
      may have no effect under certain cases. These cases are listed in the 
      description of the usageParameterControl operational attribute, 
      which is under the Vcc and Vpc components.
      
      When disabled is selected, UPC for this connection is disabled 
      regardless of the provisioning of the parent AtmIf component."
   DEFVAL     { sameAsInterface }
::= { mscAtmIfVccVcdTrafficEntry 70 }

mscAtmIfVccVcdBearerClassBbc OBJECT-TYPE
   SYNTAX     INTEGER  {
                 a(1),
                 c(3),
                 x(16),
                 vp(24),
                 derivedFromServiceCategory(31) }
   ACCESS     read-write
   STATUS     obsolete
   DESCRIPTION
     "This attribute is migrated to the AtmTmProv group.
      
      This attribute specifies the bearer capability. This attribute is only 
      used for SPVC and SPVP connections. It is one of the Broadband 
      Bearer Capability (BBC) attributes. The purpose of the BBC 
      information element is to indicate a requested broadband 
      connection-oriented bearer service to be provided by the network.
      
      The value derivedFromServiceCategory specifies that the actual 
      value which is used for this connection is derived from the value of 
      the atmServiceCategory. Either, this attribute must be set to 
      derivedFromServiceCategory, or the atmServiceCategory attribute 
      must be set to derivedFromBBC, but not both.
      
      Class a service is a connection-oriented, constant bit rate ATM 
      transport service. Class a service has end to end timing 
      requirements and may require stringent cell loss, cell delay and cell 
      delay variation performance.When a is set, the user is requesting 
      more than an ATM only service. The network may look at the AAL 
      to provide interworking based upon its contents. 
      
      Class c service is a connection-oriented, variable bit rate ATM 
      transport service. Class c service has no end-to-end timing 
      requirements. When c is set, the user is requesting more than an 
      ATM only service. The network interworking function may look at 
      the AAL and provide service based on it.
      
      Class x service is a connection-oriented ATM transport service 
      where the AAL, trafficType (vbr or cbr) and timing requirements 
      are user defined (that is, transparent to the network).When x is set 
      the user is requesting an ATM only service from the network.
      
      Class vp service is used to specify a transparent VP service. When 
      the value of this attribute is vp, the user is requesting an ATM only 
      service from the network. In this case, the network shall not process 
      any higher layer protocol. This service differs from class x service 
      in that with the class vp service both the VCI field (except or VCI 
      values 0, 3, 4, and 6 through 15) and Payload Type field are 
      transported transparently by the network. This attribute value is 
      only applicable to SPVP connections."
   DEFVAL     { derivedFromServiceCategory }
::= { mscAtmIfVccVcdTrafficEntry 71 }

mscAtmIfVccVcdTransferCapabilityBbc OBJECT-TYPE
   SYNTAX     INTEGER  {
                 n0(0),
                 n1(1),
                 n2(2),
                 n5(5),
                 n8(8),
                 n9(9),
                 n10(10),
                 notApplicable(30),
                 derivedFromServiceCategory(31) }
   ACCESS     read-write
   STATUS     obsolete
   DESCRIPTION
     "This attribute is migrated to the AtmTmProv group.
      
      This attribute specifies the transfer capability for this connection. 
      Uni 3.0/3.1 traffic type and end-to-end timing parameters are 
      mapped into this parameter as follows:
      <transferCapability: TrafficType, Timing>
      0: NoIndication, NoIndication
      1: NoIndication, yes
      2: NoIndication, no
      5: CBR, yes
      8: VBR, NoIndication
      9: VBR, yes
      10: VBR, no
      
      NotApplicable specifies that the user does not want to specify the 
      transfer capability.
      
      The CBR traffic type refers to traffic offered on services such as a 
      constant bit rate video service or a circuit emulation.
      
      The VBR traffic type refers to traffic offered on services such as 
      packetized audio and video, or data.
      
      The value no indication for traffic type is used if the user has not set 
      the traffic type; similarly for end-to-end timing.
      
      The value yes for end-to-end timing indicates that end-to-end 
      timing is required.
      
      The value no for end-to-end timing indicates that end-to-end timing 
      is not required.
      
      The value derivedFromServiceCategory specifies that the actual 
      value which is used for this connection is derived from the value of 
      the atmServiceCategory. Either, this attribute must be set to 
      derivedFromServiceCategory, or the atmServiceCategory attribute 
      must be set to derivedFromBBC, but not both."
   DEFVAL     { derivedFromServiceCategory }
::= { mscAtmIfVccVcdTrafficEntry 72 }

mscAtmIfVccVcdClippingBbc OBJECT-TYPE
   SYNTAX     INTEGER  {
                 no(0),
                 yes(1) }
   ACCESS     read-write
   STATUS     obsolete
   DESCRIPTION
     "This attribute is migrated to the AtmTmProv group.
      
      This attribute specifies the value for the clipping susceptibility 
      parameter in the BBC Information Element. This attribute is only 
      used for SPVC connections. It is one of the Broadband Bearer 
      Capability attributes.
      
      Clipping is an impairment in which the first fraction of a second of 
      information to be transferred is lost. It occurs after a call is 
      answered and before an associated connection is switched through."
   DEFVAL     { no }
::= { mscAtmIfVccVcdTrafficEntry 74 }

mscAtmIfVccVcdBestEffort OBJECT-TYPE
   SYNTAX     INTEGER  {
                 indicated(0),
                 notIndicated(1),
                 derivedFromServiceCategory(15) }
   ACCESS     read-write
   STATUS     obsolete
   DESCRIPTION
     "This attribute is migrated to the AtmTmProv group.
      
      This attribute specifies the value of the best effort parameter in the 
      ATM Traffic Descriptor Information Element. This attribute is only 
      used for Soft PVC connections. It is one of the Broadband Bearer 
      Capability attributes.
      
      The value indicated implies that the quality of service for this 
      connection is not guaranteed.
      
      The value notIndicated implies that the quality of service for this 
      connection is guaranteed.
      
      The value derivedFromServiceCategory specifies that the actual 
      value which is used for this connection is derived from the value of 
      the atmServiceCategory. Either, this attribute must be set to 
      derivedFromServiceCategory, or the atmServiceCategory attribute 
      must be set to derivedFromBBC, but not both."
   DEFVAL     { derivedFromServiceCategory }
::= { mscAtmIfVccVcdTrafficEntry 75 }

mscAtmIfVccVcdFwdFrameDiscard OBJECT-TYPE
   SYNTAX     INTEGER  {
                 notIndicated(0),
                 indicated(1) }
   ACCESS     read-write
   STATUS     obsolete
   DESCRIPTION
     "This attribute specifies the activation of frame discard functionality 
      in the forward data direction, at relay points, for this connection. It 
      applies to each hop of the connection. Frame discard functions 
      should not be requested if this connection is not transferring frame 
      (AAL5) traffic. Setting the value to indicated for any other traffic 
      type results in all traffic being discarded.
      
      If this connection point is a permanent (provisioned) VCC mid-
      point, this attribute specifies whether the Partial Packet 
      Discard (PPD) function is to be enabled or disabled in the transmit 
      direction at this connecting point. The PPD function allows the 
      connecting point to discard the remainder of a cell-forwarded AAL5 
      frame if one cell of this frame has been discarded. The PPD 
      function increases the 'goodput' of the link, since cells which are 
      only going to be discarded by the AAL5 reassembly are not 
      transmitted.
      
      At a permanent VCC connecting point which is not a connection 
      endpoint, when this attribute is set to indicated, the PPD function is 
      applied to transmit traffic at this connecting point. It should not be 
      indicated for connections whose end points are not performing 
      AAL5 segmentation and reassembly. When this attribute is set to 
      notIndicated, the PPD feature is not applied to transmit traffic at 
      this connecting point.
      
      At a SPVC origin on a PNNI interface, a value of indicated 
      specifies that frame discard is requested in the forward direction. 
      The frame discard function for SPVCs consists of PPD at the SPVC 
      origin and at all intermediate connecting points. When this attribute 
      is set to notIndicated, forward frame discard is not requested in the 
      SPVC call setup. Thus PPD is not enabled at the SPVC origin nor at 
      any intermediate connecting point.
      
      At all points along a VPC, this setting is ignored.
      
      At a permanent VCC connection endpoint, this value is ignored. If 
      AAL5 segmentation and reassembly has been requested, PPD and 
      Early Packet Discard (EPD) are automatically enabled.
      
      This attribute has been migrated to txFrameDiscard."
   DEFVAL     { notIndicated }
::= { mscAtmIfVccVcdTrafficEntry 76 }

mscAtmIfVccVcdBwdFrameDiscard OBJECT-TYPE
   SYNTAX     INTEGER  {
                 notIndicated(0),
                 indicated(1) }
   ACCESS     read-write
   STATUS     obsolete
   DESCRIPTION
     "This attribute specifies the activation of frame discard functionality 
      in the backward data direction, at relay points, for this connection. 
      It applies to each hop of the connection. Frame discard functions 
      should not be requested if this connection is not transferring frame 
      (AAL5) traffic. Setting the value to indicated for any other traffic 
      type results in all traffic being discarded.
      
      If this connection point is a permanent (provisioned) VCC mid-
      point, this attribute specifies whether the Partial Packet Discard 
      (PPD) function is to be enabled or disabled in the receive direction 
      at this connecting point. The PPD function allows the connecting 
      point to discard the remainder of a cell-forwarded AAL5 frame if 
      one cell of this frame has been discarded. The PPD function 
      increases the 'goodput' of the link, since cells which are only going 
      to be discarded by the AAL5 reassembly are not received.
      
      At a permanent VCC connecting point which is not a connection 
      endpoint, when this attribute is set to indicated, the PPD function is 
      applied to receive traffic at this connecting point. It should not be 
      indicated for connections whose end points are not performing 
      AAL5 segmentation and reassembly. When this attribute is set to 
      notIndicated, the PPD feature is not applied to receive traffic at this 
      connecting point.
      
      At a SPVC origin on a PNNI interface, a value of indicated 
      specifies that frame discard is requested in the backward direction. 
      The frame discard function for SPVCs consists of PPD at the SPVC 
      origin and at all intermediate connecting points. When this attribute 
      is set to notIndicated, backwards frame discard is not requested in 
      the SPVC call setup. Thus PPD is not enabled at the SPVC origin 
      nor at any intermediate connecting point.
      
      At all points along a VPC, this setting is ignored.
      
      At a permanent VCC connection endpoint, this value is ignored. If 
      AAL5 segmentation and reassembly has been requested, PPD and 
      Early Packet Discard (EPD) are automatically enabled.
      
      This attribute has been migrated to rxFrameDiscard."
   DEFVAL     { notIndicated }
::= { mscAtmIfVccVcdTrafficEntry 77 }

mscAtmIfVccVcdAcctTable OBJECT-TYPE
   SYNTAX     SEQUENCE OF MscAtmIfVccVcdAcctEntry
   ACCESS     not-accessible
   STATUS     mandatory
   DESCRIPTION
     "This group contains the provisionable ATM accounting attributes 
      for a Vcc, Vpc, or Vpt component."
::= { mscAtmIfVccVcd 111 }

mscAtmIfVccVcdAcctEntry OBJECT-TYPE
   SYNTAX     MscAtmIfVccVcdAcctEntry
   ACCESS     not-accessible
   STATUS     mandatory
   DESCRIPTION
     "An entry in the mscAtmIfVccVcdAcctTable."
   INDEX {
      mscAtmIfIndex,
      mscAtmIfVccIndex,
      mscAtmIfVccVcdIndex }
::= { mscAtmIfVccVcdAcctTable 1 }

MscAtmIfVccVcdAcctEntry ::= SEQUENCE {
   mscAtmIfVccVcdCorrelationTag
      AsciiString }

mscAtmIfVccVcdCorrelationTag OBJECT-TYPE
   SYNTAX     AsciiString (SIZE (0..32))
   ACCESS     read-write
   STATUS     mandatory
   DESCRIPTION
     "This attribute specifies a unique indentifier for each end of a PVC. It 
      that may be used by downstream processing systems to correlate 
      accounting records issued at different nodes in the network. The 
      attribute can be up to 32 bytes long. If it is less than 32 bytes, it is 
      zero filled on the right to create a 32 byte value. The resulting value 
      is recorded in the attribute callConnId for this PVC's ATM 
      accounting records.
      If the attribute is a null string then this PVC does not have any 
      accounting records generated for it."
   DEFVAL     { ''H }  -- ""
::= { mscAtmIfVccVcdAcctEntry 10 }

mscAtmIfVccVcdTxTdpTable OBJECT-TYPE
   SYNTAX     SEQUENCE OF MscAtmIfVccVcdTxTdpEntry
   ACCESS     not-accessible
   STATUS     obsolete
   DESCRIPTION
     "This attribute is migrated to the AtmTmProv group.
      
      This attribute is a vector of five traffic parameters whose meanings 
      are defined by the txTrafficDescType attribute. The values of peak 
      cell rate (PCR), sustained cell rate (SCR) and requested shaping rate 
      are expressed in cell/s. Maximum burst size (MBS) is expressed in 
      cells. CDVT is expressed in microseconds. The values of PCR, 
      SCR, MBS and CDVT are used for connection admission control 
      (CAC). The value of CDVT is only used for connections where the 
      atmServiceCategory is constantBitRate. For all other values of 
      atmServiceCategory, CDVT is ignored. The values of PCR, SCR 
      and requested shaping rate are used to determine the actual shaping 
      rate where traffic shaping is enabled.
      
      When txTrafficDescType is 1 or 2, all of the parameters must be set 
      to zero.
      
      When txTrafficDescType is 3, parameter 1 represents the PCR for 
      CLP equal to 0 and 1 traffic; parameter 4 represents the CDVT; and 
      parameter 5 represents the requested shaping rate. A non-zero value 
      in parameter 5 overrides any value in parameter 1. This result is 
      used as the PCR. Parameter 1 must be non-zero. Parameters 2 and 3 
      must be zero.
      
      When txTrafficDescType is 4, parameter 1 represents the PCR for 
      CLP equal to 0 and 1 traffic with cell discard; parameter 2 
      represents the PCR for CLP equal to 0 traffic; parameter 4 
      represents the CDVT; and parameter 5 represents the requested 
      shaping rate. A non-zero value in parameter 5 overrides any value in 
      parameter 1. This result is used as the PCR. Parameter 1 must be 
      greater than or equal to parameter 2. Parameters 1 and 2 must be 
      non-zero. Parameter 3 must be zero.
      
      When txTrafficDescType is 5, parameter 1 represents the PCR for 
      CLP equal to 0 and 1 traffic with cell tagging; parameter 2 
      represents the PCR for CLP equal to 0 traffic; parameter 4 
      represents the CDVT; and parameter 5 represents the requested 
      shaping rate. A non-zero value in parameter 5 overrides any value in 
      parameter 1. This result is used as the PCR. Parameter 1 must be 
      greater than or equal to parameter 2. Parameters 1 and 2 must be 
      non-zero. Parameter 3 must be zero.
      
      When txTrafficDescType is 6, parameter 1 represents the PCR for 
      CLP equal to 0 and 1 traffic; parameter 2 represents the SCR for 
      CLP equal to 0 and 1 traffic; parameter 3 represents the MBS for 
      CLP equal to 0 and 1 traffic; parameter 4 represents the CDVT; and 
      parameter 5 represents the requested shaping rate. A non-zero value 
      in parameter 5 overrides any value in parameter 1. This result is 
      used as the PCR. Parameters 1, 2 and 3 must be non-zero. 
      Parameter 1 must be greater than or equal to parameter 2. Parameter 
      5, must either be zero (unused) or greater than or equal to parameter 
      2.
      
      When txTrafficDescType is 7, parameter 1 represents the PCR for 
      CLP equal to 0 and 1 traffic; parameter 2 represents the SCR for 
      CLP equal to 0 with cell discard; parameter 3 represents the MBS 
      for CLP equal to 0 traffic; parameter 4 represents the CDVT; and 
      parameter 5 represents the requested shaping rate. A non-zero value 
      in parameter 5 overrides any value in parameter 1. This result is 
      used as the PCR. Parameters 1, 2 and 3 must be non-zero. 
      Parameter 1 must be greater than or equal to parameter 2. Parameter 
      5, must either be zero (unused) or greater than or equal to parameter 
      2.
      
      When txTrafficDescType is 8, parameter 1 represents the PCR for 
      CLP equal to 0 and 1 traffic; parameter 2 represents the SCR for 
      CLP equal to 0 traffic with cell tagging; parameter 3 represents the 
      MBS for CLP equal to 0 traffic; parameter 4 represents the CDVT; 
      and parameter 5 represents the requested shaping rate. A non-zero 
      value in parameter 5 overrides any value in parameter 1. This result 
      is used as the PCR. Parameters 1, 2 and 3 must be non-zero. 
      Parameter 1 must be greater than or equal to parameter 2. Parameter 
      5, must either be zero (unused) or greater than or equal to parameter 
      2.
      
      Whenever it is valid for PCR to be specified, parameter 5 may also 
      be used to specify a requested shaping rate. A non-zero value in 
      parameter 5 overrides the value in parameter 1 and is used as the 
      peak cell rate in calculations of CAC and shaping rate.
      
      For txTrafficDescType 3, 4 and 5, the transmit traffic is shaped at 
      the next rate less than the PCR. 
      
      For txTrafficDescType 6, 7 and 8, the transmit traffic is shaped at 
      the highest available rate which is between PCR and SCR. 
      However, if there is no available shaping rate between PCR and 
      SCR, traffic is shaped at the next rate above the PCR."
::= { mscAtmIfVccVcd 297 }

mscAtmIfVccVcdTxTdpEntry OBJECT-TYPE
   SYNTAX     MscAtmIfVccVcdTxTdpEntry
   ACCESS     not-accessible
   STATUS     obsolete
   DESCRIPTION
     "An entry in the mscAtmIfVccVcdTxTdpTable."
   INDEX {
      mscAtmIfIndex,
      mscAtmIfVccIndex,
      mscAtmIfVccVcdIndex,
      mscAtmIfVccVcdTxTdpIndex }
::= { mscAtmIfVccVcdTxTdpTable 1 }

MscAtmIfVccVcdTxTdpEntry ::= SEQUENCE {
   mscAtmIfVccVcdTxTdpIndex
      Integer32,
   mscAtmIfVccVcdTxTdpValue
      Unsigned32 }

mscAtmIfVccVcdTxTdpIndex OBJECT-TYPE
   SYNTAX     Integer32 (1..5)
   ACCESS     not-accessible
   STATUS     obsolete
   DESCRIPTION
     "This variable represents the mscAtmIfVccVcdTxTdpTable
      specific index for the mscAtmIfVccVcdTxTdpTable."
::= { mscAtmIfVccVcdTxTdpEntry 1 }

mscAtmIfVccVcdTxTdpValue OBJECT-TYPE
   SYNTAX     Unsigned32 (0..2147483647)
   ACCESS     read-write
   STATUS     obsolete
   DESCRIPTION
     "This variable represents an individual value for the
      mscAtmIfVccVcdTxTdpTable."
::= { mscAtmIfVccVcdTxTdpEntry 2 }

mscAtmIfVccVcdRxTdpTable OBJECT-TYPE
   SYNTAX     SEQUENCE OF MscAtmIfVccVcdRxTdpEntry
   ACCESS     not-accessible
   STATUS     obsolete
   DESCRIPTION
     "This attribute is migrated to the AtmTmProv group.
      
      This attribute is a vector of four traffic parameters whose meanings 
      are defined by the rxTrafficDescType attribute. The values of peak 
      cell rate (PCR) and sustained cell rate (SCR) are expressed in 
      cell/s. Maximum burst size (MBS) is expressed in cells. The value 
      of CDVT is expressed in microseconds. The values of PCR, SCR, 
      MBS and CDVT are used for usage parameter control (UPC).
      
      When rxTrafficDescType is 1 or 2, all of the parameters must be set 
      to zero (unused).
      
      When rxTrafficDescType is 3, parameter 1 represents the PCR for 
      CLP equal to 0 and 1 traffic. Parameter 1 must be non-zero. 
      Parameters 2 and 3 must be set to zero (unused).
      
      When rxTrafficDescType is 4, parameter 1 represents the PCR for 
      CLP equal to 0 and 1 traffic; parameter 2 represents the PCR for 
      CLP equal to 0 traffic with cell discard. Parameters 1 and 2 must be 
      non-zero. Parameter 3 must be set to zero (unused). Parameter 1 
      must be greater than or equal to parameter 2.
      
      When rxTrafficDescType is 5, parameter 1 represents the PCR for 
      CLP equal to 0 and 1 traffic; parameter 2 represents the PCR for 
      CLP equal to 0 traffic with cell tagging. Parameters 1 and 2 must be 
      non-zero. Parameter 3 must be set to zero (unused). Parameter 1 
      must be greater than or equal to parameter 2.
      
      When rxTrafficDescType is a 6, parameter 1 represents the PCR for 
      CLP equal to 0 and 1 traffic; parameter 2 represents the SCR for 
      CLP equal to 0 and 1 traffic; parameter 3 represents the MBS for 
      CLP equal to 0 and 1 traffic. Parameters 1, 2 and 3 must be non-
      zero. Parameter 1 must be greater than or equal to Parameter 2. 
      
      When rxTrafficDescType is 7, parameter 1 represents the PCR for 
      CLP equal to 0 and 1 traffic; parameter 2 represents the SCR for 
      CLP equal to 0 traffic with cell discard; parameter 3 represents the 
      MBS for CLP equal to 0 traffic. Parameters 1, 2 and 3 must be non-
      zero. Parameter 1 must be greater than or equal to parameter 2. 
      
      When rxTrafficDescType is 8, parameter 1 represents the PCR for 
      CLP equal to 0 and 1 traffic; parameter 2 represents the SCR for 
      CLP equal to 0 traffic with cell tagging; parameter 3 represents the 
      MBS for CLP equal to 0 traffic. Parameter 1, 2 and 3 must be non-
      zero. Parameter 1 must be greater than or equal to parameter 2.
      
      When rxTrafficDescType is any value from 3 through 8, parameter 
      4 represents the CDVT. If this value is zero, the CDVT is taken 
      from the ConnectionAdministrator defaults for the particular 
      atmServiceCategory of this connection.
      
      When rxTrafficDescriptorType is 3 through 8, there are certain 
      extreme combinations of rxTrafficDescParm which are outside the 
      capabilities of the UPC hardware. The check prov command detects 
      such cases and generates an error message. If this happens, adjust 
      the parameters until they fall within the supported limits. 
      
      To calculate the limits, use the following formulae:
      I1 = 1 000 000 000 / PCR
      L1 = CDVT * 1000
      I2 = 1 000 000 000 / SCR
      L2 = CDVT + (MBS - 1) * (I2 - I1)
      I1 and I2 must be less than or equal to 335 523 840. I1 + L1 must 
      be less than or equal to 1 342 156 800. I2 + L2 must be less than or 
      equal to 1 342 156 800. Note that I2 and L2 only apply when the 
      rxTrafficDescriptorType is 6 through 8.
      
      If the values of I1, L1, I2 or L2 are closer to the limits described 
      above, a further restriction applies. Specifically, if either:
      I1 > 41 940 480 or
      I2 > 41 940 480 or
      I1 + L1 > 167 769 600 or
      I2 + L2 > 167 769 600
      then both I1 and I2 must be greater than 20 480. 
      
      Parameter 5 of the rxTrafficDescParm is always unused. 
      
      If the rxTrafficDescType is sameAsTx, the values in this attribute 
      are taken from the txTrafficDescParm."
::= { mscAtmIfVccVcd 298 }

mscAtmIfVccVcdRxTdpEntry OBJECT-TYPE
   SYNTAX     MscAtmIfVccVcdRxTdpEntry
   ACCESS     not-accessible
   STATUS     obsolete
   DESCRIPTION
     "An entry in the mscAtmIfVccVcdRxTdpTable."
   INDEX {
      mscAtmIfIndex,
      mscAtmIfVccIndex,
      mscAtmIfVccVcdIndex,
      mscAtmIfVccVcdRxTdpIndex }
::= { mscAtmIfVccVcdRxTdpTable 1 }

MscAtmIfVccVcdRxTdpEntry ::= SEQUENCE {
   mscAtmIfVccVcdRxTdpIndex
      Integer32,
   mscAtmIfVccVcdRxTdpValue
      Unsigned32 }

mscAtmIfVccVcdRxTdpIndex OBJECT-TYPE
   SYNTAX     Integer32 (1..5)
   ACCESS     not-accessible
   STATUS     obsolete
   DESCRIPTION
     "This variable represents the mscAtmIfVccVcdRxTdpTable
      specific index for the mscAtmIfVccVcdRxTdpTable."
::= { mscAtmIfVccVcdRxTdpEntry 1 }

mscAtmIfVccVcdRxTdpValue OBJECT-TYPE
   SYNTAX     Unsigned32 (0..2147483647)
   ACCESS     read-write
   STATUS     obsolete
   DESCRIPTION
     "This variable represents an individual value for the
      mscAtmIfVccVcdRxTdpTable."
::= { mscAtmIfVccVcdRxTdpEntry 2 }

mscAtmIfVccVcdFqpTable OBJECT-TYPE
   SYNTAX     SEQUENCE OF MscAtmIfVccVcdFqpEntry
   ACCESS     not-accessible
   STATUS     obsolete
   DESCRIPTION
     "This attribute is migrated to the AtmTmProv group.
      
      This attribute is a vector of three elements that specify the quality of 
      service parameters for the forward direction for this connection. 
      This attribute is used for SPVC connections.
      
      The cdv element specifies the acceptable peak-to-peak Cell Delay 
      Variation (CDV) of real-time connections (CBR, and rt-VBR). It is 
      signalled through the extended QoS information element.
      
      The ctd specifies the acceptable maximum Cell Transfer Delay 
      (maxCtd) of real-time connections (CBR, and rt-VBR). 
      It is signalled through the end to end transit delay information 
      element.
      
      The clr specifies the acceptable Cell Loss Ratio (CLR) of CBR, rt-
      VBR, and nrt-VBR connections. It is signalled through the extended 
      QoS information element."
::= { mscAtmIfVccVcd 359 }

mscAtmIfVccVcdFqpEntry OBJECT-TYPE
   SYNTAX     MscAtmIfVccVcdFqpEntry
   ACCESS     not-accessible
   STATUS     obsolete
   DESCRIPTION
     "An entry in the mscAtmIfVccVcdFqpTable."
   INDEX {
      mscAtmIfIndex,
      mscAtmIfVccIndex,
      mscAtmIfVccVcdIndex,
      mscAtmIfVccVcdFqpIndex }
::= { mscAtmIfVccVcdFqpTable 1 }

MscAtmIfVccVcdFqpEntry ::= SEQUENCE {
   mscAtmIfVccVcdFqpIndex
      INTEGER,
   mscAtmIfVccVcdFqpValue
      Unsigned32 }

mscAtmIfVccVcdFqpIndex OBJECT-TYPE
   SYNTAX     INTEGER  {
                 cdv(0),
                 ctd(1),
                 clr(2) }
   ACCESS     not-accessible
   STATUS     obsolete
   DESCRIPTION
     "This variable represents the mscAtmIfVccVcdFqpTable
      specific index for the mscAtmIfVccVcdFqpTable."
::= { mscAtmIfVccVcdFqpEntry 1 }

mscAtmIfVccVcdFqpValue OBJECT-TYPE
   SYNTAX     Unsigned32 (0..2147483647)
   ACCESS     read-write
   STATUS     obsolete
   DESCRIPTION
     "This variable represents an individual value for the
      mscAtmIfVccVcdFqpTable."
::= { mscAtmIfVccVcdFqpEntry 2 }

mscAtmIfVccVcdBqpTable OBJECT-TYPE
   SYNTAX     SEQUENCE OF MscAtmIfVccVcdBqpEntry
   ACCESS     not-accessible
   STATUS     obsolete
   DESCRIPTION
     "This attribute is migrated to the AtmTmProv group.
      
      This attribute is a vector of three elements that specify the quality of 
      service parameters for the backward direction for this connection. 
      This attribute is used for SPVC connections.
      
      The cdv element specifies the acceptable peak-to-peak Cell Delay 
      Variation (CDV) of real-time connections (CBR, and rt-VBR). 
      
      It is signalled through the extended QoS information element.
      
      The ctd specifies the acceptable maximum Cell Transfer Delay 
      (maxCtd) of real-time connections (CBR, and rt-VBR). It is 
      signalled through the end to end transit delay information element.
      
      The clr specifies the acceptable Cell Loss Ratio (CLR) of CBR, rt-
      VBR, and nrt-VBR connections. It is signalled through the extended 
      QoS information element."
::= { mscAtmIfVccVcd 360 }

mscAtmIfVccVcdBqpEntry OBJECT-TYPE
   SYNTAX     MscAtmIfVccVcdBqpEntry
   ACCESS     not-accessible
   STATUS     obsolete
   DESCRIPTION
     "An entry in the mscAtmIfVccVcdBqpTable."
   INDEX {
      mscAtmIfIndex,
      mscAtmIfVccIndex,
      mscAtmIfVccVcdIndex,
      mscAtmIfVccVcdBqpIndex }
::= { mscAtmIfVccVcdBqpTable 1 }

MscAtmIfVccVcdBqpEntry ::= SEQUENCE {
   mscAtmIfVccVcdBqpIndex
      INTEGER,
   mscAtmIfVccVcdBqpValue
      Unsigned32 }

mscAtmIfVccVcdBqpIndex OBJECT-TYPE
   SYNTAX     INTEGER  {
                 cdv(0),
                 ctd(1),
                 clr(2) }
   ACCESS     not-accessible
   STATUS     obsolete
   DESCRIPTION
     "This variable represents the mscAtmIfVccVcdBqpTable
      specific index for the mscAtmIfVccVcdBqpTable."
::= { mscAtmIfVccVcdBqpEntry 1 }

mscAtmIfVccVcdBqpValue OBJECT-TYPE
   SYNTAX     Unsigned32 (0..2147483647)
   ACCESS     read-write
   STATUS     obsolete
   DESCRIPTION
     "This variable represents an individual value for the
      mscAtmIfVccVcdBqpTable."
::= { mscAtmIfVccVcdBqpEntry 2 }


-- AtmIf/n Vcc/vpi.vci Vcd TrafficManagement, 
-- AtmIf/n Vpc/vci Vpd TrafficManagement,
-- AtmIf/n Vpt/vpi Vpd TrafficManagement,
-- AtmIf/n Vpt/vpi Vcc/vci Vcd TrafficManagement
-- This component contains provisioned traffic management attributes 
-- of a connection. It is added automatically when a Vcc, Vpc, or Vpt is 
-- added in provisioning mode. It is a mandatory subcomponent of the 
-- Vcd or Vpd component.

mscAtmIfVccVcdTm OBJECT IDENTIFIER ::= { mscAtmIfVccVcd 2 }



mscAtmIfVccVcdTmRowStatusTable OBJECT-TYPE
   SYNTAX     SEQUENCE OF MscAtmIfVccVcdTmRowStatusEntry
   ACCESS     not-accessible
   STATUS     mandatory
   DESCRIPTION
     "This entry controls the addition and deletion of 
      mscAtmIfVccVcdTm components."
::= { mscAtmIfVccVcdTm 1 }

mscAtmIfVccVcdTmRowStatusEntry OBJECT-TYPE
   SYNTAX     MscAtmIfVccVcdTmRowStatusEntry
   ACCESS     not-accessible
   STATUS     mandatory
   DESCRIPTION
     "A single entry in the table represents a single 
      mscAtmIfVccVcdTm component."
   INDEX {
      mscAtmIfIndex,
      mscAtmIfVccIndex,
      mscAtmIfVccVcdIndex,
      mscAtmIfVccVcdTmIndex }
::= { mscAtmIfVccVcdTmRowStatusTable 1 }

MscAtmIfVccVcdTmRowStatusEntry ::= SEQUENCE {
   mscAtmIfVccVcdTmRowStatus
      RowStatus,
   mscAtmIfVccVcdTmComponentName
      DisplayString,
   mscAtmIfVccVcdTmStorageType
      StorageType,
   mscAtmIfVccVcdTmIndex
      NonReplicated }

mscAtmIfVccVcdTmRowStatus OBJECT-TYPE
   SYNTAX     RowStatus 
   ACCESS     read-only
   STATUS     mandatory
   DESCRIPTION
     "This variable is used as the basis for SNMP naming of
      mscAtmIfVccVcdTm components.
      These components cannot be added nor deleted."
::= { mscAtmIfVccVcdTmRowStatusEntry 1 }

mscAtmIfVccVcdTmComponentName OBJECT-TYPE
   SYNTAX     DisplayString 
   ACCESS     read-only
   STATUS     mandatory
   DESCRIPTION
     "This variable provides the component's string name for
      use with the ASCII Console Interface"
::= { mscAtmIfVccVcdTmRowStatusEntry 2 }

mscAtmIfVccVcdTmStorageType OBJECT-TYPE
   SYNTAX     StorageType 
   ACCESS     read-only
   STATUS     mandatory
   DESCRIPTION
     "This variable represents the storage type value for the
      mscAtmIfVccVcdTm tables."
::= { mscAtmIfVccVcdTmRowStatusEntry 4 }

mscAtmIfVccVcdTmIndex OBJECT-TYPE
   SYNTAX     NonReplicated 
   ACCESS     not-accessible
   STATUS     mandatory
   DESCRIPTION
     "This variable represents the index for the mscAtmIfVccVcdTm tables."
::= { mscAtmIfVccVcdTmRowStatusEntry 10 }

mscAtmIfVccVcdTmProvTable OBJECT-TYPE
   SYNTAX     SEQUENCE OF MscAtmIfVccVcdTmProvEntry
   ACCESS     not-accessible
   STATUS     mandatory
   DESCRIPTION
     "This group contains traffic related provisionable attributes for the 
      Vcc, Vpc, and Vpt components. Changing any of the attributes in 
      this group causes a service interruption on the Vcc, Vpc, or Vpt 
      component."
::= { mscAtmIfVccVcdTm 100 }

mscAtmIfVccVcdTmProvEntry OBJECT-TYPE
   SYNTAX     MscAtmIfVccVcdTmProvEntry
   ACCESS     not-accessible
   STATUS     mandatory
   DESCRIPTION
     "An entry in the mscAtmIfVccVcdTmProvTable."
   INDEX {
      mscAtmIfIndex,
      mscAtmIfVccIndex,
      mscAtmIfVccVcdIndex,
      mscAtmIfVccVcdTmIndex }
::= { mscAtmIfVccVcdTmProvTable 1 }

MscAtmIfVccVcdTmProvEntry ::= SEQUENCE {
   mscAtmIfVccVcdTmTxTrafficDescType
      INTEGER,
   mscAtmIfVccVcdTmFwdQosClass
      INTEGER,
   mscAtmIfVccVcdTmTxQueueLimit
      Unsigned32,
   mscAtmIfVccVcdTmHoldingPriority
      INTEGER,
   mscAtmIfVccVcdTmRxTrafficDescType
      INTEGER,
   mscAtmIfVccVcdTmBwdQosClass
      INTEGER,
   mscAtmIfVccVcdTmAtmServiceCategory
      INTEGER,
   mscAtmIfVccVcdTmTrafficShaping
      INTEGER,
   mscAtmIfVccVcdTmUnshapedTransmitQueueing
      INTEGER,
   mscAtmIfVccVcdTmWeight
      Unsigned32,
   mscAtmIfVccVcdTmForceTagging
      INTEGER,
   mscAtmIfVccVcdTmUsageParameterControl
      INTEGER,
   mscAtmIfVccVcdTmBearerClassBbc
      INTEGER,
   mscAtmIfVccVcdTmTransferCapabilityBbc
      INTEGER,
   mscAtmIfVccVcdTmClippingBbc
      INTEGER,
   mscAtmIfVccVcdTmBestEffort
      INTEGER,
   mscAtmIfVccVcdTmTxPacketWiseDiscard
      INTEGER,
   mscAtmIfVccVcdTmRxPacketWiseDiscard
      INTEGER,
   mscAtmIfVccVcdTmAbrConnectionType
      INTEGER }

mscAtmIfVccVcdTmTxTrafficDescType OBJECT-TYPE
   SYNTAX     INTEGER  {
                 n1(1),
                 n2(2),
                 n3(3),
                 n4(4),
                 n5(5),
                 n6(6),
                 n7(7),
                 n8(8),
                 n9(9) }
   ACCESS     read-write
   STATUS     mandatory
   DESCRIPTION
     "This attribute specifies the type of traffic management which is 
      applied to the transmit direction of this connection as defined in the 
      ATM Forum. The txTrafficDescType determines the number and 
      meaning of the parameters in the txTrafficDescParm attribute.
      
      This attribute can have a value of 9 if and only if the 
      atmServiceCategory is availableBitRate."
   DEFVAL     { n1 }
::= { mscAtmIfVccVcdTmProvEntry 10 }

mscAtmIfVccVcdTmFwdQosClass OBJECT-TYPE
   SYNTAX     INTEGER  {
                 n0(0),
                 n1(1),
                 n2(2),
                 n3(3),
                 n4(4) }
   ACCESS     read-write
   STATUS     mandatory
   DESCRIPTION
     "This attribute specifies the quality of service for the forward 
      direction for this connection. This attribute is only used for SPVC 
      connections.
      
      Class 1 supports a QOS that meets Service Class A performance 
      requirements (circuit emulation, constant bit rate video).
      
      Class 2 supports a QOS that meets Service Class B performance 
      requirements (variable bit rate audio and video).
      
      Class 3 supports a QOS that meets Service Class C performance 
      requirements (Connection-Oriented Data Transfer).
      
      Class 4 supports a QOS that meets Service Class D performance 
      requirements (Connectionless Data Transfer).
      
      Class 0 is the unspecified bit rate QOS class; no objective is 
      specified for the performance parameters."
   DEFVAL     { n0 }
::= { mscAtmIfVccVcdTmProvEntry 21 }

mscAtmIfVccVcdTmTxQueueLimit OBJECT-TYPE
   SYNTAX     Unsigned32 (0 | 5..512000)
   ACCESS     read-write
   STATUS     mandatory
   DESCRIPTION
     "This attribute specifies an override to the default transmit queue 
      limit for this connection. An value other than sameAsCa may be 
      specified only for ATM IP and 1pOC48SmSrAtm cards. This 
      attribute is not applicable for basic Vpts.
      
      A value of sameAsCa means to use the default common or per-VC 
      transmit queue limit as defined by the CA service category for this 
      connection. 
      
      A value from 5 to 63,488 indicates that a specific transmit queue 
      limit is requested which differs from the default which is defined 
      under the CA component for this service category. A specific value 
      is ignored for connections where common queuing is specified for 
      the service category. 
      
      For the 1pOC48SmSrAtm card, this attribute is used to set the per 
      VC utilization limit.
      
      The actual transmit queue limit for a connection is visible in the Vcc 
      Tm, Vpc Tm or Vpt txQueueThresholds attribute.

      VALUES (

      0 = sameAsCa

      )"
   DEFVAL     { 0 }
::= { mscAtmIfVccVcdTmProvEntry 22 }

mscAtmIfVccVcdTmHoldingPriority OBJECT-TYPE
   SYNTAX     INTEGER  {
                 n0(0),
                 n1(1),
                 n2(2),
                 n3(3),
                 n4(4) }
   ACCESS     read-write
   STATUS     mandatory
   DESCRIPTION
     "This attribute specifies the holding priority of this connection. In a 
      situation where the link bandwidth fluctuates, such as over an IMA 
      link, holding priority is used to determine which connections are 
      held and which are released. Holding priority 4 connections are the 
      first to be released. Holding priority 0 connections are the last to be 
      released. This value provisioned in the Vcd or Vpd may be 
      overridden by certain applications, for example Vcc Test, which run 
      over this connection. The default holding priority for a provisioned 
      connection is higher then default holding priorities for dynamic 
      (SVC) connections. 
      
      This attribute is not applicable for Vpt Vccs."
   DEFVAL     { n2 }
::= { mscAtmIfVccVcdTmProvEntry 25 }

mscAtmIfVccVcdTmRxTrafficDescType OBJECT-TYPE
   SYNTAX     INTEGER  {
                 n1(1),
                 n2(2),
                 n3(3),
                 n4(4),
                 n5(5),
                 n6(6),
                 n7(7),
                 n8(8),
                 n9(9),
                 sameAsTx(15) }
   ACCESS     read-write
   STATUS     mandatory
   DESCRIPTION
     "This attribute specifies the type of traffic management which is 
      applied to the receive direction of this connection as defined in the 
      ATM Forum. The rxTrafficDescType determines the number and 
      meaning of the parameters in the rxTrafficDescParm attribute.
      
      When this attribute is set to sameAsTx, the rxTrafficDescType as 
      well as the rxTrafficDescParm are taken from the 
      txTrafficDescType and txTrafficDescParm values."
   DEFVAL     { sameAsTx }
::= { mscAtmIfVccVcdTmProvEntry 30 }

mscAtmIfVccVcdTmBwdQosClass OBJECT-TYPE
   SYNTAX     INTEGER  {
                 n0(0),
                 n1(1),
                 n2(2),
                 n3(3),
                 n4(4),
                 sameAsFwd(15) }
   ACCESS     read-write
   STATUS     mandatory
   DESCRIPTION
     "This attribute specifies the quality of service for the backward 
      direction for this connection. This attribute is only used for SPVC 
      connections.
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified bit rate QOS class; no objective is 
      specified for the performance parameters.
      
      The sameAsFwd selection sets the backward quality of service to 
      be the same as the forward quality of service."
   DEFVAL     { sameAsFwd }
::= { mscAtmIfVccVcdTmProvEntry 41 }

mscAtmIfVccVcdTmAtmServiceCategory OBJECT-TYPE
   SYNTAX     INTEGER  {
                 unspecifiedBitRate(0),
                 constantBitRate(1),
                 rtVariableBitRate(2),
                 nrtVariableBitRate(3),
                 availableBitRate(4),
                 derivedFromBBC(15) }
   ACCESS     read-write
   STATUS     mandatory
   DESCRIPTION
     "This attribute specifies the ATM service category for both directions 
      of the connection. 
      
      The value derivedFromBBC may only be used if the SrcPvc 
      component is provisioned under this Vcc. Otherwise a specific 
      ATM service category must be specified. 
      
      If this attribute is set to derivedFromBBC, the Broadband Bearer 
      Capability (BBC) and bestEffort attributes are used to determine the 
      atmServiceCategory of this connection. 
      
      If this attribute is set to other than derivedFromBBC, the value of 
      this attribute is used to override the provisioned BBC Information 
      Element parameters. In those cases, the BBC attributes are not used. 
      
      The constantBitRate service category is intended for real time 
      applications, that is those requiring tightly constrained delay and 
      delay variation, as would be appropriate for voice and video 
      applications. The consistent availability of a fixed quantity of 
      bandwidth is considered appropriate for CBR service. Cells which 
      are delayed beyond the value specified by Cell Transfer Delay are 
      assumed to be of significantly reduced value to the application.
      
      The rtVariableBitRate service category is intended for real time 
      applications, that is those requiring tightly constrained delay and 
      delay variation, as would be appropriate for voice and video 
      applications. Sources are expected to transmit at a rate which varies 
      with time. Equivalently, the source can be described as 'bursty'. 
      Cells which are delayed beyond the value specified by CTD are 
      assumed to be of significantly reduced value to the application. Real 
      time VBR service may support statistical multiplexing of real time 
      sources.
      
      The nrtVariableBitRate service category is intended for non-real 
      time applications which have bursty traffic characteristics and which 
      can be characterized in terms of a PCR, SCR, and MBS. For those 
      cells which are transferred within the traffic contract, the application 
      expects a low cell loss ratio. For all connections, it expects a bound 
      on the mean cell transfer delay. Non-real time VBR service may 
      support statistical multiplexing of connections. 
      
      The availableBitRate service is an ATM layer service category for 
      which the limiting ATM layer transfer characteristics provided by 
      the network may change subsequent to connection establishment. 
      ABR service has a flow control mechanism which supports several 
      types of feedback to control the source rate in response to changing 
      ATM layer transfer characteristics. ABR service is not intended to 
      support real-time applications. 
      
      The unspecifiedBitRate service is intended for non-real time 
      applications; that is, those not requiring tightly constrained delay 
      and delay variation. UBR sources are expected to be bursty. UBR 
      service supports a high degree of statistical multiplexing among 
      sources. UBR service does not specify traffic related service 
      guarantees. No numerical commitments are made with respect to 
      the cell loss ratio experienced by a UBR connection, or as to the 
      cell transfer delay experienced by cells on the connection."
   DEFVAL     { unspecifiedBitRate }
::= { mscAtmIfVccVcdTmProvEntry 42 }

mscAtmIfVccVcdTmTrafficShaping OBJECT-TYPE
   SYNTAX     INTEGER  {
                 disabled(1),
                 sameAsCa(2) }
   ACCESS     read-write
   STATUS     mandatory
   DESCRIPTION
     "This attribute specifies whether this connection uses traffic shaping 
      when transmitting traffic to the ATM interface.
      
      This attribute is ignored if the atmServiceCategory is 
      availableBitRate.
      
      Traffic shaping is not available on the 1pOC12SmLrAtm card, 
      therefore this attribute is ignored.
      
      When sameAsCa is selected, traffic shaping for the connection is 
      based on the trafficShaping attribute of the connection's service 
      category component under the CA. If the service category has 
      trafficShaping set to enabled or inverseUpc, then traffic shaping is 
      enabled for the connection. Note that enabling traffic shaping may 
      have no effect under certain cases. These cases are listed in the 
      description of the trafficShaping operational attribute, which is 
      under the Vcc Tm, Vpc Tm, or Vpt Tm components.
      
      When disabled is selected, traffic shaping for this connection is 
      disabled regardless of the provisioning of the connection's service 
      category component."
   DEFVAL     { sameAsCa }
::= { mscAtmIfVccVcdTmProvEntry 50 }

mscAtmIfVccVcdTmUnshapedTransmitQueueing OBJECT-TYPE
   SYNTAX     INTEGER  {
                 common(1),
                 sameAsCa(3) }
   ACCESS     read-write
   STATUS     mandatory
   DESCRIPTION
     "This attribute only applies when this connection is unshaped. This 
      attribute specifies the transmit queueing method for this connection 
      if it is unshaped. The two possible methods are per-VC queuing and 
      common queuing. 
      
      On ATM IP FPs, this attribute must be set to sameAsCa. 
      
      This attribute is ignored in the following situations:
      - if the connection has trafficShaping enabled or inverseUpc, or 
      - if the atmServiceCategory is availableBitRate, or
      - if the atmServiceCategory is constantBitRate and this is a CQC-
      based ATM FP.
      - for basic Vpts and standard Vpt Vccs
      
      When this attribute is set to sameAsCa, the transmit queueing 
      method for the connection is based on the 
      unshapedTransmitQueueing attribute of the connection's service 
      category component under the CA. 
      
      When this attribute is set to common, transmit traffic on this 
      unshaped connection is destined for the common queue."
   DEFVAL     { sameAsCa }
::= { mscAtmIfVccVcdTmProvEntry 60 }

mscAtmIfVccVcdTmWeight OBJECT-TYPE
   SYNTAX     Unsigned32 (0 | 1..4095 | 65535)
   ACCESS     read-write
   STATUS     mandatory
   DESCRIPTION
     "This attribute specifies an override for the weight of this unshaped 
      connection. This attribute is ignored for shaped connections, for 
      ABR connections, for connections on a CQC-based ATM FP and 
      basic Vpts.
      
      When the value is set to sameAsCa, the weight is determined by the 
      fairnessWeight attribute under the CA service category component 
      for all but standard Vpt Vccs. For standard Vpt Vccs, the weight is 
      determined by the Vcc's service category, when the value is set to 
      sameAsCa.
      
      When this attribute is set to a value from 1 to 4095, that value is 
      used for the fairness weight of this connection relative to other 
      connections. For all but standard Vpt Vccs, fairness weight 
      determines the proportion of transmit cell opportunities which are 
      allocated to this connection, compared to other connections in the 
      same service category. For standard Vpt Vccs, fairness weight 
      determines the proportion of transmit cell opportunities which are 
      allocated to this connection, compared to other connections 
      associated with the Vpt.
      
      When the value is set to upToQueueLimit, the fairness weight is 
      limited only by the txQueueLimit.

      VALUES (

      0 = upToQueueLimit

      65535 = sameAsCa

      )"
   DEFVAL     { 65535 }
::= { mscAtmIfVccVcdTmProvEntry 61 }

mscAtmIfVccVcdTmForceTagging OBJECT-TYPE
   SYNTAX     INTEGER  {
                 enabled(0),
                 disabled(1),
                 sameAsCa(2) }
   ACCESS     read-write
   STATUS     mandatory
   DESCRIPTION
     "This attribute specifies whether force tagging is enforced for this 
      connection for cells in the transmit direction. 
      
      On CQC-based ATM cards and for Vpts, this attribute is not 
      applicable and is ignored. 
      
      When the value is set to sameAsCa, the force tagging functionality 
      is determined by the forceTagging attribute under the CA service 
      category component. 
      
      When the value is set to enabled, force tagging is enabled for cells 
      in the transmit direction on this connection. When this option is 
      selected, the CLP bit is set to 1 for all cells in the transmit direction. 
      Cells which are tagged are counted in the txCellClp attribute. 
      
      When the value is set to disabled, force tagging is disabled for cells 
      in the transmit direction on this connection. When this option is 
      selected, the CLP bit is unchanged for cells in the transmit 
      direction."
   DEFVAL     { sameAsCa }
::= { mscAtmIfVccVcdTmProvEntry 62 }

mscAtmIfVccVcdTmUsageParameterControl OBJECT-TYPE
   SYNTAX     INTEGER  {
                 enforced(0),
                 disabled(1),
                 sameAsCa(2),
                 monitored(4) }
   ACCESS     read-write
   STATUS     mandatory
   DESCRIPTION
     "This attribute specifies whether this connection enforces usage 
      parameter control when receiving traffic from the ATM interface.
      
      When sameAsCa is selected, UPC for the connection is based on 
      the usageParameterControl attribute of the service category 
      component under the AtmIf CA. If the service category has UPC 
      enforced or monitored, then UPC is set to that value for the 
      connection. 
      
      When disabled is selected, UPC for this connection is disabled 
      regardless of the provisioning of the service category. 
      
      When enforced is selected, UPC for this connection is enforced 
      regardless of the provisioning of the service category. 
      
      Note that setting UPC to enforced or monitored may have no effect 
      under certain cases. These cases are listed in the description of the 
      usageParameterControl operational attribute, which is under the 
      Vcc, Vpc, and Vpt components."
   DEFVAL     { sameAsCa }
::= { mscAtmIfVccVcdTmProvEntry 70 }

mscAtmIfVccVcdTmBearerClassBbc OBJECT-TYPE
   SYNTAX     INTEGER  {
                 a(1),
                 c(3),
                 x(16),
                 vp(24),
                 derivedFromServiceCategory(31) }
   ACCESS     read-write
   STATUS     mandatory
   DESCRIPTION
     "This attribute specifies the bearer capability. This attribute is only 
      used for SPVC and SPVP connections. It is one of the Broadband 
      Bearer Capability (BBC) attributes. The purpose of the BBC 
      information element is to indicate a requested broadband 
      connection-oriented bearer service to be provided by the network.
      
      The value derivedFromServiceCategory specifies that the actual 
      value which is used for this connection is derived from the value of 
      the atmServiceCategory. Either, this attribute must be set to 
      derivedFromServiceCategory, or the atmServiceCategory attribute 
      must be set to derivedFromBBC, but not both.
      
      Class a service is a connection-oriented, constant bit rate ATM 
      transport service. Class a service has end to end timing 
      requirements and may require stringent cell loss, cell delay and cell 
      delay variation performance.When a is set, the user is requesting 
      more than an ATM only service. The network may look at the AAL 
      to provide interworking based upon its contents. 
      
      Class c service is a connection-oriented, variable bit rate ATM 
      transport service. Class c service has no end-to-end timing 
      requirements. When c is set, the user is requesting more than an 
      ATM only service. The network interworking function may look at 
      the AAL and provide service based on it.
      
      Class x service is a connection-oriented ATM transport service 
      where the AAL, trafficType (vbr or cbr) and timing requirements 
      are user defined (that is, transparent to the network).When x is set 
      the user is requesting an ATM only service from the network. In this 
      case, the network shall not process any higher layer protocol.
      
      Class vp service is used to specify a transparent VP service. When 
      the value of this attribute is vp, the user is requesting an ATM only 
      service from the network. In this case, the network shall not process 
      any higher layer protocol. This service differs from class x service 
      in that with the class vp service both the VCI field (except or VCI 
      values 0, 3, 4, and 6 through 15) and Payload Type field are 
      transported transparently by the network. This attribute value is 
      only applicable to SPVP connections."
   DEFVAL     { derivedFromServiceCategory }
::= { mscAtmIfVccVcdTmProvEntry 71 }

mscAtmIfVccVcdTmTransferCapabilityBbc OBJECT-TYPE
   SYNTAX     INTEGER  {
                 n0(0),
                 n1(1),
                 n2(2),
                 n5(5),
                 n8(8),
                 n9(9),
                 n10(10),
                 notApplicable(30),
                 derivedFromServiceCategory(31) }
   ACCESS     read-write
   STATUS     mandatory
   DESCRIPTION
     "This attribute specifies the transfer capability for this connection. 
      Uni 3.0/3.1 traffic type and end-to-end timing parameters are 
      mapped into this parameter as follows:
      <transferCapability: TrafficType, Timing>
      0: NoIndication, NoIndication
      1: NoIndication, yes
      2: NoIndication, no
      5: CBR, yes
      8: VBR, NoIndication
      9: VBR, yes
      10: VBR, no
      
      notApplicable specifies that the user does not want to specify the 
      transfer capability.
      
      The CBR traffic type refers to traffic offered on services such as a 
      constant bit rate video service or a circuit emulation.
      The VBR traffic type refers to traffic offered on services such as 
      packetized audio and video, or data.
      
      The value no indication for traffic type is used if the user has not set 
      the traffic type; similarly for end-to-end timing.
      
      The value yes for end-to-end timing indicates that end-to-end 
      timing is required.
      
      The value no for end-to-end timing indicates that end-to-end timing 
      is not required.
      
      The value derivedFromServiceCategory specifies that the actual 
      value which is used for this connection is derived from the value of 
      the atmServiceCategory. Either, this attribute must be set to 
      derivedFromServiceCategory, or the atmServiceCategory attribute 
      must be set to derivedFromBBC, but not both."
   DEFVAL     { derivedFromServiceCategory }
::= { mscAtmIfVccVcdTmProvEntry 72 }

mscAtmIfVccVcdTmClippingBbc OBJECT-TYPE
   SYNTAX     INTEGER  {
                 no(0),
                 yes(1) }
   ACCESS     read-write
   STATUS     mandatory
   DESCRIPTION
     "This attribute specifies the value for the clipping susceptibility 
      parameter in the BBC Information Element. This attribute is only 
      used for SPVC connections. It is one of the Broadband Bearer 
      Capability attributes.
      
      Clipping is an impairment in which the first fraction of a second of 
      information to be transferred is lost. It occurs after a call is 
      answered and before an associated connection is switched through."
   DEFVAL     { no }
::= { mscAtmIfVccVcdTmProvEntry 74 }

mscAtmIfVccVcdTmBestEffort OBJECT-TYPE
   SYNTAX     INTEGER  {
                 indicated(0),
                 notIndicated(1),
                 derivedFromServiceCategory(15) }
   ACCESS     read-write
   STATUS     mandatory
   DESCRIPTION
     "This attribute specifies the value of the best effort parameter in the 
      ATM Traffic Descriptor Information Element. This attribute is only 
      used for Soft PVC connections. It is one of the Broadband Bearer 
      Capability attributes.
      
      The value indicated implies that the quality of service for this 
      connection is not guaranteed.
      
      The value notIndicated implies that the quality of service for this 
      connection is guaranteed.
      
      The value derivedFromServiceCategory specifies that the actual 
      value which is used for this connection is derived from the value of 
      the atmServiceCategory. Either, this attribute must be set to 
      derivedFromServiceCategory, or the atmServiceCategory attribute 
      must be set to derivedFromBBC, but not both."
   DEFVAL     { derivedFromServiceCategory }
::= { mscAtmIfVccVcdTmProvEntry 75 }

mscAtmIfVccVcdTmTxPacketWiseDiscard OBJECT-TYPE
   SYNTAX     INTEGER  {
                 disabled(0),
                 enabled(1) }
   ACCESS     read-write
   STATUS     mandatory
   DESCRIPTION
     "This attribute specifies whether packet-wise discard functions are to 
      be enabled or disabled in the transmit data direction for this 
      connection. Packet-wise discard functions should only be requested 
      if this connection is transferring AAL5 frame traffic. This attribute 
      is not applicable for Vpts.
      
      Packet-wise functions increase the 'goodput' of the link. The 
      transmit packet-wise functions are Early Packet Discard (EPD) and 
      Partial Packet Discard (PPD). 
      
      EPD allows the connection to discard an entire frame once the 
      transmit queue has reached the EPD threshold. EPD increases the 
      'goodput' of a link, since discarding an entire frame means that 
      some queue capacity is guarded for some other frame which is 
      already partially transmitted. All cells of the frame are discarded 
      from the Beginning of Message (BOM) cell up to and including the 
      End of Message (EOM) cell. 
      
      PPD allows the connection to discard the remainder of a cell-
      forwarded AAL5 frame if one cell of this frame has been discarded. 
      All cells are discarded up to but not including the EOM cell. The 
      PPD function increases the 'goodput' of the link, since cells which 
      are only going to be discarded at the AAL5 reassembly point are 
      not transmitted.
      
      On CQC-based ATM cards, the packet-wise discard functions are 
      PPD and EPD. PPD is available at VCC cell-transfer points. PPD is 
      not applicable at frame-cell conversion points, and is not applicable 
      for Vpcs. PPD is configured by this attribute. Packet-wise discard 
      should only be enabled for connections carrying AAL5 
      segmentation traffic. Setting the value to enabled for any other 
      traffic type may result in all traffic being discarded. On CQC-based 
      ATM FPs, EPD is automatically enabled at frame-to-cell conversion 
      points, independent of the setting of this attribute. 
      
      On CQC-based ATM cards, at a permanent VCC connection 
      endpoint, this attribute is not applicable and is ignored. If AAL5 
      segmentation and reassembly has been requested, PPD and Early 
      Packet Discard (EPD) are automatically enabled.
      
      On ATM IP cards, packet-wise discard functions include EPD and 
      PPD. PPD and EPD apply to individual VCCs and VCCs within 
      VPCs at all connection points, including tandem VPC connections. 
      Both PPD and EPD are controlled by this attribute. This attribute 
      may safely be set to enabled for any connection (Vcc or Vpc) on 
      ATM IP FPs since they have the ability to automatically detect 
      AAL5-segmented traffic on a connection, and only enable packet-
      wise discards if AAL5-segmented traffic is detected.
      
      When this attribute is set to enabled, packet-wise discard functions 
      are applied to transmit traffic at this connection point. When this 
      attribute is set to disabled, packet-wise discard functions are not 
      applied to transmit traffic at this connection point.
      
      At a SPVC origin on a PNNI interface, a value of enabled specifies 
      that frame discard is requested in the backward direction. When this 
      attribute is set to disabled, backward frame discard is not requested 
      in the SPVC call setup. 
      
      The transmit packet-wise discard functions that are active are 
      visible in the Vcc/Vpc Tm txPacketWiseDiscard operational 
      attribute."
   DEFVAL     { disabled }
::= { mscAtmIfVccVcdTmProvEntry 76 }

mscAtmIfVccVcdTmRxPacketWiseDiscard OBJECT-TYPE
   SYNTAX     INTEGER  {
                 disabled(0),
                 enabled(1) }
   ACCESS     read-write
   STATUS     mandatory
   DESCRIPTION
     "This attribute specifies whether packet-wise discard functions are to 
      be enabled or disabled in the receive data direction for this 
      connection. Packet-wise discard functions should only be requested 
      if this connection is transferring AAL5 frame traffic. This attribute 
      is not applicable for Vpts.
      
      Packet-wise functions increase the 'goodput' of the link. The 
      receive packet-wise function is Partial Packet Discard (PPD). 
      
      PPD allows the connection to discard the remainder of a cell-
      forwarded AAL5 frame if one cell of this frame has been discarded, 
      for example due to UPC. All cells are discarded up to but not 
      including the EOM cell. The PPD function increases the 'goodput' 
      of the link, since cells which are only going to be discarded at the 
      AAL5 reassembly point are not transmitted.
      
      PPD is available at all VCC connection points where UPC may be 
      activated. PPD is not applicable for Vpcs. 
      
      On CQC-based ATM FPs, packet-wise discards should only be 
      enabled for connections carrying AAL5 segmentation traffic. 
      Setting the value to enabled for any other traffic type may result in 
      traffic being discarded. 
      
      On CQC-based ATM cards, at a permanent VCC connection 
      endpoint, this attribute is not applicable and is ignored. If AAL5 
      segmentation and reassembly has been requested, PPD and Early 
      Packet Discard (EPD) are automatically enabled.
      
      On ATM IP cards, this attribute may safely be set to enabled for any 
      connection (Vcc or Vpc) since they have the ability to automatically 
      detect AAL5-segmented traffic on a connection, and only enables 
      packet-wise discards if AAL5-segmented traffic is detected.
      
      When this attribute is set to enabled, packet-wise discard functions 
      are applied to receive traffic at this connection point. When this 
      attribute is set to disabled, packet-wise discard functions are not 
      applied to receive traffic at this connection point.
      
      At a SPVC origin on a PNNI interface, a value of enabled specifies 
      that frame discard is requested in the forward direction. When this 
      attribute is set to disabled, forward frame discard is not requested in 
      the SPVC call setup. 
      
      The receive packet-wise discard functions that are active are visible 
      in the Vcc/Vpc Tm rxPacketWiseDiscard operational attribute."
   DEFVAL     { disabled }
::= { mscAtmIfVccVcdTmProvEntry 78 }

mscAtmIfVccVcdTmAbrConnectionType OBJECT-TYPE
   SYNTAX     INTEGER  {
                 abrSwitch(0),
                 virtualSourceDest(3),
                 sourceDest(4),
                 nonAbrInterworking(5),
                 sameAsCa(14) }
   ACCESS     read-write
   STATUS     mandatory
   DESCRIPTION
     "This attribute specifies the type of ABR behavior which is to be 
      enforced at this connection. This attribute is only applicable if the 
      atmServiceCategory attribute is availableBitRate. If the 
      atmServicecategory attribute is not availableBitRate, this attribute 
      value is ignored.
      
      The actual ABR functionality which is in effect is visible in the 
      Vcc/Vpc/Vpt Tm abrConnectionType operational attribute.
      
      For CQC-based ATM cards, the only allowable values are 
      sameAsCa, nonAbrInterworking or abrSwitch. If abrSwitch is 
      selected, the CQC implements EFCI marking behavior.
      
      For the 1pOC12SmLrAtm card, the only allowable values are 
      sameAsCa or abrSwitch. If abrSwitch is selected, EFCI marking 
      behavior is implemented.
      
      sameAsCa is used to request the default behavior as specified in the 
      CA Abr component for this Vcc. Otherwise, this attribute overrides 
      the default behavior. 
      
      virtualSourceDest is used to request that this connection point 
      function as a virtual source/virtual destination. VS/VD functionality 
      is only supported on ATM IP FPs.
      
      sourceDest requires that this connection point function as a S/D for 
      RM cells. S/D mode is automatically invoked at this connection 
      point either if this is a connection end point, or if the next hop 
      connection point is configured as nonAbrInterworking.
      
      nonAbrInterworking is used to request that this connection point 
      function as an interworking between ABR and non-ABR service 
      categories. This means that there are no RM cells on the link side of 
      this connection, and that the next hop connection point is 
      performing as an ABR sourceDest.
      
      abrSwitch is used to request ABR switch behavior for this 
      connection point. The ABR switch behavior is first, to confirm to 
      virtualSourceDest or nonAbrInterworking setting on the next hop, 
      and otherwise to implement ABR ER switch behavior. For CQC-
      based FPs, ABR switch behavior is implemented as EFCI marking."
   DEFVAL     { sameAsCa }
::= { mscAtmIfVccVcdTmProvEntry 90 }

mscAtmIfVccVcdTmTxTdpTable OBJECT-TYPE
   SYNTAX     SEQUENCE OF MscAtmIfVccVcdTmTxTdpEntry
   ACCESS     not-accessible
   STATUS     mandatory
   DESCRIPTION
     "This attribute is a vector of five traffic parameters whose meanings 
      are defined by the txTrafficDescType attribute. 
      
      The values of peak cell rate (PCR), sustained cell rate (SCR), 
      Minimum Cell Rate (MCR) and requested shaping rate are 
      expressed in cell/s. Maximum burst size (MBS) is expressed in 
      cells. CDVT is expressed in microseconds. The values of PCR, 
      SCR, MCR, MBS and CDVT are used for connection admission 
      control (CAC). The value of CDVT is only used for connections 
      where the atmServiceCategory is constantBitRate. For all other 
      values of atmServiceCategory, CDVT is ignored. The values of 
      PCR, SCR, MCR and requested shaping rate are used to determine 
      the actual shaping rate where traffic shaping is enabled.
      
      When txTrafficDescType is 1 or 2, all of the parameters must be set 
      to zero.
      
      When txTrafficDescType is 3, parameter 1 represents the PCR for 
      CLP equal to 0 and 1 traffic; parameter 4 represents the CDVT; and 
      parameter 5 represents the requested shaping rate. A non-zero value 
      in parameter 5 overrides any value in parameter 1. This result is 
      used as the PCR. Parameter 1 must be non-zero. Parameters 2 and 3 
      must be zero.
      
      When txTrafficDescType is 4, parameter 1 represents the PCR for 
      CLP equal to 0 and 1 traffic with cell discard; parameter 2 
      represents the PCR for CLP equal to 0 traffic; parameter 4 
      represents the CDVT; and parameter 5 represents the requested 
      shaping rate. A non-zero value in parameter 5 overrides any value in 
      parameter 1. This result is used as the PCR. Parameter 1 must be 
      greater than or equal to parameter 2. Parameters 1 and 2 must be 
      non-zero. Parameter 3 must be zero.
      
      When txTrafficDescType is 5, parameter 1 represents the PCR for 
      CLP equal to 0 and 1 traffic with cell tagging; parameter 2 
      represents the PCR for CLP equal to 0 traffic; parameter 4 
      represents the CDVT; and parameter 5 represents the requested 
      shaping rate. A non-zero value in parameter 5 overrides any value in 
      parameter 1. This result is used as the PCR. Parameter 1 must be 
      greater than or equal to parameter 2. Parameters 1 and 2 must be 
      non-zero. Parameter 3 must be zero.
      
      When txTrafficDescType is 6, parameter 1 represents the PCR for 
      CLP equal to 0 and 1 traffic; parameter 2 represents the SCR for 
      CLP equal to 0 and 1 traffic; parameter 3 represents the MBS for 
      CLP equal to 0 and 1 traffic; parameter 4 represents the CDVT; and 
      parameter 5 represents the requested shaping rate. A non-zero value 
      in parameter 5 overrides any value in parameter 1. This result is 
      used as the PCR. Parameters 1, 2 and 3 must be non-zero. 
      Parameter 1 must be greater than or equal to parameter 2. Parameter 
      5, must either be zero (unused) or greater than or equal to parameter 
      2.
      
      When txTrafficDescType is 7, parameter 1 represents the PCR for 
      CLP equal to 0 and 1 traffic; parameter 2 represents the SCR for 
      CLP equal to 0 with cell discard; parameter 3 represents the MBS 
      for CLP equal to 0 traffic; parameter 4 represents the CDVT; and 
      parameter 5 represents the requested shaping rate. A non-zero value 
      in parameter 5 overrides any value in parameter 1. This result is 
      used as the PCR. Parameters 1, 2 and 3 must be non-zero. 
      Parameter 1 must be greater than or equal to parameter 2. Parameter 
      5, must either be zero (unused) or greater than or equal to parameter 
      2.
      
      When txTrafficDescType is 8, parameter 1 represents the PCR for 
      CLP equal to 0 and 1 traffic; parameter 2 represents the SCR for 
      CLP equal to 0 traffic with cell tagging; parameter 3 represents the 
      MBS for CLP equal to 0 traffic; parameter 4 represents the CDVT; 
      and parameter 5 represents the requested shaping rate. A non-zero 
      value in parameter 5 overrides any value in parameter 1. This result 
      is used as the PCR. Parameters 1, 2 and 3 must be non-zero. 
      Parameter 1 must be greater than or equal to parameter 2. Parameter 
      5, must either be zero (unused) or greater than or equal to parameter 
      2.
      
      When txTrafficDescType is 9, parameter 1 represents the PCR; 
      parameter 2 represents the CDVT; parameter 3 represents the MCR; 
      parameter 4 and parameter 5 represent are not used and must be 
      zero. Parameter 1 must be non-zero and must be greater than or 
      equal to parameter 3. Parameter 3 may be optionally zero.
      
      Whenever it is valid for PCR to be specified, parameter 5 may also 
      be used to specify a requested shaping rate. A non-zero value in 
      parameter 5 overrides the value in parameter 1 and is used as the 
      peak cell rate in calculations of CAC and shaping rate. When the 
      atmServiceCategory is availableBitRate (ABR), the shaping rate is 
      dynamically chosen, based on the ABR flow control mechanism, as 
      a value between the MCR and the PCR or the requested shaping 
      rate if applicable.
      
      For txTrafficDescType 3, 4 and 5, the transmit traffic is shaped at 
      the next available shaping rate less than the PCR. 
      
      For txTrafficDescType 6, 7 and 8 if linear traffic shaping is selected, 
      the transmit traffic is shaped at the highest available rate which is 
      between PCR and SCR. However, if there is no available shaping 
      rate between PCR and SCR, traffic is shaped at the next rate above 
      the PCR. 
      
      For txTrafficDescType 6, 7 and 8 if inverse-UPC traffic shaping is 
      selected, the transmit traffic is shaped at a variable rate which 
      conforms to the PCR, SCR and MBS of the connection traffic 
      descriptor. Inverse-UPC traffic shaping is available only on ATM IP 
      cards."
::= { mscAtmIfVccVcdTm 456 }

mscAtmIfVccVcdTmTxTdpEntry OBJECT-TYPE
   SYNTAX     MscAtmIfVccVcdTmTxTdpEntry
   ACCESS     not-accessible
   STATUS     mandatory
   DESCRIPTION
     "An entry in the mscAtmIfVccVcdTmTxTdpTable."
   INDEX {
      mscAtmIfIndex,
      mscAtmIfVccIndex,
      mscAtmIfVccVcdIndex,
      mscAtmIfVccVcdTmIndex,
      mscAtmIfVccVcdTmTxTdpIndex }
::= { mscAtmIfVccVcdTmTxTdpTable 1 }

MscAtmIfVccVcdTmTxTdpEntry ::= SEQUENCE {
   mscAtmIfVccVcdTmTxTdpIndex
      Integer32,
   mscAtmIfVccVcdTmTxTdpValue
      Unsigned32 }

mscAtmIfVccVcdTmTxTdpIndex OBJECT-TYPE
   SYNTAX     Integer32 (1..5)
   ACCESS     not-accessible
   STATUS     mandatory
   DESCRIPTION
     "This variable represents the mscAtmIfVccVcdTmTxTdpTable
      specific index for the mscAtmIfVccVcdTmTxTdpTable."
::= { mscAtmIfVccVcdTmTxTdpEntry 1 }

mscAtmIfVccVcdTmTxTdpValue OBJECT-TYPE
   SYNTAX     Unsigned32 (0..2147483647)
   ACCESS     read-write
   STATUS     mandatory
   DESCRIPTION
     "This variable represents an individual value for the
      mscAtmIfVccVcdTmTxTdpTable."
::= { mscAtmIfVccVcdTmTxTdpEntry 2 }

mscAtmIfVccVcdTmRxTdpTable OBJECT-TYPE
   SYNTAX     SEQUENCE OF MscAtmIfVccVcdTmRxTdpEntry
   ACCESS     not-accessible
   STATUS     mandatory
   DESCRIPTION
     "This attribute is a vector of four traffic parameters whose meanings 
      are defined by the rxTrafficDescType attribute. The values of peak 
      cell rate (PCR), sustained cell rate (SCR) and Minimum Cell Rate 
      (MCR) are expressed in cell/s. Maximum burst size (MBS) is 
      expressed in cells. The value of CDVT is expressed in 
      microseconds. The values of PCR, SCR, MCR, MBS and CDVT 
      are used for usage parameter control (UPC).
      
      When rxTrafficDescType is 1 or 2, all of the parameters must be set 
      to zero (unused).
      
      When rxTrafficDescType is 3, parameter 1 represents the PCR for 
      CLP equal to 0 and 1 traffic. Parameter 1 must be non-zero. 
      Parameters 2 and 3 must be set to zero (unused).
      
      When rxTrafficDescType is 4, parameter 1 represents the PCR 
      for CLP equal to 0 and 1 traffic; parameter 2 represents the PCR for 
      CLP equal to 0 traffic with cell discard. Parameters 1 and 2 must be 
      non-zero. Parameter 3 must be set to zero (unused). Parameter 1 
      must be greater than or equal to parameter 2.
      
      When rxTrafficDescType is 5, parameter 1 represents the PCR for 
      CLP equal to 0 and 1 traffic; parameter 2 represents the PCR for 
      CLP equal to 0 traffic with cell tagging. Parameters 1 and 2 must be 
      non-zero. Parameter 3 must be set to zero (unused). Parameter 1 
      must be greater than or equal to parameter 2.
      
      When rxTrafficDescType is a 6, parameter 1 represents the PCR for 
      CLP equal to 0 and 1 traffic; parameter 2 represents the SCR for 
      CLP equal to 0 and 1 traffic; parameter 3 represents the MBS for 
      CLP equal to 0 and 1 traffic. Parameters 1, 2 and 3 must be non-
      zero. Parameter 1 must be greater than or equal to Parameter 2. 
      
      When rxTrafficDescType is 7, parameter 1 represents the PCR for 
      CLP equal to 0 and 1 traffic; parameter 2 represents the SCR for 
      CLP equal to 0 traffic with cell discard; parameter 3 represents the 
      MBS for CLP equal to 0 traffic. Parameters 1, 2 and 3 must be non-
      zero. Parameter 1 must be greater than or equal to parameter 2. 
      
      When rxTrafficDescType is 8, parameter 1 represents the PCR for 
      CLP equal to 0 and 1 traffic; parameter 2 represents the SCR for 
      CLP equal to 0 traffic with cell tagging; parameter 3 represents the 
      MBS for CLP equal to 0 traffic. Parameter 1, 2 and 3 must be non-
      zero. Parameter 1 must be greater than or equal to parameter 2.
      
      When rxTrafficDescType is 9, parameter 1 represents the PCR; 
      parameter 2 represents the CDVT; parameter 3 represents the MCR. 
      Parameter 4 is not used and must be zero. Parameter 1,must be non-
      zero and must be greater than or equal to parameter 3. Parameter 3 
      may optionally be zero.
      
      When rxTrafficDescType is any value from 3 through 8, parameter 
      4 represents the CDVT. 
      
      If the value of CDVT either in parameter 2 or in parameter 4 is zero, 
      the CDVT is taken from the CA defaults for the particular 
      atmServiceCategory of this connection.
      
      On a CQC-based ATM card, when rxTrafficDescriptorType is 3 
      through 8, there are certain extreme combinations of 
      rxTrafficDescParm which are outside the capabilities of the UPC 
      hardware. The check prov command detects such cases and 
      generates an error message. If this happens, adjust the parameters 
      until they fall within the supported limits. 
      
      To calculate the limits, use the following formulae:
      I1 = 1 000 000 000 / PCR
      L1 = CDVT * 1000
      I2 = 1,000,000,000 / SCR
      L2 = CDVT + (MBS - 1) * (I2 - I1)
      I1 and I2 must be less than or equal to 335,523,840. I1 + L1 must 
      be less than or equal to 1,342,156,800. I2 + L2 must be less than or 
      equal to 1,342,156,800. Note that I2 and L2 only apply when the 
      rxTrafficDescriptorType is 6 through 8.
      
      If the values of I1, L1, I2 or L2 are closer to the limits described 
      above, a further restriction applies. Specifically, if either:
      I1 > 41,940,480 or
      I2 > 41,940,480 or
      I1 + L1 > 167,769,600 or
      I2 + L2 > 167,769,600
      then both I1 and I2 must be greater than 20,480. 
      
      Parameter 5 of the rxTrafficDescParm is always unused. 
      
      If the rxTrafficDescType is sameAsTx, the values provisioned in 
      this attribute are ignored. The traffic parameters for the receive 
      direction are taken from the txTrafficDescParm."
::= { mscAtmIfVccVcdTm 457 }

mscAtmIfVccVcdTmRxTdpEntry OBJECT-TYPE
   SYNTAX     MscAtmIfVccVcdTmRxTdpEntry
   ACCESS     not-accessible
   STATUS     mandatory
   DESCRIPTION
     "An entry in the mscAtmIfVccVcdTmRxTdpTable."
   INDEX {
      mscAtmIfIndex,
      mscAtmIfVccIndex,
      mscAtmIfVccVcdIndex,
      mscAtmIfVccVcdTmIndex,
      mscAtmIfVccVcdTmRxTdpIndex }
::= { mscAtmIfVccVcdTmRxTdpTable 1 }

MscAtmIfVccVcdTmRxTdpEntry ::= SEQUENCE {
   mscAtmIfVccVcdTmRxTdpIndex
      Integer32,
   mscAtmIfVccVcdTmRxTdpValue
      Unsigned32 }

mscAtmIfVccVcdTmRxTdpIndex OBJECT-TYPE
   SYNTAX     Integer32 (1..5)
   ACCESS     not-accessible
   STATUS     mandatory
   DESCRIPTION
     "This variable represents the mscAtmIfVccVcdTmRxTdpTable
      specific index for the mscAtmIfVccVcdTmRxTdpTable."
::= { mscAtmIfVccVcdTmRxTdpEntry 1 }

mscAtmIfVccVcdTmRxTdpValue OBJECT-TYPE
   SYNTAX     Unsigned32 (0..2147483647)
   ACCESS     read-write
   STATUS     mandatory
   DESCRIPTION
     "This variable represents an individual value for the
      mscAtmIfVccVcdTmRxTdpTable."
::= { mscAtmIfVccVcdTmRxTdpEntry 2 }

mscAtmIfVccVcdTmFqpTable OBJECT-TYPE
   SYNTAX     SEQUENCE OF MscAtmIfVccVcdTmFqpEntry
   ACCESS     not-accessible
   STATUS     mandatory
   DESCRIPTION
     "This attribute is a vector of three elements that specify the quality of 
      service parameters for the forward direction for this connection. 
      This attribute is used for SPVC connections.
      
      The cdv element specifies the acceptable peak-to-peak Cell Delay 
      Variation (CDV) of real-time connections (CBR and rt-VBR). It is 
      signalled through the extended QoS information element.
      
      The ctd specifies the acceptable maximum Cell Transfer Delay 
      (maxCtd) of real-time connections (CBR and rt-VBR). 
      It is signalled through the end to end transit delay information 
      element.
      
      The clr specifies the acceptable Cell Loss Ratio (CLR) of CBR, rt-
      VBR, and nrt-VBR connections. It is signalled through the extended 
      QoS information element."
::= { mscAtmIfVccVcdTm 458 }

mscAtmIfVccVcdTmFqpEntry OBJECT-TYPE
   SYNTAX     MscAtmIfVccVcdTmFqpEntry
   ACCESS     not-accessible
   STATUS     mandatory
   DESCRIPTION
     "An entry in the mscAtmIfVccVcdTmFqpTable."
   INDEX {
      mscAtmIfIndex,
      mscAtmIfVccIndex,
      mscAtmIfVccVcdIndex,
      mscAtmIfVccVcdTmIndex,
      mscAtmIfVccVcdTmFqpIndex }
::= { mscAtmIfVccVcdTmFqpTable 1 }

MscAtmIfVccVcdTmFqpEntry ::= SEQUENCE {
   mscAtmIfVccVcdTmFqpIndex
      INTEGER,
   mscAtmIfVccVcdTmFqpValue
      Unsigned32 }

mscAtmIfVccVcdTmFqpIndex OBJECT-TYPE
   SYNTAX     INTEGER  {
                 cdv(0),
                 ctd(1),
                 clr(2) }
   ACCESS     not-accessible
   STATUS     mandatory
   DESCRIPTION
     "This variable represents the mscAtmIfVccVcdTmFqpTable
      specific index for the mscAtmIfVccVcdTmFqpTable."
::= { mscAtmIfVccVcdTmFqpEntry 1 }

mscAtmIfVccVcdTmFqpValue OBJECT-TYPE
   SYNTAX     Unsigned32 (0..2147483647)
   ACCESS     read-write
   STATUS     mandatory
   DESCRIPTION
     "This variable represents an individual value for the
      mscAtmIfVccVcdTmFqpTable."
::= { mscAtmIfVccVcdTmFqpEntry 2 }

mscAtmIfVccVcdTmBqpTable OBJECT-TYPE
   SYNTAX     SEQUENCE OF MscAtmIfVccVcdTmBqpEntry
   ACCESS     not-accessible
   STATUS     mandatory
   DESCRIPTION
     "This attribute is a vector of three elements that specify the quality of 
      service parameters for the backward direction for this connection. 
      This attribute is used for SPVC connections.
      
      The cdv element specifies the acceptable peak-to-peak Cell Delay 
      Variation (CDV) of real-time connections (CBR and rt-VBR).
      It is signalled through the extended QoS information element.
      
      The ctd specifies the acceptable maximum Cell Transfer Delay 
      (maxCtd) of real-time connections (CBR and rt-VBR). It is 
      signalled through the end to end transit delay information element.
      
      The clr specifies the acceptable Cell Loss Ratio (CLR) of CBR, rt-
      VBR, and nrt-VBR connections. It is signalled through the extended 
      QoS information element."
::= { mscAtmIfVccVcdTm 459 }

mscAtmIfVccVcdTmBqpEntry OBJECT-TYPE
   SYNTAX     MscAtmIfVccVcdTmBqpEntry
   ACCESS     not-accessible
   STATUS     mandatory
   DESCRIPTION
     "An entry in the mscAtmIfVccVcdTmBqpTable."
   INDEX {
      mscAtmIfIndex,
      mscAtmIfVccIndex,
      mscAtmIfVccVcdIndex,
      mscAtmIfVccVcdTmIndex,
      mscAtmIfVccVcdTmBqpIndex }
::= { mscAtmIfVccVcdTmBqpTable 1 }

MscAtmIfVccVcdTmBqpEntry ::= SEQUENCE {
   mscAtmIfVccVcdTmBqpIndex
      INTEGER,
   mscAtmIfVccVcdTmBqpValue
      Unsigned32 }

mscAtmIfVccVcdTmBqpIndex OBJECT-TYPE
   SYNTAX     INTEGER  {
                 cdv(0),
                 ctd(1),
                 clr(2) }
   ACCESS     not-accessible
   STATUS     mandatory
   DESCRIPTION
     "This variable represents the mscAtmIfVccVcdTmBqpTable
      specific index for the mscAtmIfVccVcdTmBqpTable."
::= { mscAtmIfVccVcdTmBqpEntry 1 }

mscAtmIfVccVcdTmBqpValue OBJECT-TYPE
   SYNTAX     Unsigned32 (0..2147483647)
   ACCESS     read-write
   STATUS     mandatory
   DESCRIPTION
     "This variable represents an individual value for the
      mscAtmIfVccVcdTmBqpTable."
::= { mscAtmIfVccVcdTmBqpEntry 2 }


-- AtmIf/n Vcc/vpi.vci Vcd Tm AvailableBitRate, 
-- AtmIf/n Vpc/vci Vpd Tm AvailableBitRate,
-- AtmIf/n Vpt/vpi Vpd Tm AvailableBitRate,
-- AtmIf/n Vpt/vpi Vcc/vci Vcd Tm AvailableBitRate
-- This component contains provisioned ABR-related attributes of a 
-- connection. It is an optional subcomponent of the Vcd Tm and Vpd 
-- Tm component. It is used to override DGCRA-related defaults in 
-- the CA Abr component. It contains the specific configuration for the 
-- ABR connection at this connection point. If this is the source of an 
-- SPVC connection, this component also contains the ABR 
-- parameters required for the SPVC call request.

mscAtmIfVccVcdTmAbr OBJECT IDENTIFIER ::= { mscAtmIfVccVcdTm 2 }



mscAtmIfVccVcdTmAbrRowStatusTable OBJECT-TYPE
   SYNTAX     SEQUENCE OF MscAtmIfVccVcdTmAbrRowStatusEntry
   ACCESS     not-accessible
   STATUS     mandatory
   DESCRIPTION
     "This entry controls the addition and deletion of 
      mscAtmIfVccVcdTmAbr components."
::= { mscAtmIfVccVcdTmAbr 1 }

mscAtmIfVccVcdTmAbrRowStatusEntry OBJECT-TYPE
   SYNTAX     MscAtmIfVccVcdTmAbrRowStatusEntry
   ACCESS     not-accessible
   STATUS     mandatory
   DESCRIPTION
     "A single entry in the table represents a single 
      mscAtmIfVccVcdTmAbr component."
   INDEX {
      mscAtmIfIndex,
      mscAtmIfVccIndex,
      mscAtmIfVccVcdIndex,
      mscAtmIfVccVcdTmIndex,
      mscAtmIfVccVcdTmAbrIndex }
::= { mscAtmIfVccVcdTmAbrRowStatusTable 1 }

MscAtmIfVccVcdTmAbrRowStatusEntry ::= SEQUENCE {
   mscAtmIfVccVcdTmAbrRowStatus
      RowStatus,
   mscAtmIfVccVcdTmAbrComponentName
      DisplayString,
   mscAtmIfVccVcdTmAbrStorageType
      StorageType,
   mscAtmIfVccVcdTmAbrIndex
      NonReplicated }

mscAtmIfVccVcdTmAbrRowStatus OBJECT-TYPE
   SYNTAX     RowStatus 
   ACCESS     read-write
   STATUS     mandatory
   DESCRIPTION
     "This variable is used as the basis for SNMP naming of
      mscAtmIfVccVcdTmAbr components.
      These components can be added and deleted."
::= { mscAtmIfVccVcdTmAbrRowStatusEntry 1 }

mscAtmIfVccVcdTmAbrComponentName OBJECT-TYPE
   SYNTAX     DisplayString 
   ACCESS     read-only
   STATUS     mandatory
   DESCRIPTION
     "This variable provides the component's string name for
      use with the ASCII Console Interface"
::= { mscAtmIfVccVcdTmAbrRowStatusEntry 2 }

mscAtmIfVccVcdTmAbrStorageType OBJECT-TYPE
   SYNTAX     StorageType 
   ACCESS     read-only
   STATUS     mandatory
   DESCRIPTION
     "This variable represents the storage type value for the
      mscAtmIfVccVcdTmAbr tables."
::= { mscAtmIfVccVcdTmAbrRowStatusEntry 4 }

mscAtmIfVccVcdTmAbrIndex OBJECT-TYPE
   SYNTAX     NonReplicated 
   ACCESS     not-accessible
   STATUS     mandatory
   DESCRIPTION
     "This variable represents the index for the mscAtmIfVccVcdTmAbr tables."
::= { mscAtmIfVccVcdTmAbrRowStatusEntry 10 }

mscAtmIfVccVcdTmAbrProvTable OBJECT-TYPE
   SYNTAX     SEQUENCE OF MscAtmIfVccVcdTmAbrProvEntry
   ACCESS     not-accessible
   STATUS     mandatory
   DESCRIPTION
     "This group contains provisioned attributes for the ABR ATM 
      connections configured on an ATM interface."
::= { mscAtmIfVccVcdTmAbr 110 }

mscAtmIfVccVcdTmAbrProvEntry OBJECT-TYPE
   SYNTAX     MscAtmIfVccVcdTmAbrProvEntry
   ACCESS     not-accessible
   STATUS     mandatory
   DESCRIPTION
     "An entry in the mscAtmIfVccVcdTmAbrProvTable."
   INDEX {
      mscAtmIfIndex,
      mscAtmIfVccIndex,
      mscAtmIfVccVcdIndex,
      mscAtmIfVccVcdTmIndex,
      mscAtmIfVccVcdTmAbrIndex }
::= { mscAtmIfVccVcdTmAbrProvTable 1 }

MscAtmIfVccVcdTmAbrProvEntry ::= SEQUENCE {
   mscAtmIfVccVcdTmAbrInitialCellRate
      Unsigned32,
   mscAtmIfVccVcdTmAbrTransientBufferExposure
      Unsigned32,
   mscAtmIfVccVcdTmAbrFixedRoundTripTime
      Unsigned32,
   mscAtmIfVccVcdTmAbrRateDecreaseFactor
      Unsigned32,
   mscAtmIfVccVcdTmAbrRateIncreaseFactor
      Unsigned32,
   mscAtmIfVccVcdTmAbrMaxCellPerRmCell
      Unsigned32,
   mscAtmIfVccVcdTmAbrMaxTimeBetweenRmCells
      Unsigned32,
   mscAtmIfVccVcdTmAbrCutoffDecreaseFactor
      Unsigned32,
   mscAtmIfVccVcdTmAbrAcrDecreaseTimeFactor
      Unsigned32,
   mscAtmIfVccVcdTmAbrDgcraMaximumDelay
      Unsigned32,
   mscAtmIfVccVcdTmAbrDgcraMinimumDelay
      Unsigned32,
   mscAtmIfVccVcdTmAbrFarEndAcrDecreaseTimeFactor
      Unsigned32,
   mscAtmIfVccVcdTmAbrFarEndInitialCellRate
      Unsigned32 }

mscAtmIfVccVcdTmAbrInitialCellRate OBJECT-TYPE
   SYNTAX     Unsigned32 (0..16777215 | 16777216 | 16777217 | 16777218)
   ACCESS     read-write
   STATUS     mandatory
   DESCRIPTION
     "This attribute specifies the Initial Cell Rate (ICR) parameter for this 
      connection. ICR is the rate at which a source should send initially 
      and after an idle period.
      
      When this attribute is set to sameAsCa, the initial cell rate is 
      determined by the AtmIf CA Abr/0 icr attribute. When the value of 
      this attribute is set to useMcr, ICR is set to the same value as the 
      Minimum Cell Rate (MCR) for the connection.
      
      When the value of this attribute is set to usePcr, ICR is set to the 
      same value as the Peak Cell Rate (PCR) for the connection.
      
      If this attribute is specified less than the MCR of the connection, 
      then the MCR is used as the ICR. If this attribute is specified more 
      than PCR of the connection, then PCR is used as the ICR.
      
      This attribute is ignored under all conditions where the operational 
      attribute abrConnectionType indicates erSwitch or efciSwitch.

      VALUES (

      16777216 = sameAsCa

      16777217 = useMcr

      16777218 = usePcr

      )"
   DEFVAL     { 16777216 }
::= { mscAtmIfVccVcdTmAbrProvEntry 10 }

mscAtmIfVccVcdTmAbrTransientBufferExposure OBJECT-TYPE
   SYNTAX     Unsigned32 (0..16777215)
   ACCESS     read-write
   STATUS     mandatory
   DESCRIPTION
     "This attribute specifies the Transient Buffer Exposure (TBE) for this 
      connection. TBE is the negotiated number of cells that the network 
      would like to limit the source to send during start-up periods, before 
      the first Resource Management (RM) cell returns.
      
      TBE divided by fixedRoundTripTime determines an upper bound 
      for the operational value of initialCellRate, the rate at which a 
      source should send initially and after an idle period.
      
      TBE divided by maxCellsPerRmCell specifies the operational value 
      of forwardRmCellLimit, the limit of the number of forward 
      Resource Management (RM) cells which may be sent in the 
      absence of received backward RM cells.
      
      This attribute is ignored under all conditions where the operational 
      attribute abrConnectionType is set to erSwitch."
   DEFVAL     { 16777215 }
::= { mscAtmIfVccVcdTmAbrProvEntry 11 }

mscAtmIfVccVcdTmAbrFixedRoundTripTime OBJECT-TYPE
   SYNTAX     Unsigned32 (0..16700000)
   ACCESS     read-write
   STATUS     mandatory
   DESCRIPTION
     "This attribute specifies the Fixed Round-Trip Time (FRTT) 
      parameter for this connection. FRTT is the sum of the fixed and 
      propagation delays from the source to a destination and back.
      
      The value of transientBufferExposure divided by the value of FRTT 
      (in seconds) determines an upper bound for the operational value of 
      initialCellRate, the rate at which a source should send initially and 
      after an idle period.
      
      This attribute is ignored under all conditions where the operational 
      attribute abrConnectionType indicates erSwitch or efciSwitch."
   DEFVAL     { 5000000 }
::= { mscAtmIfVccVcdTmAbrProvEntry 12 }

mscAtmIfVccVcdTmAbrRateDecreaseFactor OBJECT-TYPE
   SYNTAX     Unsigned32 (0..15 | 16777216)
   ACCESS     read-write
   STATUS     mandatory
   DESCRIPTION
     "This attribute specifies the Rate Decrease Factor (RDF) for this 
      connection. The RDF value is computed by using the provisioned 
      value of this attribute, n, as 2 to the inverse power n. For example, if 
      the value of this attribute is 8, RDF is 2E-8 = 1/256.
      
      RDF controls the amount by which the cell transmission rate may 
      decrease upon receipt of a backward Resource Management (RM) 
      cell. For example, if a backward RM cell is received with the 
      Congestion Indication (CI) field set to 1, the Allowed Cell Rate 
      (ACR) value would be reduced by the amount (RDF*ACR). The 
      ACR is not allowed to fall below the Minimum Cell Rate (MCR), in 
      which case the ACR is set to MCR.
      
      This attribute is ignored under all conditions where the operational 
      attribute abrConnectionType has the value erSwitch.

      VALUES (

      16777216 = sameAsCa

      )"
   DEFVAL     { 16777216 }
::= { mscAtmIfVccVcdTmAbrProvEntry 13 }

mscAtmIfVccVcdTmAbrRateIncreaseFactor OBJECT-TYPE
   SYNTAX     Unsigned32 (0..15 | 16777216)
   ACCESS     read-write
   STATUS     mandatory
   DESCRIPTION
     "This attribute specifies the Rate Increase Factor (RIF) for this 
      connection. The RIF value is computed by using the provisioned 
      value of this attribute, n, as 2 to the inverse power n. For example, if 
      the value of this attribute is 6, RIF is 2E-6 = 1/64.
      
      RIF controls the amount by which the cell transmission rate may 
      increase upon receipt of a backward Resource Management (RM) 
      cell. For example, if a backward RM cell is received with the 
      Congestion Indication (CI) and the No Increase (NI) fields both set 
      to 0, the Allowed Cell Rate (ACR) value would be increased by the 
      amount (RIF*ACR). The ACR is not allowed to exceed the Peak 
      Cell Rate (PCR), in which case the ACR is set to PCR.
      
      This attribute is ignored under all conditions where the operational 
      attribute abrConnectionType has the value erSwitch.

      VALUES (

      16777216 = sameAsCa

      )"
   DEFVAL     { 16777216 }
::= { mscAtmIfVccVcdTmAbrProvEntry 14 }

mscAtmIfVccVcdTmAbrMaxCellPerRmCell OBJECT-TYPE
   SYNTAX     Unsigned32 (2 | 4 | 8 | 16 | 32 | 64 | 128 | 256 | 16777216)
   ACCESS     read-write
   STATUS     mandatory
   DESCRIPTION
     "This attribute specifies the maximum number of cells an ABR 
      source may transmit for each forward Resource Management (RM) 
      cell. The count of the cells transmitted includes data cells, OAM 
      cells, backward RM cells, and the forward RM cell.
      
      A value of 2 is not recommended although it is permitted according 
      to the ATM Forum standard. When this attribute is set to a value of 
      2, it is possible that only one forward and one backward RM cell 
      are repeatedly transmitted, and all data traffic is queued up 
      indefinitely.
      
      This attribute is ignored under all conditions where the operational 
      attribute abrConnectionType has the value erSwitch.

      VALUES (

      16777216 = sameAsCa

      )"
   DEFVAL     { 16777216 }
::= { mscAtmIfVccVcdTmAbrProvEntry 15 }

mscAtmIfVccVcdTmAbrMaxTimeBetweenRmCells OBJECT-TYPE
   SYNTAX     Unsigned32 (781 | 1563 | 3125 | 6250 | 12500 | 25000 | 50000 | 100000 | 16777216)
   ACCESS     read-write
   STATUS     mandatory
   DESCRIPTION
     "This attribute specifies the TRM parameter for this connection.
      
      TRM provides an lower bound on the time interval between forward 
      Resource Management (RM) cells for an ABR source. Since the last 
      forward RM cell was sent, if at least TRM time has elapsed since 
      and at least two other cells have been sent, then the next cell to be 
      transmitted would be a forward RM cell.
      
      This attribute is ignored under all conditions where the operational 
      attribute abrConnectionType has the value erSwitch.
      
      The provisioned value of 781 is signalled as TRM = 0, in the ABR 
      Additional Parameters Information Element. 
      1563 is signalled as TRM = 1. 
      3125 is signalled as TRM = 2. 
      6250 is signalled as TRM = 3. 
      12500 is signalled as TRM = 4 
      25000 is signalled as TRM = 5. 
      50000 is signalled as TRM = 6. 
      100000 is signalled as TRM = 7.

      VALUES (

      16777216 = sameAsCa

      )"
   DEFVAL     { 16777216 }
::= { mscAtmIfVccVcdTmAbrProvEntry 16 }

mscAtmIfVccVcdTmAbrCutoffDecreaseFactor OBJECT-TYPE
   SYNTAX     Unsigned32 (0 | 1 | 2 | 4 | 8 | 16 | 32 | 64 | 16777216)
   ACCESS     read-write
   STATUS     mandatory
   DESCRIPTION
     "This attribute specifies the Cutoff Decrease Factor (CDF) parameter 
      for this connection. When the value of this attribute is non-zero, 
      CDF is computed as the inverse of the value. For example, if the 
      value is 32, the value of CDF is 1/32. When the value of this 
      attribute is 0, CDF is also zero.
      
      CDF controls the decrease in the Allowed Cell Rate (ACR) 
      associated with the CRM parameter, the limit of the number of 
      forward Resource Management (RM) cells which may be sent in 
      the absence of received backward RM cells. When this limit is 
      crossed, the ACR value would be decreased by the amount 
      (CDF*ACR). The ACR is not allowed to fall below the Minimum 
      Cell Rate (MCR), in which case the ACR is set to MCR.
      
      The value of CRM is indicated by the forwardRmCellLimit 
      attribute.
      
      This attribute is ignored under all conditions where the operational 
      attribute abrConnectionType indicates erSwitch or efciSwitch.

      VALUES (

      16777216 = sameAsCa

      )"
   DEFVAL     { 16777216 }
::= { mscAtmIfVccVcdTmAbrProvEntry 17 }

mscAtmIfVccVcdTmAbrAcrDecreaseTimeFactor OBJECT-TYPE
   SYNTAX     Unsigned32 (0..1023 | 16777216)
   ACCESS     read-write
   STATUS     mandatory
   DESCRIPTION
     "This attribute specifies the Allowed Cell Rate Decrease Time Factor 
      (ADTF) parameter for this connection.
      
      ADTF is the maximum time interval permitted between sending 
      forward Resource Management (RM) cells before the Allowed Cell 
      Rate (ACR) is decreased to initialCellRate. In other words, if the 
      source does not transit a forward RM cell for the period specified by 
      adtf, it reduces its ACR to the value of its initialCellRate.
      
      This attribute is ignored under all conditions where the operational 
      attribute abrConnectionType indicates erSwitch or efciSwitch.

      VALUES (

      16777216 = sameAsCa

      )"
   DEFVAL     { 16777216 }
::= { mscAtmIfVccVcdTmAbrProvEntry 18 }

mscAtmIfVccVcdTmAbrDgcraMaximumDelay OBJECT-TYPE
   SYNTAX     Unsigned32 (1..16700000 | 16777216)
   ACCESS     read-write
   STATUS     mandatory
   DESCRIPTION
     "This attribute specifies an upper bound on the delay after which the 
      rate change induced by a backward Resource Management (RM) 
      cell departing from this connection point (in the backward 
      direction) is expected to be observed at this connection point (in the 
      forward direction).
      
      This upper bound may be approximated as the sum of the round trip 
      fixed and propagation delays and the maximum queuing delays 
      between the ABR source and this interface.
      
      The value of this attribute is used in policing an ABR connection 
      using the Dynamic General Cell Rate Algorithm (DGCRA). A 
      larger value for this attribute implies a more lenient policer. When 
      there is a reduction in the Allowed Cell Rate (ACR), the policer 
      waits for a correspondingly longer period of time before it enforces 
      at the new cell rate.
      
      The value of this attribute must not be less than the 
      dgcraMinimumDelay attribute.

      VALUES (

      16777216 = sameAsCa

      )"
   DEFVAL     { 16777216 }
::= { mscAtmIfVccVcdTmAbrProvEntry 19 }

mscAtmIfVccVcdTmAbrDgcraMinimumDelay OBJECT-TYPE
   SYNTAX     Unsigned32 (1..16700000 | 16777216)
   ACCESS     read-write
   STATUS     mandatory
   DESCRIPTION
     "This attribute specifies a lower bound on the delay after which the 
      rate change induced by a backward Resource Management (RM) 
      cell departing from this connection point (in the backward 
      direction) is expected to be observed at this connection point (in the 
      forward connection).
      
      This lower bound may be approximated as the sum of the round trip 
      fixed and propagation delays between the ABR source and this 
      interface.
      
      The value of this attribute is used in policing an ABR connection 
      using the Dynamic General Cell Rate Algorithm (DGCRA). A 
      smaller value for this attribute implies a more lenient policer. When 
      there is a increase in the Allowed Cell Rate (ACR), the policer waits 
      for a correspondingly shorter period of time before it enforces at the 
      new cell rate.

      VALUES (

      16777216 = sameAsCa

      )"
   DEFVAL     { 16777216 }
::= { mscAtmIfVccVcdTmAbrProvEntry 20 }

mscAtmIfVccVcdTmAbrFarEndAcrDecreaseTimeFactor OBJECT-TYPE
   SYNTAX     Unsigned32 (0..1023)
   ACCESS     read-write
   STATUS     mandatory
   DESCRIPTION
     "This attribute specifies the Allowed Cell Rate Decrease Time Factor 
      (ADTF) of the far end ABR source. The value specified should be 
      the same as the ADTF parameter at the far end of this ABR 
      connection. 
      
      The value of this attribute is used in policing an ABR connection 
      using the Dynamic Generic Cell Rate Algorithm (DGCRA). A 
      larger value for this attribute implies a more lenient policer. When 
      the delay between two consecutive forward Resource Management 
      (RM) cells received at this interface corresponds to a value greater 
      than the value of this attribute, the policer begins to limit enforce 
      the incoming traffic at the initial cell rate (ICR) of the far end, as 
      specified by the farEndInitialCellRate attribute."
   DEFVAL     { 50 }
::= { mscAtmIfVccVcdTmAbrProvEntry 21 }

mscAtmIfVccVcdTmAbrFarEndInitialCellRate OBJECT-TYPE
   SYNTAX     Unsigned32 (0..16777215)
   ACCESS     read-write
   STATUS     mandatory
   DESCRIPTION
     "This attribute specifies the Initial Cell Rate (ICR) of the far end 
      ABR source. The value specified should be the same as the ICR 
      parameter at the far end of this ABR connection. 
      
      The value of this attribute is used in policing an ABR connection 
      using the Dynamic Generic Cell Rate Algorithm (DGCRA). A 
      larger value for this attribute implies a more lenient policer. When 
      the delay between two consecutive forward Resource Management 
      (RM) cells received at this interface corresponds to a value greater 
      than the farEndAcrDecreaseTimeFactor attribute, the policer begins 
      to enforce the incoming traffic at the value of this attribute.
      
      If this attribute is specified less than the MCR of the connection, 
      then the MCR is used as the feIcr. If this attribute is more than the 
      PCR of the connection, then PCR is used as the feIcr."
   DEFVAL     { 0 }
::= { mscAtmIfVccVcdTmAbrProvEntry 22 }


-- AtmIf/n Vcc/x.y Vcd PerformanceMonitoring
-- AtmIf/n Vpc/x Vpd PerformanceMonitoring
-- This component represents the Performance Monitoring (Pm) 
-- function on a provisioned connection. No Performane Monitoring is 
-- done unless this component is present. The attribute values override 
-- corresponding values in the AtmIf Pm settings. There can be a 
-- maximum of 255 Pms on one LP.

mscAtmIfVccVcdPm OBJECT IDENTIFIER ::= { mscAtmIfVccVcd 3 }



mscAtmIfVccVcdPmRowStatusTable OBJECT-TYPE
   SYNTAX     SEQUENCE OF MscAtmIfVccVcdPmRowStatusEntry
   ACCESS     not-accessible
   STATUS     mandatory
   DESCRIPTION
     "This entry controls the addition and deletion of 
      mscAtmIfVccVcdPm components."
::= { mscAtmIfVccVcdPm 1 }

mscAtmIfVccVcdPmRowStatusEntry OBJECT-TYPE
   SYNTAX     MscAtmIfVccVcdPmRowStatusEntry
   ACCESS     not-accessible
   STATUS     mandatory
   DESCRIPTION
     "A single entry in the table represents a single 
      mscAtmIfVccVcdPm component."
   INDEX {
      mscAtmIfIndex,
      mscAtmIfVccIndex,
      mscAtmIfVccVcdIndex,
      mscAtmIfVccVcdPmIndex }
::= { mscAtmIfVccVcdPmRowStatusTable 1 }

MscAtmIfVccVcdPmRowStatusEntry ::= SEQUENCE {
   mscAtmIfVccVcdPmRowStatus
      RowStatus,
   mscAtmIfVccVcdPmComponentName
      DisplayString,
   mscAtmIfVccVcdPmStorageType
      StorageType,
   mscAtmIfVccVcdPmIndex
      NonReplicated }

mscAtmIfVccVcdPmRowStatus OBJECT-TYPE
   SYNTAX     RowStatus 
   ACCESS     read-write
   STATUS     mandatory
   DESCRIPTION
     "This variable is used as the basis for SNMP naming of
      mscAtmIfVccVcdPm components.
      These components can be added and deleted."
::= { mscAtmIfVccVcdPmRowStatusEntry 1 }

mscAtmIfVccVcdPmComponentName OBJECT-TYPE
   SYNTAX     DisplayString 
   ACCESS     read-only
   STATUS     mandatory
   DESCRIPTION
     "This variable provides the component's string name for
      use with the ASCII Console Interface"
::= { mscAtmIfVccVcdPmRowStatusEntry 2 }

mscAtmIfVccVcdPmStorageType OBJECT-TYPE
   SYNTAX     StorageType 
   ACCESS     read-only
   STATUS     mandatory
   DESCRIPTION
     "This variable represents the storage type value for the
      mscAtmIfVccVcdPm tables."
::= { mscAtmIfVccVcdPmRowStatusEntry 4 }

mscAtmIfVccVcdPmIndex OBJECT-TYPE
   SYNTAX     NonReplicated 
   ACCESS     not-accessible
   STATUS     mandatory
   DESCRIPTION
     "This variable represents the index for the mscAtmIfVccVcdPm tables."
::= { mscAtmIfVccVcdPmRowStatusEntry 10 }

mscAtmIfVccVcdPmProvTable OBJECT-TYPE
   SYNTAX     SEQUENCE OF MscAtmIfVccVcdPmProvEntry
   ACCESS     not-accessible
   STATUS     mandatory
   DESCRIPTION
     "This group contains provisioned attributes which specify 
      Performance Monitoring (PM) measurements, namely, Availability 
      Ratio (AR) and Cell Loss Ratio (CLR), and control modes for the 
      connection. The values specified in this group override those 
      specified by AtmIf Pm settings."
::= { mscAtmIfVccVcdPm 100 }

mscAtmIfVccVcdPmProvEntry OBJECT-TYPE
   SYNTAX     MscAtmIfVccVcdPmProvEntry
   ACCESS     not-accessible
   STATUS     mandatory
   DESCRIPTION
     "An entry in the mscAtmIfVccVcdPmProvTable."
   INDEX {
      mscAtmIfIndex,
      mscAtmIfVccIndex,
      mscAtmIfVccVcdIndex,
      mscAtmIfVccVcdPmIndex }
::= { mscAtmIfVccVcdPmProvTable 1 }

MscAtmIfVccVcdPmProvEntry ::= SEQUENCE {
   mscAtmIfVccVcdPmSegSwitchSideMeasurement
      OCTET STRING,
   mscAtmIfVccVcdPmSegLinkSideMeasurement
      OCTET STRING,
   mscAtmIfVccVcdPmControlMode
      INTEGER }

mscAtmIfVccVcdPmSegSwitchSideMeasurement OBJECT-TYPE
   SYNTAX     OCTET STRING (SIZE (1))
   ACCESS     read-write
   STATUS     mandatory
   DESCRIPTION
     "This attribute specifies the set of Performance Monitoring (PM) 
      measurements on the switch side configuration for the connection.
      
      sameAsInterface means that the measurements specified by the 
      segSwitchSideMeasurement attribute of the AtmIf Pm component 
      will be performed. No other values may be specified if 
      sameAsInterface is selected. If the value is empty, no switch side 
      PM measurements are done.

      Description of bits:
      availabilityRatio(0)
      cellLossRatio(1)
      sameAsInterface(2)"
   DEFVAL     { '20'H }
::= { mscAtmIfVccVcdPmProvEntry 1 }

mscAtmIfVccVcdPmSegLinkSideMeasurement OBJECT-TYPE
   SYNTAX     OCTET STRING (SIZE (1))
   ACCESS     read-write
   STATUS     mandatory
   DESCRIPTION
     "This attribute specifies the set of Performance Monitoring (PM) 
      measurements on the link side configuration for the connection.
      
      sameAsInterface means that the measurements specified by the 
      segLinkSideMeasurement attribute of the AtmIf Pm component will 
      be performed. No other values may be specified if sameAsInterface 
      is selected. If the value is empty, no link side PM measurements are 
      done.
      
      The following are valid sets:
      (~sameAsInterface ~availabilityRatio ~cellLossRatio)
      (~sameAsInterface ~availabilityRatio cellLossRatio)
      (~sameAsInterface availabilityRatio ~cellLossRatio)
      (~sameAsInterface availabilityRatio cellLossRatio)
      (sameAsInterface ~availabilityRatio ~cellLossRatio)

      Description of bits:
      availabilityRatio(0)
      cellLossRatio(1)
      sameAsInterface(2)"
   DEFVAL     { '20'H }
::= { mscAtmIfVccVcdPmProvEntry 2 }

mscAtmIfVccVcdPmControlMode OBJECT-TYPE
   SYNTAX     INTEGER  {
                 autoStart(0),
                 onDemand(1),
                 sameAsInterface(2) }
   ACCESS     read-write
   STATUS     mandatory
   DESCRIPTION
     "This attribute specifies the control mode of Performance Monitoring 
      (PM) measurements for the connection.
      
      autoStart means that PM activation procedures will start when the 
      provisioned data is activated.
      
      onDemand means that PM activation procedures will start when the 
      operator issues the START command. The PM measurements in this 
      mode will continue until the operator issues the STOP command.
      
      sameAsInterface means that the behavior will be as specified by the 
      controlMode attribute of the AtmIf Pm component."
   DEFVAL     { sameAsInterface }
::= { mscAtmIfVccVcdPmProvEntry 3 }


-- AtmIf/n Vcc/vpi.vci Loop
-- The Loop component configures an ATM connection so that cells 
-- received from the ATM interface are retransmitted back to the 
-- interface through that connection. The Loop component requires 
-- exclusive use of its parent Vcc or Vpc and cannot co-exist with other 
-- ATM service components (such as Nep, Nrp, and Test).

mscAtmIfVccLoop OBJECT IDENTIFIER ::= { mscAtmIfVcc 3 }



mscAtmIfVccLoopRowStatusTable OBJECT-TYPE
   SYNTAX     SEQUENCE OF MscAtmIfVccLoopRowStatusEntry
   ACCESS     not-accessible
   STATUS     mandatory
   DESCRIPTION
     "This entry controls the addition and deletion of 
      mscAtmIfVccLoop components."
::= { mscAtmIfVccLoop 1 }

mscAtmIfVccLoopRowStatusEntry OBJECT-TYPE
   SYNTAX     MscAtmIfVccLoopRowStatusEntry
   ACCESS     not-accessible
   STATUS     mandatory
   DESCRIPTION
     "A single entry in the table represents a single 
      mscAtmIfVccLoop component."
   INDEX {
      mscAtmIfIndex,
      mscAtmIfVccIndex,
      mscAtmIfVccLoopIndex }
::= { mscAtmIfVccLoopRowStatusTable 1 }

MscAtmIfVccLoopRowStatusEntry ::= SEQUENCE {
   mscAtmIfVccLoopRowStatus
      RowStatus,
   mscAtmIfVccLoopComponentName
      DisplayString,
   mscAtmIfVccLoopStorageType
      StorageType,
   mscAtmIfVccLoopIndex
      NonReplicated }

mscAtmIfVccLoopRowStatus OBJECT-TYPE
   SYNTAX     RowStatus 
   ACCESS     read-write
   STATUS     mandatory
   DESCRIPTION
     "This variable is used as the basis for SNMP naming of
      mscAtmIfVccLoop components.
      These components can be added and deleted."
::= { mscAtmIfVccLoopRowStatusEntry 1 }

mscAtmIfVccLoopComponentName OBJECT-TYPE
   SYNTAX     DisplayString 
   ACCESS     read-only
   STATUS     mandatory
   DESCRIPTION
     "This variable provides the component's string name for
      use with the ASCII Console Interface"
::= { mscAtmIfVccLoopRowStatusEntry 2 }

mscAtmIfVccLoopStorageType OBJECT-TYPE
   SYNTAX     StorageType 
   ACCESS     read-only
   STATUS     mandatory
   DESCRIPTION
     "This variable represents the storage type value for the
      mscAtmIfVccLoop tables."
::= { mscAtmIfVccLoopRowStatusEntry 4 }

mscAtmIfVccLoopIndex OBJECT-TYPE
   SYNTAX     NonReplicated 
   ACCESS     not-accessible
   STATUS     mandatory
   DESCRIPTION
     "This variable represents the index for the mscAtmIfVccLoop tables."
::= { mscAtmIfVccLoopRowStatusEntry 10 }


-- AtmIf/n Vcc/vpi.vci Nep
-- The NailedUpEndPoint component is used to link a VCC to an 
-- application that sends and receives frames using the connection. 
-- The Nep component requires exclusive use of its parent Vcc and 
-- cannot co-exist with other ATM service components (such as Nrp, 
-- Test, and Loop).

mscAtmIfVccNep OBJECT IDENTIFIER ::= { mscAtmIfVcc 5 }



mscAtmIfVccNepRowStatusTable OBJECT-TYPE
   SYNTAX     SEQUENCE OF MscAtmIfVccNepRowStatusEntry
   ACCESS     not-accessible
   STATUS     mandatory
   DESCRIPTION
     "This entry controls the addition and deletion of 
      mscAtmIfVccNep components."
::= { mscAtmIfVccNep 1 }

mscAtmIfVccNepRowStatusEntry OBJECT-TYPE
   SYNTAX     MscAtmIfVccNepRowStatusEntry
   ACCESS     not-accessible
   STATUS     mandatory
   DESCRIPTION
     "A single entry in the table represents a single 
      mscAtmIfVccNep component."
   INDEX {
      mscAtmIfIndex,
      mscAtmIfVccIndex,
      mscAtmIfVccNepIndex }
::= { mscAtmIfVccNepRowStatusTable 1 }

MscAtmIfVccNepRowStatusEntry ::= SEQUENCE {
   mscAtmIfVccNepRowStatus
      RowStatus,
   mscAtmIfVccNepComponentName
      DisplayString,
   mscAtmIfVccNepStorageType
      StorageType,
   mscAtmIfVccNepIndex
      NonReplicated }

mscAtmIfVccNepRowStatus OBJECT-TYPE
   SYNTAX     RowStatus 
   ACCESS     read-write
   STATUS     mandatory
   DESCRIPTION
     "This variable is used as the basis for SNMP naming of
      mscAtmIfVccNep components.
      These components can be added and deleted."
::= { mscAtmIfVccNepRowStatusEntry 1 }

mscAtmIfVccNepComponentName OBJECT-TYPE
   SYNTAX     DisplayString 
   ACCESS     read-only
   STATUS     mandatory
   DESCRIPTION
     "This variable provides the component's string name for
      use with the ASCII Console Interface"
::= { mscAtmIfVccNepRowStatusEntry 2 }

mscAtmIfVccNepStorageType OBJECT-TYPE
   SYNTAX     StorageType 
   ACCESS     read-only
   STATUS     mandatory
   DESCRIPTION
     "This variable represents the storage type value for the
      mscAtmIfVccNep tables."
::= { mscAtmIfVccNepRowStatusEntry 4 }

mscAtmIfVccNepIndex OBJECT-TYPE
   SYNTAX     NonReplicated 
   ACCESS     not-accessible
   STATUS     mandatory
   DESCRIPTION
     "This variable represents the index for the mscAtmIfVccNep tables."
::= { mscAtmIfVccNepRowStatusEntry 10 }

mscAtmIfVccNepProvTable OBJECT-TYPE
   SYNTAX     SEQUENCE OF MscAtmIfVccNepProvEntry
   ACCESS     not-accessible
   STATUS     mandatory
   DESCRIPTION
     "This group contains provisionable attributes for the Nep component."
::= { mscAtmIfVccNep 100 }

mscAtmIfVccNepProvEntry OBJECT-TYPE
   SYNTAX     MscAtmIfVccNepProvEntry
   ACCESS     not-accessible
   STATUS     mandatory
   DESCRIPTION
     "An entry in the mscAtmIfVccNepProvTable."
   INDEX {
      mscAtmIfIndex,
      mscAtmIfVccIndex,
      mscAtmIfVccNepIndex }
::= { mscAtmIfVccNepProvTable 1 }

MscAtmIfVccNepProvEntry ::= SEQUENCE {
   mscAtmIfVccNepApplicationName
      Link }

mscAtmIfVccNepApplicationName OBJECT-TYPE
   SYNTAX     Link 
   ACCESS     read-only
   STATUS     mandatory
   DESCRIPTION
     "This attribute specifies the application that sends and receives 
      frames using the VCC. This attribute is set, for example, by 
      provisioning the Trunk AtmAccess AtmConnection attribute. If it is 
      properly configured, this attribute will show a value such as
      'Trk/22 AtmAccess'."
::= { mscAtmIfVccNepProvEntry 10 }


-- AtmIf/n Vcc/vpi.vci Test
-- The Test component allows test traffic to be sent over an ATM 
-- connection. It is used to verify the integrity of hardware carrying 
-- ATM traffic, and provides test capabilities similar to those provided 
-- by non-ATM port and line tests. The Test component requires 
-- exclusive use of its parent Vcc and cannot co-exist with other ATM 
-- service components (such as Nep, Nrp, and Loop).
-- 
-- An ATM connection test circulates traffic through a VCC having a 
-- Test component at one end and the other end configured to loop 
-- back ATM cells. The Test component generates test frames, 
-- transforms them into ATM cells using AAL5 segmentation, and 
-- transmits them through the VCC; the returned cells are received by 
-- the Test component, reassembled back into frames, and the frames 
-- are consumed.
-- 
-- The test frames generated by the test are grouped into two 
-- independent streams.
-- 1) The loading frame stream circulates a set of "loading frames" 
-- through the connection as rapidly as possible. The intent of this 
-- stream is to verify the operation of the connection under a 
-- controlled load.
-- 2) The verification stream transmits a series of "verification frames" 
-- through the connection; as each frame is returned, the Test 
-- component verifies its contents and the next verification frame in 
-- the series is transmitted. The intent of this stream is to verify that 
-- frames are not being corrupted.
-- The test can be configured to send frames from either or both 
-- streams. The size and content of the test frames can also be 
-- controlled.

mscAtmIfVccTest OBJECT IDENTIFIER ::= { mscAtmIfVcc 6 }



mscAtmIfVccTestRowStatusTable OBJECT-TYPE
   SYNTAX     SEQUENCE OF MscAtmIfVccTestRowStatusEntry
   ACCESS     not-accessible
   STATUS     mandatory
   DESCRIPTION
     "This entry controls the addition and deletion of 
      mscAtmIfVccTest components."
::= { mscAtmIfVccTest 1 }

mscAtmIfVccTestRowStatusEntry OBJECT-TYPE
   SYNTAX     MscAtmIfVccTestRowStatusEntry
   ACCESS     not-accessible
   STATUS     mandatory
   DESCRIPTION
     "A single entry in the table represents a single 
      mscAtmIfVccTest component."
   INDEX {
      mscAtmIfIndex,
      mscAtmIfVccIndex,
      mscAtmIfVccTestIndex }
::= { mscAtmIfVccTestRowStatusTable 1 }

MscAtmIfVccTestRowStatusEntry ::= SEQUENCE {
   mscAtmIfVccTestRowStatus
      RowStatus,
   mscAtmIfVccTestComponentName
      DisplayString,
   mscAtmIfVccTestStorageType
      StorageType,
   mscAtmIfVccTestIndex
      NonReplicated }

mscAtmIfVccTestRowStatus OBJECT-TYPE
   SYNTAX     RowStatus 
   ACCESS     read-write
   STATUS     mandatory
   DESCRIPTION
     "This variable is used as the basis for SNMP naming of
      mscAtmIfVccTest components.
      These components can be added and deleted."
::= { mscAtmIfVccTestRowStatusEntry 1 }

mscAtmIfVccTestComponentName OBJECT-TYPE
   SYNTAX     DisplayString 
   ACCESS     read-only
   STATUS     mandatory
   DESCRIPTION
     "This variable provides the component's string name for
      use with the ASCII Console Interface"
::= { mscAtmIfVccTestRowStatusEntry 2 }

mscAtmIfVccTestStorageType OBJECT-TYPE
   SYNTAX     StorageType 
   ACCESS     read-only
   STATUS     mandatory
   DESCRIPTION
     "This variable represents the storage type value for the
      mscAtmIfVccTest tables."
::= { mscAtmIfVccTestRowStatusEntry 4 }

mscAtmIfVccTestIndex OBJECT-TYPE
   SYNTAX     NonReplicated 
   ACCESS     not-accessible
   STATUS     mandatory
   DESCRIPTION
     "This variable represents the index for the mscAtmIfVccTest tables."
::= { mscAtmIfVccTestRowStatusEntry 10 }

mscAtmIfVccTestStateTable OBJECT-TYPE
   SYNTAX     SEQUENCE OF MscAtmIfVccTestStateEntry
   ACCESS     not-accessible
   STATUS     mandatory
   DESCRIPTION
     "This group contains the three OSI State attributes. The descriptions 
      generically indicate what each state attribute implies about the 
      component. Note that not all the values and state combinations 
      described here are supported by every component which reuses this 
      group. For component-specific information and the valid state 
      combinations, refer to the appropriate NTP."
::= { mscAtmIfVccTest 100 }

mscAtmIfVccTestStateEntry OBJECT-TYPE
   SYNTAX     MscAtmIfVccTestStateEntry
   ACCESS     not-accessible
   STATUS     mandatory
   DESCRIPTION
     "An entry in the mscAtmIfVccTestStateTable."
   INDEX {
      mscAtmIfIndex,
      mscAtmIfVccIndex,
      mscAtmIfVccTestIndex }
::= { mscAtmIfVccTestStateTable 1 }

MscAtmIfVccTestStateEntry ::= SEQUENCE {
   mscAtmIfVccTestAdminState
      INTEGER,
   mscAtmIfVccTestOperationalState
      INTEGER,
   mscAtmIfVccTestUsageState
      INTEGER }

mscAtmIfVccTestAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock -force or 
      Lock command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscAtmIfVccTestStateEntry 1 }

mscAtmIfVccTestOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscAtmIfVccTestStateEntry 2 }

mscAtmIfVccTestUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscAtmIfVccTestStateEntry 3 }

mscAtmIfVccTestSetupTable OBJECT-TYPE
   SYNTAX     SEQUENCE OF MscAtmIfVccTestSetupEntry
   ACCESS     not-accessible
   STATUS     mandatory
   DESCRIPTION
     "This group contains attributes that govern the operation of an ATM 
      connection test. These attributes cannot be changed while the test is 
      running."
::= { mscAtmIfVccTest 110 }

mscAtmIfVccTestSetupEntry OBJECT-TYPE
   SYNTAX     MscAtmIfVccTestSetupEntry
   ACCESS     not-accessible
   STATUS     mandatory
   DESCRIPTION
     "An entry in the mscAtmIfVccTestSetupTable."
   INDEX {
      mscAtmIfIndex,
      mscAtmIfVccIndex,
      mscAtmIfVccTestIndex }
::= { mscAtmIfVccTestSetupTable 1 }

MscAtmIfVccTestSetupEntry ::= SEQUENCE {
   mscAtmIfVccTestFrmTypes
      OCTET STRING,
   mscAtmIfVccTestFrmSize
      Unsigned32,
   mscAtmIfVccTestFrmPatternType
      INTEGER,
   mscAtmIfVccTestCustomizedPattern
      Hex,
   mscAtmIfVccTestDuration
      Unsigned32,
   mscAtmIfVccTestBandwidthElastic
      INTEGER,
   mscAtmIfVccTestOverrideHoldingPriority
      INTEGER }

mscAtmIfVccTestFrmTypes OBJECT-TYPE
   SYNTAX     OCTET STRING (SIZE (1))
   ACCESS     read-write
   STATUS     mandatory
   DESCRIPTION
     "This attribute specifies the types of the test frames to be transmitted 
      during the ATM connection test. It must contain at least one of the 
      following:
      loading: A set of 'loading frames' is circulated over the link as 
      rapidly as possible. This frame type should be selected when the 
      test is intended to verify the operation of the connection under a 
      specified load. These frames are not checked for bit errors.
      verification: A single 'verification frame' is transmitted over the 
      link; when the frame is returned, its contents are verified and the 
      next verification frame in the series is transmitted. This frame type 
      should be selected when the test is intended to verify that frames are 
      not being corrupted as they pass over the connection.

      Description of bits:
      loading(0)
      verification(1)"
   DEFVAL     { 'c0'H }
::= { mscAtmIfVccTestSetupEntry 10 }

mscAtmIfVccTestFrmSize OBJECT-TYPE
   SYNTAX     Unsigned32 (4..4096)
   ACCESS     read-write
   STATUS     mandatory
   DESCRIPTION
     "This attribute defines the size of the test frames used in an ATM 
      connection test."
   DEFVAL     { 1024 }
::= { mscAtmIfVccTestSetupEntry 20 }

mscAtmIfVccTestFrmPatternType OBJECT-TYPE
   SYNTAX     INTEGER  {
                 ccitt32kBitPattern(0),
                 ccitt8MBitPattern(1),
                 customizedPattern(2) }
   ACCESS     read-write
   STATUS     mandatory
   DESCRIPTION
     "This attribute specifies the bit sequence used to fill the frames used 
      in the ATM connection test. It must contain one of the following 
      values:
      ccitt32kBitPattern: a pseudo-random sequence of 32 Kbit is used
      ccitt8MBitPattern: a pseudo-random sequence of 8Mbit is used
      customizedPattern: the pattern defined in the customizedPattern 
      attribute is used"
   DEFVAL     { ccitt32kBitPattern }
::= { mscAtmIfVccTestSetupEntry 30 }

mscAtmIfVccTestCustomizedPattern OBJECT-TYPE
   SYNTAX     Hex (0..4294967295)
   ACCESS     read-write
   STATUS     mandatory
   DESCRIPTION
     "This attribute specifies a 32 bit sequence to be used to fill frames 
      when the framePatternType attribute is set to customizedPattern. 
      The default value gives a pattern of alternating 0 and 1 bits."
   DEFVAL     { 1431655765 }
::= { mscAtmIfVccTestSetupEntry 40 }

mscAtmIfVccTestDuration OBJECT-TYPE
   SYNTAX     Unsigned32 (1..30240)
   ACCESS     read-write
   STATUS     mandatory
   DESCRIPTION
     "This attribute specifies the maximum number of minutes that the 
      ATM connection test is allowed to run. The maximum allowed 
      value permits the test to be run for up to 21 days."
   DEFVAL     { 1 }
::= { mscAtmIfVccTestSetupEntry 50 }

mscAtmIfVccTestBandwidthElastic OBJECT-TYPE
   SYNTAX     INTEGER  {
                 no(0),
                 yes(1) }
   ACCESS     read-write
   STATUS     mandatory
   DESCRIPTION
     "This attribute specifies whether the connection (VCC) should be 
      configured with elastic bandwidth or not. Elastic bandwidth is of 
      importance in conjuction with IMA links, where some links fail and 
      the resulting bandwidth is less than the requested bandwidth for all 
      connections. In that case, some connections may be reduced in 
      bandwidth based on the setting of the bwElastic attribute.
      
      If this attribute is set to yes, the Test application signals to the 
      connection that the bandwidth for this connection is elastic, and 
      may be reduced in the case of IMA link failures. If the bandwidth is 
      reduced, the rate of test cells which can be handled by the 
      connection will also be reduced. 
      
      If this attribute is set to no, the Test application signals to the 
      connection that the bandwidth for this connection must be 
      maintained at the requested level. If the connection cannot maintain 
      the full bandwidth, the connection may be released (cleared) based 
      on the holding priority of the connection."
   DEFVAL     { no }
::= { mscAtmIfVccTestSetupEntry 60 }

mscAtmIfVccTestOverrideHoldingPriority OBJECT-TYPE
   SYNTAX     INTEGER  {
                 n0(0),
                 n1(1),
                 n2(2),
                 n3(3),
                 n4(4),
                 noOverride(6) }
   ACCESS     read-write
   STATUS     mandatory
   DESCRIPTION
     "This attribute specifies the override holding priority which should 
      be signalled to the VCC connection at the start of the test. Holding 
      priority is of importance in conjuction with IMA links, where some 
      links fail and the resulting bandwidth is less than the requested 
      bandwidth for all connections. In that case, some connections may 
      be released based on the connection's holding priority.
      
      Zero (0) is thie highest holding priority, and four (4) is the lowest 
      priority. A setting of zero to four overrides whatever holding 
      priority that has been configured at the connection (VCC). A setting 
      of noOverride means that the connection should use its internally 
      configured holding priority."
   DEFVAL     { noOverride }
::= { mscAtmIfVccTestSetupEntry 70 }

mscAtmIfVccTestResultsTable OBJECT-TYPE
   SYNTAX     SEQUENCE OF MscAtmIfVccTestResultsEntry
   ACCESS     not-accessible
   STATUS     mandatory
   DESCRIPTION
     "This group contains attributes that show the result of an ATM 
      connection test; if no test is running, the attribute group contains the 
      results of the most recently completed test. The attributes of the 
      Results group are reset to their inital values whenever a test is 
      started or any attribute of the Setup group is set."
::= { mscAtmIfVccTest 120 }

mscAtmIfVccTestResultsEntry OBJECT-TYPE
   SYNTAX     MscAtmIfVccTestResultsEntry
   ACCESS     not-accessible
   STATUS     mandatory
   DESCRIPTION
     "An entry in the mscAtmIfVccTestResultsTable."
   INDEX {
      mscAtmIfIndex,
      mscAtmIfVccIndex,
      mscAtmIfVccTestIndex }
::= { mscAtmIfVccTestResultsTable 1 }

MscAtmIfVccTestResultsEntry ::= SEQUENCE {
   mscAtmIfVccTestElapsedTime
      Unsigned32,
   mscAtmIfVccTestTimeRemaining
      Unsigned32,
   mscAtmIfVccTestCauseOfTermination
      INTEGER,
   mscAtmIfVccTestBytesTx
      PassportCounter64,
   mscAtmIfVccTestBytesRx
      PassportCounter64,
   mscAtmIfVccTestLoadingFrmTx
      PassportCounter64,
   mscAtmIfVccTestLoadingFrmRx
      PassportCounter64,
   mscAtmIfVccTestLoadingFrmLost
      PassportCounter64,
   mscAtmIfVccTestVerificationFrmTx
      PassportCounter64,
   mscAtmIfVccTestVerificationFrmRx
      PassportCounter64,
   mscAtmIfVccTestVerificationFrmBad
      PassportCounter64,
   mscAtmIfVccTestUnrecognizableFrmRx
      PassportCounter64 }

mscAtmIfVccTestElapsedTime OBJECT-TYPE
   SYNTAX     Unsigned32 (0..30240)
   ACCESS     read-only
   STATUS     mandatory
   DESCRIPTION
     "This attribute displays the number of minutes that the test has been 
      running."
   DEFVAL     { 0 }
::= { mscAtmIfVccTestResultsEntry 10 }

mscAtmIfVccTestTimeRemaining OBJECT-TYPE
   SYNTAX     Unsigned32 (0..30240)
   ACCESS     read-only
   STATUS     mandatory
   DESCRIPTION
     "This attribute displays the number of minutes that the test will 
      continue to run before stopping automatically."
   DEFVAL     { 0 }
::= { mscAtmIfVccTestResultsEntry 20 }

mscAtmIfVccTestCauseOfTermination OBJECT-TYPE
   SYNTAX     INTEGER  {
                 testTimeExpired(0),
                 stoppedByOperator(1),
                 neverStarted(2),
                 testRunning(3) }
   ACCESS     read-only
   STATUS     mandatory
   DESCRIPTION
     "This attribute displays the reason the test ended. It contains one fo 
      the following values.
      testTimeExpired: the test ran for the specified duration
      stoppedByOperator: a STOP command was issued
      neverStarted: the test has not been started
      testRunning: the test is currently running"
   DEFVAL     { neverStarted }
::= { mscAtmIfVccTestResultsEntry 30 }

mscAtmIfVccTestBytesTx OBJECT-TYPE
   SYNTAX     PassportCounter64 
   ACCESS     read-only
   STATUS     mandatory
   DESCRIPTION
     "This attribute displays the number of bytes sent during the test. The 
      counter wraps to zero if it exceeds its maximum value of (2**64)-1."
::= { mscAtmIfVccTestResultsEntry 40 }

mscAtmIfVccTestBytesRx OBJECT-TYPE
   SYNTAX     PassportCounter64 
   ACCESS     read-only
   STATUS     mandatory
   DESCRIPTION
     "This attribute displays the number of bytes received during the test. 
      The counter wraps to zero if it exceeds its maximum value of 
      (2**64)-1."
::= { mscAtmIfVccTestResultsEntry 50 }

mscAtmIfVccTestLoadingFrmTx OBJECT-TYPE
   SYNTAX     PassportCounter64 
   ACCESS     read-only
   STATUS     mandatory
   DESCRIPTION
     "This attribute displays the number of loading frames sent during the 
      test. The counter wraps to zero if it exceeds its maximum value of 
      (2**64)-1."
::= { mscAtmIfVccTestResultsEntry 60 }

mscAtmIfVccTestLoadingFrmRx OBJECT-TYPE
   SYNTAX     PassportCounter64 
   ACCESS     read-only
   STATUS     mandatory
   DESCRIPTION
     "This attribute displays the number of loading frames received 
      during the test. The counter wraps to zero if it exceeds its maximum 
      value of (2**64)-1."
::= { mscAtmIfVccTestResultsEntry 70 }

mscAtmIfVccTestLoadingFrmLost OBJECT-TYPE
   SYNTAX     PassportCounter64 
   ACCESS     read-only
   STATUS     mandatory
   DESCRIPTION
     "This attribute displays the number of loading frames that were lost 
      during the test. The counter wraps to zero if it exceeds its maximum 
      value of (2**64)-1."
::= { mscAtmIfVccTestResultsEntry 80 }

mscAtmIfVccTestVerificationFrmTx OBJECT-TYPE
   SYNTAX     PassportCounter64 
   ACCESS     read-only
   STATUS     mandatory
   DESCRIPTION
     "This attribute displays the number of verification frames sent during 
      the test. The counter wraps to zero if it exceeds its maximum value 
      of (2**64)-1."
::= { mscAtmIfVccTestResultsEntry 90 }

mscAtmIfVccTestVerificationFrmRx OBJECT-TYPE
   SYNTAX     PassportCounter64 
   ACCESS     read-only
   STATUS     mandatory
   DESCRIPTION
     "This attribute displays the number of verification frames received 
      during the test (including errored verification frames). The counter 
      wraps to zero if it exceeds its maximum value of (2**64)-1.
      
      Note that the number of verification frames lost during the test can 
      be computed by the expression verificationFrmTx - 
      verificationFrmRx."
::= { mscAtmIfVccTestResultsEntry 100 }

mscAtmIfVccTestVerificationFrmBad OBJECT-TYPE
   SYNTAX     PassportCounter64 
   ACCESS     read-only
   STATUS     mandatory
   DESCRIPTION
     "This attribute displays the number of errored verification frames 
      received during the test. A verification frame is considered to be 
      errored if it contains a recognizable verification frame header, but 
      does not match the transmitted frame bit for bit. (Thus, a 
      verification frame that returns after the succeeding verification 
      frame has been transmitted is considered to be errored.) The counter 
      wraps to zero if it exceeds its maximum value of (2**64)-1.
      
      Note that the number of correct verification frames received during 
      the test can be computed by the expression verificationFrmRx - 
      verificationFrmBad."
::= { mscAtmIfVccTestResultsEntry 110 }

mscAtmIfVccTestUnrecognizableFrmRx OBJECT-TYPE
   SYNTAX     PassportCounter64 
   ACCESS     read-only
   STATUS     mandatory
   DESCRIPTION
     "This attribute displays the number of frames received during the test 
      which do not contain a valid loading frame header or verification 
      frame header. The counter wraps to zero if it exceeds its maximum 
      value of (2**64)-1."
::= { mscAtmIfVccTestResultsEntry 120 }


-- AtmIf/n Vpc/vpi TrafficManagement, 
-- AtmIf/n Vcc/vpi.vci TrafficManagement,
-- AtmIf/n Vpt/vpi TrafficManagement,
-- AtmIf/n Vpt/vpi Vcc/vci TrafficManagement
-- The Tm subcomponent contains the operational traffic management 
-- attributes of a connection. It is created dynamically for each 
-- activated Vcc, Vpc, or Vpt component.

mscAtmIfVccTm OBJECT IDENTIFIER ::= { mscAtmIfVcc 7 }



mscAtmIfVccTmRowStatusTable OBJECT-TYPE
   SYNTAX     SEQUENCE OF MscAtmIfVccTmRowStatusEntry
   ACCESS     not-accessible
   STATUS     mandatory
   DESCRIPTION
     "This entry controls the addition and deletion of 
      mscAtmIfVccTm components."
::= { mscAtmIfVccTm 1 }

mscAtmIfVccTmRowStatusEntry OBJECT-TYPE
   SYNTAX     MscAtmIfVccTmRowStatusEntry
   ACCESS     not-accessible
   STATUS     mandatory
   DESCRIPTION
     "A single entry in the table represents a single 
      mscAtmIfVccTm component."
   INDEX {
      mscAtmIfIndex,
      mscAtmIfVccIndex,
      mscAtmIfVccTmIndex }
::= { mscAtmIfVccTmRowStatusTable 1 }

MscAtmIfVccTmRowStatusEntry ::= SEQUENCE {
   mscAtmIfVccTmRowStatus
      RowStatus,
   mscAtmIfVccTmComponentName
      DisplayString,
   mscAtmIfVccTmStorageType
      StorageType,
   mscAtmIfVccTmIndex
      NonReplicated }

mscAtmIfVccTmRowStatus OBJECT-TYPE
   SYNTAX     RowStatus 
   ACCESS     read-only
   STATUS     mandatory
   DESCRIPTION
     "This variable is used as the basis for SNMP naming of
      mscAtmIfVccTm components.
      These components cannot be added nor deleted."
::= { mscAtmIfVccTmRowStatusEntry 1 }

mscAtmIfVccTmComponentName OBJECT-TYPE
   SYNTAX     DisplayString 
   ACCESS     read-only
   STATUS     mandatory
   DESCRIPTION
     "This variable provides the component's string name for
      use with the ASCII Console Interface"
::= { mscAtmIfVccTmRowStatusEntry 2 }

mscAtmIfVccTmStorageType OBJECT-TYPE
   SYNTAX     StorageType 
   ACCESS     read-only
   STATUS     mandatory
   DESCRIPTION
     "This variable represents the storage type value for the
      mscAtmIfVccTm tables."
::= { mscAtmIfVccTmRowStatusEntry 4 }

mscAtmIfVccTmIndex OBJECT-TYPE
   SYNTAX     NonReplicated 
   ACCESS     not-accessible
   STATUS     mandatory
   DESCRIPTION
     "This variable represents the index for the mscAtmIfVccTm tables."
::= { mscAtmIfVccTmRowStatusEntry 10 }

mscAtmIfVccTmOperTable OBJECT-TYPE
   SYNTAX     SEQUENCE OF MscAtmIfVccTmOperEntry
   ACCESS     not-accessible
   STATUS     mandatory
   DESCRIPTION
     "This group contains attributes for the Tm component to reflect 
      operational traffic attributes."
::= { mscAtmIfVccTm 100 }

mscAtmIfVccTmOperEntry OBJECT-TYPE
   SYNTAX     MscAtmIfVccTmOperEntry
   ACCESS     not-accessible
   STATUS     mandatory
   DESCRIPTION
     "An entry in the mscAtmIfVccTmOperTable."
   INDEX {
      mscAtmIfIndex,
      mscAtmIfVccIndex,
      mscAtmIfVccTmIndex }
::= { mscAtmIfVccTmOperTable 1 }

MscAtmIfVccTmOperEntry ::= SEQUENCE {
   mscAtmIfVccTmTxTrafficDescType
      INTEGER,
   mscAtmIfVccTmTxQosClass
      INTEGER,
   mscAtmIfVccTmTxQueueLength
      Unsigned32,
   mscAtmIfVccTmTxQueueCongestionState
      Unsigned32,
   mscAtmIfVccTmHoldingPriority
      INTEGER,
   mscAtmIfVccTmRxTrafficDescType
      INTEGER,
   mscAtmIfVccTmRxQosClass
      INTEGER,
   mscAtmIfVccTmAtmServiceCategory
      INTEGER,
   mscAtmIfVccTmTrafficShaping
      INTEGER,
   mscAtmIfVccTmBearerClassBbc
      INTEGER,
   mscAtmIfVccTmTransferCapabilityBbc
      INTEGER,
   mscAtmIfVccTmClippingBbc
      INTEGER,
   mscAtmIfVccTmUnshapedTransmitQueueing
      INTEGER,
   mscAtmIfVccTmBestEffort
      INTEGER,
   mscAtmIfVccTmForceTagging
      INTEGER,
   mscAtmIfVccTmWeight
      Unsigned32,
   mscAtmIfVccTmUsageParameterControl
      INTEGER,
   mscAtmIfVccTmTxPacketWiseDiscard
      OCTET STRING,
   mscAtmIfVccTmRxPacketWiseDiscard
      OCTET STRING,
   mscAtmIfVccTmBandwidthElastic
      INTEGER,
   mscAtmIfVccTmBandwidthReduction
      Unsigned32,
   mscAtmIfVccTmAbrConnectionType
      INTEGER }

mscAtmIfVccTmTxTrafficDescType OBJECT-TYPE
   SYNTAX     INTEGER  {
                 n1(1),
                 n2(2),
                 n3(3),
                 n4(4),
                 n5(5),
                 n6(6),
                 n7(7),
                 n8(8),
                 n9(9) }
   ACCESS     read-only
   STATUS     mandatory
   DESCRIPTION
     "T his attribute indicates the type of traffic management which is 
      applied to the transmit direction of this connection as defined in the 
      ATM Forum. The txTrafficDescType determines the number and 
      meaning of the parameters in the txTrafficDescParm attribute."
::= { mscAtmIfVccTmOperEntry 10 }

mscAtmIfVccTmTxQosClass OBJECT-TYPE
   SYNTAX     INTEGER  {
                 n0(0),
                 n1(1),
                 n2(2),
                 n3(3),
                 n4(4),
                 notApplicable(14) }
   ACCESS     read-only
   STATUS     mandatory
   DESCRIPTION
     "This attribute indicates the quality of service for the calling to called 
      direction for this connection. This is only applicable to Soft PVC 
      and SVC connections. 
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified QOS class; no objective is specified for 
      the performance parameters.
      
      A value of notApplicable is displayed in the case of nailed-up PVCs 
      for which this attribute has no significance."
::= { mscAtmIfVccTmOperEntry 31 }

mscAtmIfVccTmTxQueueLength OBJECT-TYPE
   SYNTAX     Unsigned32 (0..30720)
   ACCESS     read-only
   STATUS     mandatory
   DESCRIPTION
     "This attribute indicates the current number of cells in the transmit 
      queue for this connection. 
      
      If this connection has unshapedTransmitQueueing attribute 
      displayed as common, this attribute displays the length of the 
      common queue which is used for this atm service category. 
      
      If this connection has unshapedTransmitQueueing attribute 
      displayed as fifo, this attribute indicates the number of cells for this 
      connection which are enqueued in a first-in-first-out queuing 
      method for this atm service category. This will only occur for 
      connections on ATM IP cards with atmServiceCategory of nrtVbr 
      or ubr. 
      
      If this connection has unshapedTransmitQueueing attribute 
      displayed as perVc or as notApplicable, this attribute displays the 
      length of the per-VC queue.
      
      For the 1pOC48SmSrAtm card, this attribute displays the current 
      number of cells in the link class queue used by this connection to 
      buffer its traffic.
      
      
      This attribute does not apply to basic Vpts."
::= { mscAtmIfVccTmOperEntry 32 }

mscAtmIfVccTmTxQueueCongestionState OBJECT-TYPE
   SYNTAX     Unsigned32 (0..3)
   ACCESS     read-only
   STATUS     mandatory
   DESCRIPTION
     "This attribute indicates the congestion state of the transmit queue 
      for this connection. 
      
      If this connection has unshapedTransmitQueueing attribute 
      displayed as common, this attribute displays the congestion state of 
      the common queue. If this connection has 
      unshapedTransmitQueueing attribute displayed as perVc or as 
      notApplicable, this attribute displays the congestion state of the per-
      VC queue.
      
      For the 1pOC48SmSrAtm card, this attribute displays the current 
      congestion state of the link class queue used by this connection to 
      buffer its traffic.
      
      The congestion state of a queue is indicated by a numeric value 
      ranging from 0 to 3. When a queue is in a congested state x, only 
      traffic with discard priority (DP) 0 to x are enqueued. Traffic with 
      DP > x is discarded. 
      
      For example, if the congestion state is 3, there is no congestion and 
      all traffic is enqueued. Likewise, when the congestion state is 0, 
      there is maximum congestion and only traffic with DP=0 is 
      enqueued on that queue.
      
      This attribute does not apply to basic Vpts."
::= { mscAtmIfVccTmOperEntry 33 }

mscAtmIfVccTmHoldingPriority OBJECT-TYPE
   SYNTAX     INTEGER  {
                 n0(0),
                 n1(1),
                 n2(2),
                 n3(3),
                 n4(4),
                 notApplicable(6) }
   ACCESS     read-only
   STATUS     mandatory
   DESCRIPTION
     "This attribute indicates the actual holding priority in effect for this 
      connection. In a situation where the link bandwidth fluctuates, such 
      as over an IMA link, holding priority is used to determine which 
      connections are held and which are released. Holding priority 4 
      connections are the first to be released. Holding priority 0 
      connections are the last to be released. Some applications, for 
      example Vcc Test, may override the provisioned holding priority. 
      
      A value of notApplicable is displayed when this is an elastic 
      connection. Holding priority does not apply to bandwidth elastic 
      connections.
      
      Holding priority has no effect if the equivalent cell rate (ECR) for a 
      connection is zero.
      
      This attribute does not apply to Vpt Vccs."
::= { mscAtmIfVccTmOperEntry 35 }

mscAtmIfVccTmRxTrafficDescType OBJECT-TYPE
   SYNTAX     INTEGER  {
                 n1(1),
                 n2(2),
                 n3(3),
                 n4(4),
                 n5(5),
                 n6(6),
                 n7(7),
                 n8(8),
                 n9(9) }
   ACCESS     read-only
   STATUS     mandatory
   DESCRIPTION
     "This attribute indicates the type of traffic management which is 
      applied to the receive direction of this connection as defined in the 
      ATM Forum. The rxTrafficDescType determines the number and 
      meaning of the parameters in the rxTrafficDescParm attribute."
::= { mscAtmIfVccTmOperEntry 40 }

mscAtmIfVccTmRxQosClass OBJECT-TYPE
   SYNTAX     INTEGER  {
                 n0(0),
                 n1(1),
                 n2(2),
                 n3(3),
                 n4(4),
                 notApplicable(14),
                 sameAsFwd(15) }
   ACCESS     read-only
   STATUS     mandatory
   DESCRIPTION
     "This attribute indicates the quality of service for the called to calling 
      direction for this connection. This is only applicable to Soft PVC 
      and SVC connections. 
      
      Class 1 supports a QOS that meets Service Class A performance 
      requirements (circuit emulation, constant bit rate video).
      
      Class 2 supports a QOS that meets Service Class B performance 
      requirements (variable bit rate audio and video).
      
      Class 3 supports a QOS that meets Service Class C performance 
      requirements (Connection-Oriented Data Transfer).
      
      Class 4 supports a QOS that meets Service Class D performance 
      requirements (Connectionless Data Transfer).
      
      Class 0 is the unspecified QOS class; no objective is specified for 
      the performance parameters.
      
      A value of notApplicable is displayed in the case of nailed-up PVCs 
      for which this attribute has no significance."
::= { mscAtmIfVccTmOperEntry 61 }

mscAtmIfVccTmAtmServiceCategory OBJECT-TYPE
   SYNTAX     INTEGER  {
                 unspecifiedBitRate(0),
                 constantBitRate(1),
                 rtVariableBitRate(2),
                 nrtVariableBitRate(3),
                 availableBitRate(4) }
   ACCESS     read-only
   STATUS     mandatory
   DESCRIPTION
     "This attribute indicates the ATM service category used for traffic in 
      both directions of the connection. 
      
      The constantBitRate service category is intended for real time 
      applications, that is, those requiring tightly constrained delay and 
      delay variation, as would be appropriate for voice and video 
      applications. The consistent availability of a fixed quantity of 
      bandwidth is considered appropriate for CBR service. Cells which 
      are delayed beyond the value specified by Cell Transfer Delay are 
      assumed to have significantly reduced value for the application.
      
      The rtVariableBitRate service category is intended for real time 
      applications; that is those requiring tightly constrained delay and 
      delay variation, as would be appropriate for voice and video 
      applications. Sources are expected to transmit at a rate which varies 
      with time. Equivalently, the source can be described as 'bursty'. 
      Cells which are delayed beyond the value specified by Cell Transfer 
      Delay are assumed to be of significantly reduced value to the 
      application. Real time VBR service may support statistical 
      multiplexing of real time sources.
      
      The nrtVariableBitRate service category is intended for non-real 
      time applications which have bursty traffic characteristics and which 
      can be characterized in terms of a PCR, SCR, and MBS. For those 
      cells which are transferred within the traffic contract, the application 
      expects a low cell loss ratio. For all connections, it expects a bound 
      on the mean cell transfer delay. Non-real time VBR service may 
      support statistical multiplexing of connections.
      
      The availableBitRate service is an ATM layer service category for 
      which the limiting ATM layer transfer characteristics provided by 
      the network may change subsequent to connection establishment. 
      ABR service has a flow control mechanism which supports several 
      types of feedback to control the source rate in response to changing 
      ATM layer transfer characteristics. ABR service is not intended to 
      support real-time applications.
      
      The unspecifiedBitRate service is intended for non-real time 
      applications, that is those not requiring tightly constrained delay 
      and delay variation. UBR sources are expected to be bursty. UBR 
      service supports a high degree of statistical multiplexing among 
      sources. UBR service does not specify traffic related service 
      guarantees. No numerical commitments are made with respect to 
      the cell loss ratio experienced by a UBR connection, or as to the 
      cell transfer delay experienced by cells on the connection."
::= { mscAtmIfVccTmOperEntry 62 }

mscAtmIfVccTmTrafficShaping OBJECT-TYPE
   SYNTAX     INTEGER  {
                 disabled(1),
                 notApplicable(4),
                 linear(5),
                 inverseUpc(6) }
   ACCESS     read-only
   STATUS     mandatory
   DESCRIPTION
     "This attribute indicates the traffic shaping state of the connection.
      
      A value of notApplicable indicates that traffic shaping is not 
      applicable or not supported for this connection. This is the case:
      - when the txTrafficDescType is 1 or 2.
      - for standard Vpt Vccs and basic Vpts.
      - for CQC-based ATM cards, when the atmServiceCategory is 
      constantBitRate.
      
      In these cases, the value of notApplicable is set regardless of 
      whether traffic shaping is enabled or disabled in the provisioning 
      data.
      
      For the 1pOC12SmLrAtm card, traffic shaping is not available, 
      therefore this attribute is always notApplicable.
      
      A value of disabled indicates that traffic shaping is applicable and 
      supported for the type of connection but has been turned off in the 
      provisioning data.
      
      A value of linear or inverseUpc indicates that traffic shaping is 
      applicable and supported for the type of connection and has been 
      turned on in the provisioning data. This is the only case that 
      indicates that traffic shaping is performed on the connection. In this 
      case, the actual shaping rate is reflected in the txTrafficDescParm 
      attribute, parameter number 4. A value of linear indicates that 
      traffic is being shaped at the constant rate indicated in 
      txTrafficDescParm 4.
      
      A value of inverseUpc is possible only on ATM IP cards. This value 
      indicates that the shaper strictly conforms to the requirements of a 
      dual leaky bucket UPC enforcer. This value is indicated if traffic 
      shaping is enabled, and the txTrafficDescType for this connection is 
      6, 7 or 8.
      
      Traffic shaping for connections with atmServiceCategory as 
      availableBitRate (txTrafficDescType 9) depends upon the 
      abrConnectionType attribute. If abrConnectionType is sourceDest 
      or virtualSourceDest, the value of this attribute is linear. If 
      abrConnectionType is erSwitch or efciSwitch, this attribute is 
      notApplicable."
::= { mscAtmIfVccTmOperEntry 70 }

mscAtmIfVccTmBearerClassBbc OBJECT-TYPE
   SYNTAX     INTEGER  {
                 a(1),
                 c(3),
                 x(16),
                 vp(24),
                 notApplicable(30) }
   ACCESS     read-only
   STATUS     mandatory
   DESCRIPTION
     "This attribute indicates the bearer capability for this connection.
      
      Class a service is a connection-oriented, constant bit rate ATM 
      transport service. Class a service has end to end timing 
      requirements and may require stringent cell loss, cell delay and cell 
      delay variation performance.When a is displayed, the user is 
      requesting more than an ATM only service. The network may look 
      at the AAL to provide interworking based upon its contents. 
      
      Class c service is a connection-oriented, variable bit rate ATM 
      transport service. Class c service has no end-to-end timing 
      requirements.When c is displayed, the user is requesting more than 
      an ATM only service. The network interworking function may look 
      at the AAL and provide service based on it.
      
      Class x service is a connection-oriented ATM transport service 
      where the AAL, trafficType (cbr or vbr), and timing requirements 
      are user defined (that is, transparent to the network). When the 
      value of this attribute is x, the user is requesting an ATM only 
      service from the network. In this case, the network shall not process 
      any higher layer protocol.
      
      Class vp service is used to indicate a transparent VP service when 
      the user is requesting an ATM only service from the network. In this 
      case, the network does not process any higher layer protocol. This 
      service differs from class x service in that with the class vp service 
      both the VCI field (except for VCI values 0, 3, 4, and 6 through 15) 
      and Payload Type field are transported transparently by the network. 
      This attribute value is only applicable to SPVP and SVP 
      connections.
      
      A value of notApplicable is displayed in the case of nailed-up PVCs 
      for which this attribute has no significance."
::= { mscAtmIfVccTmOperEntry 71 }

mscAtmIfVccTmTransferCapabilityBbc OBJECT-TYPE
   SYNTAX     INTEGER  {
                 n0(0),
                 n1(1),
                 n2(2),
                 n5(5),
                 n8(8),
                 n9(9),
                 n10(10),
                 notApplicable(30) }
   ACCESS     read-only
   STATUS     mandatory
   DESCRIPTION
     "This attribute indicates the transfer capability for this connection. 
      Uni 3.0/3.1 traffic type and end-to-end timing parameters are 
      mapped into this parameter as follows:
      <transferCapability: TrafficType, Timing>
      0: NoIndication, NoIndication
      1: NoIndication, yes
      2: NoIndication, no
      5: CBR, yes
      8: VBR, NoIndication
      9: VBR, yes
      10: VBR, no
      
      A value of notApplicable is displayed in the case of nailed-up PVCs 
      for which this attribute has no significance, or in the case that the 
      transfer capability in the call request was set to NoIndication.
      
      The CBR traffic type refers to traffic offered on services such as a 
      constant bit rate video service or a circuit emulation.
      
      The VBR traffic type refers to traffic offered on services such as 
      packetized audio and video, or data.
      
      The value NoIndication for traffic type is used if the user has not set 
      the traffic type; similarly for end-to-end timing.
      
      The value yes for end-to-end timing indicates that end-to-end 
      timing is required for the connection.
      
      The value no for end-to-end timing indicates that end-to-end timing 
      is not required for the connection."
::= { mscAtmIfVccTmOperEntry 72 }

mscAtmIfVccTmClippingBbc OBJECT-TYPE
   SYNTAX     INTEGER  {
                 no(0),
                 yes(1),
                 notApplicable(14) }
   ACCESS     read-only
   STATUS     mandatory
   DESCRIPTION
     "This attribute indicates the value of the clipping susceptibility 
      parameter in the broadband bearer capability (BBC) Information 
      Element.
      
      Clipping is an impairment in which the first fraction of a second of 
      information to be transferred is lost. It occurs after a call is 
      answered and before an associated connection is switched through.
      
      A value of notApplicable is displayed in the case of nailed-up PVCs 
      for which this attribute has no significance."
::= { mscAtmIfVccTmOperEntry 74 }

mscAtmIfVccTmUnshapedTransmitQueueing OBJECT-TYPE
   SYNTAX     INTEGER  {
                 perVc(0),
                 common(1),
                 notApplicable(4),
                 fifo(5) }
   ACCESS     read-only
   STATUS     mandatory
   DESCRIPTION
     "This attribute indicates the unshaped transmit queuing state of the 
      connection.
      
      A value of common indicates that transmit traffic is being enqueued 
      onto the common transmit queue for this service category. 
      The txQueueLength attribute indicates the current length of the 
      common transmit queue.
      
      A value of fifo indicates that transmit traffic is being queued in a 
      first-in-first-out basis for this service category. This is similar to 
      common queueing, but the txQueueLength attribute indicates the 
      number of cells in this connection queue. A value of fifo will only 
      be indicated for connections on ATM IP cards with 
      atmServiceCategory of nrtVbr or ubr. 
      
      A value of perVc indicates that transmit traffic is being enqueued 
      onto a per-VC queue for this connection. 
      
      A value of notApplicable indicates that transmit traffic is being 
      shaped for this connection, or that unshaped transmit queuing is not 
      applicable for this type of connection. Transmit traffic for a shaped 
      connection is enqueued onto a per-VC queue, but this attribute is 
      only applicable for unshaped connections. Unshaped transmit 
      queuing is not applicable for basic Vpts.
      
      For 1pOC12SmLrAtm cards, perVc queueing is not available thus 
      this attribute only indicates common or notApplicable."
::= { mscAtmIfVccTmOperEntry 75 }

mscAtmIfVccTmBestEffort OBJECT-TYPE
   SYNTAX     INTEGER  {
                 indicated(0),
                 notIndicated(1),
                 notApplicable(14) }
   ACCESS     read-only
   STATUS     mandatory
   DESCRIPTION
     "This attribute indicates value of best effort parameter in the ATM 
      Traffic Descriptor Information Element.
      
      The value indicated implies that the quality of service for this 
      connection is not guaranteed.
      
      The value notIndicated implies that the quality of service for this 
      connection is guaranteed.
      
      A value of notApplicable is displayed in the case of nailed-up PVCs 
      for which this attribute has no significance."
::= { mscAtmIfVccTmOperEntry 76 }

mscAtmIfVccTmForceTagging OBJECT-TYPE
   SYNTAX     INTEGER  {
                 enabled(0),
                 disabled(1) }
   ACCESS     read-only
   STATUS     mandatory
   DESCRIPTION
     "This attribute indicates the state of force tagging option for this 
      connection. Force tagging refers to setting the CLP bit for all cells 
      on a connection. 
      
      For CQC-based ATM cards, this attribute is not applicable and is 
      not displayed.
      
      A value of enabled indicates that the CLP bit is being set to 1 for all 
      cells in the transmit direction on this connection. 
      
      A value of disabled indicates that the CLP bit is unchanged for cells 
      in the transmit direction on this connection. disabled is always 
      displayed for Vpts since forced tagging is applied on a per Vpt Vcc 
      basis."
::= { mscAtmIfVccTmOperEntry 78 }

mscAtmIfVccTmWeight OBJECT-TYPE
   SYNTAX     Unsigned32 (0 | 1..4095 | 65534)
   ACCESS     read-only
   STATUS     mandatory
   DESCRIPTION
     "This attribute indicates the relative weight of this unshaped 
      connection. Connections with a larger weight get a larger proportion 
      of the link bandwidth or in the case of standard Vpt Vccs, the Vpt 
      bandwidth.
      
      For all but standard Vpt Vccs, the default connection weight is 
      determined by the weight policy for a service category and the 
      traffic descriptor for a connection. For standard Vpt Vccs, the 
      default connection weight is determined by the Vcc's service 
      category.
      
      For CQC-based ATM cards, this attribute is not applicable and is 
      not displayed.
      
      A value from 1 to 4095 indicates an actual weight. The value 
      upToQueueLimit indicates that the weight of a connection is up to 
      the transmit queue limit for this connection. upToQueueLimit is 
      used with common (first-in-first-out) queueing. 
      
      This attribute is displayed as notApplicable if:
      - this connection has trafficShaping displayed as linear or 
      inverseUpc.
      - this is a basic Vpt.

      VALUES (

      0 = upToQueueLimit

      65534 = notApplicable

      )"
::= { mscAtmIfVccTmOperEntry 79 }

mscAtmIfVccTmUsageParameterControl OBJECT-TYPE
   SYNTAX     INTEGER  {
                 enforced(0),
                 disabled(1),
                 notApplicable(3),
                 monitored(4) }
   ACCESS     read-only
   STATUS     mandatory
   DESCRIPTION
     "This attribute indicates the UPC state of the connection.
      
      A value of notApplicable indicates that UPC is not applicable or not 
      supported for the connection. This is the case:
      - when the connection's rxTrafficDescType is 1 or 2. 
      - for standard Vpt Vccs and basic Vpts.
      
      A value of notApplicable is set regardless of whether UPC is 
      disabled or enabled in provisioning data.
      
      A value of disabled indicates that UPC is applicable and supported 
      for the type of connection but has been turned off in the 
      provisioning data.
      
      A value of enforced indicates that UPC is actively checking 
      conformance for the connection and is discarding or tagging cells 
      which do not conform to the connection traffic contract. The traffic 
      descriptor parameters used for UPC conformance are reflected in 
      the rxTrafficDescParms of the connection. On ATM IP cards, the 
      counts of UPC violations are visible in the Vcc, Vpc or Vpt 
      rxUpcViolationsOnEnforcer1 or rxUpcViolationsOnEnforcer2 
      attributes. 
      
      ATM IP cards provide the ability to monitor UPC violations without 
      tagging or discarding. A value of monitored indicates that UPC is 
      actively checking conformance for the connection and counting the 
      violations, but is not discarding or tagging cells which do not 
      conform to the connection traffic contract. The traffic descriptor 
      parameters used for UPC conformance are reflected in the 
      rxTrafficDescParms of the connection. The counts of UPC 
      violations are visible in the Vcc, Vpc or Vpt. 
      rxUpcViolationsOnEnforcer1 or rxUpcViolationsOnEnforcer2 
      attributes. The value of monitored appears only on ATM IP cards. 
      
      If the atmServiceCategory for this connection is availableBitRate, a 
      value of enforced indicates that Dynamic Generic Cell Rate 
      Algorithm (DGCRA) is active for the connection. The traffic 
      descriptor parameters used for DGCRA enforcement are reflected in 
      the rxTrafficDescParm of the connection."
::= { mscAtmIfVccTmOperEntry 80 }

mscAtmIfVccTmTxPacketWiseDiscard OBJECT-TYPE
   SYNTAX     OCTET STRING (SIZE (1))
   ACCESS     read-only
   STATUS     mandatory
   DESCRIPTION
     "This attribute indicates the current set of packet-wise discard 
      functions in effect in the transmit data direction at this connection 
      point.
      
      A value of ppd indicates that the Partial Packet Discard (PPD) 
      function is in effect. PPD may be applied at an intermediate 
      connecting point for a connection which is transporting frame traffic 
      (AAL5 at the endpoint). PPD is controlled by provisioning for 
      PVCs and SPVCs, and by call setup parameters in the AAL and 
      Traffic Descriptor Information Elements.
      
      A value of epd indicates that the Early Packet Discard (EPD) 
      function is in effect at this connection endpoint. On CQC-based 
      ATM cards, PPD and EPD are enabled by default at a connection 
      endpoint which is performing AAL5 segmentation and assembly.
      
      A value of wred indicates that Weighted Random Early Detection is 
      in effect at this connection point. W-RED can be enabled by 
      provisioning for PVCs and SPVCs.
      
      On ATM IP cards, all packet-wise discard functions also apply to 
      provisioned virtual path connections (VPCs). On CQC-based ATM 
      cards, packet-wise functions are not applicable for VPCs.
      
      This attribute is not applicable for Vpts.

      Description of bits:
      ppd(0)
      epd(1)
      wred(2)"
::= { mscAtmIfVccTmOperEntry 85 }

mscAtmIfVccTmRxPacketWiseDiscard OBJECT-TYPE
   SYNTAX     OCTET STRING (SIZE (1))
   ACCESS     read-only
   STATUS     mandatory
   DESCRIPTION
     "This attribute indicates the current set of packet-wise discard 
      functions in effect in the receive data direction at this connection 
      point.
      
      A value of ppd indicates that the Partial Packet Discard (PPD) 
      function is in effect. PPD may be applied at an intermediate 
      connecting point for a connection which is transporting frame traffic 
      (AAL5 at the endpoint). PPD is controlled by provisioning for 
      PVCs and SPVCs, and by call setup parameters in the AAL and 
      Traffic Descriptor Information Elements.
      
      A value of epd indicates that the Early Packet Discard (EPD) 
      function is in effect at this connection endpoint. PPD and EPD are 
      enabled by default at a connection endpoint which is performing 
      AAL5 segmentation and assembly.
      
      On ATM IP cards, all packet-wise discard functions also apply to 
      provisioned virtual path connections (VPCs). On CQC-based ATM 
      cards, packet-wise functions are not applicable for VPCs.
      
      This attribute is not applicable for Vpts.

      Description of bits:
      ppd(0)
      epd(1)"
::= { mscAtmIfVccTmOperEntry 86 }

mscAtmIfVccTmBandwidthElastic OBJECT-TYPE
   SYNTAX     INTEGER  {
                 no(0),
                 yes(1) }
   ACCESS     read-only
   STATUS     mandatory
   DESCRIPTION
     "This attribute is only of importance for connections which are 
      carried on a link with a variable bandwidth. For example, the 
      bandwidth may be reduced in the event that one or more physical 
      links in the IMA group fail, such that the originally requested 
      bandwidth cannot be maintained. This attribute shows whether the 
      application (for example, Trunk) running on this connection can 
      continue to operate if the bandwidth is reduced. If the bandwidth is 
      reduced, the amount by which it is reduced is displayed in the 
      bandwidthReduction attribute. 
      
      A value of yes, indicates that this connection is elastic, and the 
      bandwidth may be reduced but the connection is not released. 
      
      A value of no indicates that the bandwidth for this connection is not 
      reduced in the event of link bandwidth reduction. However, this 
      connection may be released based on its holdingPriority.
      
      Bandwidth elasticity has no effect for connections which have an 
      equivalent cell rate (ECR) of zero. 
      
      This attribute is not applicable for Vpts and Vpt Vccs."
::= { mscAtmIfVccTmOperEntry 90 }

mscAtmIfVccTmBandwidthReduction OBJECT-TYPE
   SYNTAX     Unsigned32 (0..2147483647)
   ACCESS     read-only
   STATUS     mandatory
   DESCRIPTION
     "This attribute shows the amount by which the bandwidth has been 
      reduced for this connection. This value is non-zero only for 
      connections which have bandwidthElastic displayed as yes, and 
      which are also operating in a reduced bandwidth mode. This is 
      typically the case for selected connections running over an IMA 
      link. This attribute takes a value from 0 (no reduction) up to the 
      ECR. For all connections which are running at their full allocated 
      bandwidth, bwReduction has the value 0. Connections which have 
      been reduced in allocated bandwidth have a positive number for this 
      attribute. The bwReduction may be subtracted from the ECR (which 
      is displayed as txTrafficDescParm 5) to determine the actual 
      bandwidth allocated to this connection."
::= { mscAtmIfVccTmOperEntry 100 }

mscAtmIfVccTmAbrConnectionType OBJECT-TYPE
   SYNTAX     INTEGER  {
                 erSwitch(1),
                 efciSwitch(2),
                 virtualSourceDest(3),
                 sourceDest(4),
                 nonAbrInterworking(5),
                 notApplicable(15) }
   ACCESS     read-only
   STATUS     mandatory
   DESCRIPTION
     "This attribute indicates the type of ABR behavior which is in effect 
      at this connection. This attribute is only applicable if the 
      atmServiceCategory attribute is availableBitRate. If the 
      atmServiceCategory attribute is not availableBitRate, this attribute 
      value is set to notApplicable.
      
      For CQC-based ATM cards and the 1pOC12SmLrAtm card, the 
      notApplicable, efciSwitch or nonAbrInterworking. In EFCI 
      marking mode, the Explicit Forward Congestion Indication (EFCI) 
      field in the data cell headers is used to indicate transmit queue 
      congestion. 
      
      For ATM IP cards other than 1pOC12SmLrAtm, if the displayed as 
      connectionEndPoint, this attribute has the value sourceDest. In this 
      mode, the ABR Source and Destination behavior is in effect at this 
      connection. This attribute is also sourceDest in the case where the 
      next hop connection is specified as nonAbrInterworking. The next 
      hop connection is the Vcc or Vpc identified by the nextHop attribute 
      of the Nrp or Rp component. 
      
      If the connectionPointType is not connectionEndPoint, the value of 
      this attribute depends upon the abrConnectionType provisioning 
      and the card type to which the traffic is forwarded on the backplane. 
      The default abrConnectionType is provisioned at the CA Abr 
      abrConnectionType attribute, and may be overridden for a 
      provisioned connection in the Vcd Tm abrConnectionType or Vpd 
      Tm abrConnectionType attribute. If the CA Abr abrConnectionType 
      attribute is virtualSourceDest at either one of the two connection 
      points, and if both the connection points are defined on ATM IP 
      cards, virtual source and destination behavior is applied to the 
      connection. In this instance, the attribute displays the value 
      virtualSourceDest.
      
      This attribute has the value erSwitch if ABR explicit rate 
      functionality is in effect at this connection. In this mode, the switch 
      may modify the Explicit Rate (ER) field of backward Resource 
      Management (RM) cells to indicate the status of congestion at this 
      connection point.
      
      This attribute has the value nonAbrInterworking in the case where 
      this connection point is functioning as an SPVC origin for an ABR 
      connection where the link side of this connection is configured as a 
      non-ABR ATM service category. This means that there are no RM 
      cells on the link side of this connection, and that the next hop 
      connection point is performing as an ABR sourceDest."
::= { mscAtmIfVccTmOperEntry 110 }

mscAtmIfVccTmTxTdpTable OBJECT-TYPE
   SYNTAX     SEQUENCE OF MscAtmIfVccTmTxTdpEntry
   ACCESS     not-accessible
   STATUS     mandatory
   DESCRIPTION
     "This attribute is a vector of five transmit traffic parameters whose 
      mapping is defined by the txTrafficDescType attribute. 
      
      The values of peak cell rate (PCR), sustained cell rate (SCR), 
      Minimum Cell Rate (MCR), actual cell rate (ACR), explicit rate 
      (ER), equivalent cell rate (ECR), and actual shaping rate are 
      expressed in cell/s. Maximum burst size (MBS) is expressed in 
      cells. CDVT is expressed in microseconds. 
      
      When txTrafficDescType is 1 or 2, parameters 1 through 5 are 
      unused.
      
      In this description, PCR is the greater of either the PCR or the 
      requested shaping rate (parameter 1 or parameter 5) specified in the 
      txTrafficDescParm attribute under the Vcd Tm or Vpd Tm 
      component.
      
      When txTrafficDescType is 3, parameter 1 represents the PCR for 
      CLP equal to 0 or 1 traffic; parameters 2 and 3 are unused.
      
      When txTrafficDescType is 4, parameter 1 represents the PCR for 
      CLP equal to 0 and 1 traffic; parameter 2 represents the PCR for 
      CLP equal to 0 traffic with cell discard.
      
      When txTrafficDescType is 5, parameter 1 represents the PCR for 
      CLP equal to 0 and 1 traffic; parameter 2 represents the PCR for 
      CLP equal to 0 traffic with cell tagging.
      
      When txTrafficDescType is 6, parameter 1 represents the PCR for 
      CLP equal to 0 and 1 traffic; parameter 2 represents the SCR for 
      CLP equal to 0 and 1 traffic; parameter 3 represents the MBS for 
      CLP equal to 0 and 1 traffic.
      
      When txTrafficDescType is 7, parameter 1 represents the PCR for 
      CLP equal to 0 and 1 traffic; parameter 2 represents the SCR for 
      CLP equal to 0 traffic with cell discard; parameter 3 represents the 
      MBS for CLP equal to 0 traffic.
      
      When txTrafficDescType is 8, parameter 1 represents the PCR for 
      CLP equal to 0 and 1 traffic; parameter 2 represents the SCR for 
      CLP equal to 0 traffic with cell tagging; parameter 3 represents the 
      MBS for CLP equal to 0 traffic.
      
      When txTrafficDescType is 3, 4, 5, 6, 7, or 8, parameter 4 reflects 
      the actual shaping rate in cell/s for this connection. For CQC-based 
      ATM cards, the set of available shaping rates is based on the 
      number of interfaces doing shaping (attribute 
      perVcQueueInterfaces), and the shapingScalingFactor attribute of 
      the Arc Cqc Override component. A rate of zero (0) indicates that 
      shaping is not performed, or that the interface is down. 
      
      When txTrafficDescType is 9, parameter 1 represents the PCR; 
      parameter 2 represents the Cell Delay Variation Toleration (CDVT); 
      parameter 3 represents the Minimum Cell Rate (MCR); the meaning 
      of parameter 4 depends upon the value of the abrConnectionType 
      attribute. if abrConnectionType is sourceDest or 
      virtualSourceDest, parameter 4 represents the Allowed Cell Rate 
      (ACR); If abrConnectionType is erSwitch, parameter 4 represents 
      the Explicit Rate (ER); and if abrConnectionType is efciSwitch, 
      parameter 4 reflects the actual shaping rate in cell/s for this 
      connection.
      
      When txTrafficDescType is 3, 4, 5, 6, 7, 8, or 9, parameter 5 reflects 
      the equivalent cell rate in cell/s for this connection as determined by 
      the Connection Admission Control (CAC) algorithm. The 
      equivalent cell rate is useful in determining the admission 
      characteristics of this connection."
::= { mscAtmIfVccTm 451 }

mscAtmIfVccTmTxTdpEntry OBJECT-TYPE
   SYNTAX     MscAtmIfVccTmTxTdpEntry
   ACCESS     not-accessible
   STATUS     mandatory
   DESCRIPTION
     "An entry in the mscAtmIfVccTmTxTdpTable."
   INDEX {
      mscAtmIfIndex,
      mscAtmIfVccIndex,
      mscAtmIfVccTmIndex,
      mscAtmIfVccTmTxTdpIndex }
::= { mscAtmIfVccTmTxTdpTable 1 }

MscAtmIfVccTmTxTdpEntry ::= SEQUENCE {
   mscAtmIfVccTmTxTdpIndex
      Integer32,
   mscAtmIfVccTmTxTdpValue
      Unsigned32 }

mscAtmIfVccTmTxTdpIndex OBJECT-TYPE
   SYNTAX     Integer32 (1..5)
   ACCESS     not-accessible
   STATUS     mandatory
   DESCRIPTION
     "This variable represents the mscAtmIfVccTmTxTdpTable
      specific index for the mscAtmIfVccTmTxTdpTable."
::= { mscAtmIfVccTmTxTdpEntry 1 }

mscAtmIfVccTmTxTdpValue OBJECT-TYPE
   SYNTAX     Unsigned32 (0..2147483647)
   ACCESS     read-only
   STATUS     mandatory
   DESCRIPTION
     "This variable represents an individual value for the
      mscAtmIfVccTmTxTdpTable."
::= { mscAtmIfVccTmTxTdpEntry 2 }

mscAtmIfVccTmTxQThreshTable OBJECT-TYPE
   SYNTAX     SEQUENCE OF MscAtmIfVccTmTxQThreshEntry
   ACCESS     not-accessible
   STATUS     mandatory
   DESCRIPTION
     "This attribute indicates the queue limit and the discard thresholds 
      for the transmit queue of this connection. 
      
      If this connection has unshapedTransmitQueueing attribute 
      displayed as common, this attribute displays the thresholds of the 
      common queue. If this connection has unshapedTransmitQueueing 
      attribute displayed as perVc or as notApplicable, this attribute 
      displays the thresholds of the per-VC queue.
      
      The first element indicates the queue limit. The provisioned value of 
      the transmit queue limit is derived from the txQueueLimit attribute 
      under the service category subcomponents of the CA component for 
      the service category of this connection. 
      
      The second element is the threshold that marks the transition from 
      congestion state 1 to congestion state 0. This is the threshold at 
      which traffic with discard priority (DP) = 1 is discarded. This 
      threshold is set at approximately 90 percent of the first parameter, 
      the operational queue limit.
      
      The third element is the threshold that marks the transition from 
      congestion state 2 to congestion state 1. This is the threshold at 
      which traffic with DP = 2 is discarded. This threshold is set at 
      approximately 75 percent of the first parameter, the operational 
      queue limit.
      
      The fourth element is the threshold that marks the transition from 
      congestion state 3 to congestion state 2. This is the threshold at 
      which traffic with DP = 3 is discarded. This threshold is set at 
      approximately 35 percent of the first parameter, the operational 
      queue limit.
      
      This attribute does not apply to basic Vpts."
::= { mscAtmIfVccTm 452 }

mscAtmIfVccTmTxQThreshEntry OBJECT-TYPE
   SYNTAX     MscAtmIfVccTmTxQThreshEntry
   ACCESS     not-accessible
   STATUS     mandatory
   DESCRIPTION
     "An entry in the mscAtmIfVccTmTxQThreshTable."
   INDEX {
      mscAtmIfIndex,
      mscAtmIfVccIndex,
      mscAtmIfVccTmIndex,
      mscAtmIfVccTmTxQThreshIndex }
::= { mscAtmIfVccTmTxQThreshTable 1 }

MscAtmIfVccTmTxQThreshEntry ::= SEQUENCE {
   mscAtmIfVccTmTxQThreshIndex
      Integer32,
   mscAtmIfVccTmTxQThreshValue
      Unsigned32 }

mscAtmIfVccTmTxQThreshIndex OBJECT-TYPE
   SYNTAX     Integer32 (0..3)
   ACCESS     not-accessible
   STATUS     mandatory
   DESCRIPTION
     "This variable represents the mscAtmIfVccTmTxQThreshTable
      specific index for the mscAtmIfVccTmTxQThreshTable."
::= { mscAtmIfVccTmTxQThreshEntry 1 }

mscAtmIfVccTmTxQThreshValue OBJECT-TYPE
   SYNTAX     Unsigned32 (0..512000)
   ACCESS     read-only
   STATUS     mandatory
   DESCRIPTION
     "This variable represents an individual value for the
      mscAtmIfVccTmTxQThreshTable."
::= { mscAtmIfVccTmTxQThreshEntry 2 }

mscAtmIfVccTmRxTdpTable OBJECT-TYPE
   SYNTAX     SEQUENCE OF MscAtmIfVccTmRxTdpEntry
   ACCESS     not-accessible
   STATUS     mandatory
   DESCRIPTION
     "This attribute is a vector of four traffic parameters whose meanings 
      are defined by the rxTrafficDescType attribute. The values of peak 
      cell rate (PCR), sustained cell rate (SCR), minimum cell rate 
      (MCR) are expressed in cell/s. Maximum burst size (MBS) is 
      expressed in cells. Cell delay variation tolerance (CDVT) is 
      expressed in microseconds.
      
      When rxTrafficDescType is 1 or 2, none of the parameters are used.
      
      When rxTrafficDescType is 3, parameter 1 represents the PCR for 
      CLP equal to 0 and 1 traffic; parameter 4 represents the CDVT.
      
      When rxTrafficDescType is 4, parameter 1 represents the PCR for 
      CLP equal to 0 and 1 traffic; parameter 2 represents the PCR for 
      CLP equal to 0 traffic with cell discard; parameter 4 represents the 
      CDVT.
      
      When rxTrafficDescType is 5, parameter 1 represents the PCR for 
      CLP equal to 0 and 1 traffic; parameter 2 represents the PCR for 
      CLP equal to 0 traffic with cell tagging; parameter 4 represents the 
      CDVT.
      
      When rxTrafficDescType is 6, parameter 1 represents the PCR for 
      CLP equal to 0 and 1 traffic; parameter 2 represents the SCR for 
      CLP equal to 0 and 1 traffic; parameter 3 represents the MBS for 
      CLP equal to 0 and 1 traffic; parameter 4 represents the CDVT. 
      
      When rxTrafficDescType is 7, parameter 1 represents the PCR for 
      CLP equal to 0 and 1 traffic; parameter 2 represents the SCR for 
      CLP equal to 0 traffic with cell discard; parameter 3 represents the 
      MBS for CLP equal to 0 traffic; parameter 4 represents the CDVT.
      
      When rxTrafficDescType is 8, parameter 1 represents the PCR for 
      CLP equal to 0 and 1 traffic; parameter 2 represents the SCR for 
      CLP equal to 0 traffic with cell tagging; parameter 3 represents the 
      MBS for CLP equal to 0 traffic; parameter 4 represents the CDVT. 
      
      When rxTrafficDescType is 9, parameter 1 represents the PCR; 
      parameter 2 represents CDVT; parameter 3 represents the MCR; 
      parameter 4 is not used.
      
      If upc is disabled for this connection, the values of PCR, SCR, 
      MBS and CDVT are the provisioned parameters.
      
      If upc is enabled, the values of PCR, SCR, MBS, and CDVT are 
      exactly the values used by the usage parameter control hardware in 
      policing the arriving traffic. These may vary slightly from the 
      provisioned values due to granularity of the hardware. In the case 
      where the PCR is equal to the SCR, the effective MBS is zero."
::= { mscAtmIfVccTm 453 }

mscAtmIfVccTmRxTdpEntry OBJECT-TYPE
   SYNTAX     MscAtmIfVccTmRxTdpEntry
   ACCESS     not-accessible
   STATUS     mandatory
   DESCRIPTION
     "An entry in the mscAtmIfVccTmRxTdpTable."
   INDEX {
      mscAtmIfIndex,
      mscAtmIfVccIndex,
      mscAtmIfVccTmIndex,
      mscAtmIfVccTmRxTdpIndex }
::= { mscAtmIfVccTmRxTdpTable 1 }

MscAtmIfVccTmRxTdpEntry ::= SEQUENCE {
   mscAtmIfVccTmRxTdpIndex
      Integer32,
   mscAtmIfVccTmRxTdpValue
      Unsigned32 }

mscAtmIfVccTmRxTdpIndex OBJECT-TYPE
   SYNTAX     Integer32 (1..4)
   ACCESS     not-accessible
   STATUS     mandatory
   DESCRIPTION
     "This variable represents the mscAtmIfVccTmRxTdpTable
      specific index for the mscAtmIfVccTmRxTdpTable."
::= { mscAtmIfVccTmRxTdpEntry 1 }

mscAtmIfVccTmRxTdpValue OBJECT-TYPE
   SYNTAX     Unsigned32 (0..2147483647)
   ACCESS     read-only
   STATUS     mandatory
   DESCRIPTION
     "This variable represents an individual value for the
      mscAtmIfVccTmRxTdpTable."
::= { mscAtmIfVccTmRxTdpEntry 2 }

mscAtmIfVccTmTqpTable OBJECT-TYPE
   SYNTAX     SEQUENCE OF MscAtmIfVccTmTqpEntry
   ACCESS     not-accessible
   STATUS     mandatory
   DESCRIPTION
     "This attribute is a vector of three elements that indicate the quality 
      of service parameters for the forward direction for this connection. 
      This attribute is used for SPVC and SVC connections on a PNNI 
      interface.
      
      The cdv element indicates the acceptable peak-to-peak Cell Delay 
      Variation (CDV) of real-time connections (CBR and rt-VBR). 
      
      The ctd element indicates the acceptable maximum Cell Transfer 
      Delay (maxCtd) of real-time connections (CBR and rt-VBR). 
      
      The clr element indicates the acceptable Cell Loss Ratio (CLR) of 
      CBR, rt-VBR, and nrt-VBR connections."
::= { mscAtmIfVccTm 454 }

mscAtmIfVccTmTqpEntry OBJECT-TYPE
   SYNTAX     MscAtmIfVccTmTqpEntry
   ACCESS     not-accessible
   STATUS     mandatory
   DESCRIPTION
     "An entry in the mscAtmIfVccTmTqpTable."
   INDEX {
      mscAtmIfIndex,
      mscAtmIfVccIndex,
      mscAtmIfVccTmIndex,
      mscAtmIfVccTmTqpIndex }
::= { mscAtmIfVccTmTqpTable 1 }

MscAtmIfVccTmTqpEntry ::= SEQUENCE {
   mscAtmIfVccTmTqpIndex
      INTEGER,
   mscAtmIfVccTmTqpValue
      Unsigned32 }

mscAtmIfVccTmTqpIndex OBJECT-TYPE
   SYNTAX     INTEGER  {
                 cdv(0),
                 ctd(1),
                 clr(2) }
   ACCESS     not-accessible
   STATUS     mandatory
   DESCRIPTION
     "This variable represents the mscAtmIfVccTmTqpTable
      specific index for the mscAtmIfVccTmTqpTable."
::= { mscAtmIfVccTmTqpEntry 1 }

mscAtmIfVccTmTqpValue OBJECT-TYPE
   SYNTAX     Unsigned32 (0..2147483647)
   ACCESS     read-only
   STATUS     mandatory
   DESCRIPTION
     "This variable represents an individual value for the
      mscAtmIfVccTmTqpTable."
::= { mscAtmIfVccTmTqpEntry 2 }

mscAtmIfVccTmRqpTable OBJECT-TYPE
   SYNTAX     SEQUENCE OF MscAtmIfVccTmRqpEntry
   ACCESS     not-accessible
   STATUS     mandatory
   DESCRIPTION
     "This attribute is a vector of three elements that indicate the quality 
      of service parameters for the backward direction for this 
      connection. This attribute is used for SPVC and SVC connections 
      on a PNNI interface.
      
      The cdv element indicates the acceptable peak-to-peak Cell Delay 
      Variation (CDV) of real-time connections (CBR and rt-VBR). 
      
      The ctd element indicates the acceptable maximum Cell Transfer 
      Delay (maxCtd) of real-time connections (CBR and rt-VBR). 
      
      The clr element indicates the acceptable Cell Loss Ratio (CLR) of 
      CBR, rt-VBR, and nrt-VBR connections."
::= { mscAtmIfVccTm 455 }

mscAtmIfVccTmRqpEntry OBJECT-TYPE
   SYNTAX     MscAtmIfVccTmRqpEntry
   ACCESS     not-accessible
   STATUS     mandatory
   DESCRIPTION
     "An entry in the mscAtmIfVccTmRqpTable."
   INDEX {
      mscAtmIfIndex,
      mscAtmIfVccIndex,
      mscAtmIfVccTmIndex,
      mscAtmIfVccTmRqpIndex }
::= { mscAtmIfVccTmRqpTable 1 }

MscAtmIfVccTmRqpEntry ::= SEQUENCE {
   mscAtmIfVccTmRqpIndex
      INTEGER,
   mscAtmIfVccTmRqpValue
      Unsigned32 }

mscAtmIfVccTmRqpIndex OBJECT-TYPE
   SYNTAX     INTEGER  {
                 cdv(0),
                 ctd(1),
                 clr(2) }
   ACCESS     not-accessible
   STATUS     mandatory
   DESCRIPTION
     "This variable represents the mscAtmIfVccTmRqpTable
      specific index for the mscAtmIfVccTmRqpTable."
::= { mscAtmIfVccTmRqpEntry 1 }

mscAtmIfVccTmRqpValue OBJECT-TYPE
   SYNTAX     Unsigned32 (0..2147483647)
   ACCESS     read-only
   STATUS     mandatory
   DESCRIPTION
     "This variable represents an individual value for the
      mscAtmIfVccTmRqpTable."
::= { mscAtmIfVccTmRqpEntry 2 }


-- AtmIf/n Vpc/vpi Tm AvailableBitRate, 
-- AtmIf/n Vcc/vpi.vci Tm AvailableBitRate,
-- AtmIf/n Vpt/vpi Tm AvailableBitRate,
-- AtmIf/n Vpt/vpi Vcc/vci Tm AvailableBitRate
-- This component contains ABR-related operational attributes of a 
-- connection. It is dynamically created for connections where the 
-- atmServiceCategory is availableBitRate, and where 
-- abrConnectionType is sourceDest or virtualSourceDest.

mscAtmIfVccTmAbr OBJECT IDENTIFIER ::= { mscAtmIfVccTm 2 }



mscAtmIfVccTmAbrRowStatusTable OBJECT-TYPE
   SYNTAX     SEQUENCE OF MscAtmIfVccTmAbrRowStatusEntry
   ACCESS     not-accessible
   STATUS     mandatory
   DESCRIPTION
     "This entry controls the addition and deletion of 
      mscAtmIfVccTmAbr components."
::= { mscAtmIfVccTmAbr 1 }

mscAtmIfVccTmAbrRowStatusEntry OBJECT-TYPE
   SYNTAX     MscAtmIfVccTmAbrRowStatusEntry
   ACCESS     not-accessible
   STATUS     mandatory
   DESCRIPTION
     "A single entry in the table represents a single 
      mscAtmIfVccTmAbr component."
   INDEX {
      mscAtmIfIndex,
      mscAtmIfVccIndex,
      mscAtmIfVccTmIndex,
      mscAtmIfVccTmAbrIndex }
::= { mscAtmIfVccTmAbrRowStatusTable 1 }

MscAtmIfVccTmAbrRowStatusEntry ::= SEQUENCE {
   mscAtmIfVccTmAbrRowStatus
      RowStatus,
   mscAtmIfVccTmAbrComponentName
      DisplayString,
   mscAtmIfVccTmAbrStorageType
      StorageType,
   mscAtmIfVccTmAbrIndex
      NonReplicated }

mscAtmIfVccTmAbrRowStatus OBJECT-TYPE
   SYNTAX     RowStatus 
   ACCESS     read-only
   STATUS     mandatory
   DESCRIPTION
     "This variable is used as the basis for SNMP naming of
      mscAtmIfVccTmAbr components.
      These components cannot be added nor deleted."
::= { mscAtmIfVccTmAbrRowStatusEntry 1 }

mscAtmIfVccTmAbrComponentName OBJECT-TYPE
   SYNTAX     DisplayString 
   ACCESS     read-only
   STATUS     mandatory
   DESCRIPTION
     "This variable provides the component's string name for
      use with the ASCII Console Interface"
::= { mscAtmIfVccTmAbrRowStatusEntry 2 }

mscAtmIfVccTmAbrStorageType OBJECT-TYPE
   SYNTAX     StorageType 
   ACCESS     read-only
   STATUS     mandatory
   DESCRIPTION
     "This variable represents the storage type value for the
      mscAtmIfVccTmAbr tables."
::= { mscAtmIfVccTmAbrRowStatusEntry 4 }

mscAtmIfVccTmAbrIndex OBJECT-TYPE
   SYNTAX     NonReplicated 
   ACCESS     not-accessible
   STATUS     mandatory
   DESCRIPTION
     "This variable represents the index for the mscAtmIfVccTmAbr tables."
::= { mscAtmIfVccTmAbrRowStatusEntry 10 }

mscAtmIfVccTmAbrOperTable OBJECT-TYPE
   SYNTAX     SEQUENCE OF MscAtmIfVccTmAbrOperEntry
   ACCESS     not-accessible
   STATUS     mandatory
   DESCRIPTION
     "This group contains operational attributes for connections using 
      ABR service category."
::= { mscAtmIfVccTmAbr 110 }

mscAtmIfVccTmAbrOperEntry OBJECT-TYPE
   SYNTAX     MscAtmIfVccTmAbrOperEntry
   ACCESS     not-accessible
   STATUS     mandatory
   DESCRIPTION
     "An entry in the mscAtmIfVccTmAbrOperTable."
   INDEX {
      mscAtmIfIndex,
      mscAtmIfVccIndex,
      mscAtmIfVccTmIndex,
      mscAtmIfVccTmAbrIndex }
::= { mscAtmIfVccTmAbrOperTable 1 }

MscAtmIfVccTmAbrOperEntry ::= SEQUENCE {
   mscAtmIfVccTmAbrInitialCellRate
      Unsigned32,
   mscAtmIfVccTmAbrTransientBufferExposure
      Unsigned32,
   mscAtmIfVccTmAbrFixedRoundTripTime
      Unsigned32,
   mscAtmIfVccTmAbrRateDecreaseFactor
      Unsigned32,
   mscAtmIfVccTmAbrRateIncreaseFactor
      Unsigned32,
   mscAtmIfVccTmAbrMaxCellPerRmCell
      Unsigned32,
   mscAtmIfVccTmAbrMaxTimeBetweenRmCell
      Unsigned32,
   mscAtmIfVccTmAbrCutoffDecreaseFactor
      Unsigned32,
   mscAtmIfVccTmAbrAcrDecreaseTimeFactor
      Unsigned32,
   mscAtmIfVccTmAbrForwardRmCellLimit
      Unsigned32,
   mscAtmIfVccTmAbrTxRateChangeInfo
      INTEGER,
   mscAtmIfVccTmAbrAcrRateChangeInfo
      INTEGER,
   mscAtmIfVccTmAbrTxFwdRmCells
      Unsigned32,
   mscAtmIfVccTmAbrRxEfci
      INTEGER }

mscAtmIfVccTmAbrInitialCellRate OBJECT-TYPE
   SYNTAX     Unsigned32 (0..16777215)
   ACCESS     read-only
   STATUS     mandatory
   DESCRIPTION
     "This attribute indicates the Initial Cell Rate (ICR) parameter for this 
      connection. ICR is the rate at which a source should send initially 
      and after an idle period.
      
      For nailed-up connections, this attribute is determined by the 
      provisioned value of the initialCellRate attribute. For signalled 
      connections, it is indicated in the ABR Setup Parameters 
      Information Element.
      
      The ICR for a connection is a value between the MCR and the PCR. 
      Furthermore, ICR has an upper bound determined by the 
      transientBufferExposure divided by fixedRoundTripTime."
::= { mscAtmIfVccTmAbrOperEntry 10 }

mscAtmIfVccTmAbrTransientBufferExposure OBJECT-TYPE
   SYNTAX     Unsigned32 (0..16777215)
   ACCESS     read-only
   STATUS     mandatory
   DESCRIPTION
     "This attribute indicates the Transient Buffer Exposure (TBE) for 
      this connection. TBE is the negotiated number of cells that the 
      network would like to limit the resource to send during start-up 
      periods, before the first Resource Management (RM) cell returns.
      
      For nailed-up connections, this attribute is determined by the 
      provisioned value of the transientBufferExposure attribute. For 
      signalled connections, it is indicated in the ABR Setup Parameters 
      Information Element."
::= { mscAtmIfVccTmAbrOperEntry 11 }

mscAtmIfVccTmAbrFixedRoundTripTime OBJECT-TYPE
   SYNTAX     Unsigned32 (0..16700000)
   ACCESS     read-only
   STATUS     mandatory
   DESCRIPTION
     "This attribute indicates the Fixed Round-Trip Time (FRTT) 
      parameter for this connection. FRTT is the sum of the fixed and 
      propagation delays from the source to a destination and back.
      
      For nailed-up connections, this attribute is determined by the 
      provisioned value of the fixedRoundTripTime attribute. For 
      signalled connections, it is indicated in the ABR Setup Parameters 
      Information Element."
::= { mscAtmIfVccTmAbrOperEntry 12 }

mscAtmIfVccTmAbrRateDecreaseFactor OBJECT-TYPE
   SYNTAX     Unsigned32 (0..15)
   ACCESS     read-only
   STATUS     mandatory
   DESCRIPTION
     "This attribute indicates the Rate Decrease Factor (RDF) for this 
      connection. The RDF value is computed by using the operational 
      value of this attribute, n, as 2 to the inverse power n. For example, if 
      the value of this attribute is 8, RDF is 2E-8 = 1/256.
      
      RDF controls the amount by which the cell transmission rate may 
      decrease upon receipt of a backward Resource Management (RM) 
      cell. For example, if a backward RM cell is received with the 
      Congestion Indication (CI) field set to 1, the Allowed Cell Rate 
      (ACR) value would be reduced by the amount (RDF*ACR). The 
      ACR is not allowed to fall below the Minimum Cell Rate (MCR), in 
      which case the ACR is set to MCR.
      
      For nailed-up connections, this attribute is determined by the 
      provisioned value of the rateDecreaseFactor attribute. For signalled 
      connections, it is indicated in the ABR Setup Parameters 
      Information Element."
::= { mscAtmIfVccTmAbrOperEntry 13 }

mscAtmIfVccTmAbrRateIncreaseFactor OBJECT-TYPE
   SYNTAX     Unsigned32 (0..15)
   ACCESS     read-only
   STATUS     mandatory
   DESCRIPTION
     "This attribute indicates the Rate Increase Factor (RIF) for this 
      connection. The RIF value is computed by using the operational 
      value of this attribute, n, as 2 to the inverse power n. For example, if 
      the value of this attribute is 6, RIF is 2E-6 = 1/64.
      
      RIF controls the amount by which the cell transmission rate may 
      increase upon receipt of a backward Resource Management (RM) 
      cell. For example, if a backward RM cell is received with the 
      Congestion Indication (CI) and the No Increase (NI) fields both set 
      to 0, the Allowed Cell Rate (ACR) value would be increased by the 
      amount (RIF*ACR). The ACR is not allowed to exceed the Peak 
      Cell Rate (PCR), in which case the ACR is set to PCR.
      
      For nailed-up connections, this attribute is determined by the 
      provisioned value of the rateIncreaseFactor attribute. For signalled 
      connections, it is indicated in the ABR Setup Parameters 
      Information Element."
::= { mscAtmIfVccTmAbrOperEntry 14 }

mscAtmIfVccTmAbrMaxCellPerRmCell OBJECT-TYPE
   SYNTAX     Unsigned32 (2 | 4 | 8 | 16 | 32 | 64 | 128 | 256)
   ACCESS     read-only
   STATUS     mandatory
   DESCRIPTION
     "This attribute indicates the maximum number of cells an ABR 
      source may transmit for each forward Resource Management (RM) 
      cell. The count of the cells transmitted includes data cells, OAM 
      cells, backward RM cells, and the forward RM cell.
      
      For nailed-up connections, this attribute is determined by the 
      provisioned value of the maxCellsPerRmCell attribute. For 
      signalled connections, it is indicated in the ABR Additional 
      Parameters Information Element."
::= { mscAtmIfVccTmAbrOperEntry 15 }

mscAtmIfVccTmAbrMaxTimeBetweenRmCell OBJECT-TYPE
   SYNTAX     Unsigned32 (781 | 1563 | 3125 | 6250 | 12500 | 25000 | 50000 | 100000)
   ACCESS     read-only
   STATUS     mandatory
   DESCRIPTION
     "This attribute indicates the TRM parameter for this connection.
      
      TRM provides an upper bound on the time interval between forward 
      Resource Management (RM) cells for an ABR source. Since the last 
      forward RM cell was sent, if at least TRM time has elapsed since 
      and at least 2 other cells have been sent, the next cell to be 
      transmitted would be a forward RM cell.
      
      For nailed-up connections, this attribute is determined by the 
      provisioned value of the maxTimeBetweenRmCell attribute. For 
      signalled connections, it is indicated in the ABR Additional 
      Parameters Information Element."
::= { mscAtmIfVccTmAbrOperEntry 16 }

mscAtmIfVccTmAbrCutoffDecreaseFactor OBJECT-TYPE
   SYNTAX     Unsigned32 (0 | 1 | 2 | 4 | 8 | 16 | 32 | 64)
   ACCESS     read-only
   STATUS     mandatory
   DESCRIPTION
     "This attribute indicates the Cutoff Decrease Factor (CDF) parameter 
      for this connection. When the value of this attribute is non-zero, 
      CDF is computed as the inverse of the value. For example, if the 
      value is 32, the value of CDF is 1/32. When the value of this 
      attribute is 0, CDF is also zero.
      
      CDF controls the decrease in the Allowed Cell Rate (ACR) 
      associated with the forwardRmCellLimit attribute, the limit of the 
      number of forward Resource Management (RM) cells which may 
      be sent in the absence of received backward RM cells. When this 
      limit is crossed, the ACR value would be decreased by the amount 
      (CDF*ACR). The ACR is not allowed to fall below the Minimum 
      Cell Rate (MCR), in which case the ACR is set to MCR.
      
      For nailed-up connections, this attribute is determined by the 
      provisioned value of the cutoffDecreaseFactor attribute. For 
      signalled connections, it is indicated in the ABR Additional 
      Parameters Information Element."
::= { mscAtmIfVccTmAbrOperEntry 17 }

mscAtmIfVccTmAbrAcrDecreaseTimeFactor OBJECT-TYPE
   SYNTAX     Unsigned32 (0..1023)
   ACCESS     read-only
   STATUS     mandatory
   DESCRIPTION
     "This attribute indicates the Allowed Cell Rate Decrease Time Factor 
      (ADTF) parameter for this connection.
      
      ADTF is the time interval permitted between sending forward 
      Resource Management (RM) cells before the Allowed Cell Rate 
      (ACR) is decreased to initialCellRate. In other words, if the source 
      does not transit a forward RM cell for the period specified by adtf, it 
      reduces its ACR to the value of its initialCellRate.
      
      For nailed-up connections, this attribute is determined by the 
      provisioned value of the acrDecreaseTimeFactor attribute. For 
      signalled connections, it is indicated in the ABR Additional 
      Parameters Information Element."
::= { mscAtmIfVccTmAbrOperEntry 18 }

mscAtmIfVccTmAbrForwardRmCellLimit OBJECT-TYPE
   SYNTAX     Unsigned32 (1 | 3 | 7 | 15 | 31 | 63 | 127 | 255 | 511 | 1023 | 2047 | 4095)
   ACCESS     read-only
   STATUS     mandatory
   DESCRIPTION
     "This attribute indicates the CRM parameter for this connection.
      
      CRM is the limit of the number of forward Resource Management 
      (RM) cells which may be sent in the absence of received backward 
      RM cells. When this limit is crossed, the Allowed Cell Rate (ACR) 
      value would be decreased by the amount (CDF*ACR), where CDF 
      is determined by the cutoffDecreaseFactor. The ACR is not allowed 
      to fall below the Minimum Cell Rate (MCR), in which case the 
      ACR is set to MCR.
      
      The value of CRM is obtained as transientBufferExposure divided 
      by maxCellsPerRmCell."
::= { mscAtmIfVccTmAbrOperEntry 19 }

mscAtmIfVccTmAbrTxRateChangeInfo OBJECT-TYPE
   SYNTAX     INTEGER  {
                 congestionIndicated(0),
                 noIncreaseIndicated(1),
                 explicitRateIndicated(2) }
   ACCESS     read-only
   STATUS     mandatory
   DESCRIPTION
     "This attribute indicates the rate change information put into the last 
      forward Resource Management (RM) cell turned around as a 
      backward-RM cell. For connections configured as an ABR Source 
      or Destination, the turned around backward-RM cell is sent over the 
      interface. For connections configured as an ABR Virtual Source or 
      Virtual Destination, the turned around backward-RM cell is sent 
      over the backplane."
::= { mscAtmIfVccTmAbrOperEntry 20 }

mscAtmIfVccTmAbrAcrRateChangeInfo OBJECT-TYPE
   SYNTAX     INTEGER  {
                 noChange(0),
                 decreasedByRdf(1),
                 increasedByRif(2),
                 setToExplicitRate(3),
                 notApplicable(15) }
   ACCESS     read-only
   STATUS     mandatory
   DESCRIPTION
     "This attribute indicates the type of change in the Allowed Cell Rate 
      (ACR) as a result of the information in the last backward Resource 
      Management (B-RM) cell received from the interface.
      
      This attribute value is only applicable when the Vcc Tm or Vpc Tm 
      abrConnectionType attribute is sourceDest or VirtualSourceDest. 
      In all other cases, this attribute value is notApplicable.
      
      A value of noChange indicates that the rate did not change as a 
      result of the last backward RM cell received.
      
      A value of decreasedByRdf or increasedByRif indicates that the 
      ACR was increased or decreased by the corresponding factor. This 
      change is as a result of the CI or NI bit setting in the last backward 
      RM cell, or an ADTF timeout.
      
      A value of setToExplicitRate indicates that the ACR was set to the 
      ER value in the last backward RM cell."
::= { mscAtmIfVccTmAbrOperEntry 21 }

mscAtmIfVccTmAbrTxFwdRmCells OBJECT-TYPE
   SYNTAX     Unsigned32 (0..4095)
   ACCESS     read-only
   STATUS     mandatory
   DESCRIPTION
     "This attribute counts the number of forward Resource Management 
      (RM) cells sent over the interface since the last backward RM-cell 
      was received from the interface. If the value of this attribute is 
      greater than or equal to the value of forwardRmCellLimit, the 
      Allowed Cell Rate (ACR) value would be decreased by the amount 
      (CDF*ACR), where CDF is determined by the 
      cutoffDecreaseFactor.
      
      This counter is reset to zero each time a backward-RM cell is 
      received.
      
      This counter does not wrap to zero if it reaches its maximum value 
      of 4095 in order to indicate that no backward RM cell has been 
      received."
::= { mscAtmIfVccTmAbrOperEntry 22 }

mscAtmIfVccTmAbrRxEfci OBJECT-TYPE
   SYNTAX     INTEGER  {
                 notIndicated(0),
                 indicated(1) }
   ACCESS     read-only
   STATUS     mandatory
   DESCRIPTION
     "This attribute indicates the value of the Explicit Forward 
      Congestion Indication (EFCI) bit of the last data cell received from 
      the interface.
      
      When a forward Resource Management (RM) cell is turned around 
      as a backward-RM cell, the Congestion Indication (CI) field of the 
      backward-RM cell is set to 1, if the value of this attribute is 
      indicated.
      
      This attribute is set to notIndicated each time a backward-RM cell 
      is transmitted."
::= { mscAtmIfVccTmAbrOperEntry 23 }

-- 
-- *** THIS SUBTREE CURRENTLY NOT IMPLEMENTED ***
-- 

-- AtmIf/n Vcc/x.y PerformanceMonitoring
-- AtmIf/n Vpc/x PerformanceMonitoring
-- This component contains operational attributes for Performance 
-- Monitoring (PM) measurements on the connection. It also allows 
-- starting and stopping PM measurements when the controlMode 
-- attribute in the AtmIf Pm or AtmIf Vcc Vcd Pm or AtmIf Vpc Vpd 
-- Pm component is set to onDemand.

mscAtmIfVccPm OBJECT IDENTIFIER ::= { mscAtmIfVcc 14 }



mscAtmIfVccPmRowStatusTable OBJECT-TYPE
   SYNTAX     SEQUENCE OF MscAtmIfVccPmRowStatusEntry
   ACCESS     not-accessible
   STATUS     mandatory
   DESCRIPTION
     "*** THIS TABLE CURRENTLY NOT IMPLEMENTED ***

      This entry controls the addition and deletion of 
      mscAtmIfVccPm components."
::= { mscAtmIfVccPm 1 }

mscAtmIfVccPmRowStatusEntry OBJECT-TYPE
   SYNTAX     MscAtmIfVccPmRowStatusEntry
   ACCESS     not-accessible
   STATUS     mandatory
   DESCRIPTION
     "A single entry in the table represents a single 
      mscAtmIfVccPm component."
   INDEX {
      mscAtmIfIndex,
      mscAtmIfVccIndex,
      mscAtmIfVccPmIndex }
::= { mscAtmIfVccPmRowStatusTable 1 }

MscAtmIfVccPmRowStatusEntry ::= SEQUENCE {
   mscAtmIfVccPmRowStatus
      RowStatus,
   mscAtmIfVccPmComponentName
      DisplayString,
   mscAtmIfVccPmStorageType
      StorageType,
   mscAtmIfVccPmIndex
      INTEGER }

mscAtmIfVccPmRowStatus OBJECT-TYPE
   SYNTAX     RowStatus 
   ACCESS     read-only
   STATUS     mandatory
   DESCRIPTION
     "This variable is used as the basis for SNMP naming of
      mscAtmIfVccPm components.
      These components cannot be added nor deleted."
::= { mscAtmIfVccPmRowStatusEntry 1 }

mscAtmIfVccPmComponentName OBJECT-TYPE
   SYNTAX     DisplayString 
   ACCESS     read-only
   STATUS     mandatory
   DESCRIPTION
     "This variable provides the component's string name for
      use with the ASCII Console Interface"
::= { mscAtmIfVccPmRowStatusEntry 2 }

mscAtmIfVccPmStorageType OBJECT-TYPE
   SYNTAX     StorageType 
   ACCESS     read-only
   STATUS     mandatory
   DESCRIPTION
     "This variable represents the storage type value for the
      mscAtmIfVccPm tables."
::= { mscAtmIfVccPmRowStatusEntry 4 }

mscAtmIfVccPmIndex OBJECT-TYPE
   SYNTAX     INTEGER  {
                 linkSide(0),
                 switchSide(1) }
   ACCESS     not-accessible
   STATUS     mandatory
   DESCRIPTION
     "This variable represents the index for the mscAtmIfVccPm tables."
::= { mscAtmIfVccPmRowStatusEntry 10 }

mscAtmIfVccPmStatusTable OBJECT-TYPE
   SYNTAX     SEQUENCE OF MscAtmIfVccPmStatusEntry
   ACCESS     not-accessible
   STATUS     mandatory
   DESCRIPTION
     "*** THIS TABLE CURRENTLY NOT IMPLEMENTED ***

      This group contains attributes indicating the status of each 
      Performance Monitoring (PM) measurement."
::= { mscAtmIfVccPm 10 }

mscAtmIfVccPmStatusEntry OBJECT-TYPE
   SYNTAX     MscAtmIfVccPmStatusEntry
   ACCESS     not-accessible
   STATUS     mandatory
   DESCRIPTION
     "An entry in the mscAtmIfVccPmStatusTable."
   INDEX {
      mscAtmIfIndex,
      mscAtmIfVccIndex,
      mscAtmIfVccPmIndex }
::= { mscAtmIfVccPmStatusTable 1 }

MscAtmIfVccPmStatusEntry ::= SEQUENCE {
   mscAtmIfVccPmClrMeasurementStatus
      INTEGER,
   mscAtmIfVccPmArMeasurementStatus
      INTEGER,
   mscAtmIfVccPmFailureCause
      INTEGER }

mscAtmIfVccPmClrMeasurementStatus OBJECT-TYPE
   SYNTAX     INTEGER  {
                 inactive(0),
                 activating(1),
                 active(2),
                 activationFailed(3) }
   ACCESS     read-only
   STATUS     mandatory
   DESCRIPTION
     "This attribute displays the Cell Loss Ratio (CLR) measurement 
      status of the connection.
      
      inactive indicates the test is inactive.
      activating indicates the test is activating.
      active indicates the test is in progress
      activationFailed indicates the test failed to be activated. Refer to 
      the failureCause attribute for failure cause."
   DEFVAL     { inactive }
::= { mscAtmIfVccPmStatusEntry 1 }

mscAtmIfVccPmArMeasurementStatus OBJECT-TYPE
   SYNTAX     INTEGER  {
                 inactive(0),
                 activating(1),
                 active(2),
                 activationFailed(3) }
   ACCESS     read-only
   STATUS     mandatory
   DESCRIPTION
     "This attribute indicates the Availability Ratio (AR) measurement 
      status of the connection.
      
      inactive indicates the test is inactive.
      activating indicates the test is activating.
      active indicates the test is in progress
      activationFailed indicates the test failed to be activated. Refer to 
      the failureCause attribute for the failure cause."
   DEFVAL     { inactive }
::= { mscAtmIfVccPmStatusEntry 2 }

mscAtmIfVccPmFailureCause OBJECT-TYPE
   SYNTAX     INTEGER  {
                 noError(0),
                 unknownCause(1),
                 softwareResourcesUnavailable(2),
                 hardwareResourcesUnavailable(3),
                 remoteEndNoResponse(4),
                 activationCollision(5),
                 remoteEndRejectedActivation(6),
                 pcrUnsupported(7),
                 nextHopCardUnsupported(8) }
   ACCESS     read-only
   STATUS     mandatory
   DESCRIPTION
     "This attribute indicates the failure cause of Performance Monitoring 
      (PM) measurements. The following are possible causes:
      
      noError indicates no error.
      unknownCause indicates unknown failure cause.
      softwareResourcesUnavailable indicates software resources 
      reserved for a maximum of 255 active PMs on the local FP card 
      have been used up.
      hardwareResourcesUnavailable indicates hardware resources 
      reserved for a maximum of 512 active PMs CLR have been used up 
      on the Link Side local card.
      remoteEndNoResponse indicates no response from remote end.
      activationCollision indicates activation collision was detected. 
      Usually this is caused by both ends of the connection being 
      provisioned to request PM. Only one end should be so provisioned.
      remoteEndRejectedActivation indicates the remote end has rejected 
      an activation request. Usually this is due to the remote end reaching 
      a resource limit.
      pcrUnsupported indicates the Tx or Rx PCR was out of range 
      between 0 and 409600.
      nextHopCardUnsupported indicates the next hop card type is not 
      supported."
   DEFVAL     { noError }
::= { mscAtmIfVccPmStatusEntry 3 }

mscAtmIfVccPmFwdClrTable OBJECT-TYPE
   SYNTAX     SEQUENCE OF MscAtmIfVccPmFwdClrEntry
   ACCESS     not-accessible
   STATUS     mandatory
   DESCRIPTION
     "*** THIS TABLE CURRENTLY NOT IMPLEMENTED ***

      This group contains Cell Loss Ratio (CLR) measurements for the 
      forward direction of the connection. The local end is always the 
      provisioned end which sends the activation request, and the remote 
      end is the end which receives the activation request."
::= { mscAtmIfVccPm 11 }

mscAtmIfVccPmFwdClrEntry OBJECT-TYPE
   SYNTAX     MscAtmIfVccPmFwdClrEntry
   ACCESS     not-accessible
   STATUS     mandatory
   DESCRIPTION
     "An entry in the mscAtmIfVccPmFwdClrTable."
   INDEX {
      mscAtmIfIndex,
      mscAtmIfVccIndex,
      mscAtmIfVccPmIndex }
::= { mscAtmIfVccPmFwdClrTable 1 }

MscAtmIfVccPmFwdClrEntry ::= SEQUENCE {
   mscAtmIfVccPmFwdLastSampleUserCellsRx0
      PassportCounter64,
   mscAtmIfVccPmFwdLastSampleUserCellsTx0
      PassportCounter64,
   mscAtmIfVccPmFwdLastSampleClr0
      FixedPoint9,
   mscAtmIfVccPmFwdLastSampleUserCellsRx01
      PassportCounter64,
   mscAtmIfVccPmFwdLastSampleUserCellsTx01
      PassportCounter64,
   mscAtmIfVccPmFwdLastSampleClr01
      FixedPoint9,
   mscAtmIfVccPmFwdTotalClrInterval
      Unsigned32,
   mscAtmIfVccPmFwdTotalUserCellsRx0
      PassportCounter64,
   mscAtmIfVccPmFwdTotalUserCellsTx0
      PassportCounter64,
   mscAtmIfVccPmFwdAverageClr0
      FixedPoint9,
   mscAtmIfVccPmFwdMaximumClr0
      FixedPoint9,
   mscAtmIfVccPmFwdMinimumClr0
      FixedPoint9,
   mscAtmIfVccPmFwdTotalUserCellsRx01
      PassportCounter64,
   mscAtmIfVccPmFwdTotalUserCellsTx01
      PassportCounter64,
   mscAtmIfVccPmFwdAverageClr01
      FixedPoint9,
   mscAtmIfVccPmFwdMaximumClr01
      FixedPoint9,
   mscAtmIfVccPmFwdMinimumClr01
      FixedPoint9,
   mscAtmIfVccPmFwdPmCellDiscardCount
      Unsigned32 }

mscAtmIfVccPmFwdLastSampleUserCellsRx0 OBJECT-TYPE
   SYNTAX     PassportCounter64 
   ACCESS     read-only
   STATUS     mandatory
   DESCRIPTION
     "This attribute displays the number of cells with CLP=0 received at 
      the remote end over the last sample period."
::= { mscAtmIfVccPmFwdClrEntry 1 }

mscAtmIfVccPmFwdLastSampleUserCellsTx0 OBJECT-TYPE
   SYNTAX     PassportCounter64 
   ACCESS     read-only
   STATUS     mandatory
   DESCRIPTION
     "This attribute displays the number of cells with CLP=0 transmitted 
      from the local end over the last sample period."
::= { mscAtmIfVccPmFwdClrEntry 2 }

mscAtmIfVccPmFwdLastSampleClr0 OBJECT-TYPE
   SYNTAX     FixedPoint9 (0..1000000000)
   ACCESS     read-only
   STATUS     mandatory
   DESCRIPTION
     "This attribute displays CLR for CLP=0 traffic over the last sample 
      period."
::= { mscAtmIfVccPmFwdClrEntry 3 }

mscAtmIfVccPmFwdLastSampleUserCellsRx01 OBJECT-TYPE
   SYNTAX     PassportCounter64 
   ACCESS     read-only
   STATUS     mandatory
   DESCRIPTION
     "This attribute indicates the number of cells with CLP=0+1 received 
      at the remote end over the last sample period."
::= { mscAtmIfVccPmFwdClrEntry 4 }

mscAtmIfVccPmFwdLastSampleUserCellsTx01 OBJECT-TYPE
   SYNTAX     PassportCounter64 
   ACCESS     read-only
   STATUS     mandatory
   DESCRIPTION
     "This attribute indicates the number of cells with CLP=0+1 
      transmitted from the local end over the last sample period."
::= { mscAtmIfVccPmFwdClrEntry 5 }

mscAtmIfVccPmFwdLastSampleClr01 OBJECT-TYPE
   SYNTAX     FixedPoint9 (0..1000000000)
   ACCESS     read-only
   STATUS     mandatory
   DESCRIPTION
     "This attribute indicates CLR for CLP=0+1 traffic over the last 
      sample period."
::= { mscAtmIfVccPmFwdClrEntry 6 }

mscAtmIfVccPmFwdTotalClrInterval OBJECT-TYPE
   SYNTAX     Unsigned32 (0..4294967295)
   ACCESS     read-only
   STATUS     mandatory
   DESCRIPTION
     "This attribute indicates the total time duration over which Cell Loss 
      Ratio (CLR) has been calculated."
::= { mscAtmIfVccPmFwdClrEntry 7 }

mscAtmIfVccPmFwdTotalUserCellsRx0 OBJECT-TYPE
   SYNTAX     PassportCounter64 
   ACCESS     read-only
   STATUS     mandatory
   DESCRIPTION
     "This attribute indicates the number of cells with CLP=0 received at 
      the remote end over the total Cell Loss Ratio (CLR) measurement 
      interval."
::= { mscAtmIfVccPmFwdClrEntry 8 }

mscAtmIfVccPmFwdTotalUserCellsTx0 OBJECT-TYPE
   SYNTAX     PassportCounter64 
   ACCESS     read-only
   STATUS     mandatory
   DESCRIPTION
     "This attribute indicates the number of cells with CLP=0 transmitted 
      from the local end over the total Cell Loss Ratio (CLR) 
      measurement interval."
::= { mscAtmIfVccPmFwdClrEntry 9 }

mscAtmIfVccPmFwdAverageClr0 OBJECT-TYPE
   SYNTAX     FixedPoint9 (0..1000000000)
   ACCESS     read-only
   STATUS     mandatory
   DESCRIPTION
     "This attribute indicates the average CLR for CLP=0 traffic 
      calculated for the total measurement interval."
::= { mscAtmIfVccPmFwdClrEntry 10 }

mscAtmIfVccPmFwdMaximumClr0 OBJECT-TYPE
   SYNTAX     FixedPoint9 (0..1000000000)
   ACCESS     read-only
   STATUS     mandatory
   DESCRIPTION
     "This attribute indicates the maximum CLR for CLP=0 traffic 
      calculated for the total measurement interval."
::= { mscAtmIfVccPmFwdClrEntry 11 }

mscAtmIfVccPmFwdMinimumClr0 OBJECT-TYPE
   SYNTAX     FixedPoint9 (0..1000000000)
   ACCESS     read-only
   STATUS     mandatory
   DESCRIPTION
     "This attribute indicates the minimum CLR for CLP=0 traffic 
      calculated for the total measurement interval."
::= { mscAtmIfVccPmFwdClrEntry 12 }

mscAtmIfVccPmFwdTotalUserCellsRx01 OBJECT-TYPE
   SYNTAX     PassportCounter64 
   ACCESS     read-only
   STATUS     mandatory
   DESCRIPTION
     "This attribute indicates the number of cells with CLP=0+1 received 
      at the remote end over the total Cell Loss Ratio (CLR) measurement 
      interval."
::= { mscAtmIfVccPmFwdClrEntry 13 }

mscAtmIfVccPmFwdTotalUserCellsTx01 OBJECT-TYPE
   SYNTAX     PassportCounter64 
   ACCESS     read-only
   STATUS     mandatory
   DESCRIPTION
     "This attribute indicates the number of cells with CLP=0+1 
      transmitted from the local end over the total CLR measurement 
      interval."
::= { mscAtmIfVccPmFwdClrEntry 14 }

mscAtmIfVccPmFwdAverageClr01 OBJECT-TYPE
   SYNTAX     FixedPoint9 (0..1000000000)
   ACCESS     read-only
   STATUS     mandatory
   DESCRIPTION
     "This attribute displays the average CLR for CLP=0+1 traffic 
      calculated for the total measurement interval."
::= { mscAtmIfVccPmFwdClrEntry 15 }

mscAtmIfVccPmFwdMaximumClr01 OBJECT-TYPE
   SYNTAX     FixedPoint9 (0..1000000000)
   ACCESS     read-only
   STATUS     mandatory
   DESCRIPTION
     "This attribute indicates the maximum CLR for CLP=0+1 traffic 
      calculated for the total measurement interval."
::= { mscAtmIfVccPmFwdClrEntry 16 }

mscAtmIfVccPmFwdMinimumClr01 OBJECT-TYPE
   SYNTAX     FixedPoint9 (0..1000000000)
   ACCESS     read-only
   STATUS     mandatory
   DESCRIPTION
     "This attribute indicates the minimum CLR for CLP=0+1 traffic 
      calculated for the total measurement interval."
::= { mscAtmIfVccPmFwdClrEntry 17 }

mscAtmIfVccPmFwdPmCellDiscardCount OBJECT-TYPE
   SYNTAX     Unsigned32 (0..4294967295)
   ACCESS     read-only
   STATUS     mandatory
   DESCRIPTION
     "This attribute indicates the total number of Performance Monitoring 
      (PM) cells discarded."
::= { mscAtmIfVccPmFwdClrEntry 18 }

mscAtmIfVccPmBwdClrTable OBJECT-TYPE
   SYNTAX     SEQUENCE OF MscAtmIfVccPmBwdClrEntry
   ACCESS     not-accessible
   STATUS     mandatory
   DESCRIPTION
     "*** THIS TABLE CURRENTLY NOT IMPLEMENTED ***

      This group contains Cell Loss Ratio (CLR) measurements for the 
      backward direction of the connection. The local end is always the 
      provisioned end which sends the activation request, and the remote 
      end is the end which receives the activation request."
::= { mscAtmIfVccPm 12 }

mscAtmIfVccPmBwdClrEntry OBJECT-TYPE
   SYNTAX     MscAtmIfVccPmBwdClrEntry
   ACCESS     not-accessible
   STATUS     mandatory
   DESCRIPTION
     "An entry in the mscAtmIfVccPmBwdClrTable."
   INDEX {
      mscAtmIfIndex,
      mscAtmIfVccIndex,
      mscAtmIfVccPmIndex }
::= { mscAtmIfVccPmBwdClrTable 1 }

MscAtmIfVccPmBwdClrEntry ::= SEQUENCE {
   mscAtmIfVccPmBwdLastSampleUserCellsRx0
      PassportCounter64,
   mscAtmIfVccPmBwdLastSampleUserCellsTx0
      PassportCounter64,
   mscAtmIfVccPmBwdLastSampleClr0
      FixedPoint9,
   mscAtmIfVccPmBwdLastSampleUserCellsRx01
      PassportCounter64,
   mscAtmIfVccPmBwdLastSampleUserCellsTx01
      PassportCounter64,
   mscAtmIfVccPmBwdLastSampleClr01
      FixedPoint9,
   mscAtmIfVccPmBwdTotalClrInterval
      Unsigned32,
   mscAtmIfVccPmBwdTotalUserCellsRx0
      PassportCounter64,
   mscAtmIfVccPmBwdTotalUserCellsTx0
      PassportCounter64,
   mscAtmIfVccPmBwdAverageClr0
      FixedPoint9,
   mscAtmIfVccPmBwdMaximumClr0
      FixedPoint9,
   mscAtmIfVccPmBwdMinimumClr0
      FixedPoint9,
   mscAtmIfVccPmBwdTotalUserCellsRx01
      PassportCounter64,
   mscAtmIfVccPmBwdTotalUserCellsTx01
      PassportCounter64,
   mscAtmIfVccPmBwdAverageClr01
      FixedPoint9,
   mscAtmIfVccPmBwdMaximumClr01
      FixedPoint9,
   mscAtmIfVccPmBwdMinimumClr01
      FixedPoint9,
   mscAtmIfVccPmBwdPmCellDiscardCount
      Unsigned32 }

mscAtmIfVccPmBwdLastSampleUserCellsRx0 OBJECT-TYPE
   SYNTAX     PassportCounter64 
   ACCESS     read-only
   STATUS     mandatory
   DESCRIPTION
     "This attribute indicates the number of cells with CLP=0 received at 
      the local end over the last sample period."
::= { mscAtmIfVccPmBwdClrEntry 1 }

mscAtmIfVccPmBwdLastSampleUserCellsTx0 OBJECT-TYPE
   SYNTAX     PassportCounter64 
   ACCESS     read-only
   STATUS     mandatory
   DESCRIPTION
     "This attribute indicates the number of cells with CLP=0 transmitted 
      from the remote end over the last sample period."
::= { mscAtmIfVccPmBwdClrEntry 2 }

mscAtmIfVccPmBwdLastSampleClr0 OBJECT-TYPE
   SYNTAX     FixedPoint9 (0..1000000000)
   ACCESS     read-only
   STATUS     mandatory
   DESCRIPTION
     "This attribute indicates CLR for CLP=0 traffic over the last sample 
      period."
::= { mscAtmIfVccPmBwdClrEntry 3 }

mscAtmIfVccPmBwdLastSampleUserCellsRx01 OBJECT-TYPE
   SYNTAX     PassportCounter64 
   ACCESS     read-only
   STATUS     mandatory
   DESCRIPTION
     "This attribute indicates the number of cells with CLP=0+1 received 
      at the local end over the last sample period."
::= { mscAtmIfVccPmBwdClrEntry 4 }

mscAtmIfVccPmBwdLastSampleUserCellsTx01 OBJECT-TYPE
   SYNTAX     PassportCounter64 
   ACCESS     read-only
   STATUS     mandatory
   DESCRIPTION
     "This attribute indicates the number of cells with CLP=0+1 
      transmitted from the remote end over the last sample period."
::= { mscAtmIfVccPmBwdClrEntry 5 }

mscAtmIfVccPmBwdLastSampleClr01 OBJECT-TYPE
   SYNTAX     FixedPoint9 (0..1000000000)
   ACCESS     read-only
   STATUS     mandatory
   DESCRIPTION
     "This attribute display CLRfor CLP=0+1 traffic over the last sample 
      period."
::= { mscAtmIfVccPmBwdClrEntry 6 }

mscAtmIfVccPmBwdTotalClrInterval OBJECT-TYPE
   SYNTAX     Unsigned32 (0..4294967295)
   ACCESS     read-only
   STATUS     mandatory
   DESCRIPTION
     "This attribute indicates the total time duration over which Cell Loss 
      Ratio (CLR) measurement has been calculated."
::= { mscAtmIfVccPmBwdClrEntry 7 }

mscAtmIfVccPmBwdTotalUserCellsRx0 OBJECT-TYPE
   SYNTAX     PassportCounter64 
   ACCESS     read-only
   STATUS     mandatory
   DESCRIPTION
     "This attribute indicates the number of cells with CLP=0 received at 
      the local end over the total Cell Loss Ratio (CLR) measurement 
      interval in the backward direction."
::= { mscAtmIfVccPmBwdClrEntry 8 }

mscAtmIfVccPmBwdTotalUserCellsTx0 OBJECT-TYPE
   SYNTAX     PassportCounter64 
   ACCESS     read-only
   STATUS     mandatory
   DESCRIPTION
     "This attribute indicates the number of cells with CLP=0 transmitted 
      from the remote end over the total Cell Loss Ratio (CLR) 
      measurement interval."
::= { mscAtmIfVccPmBwdClrEntry 9 }

mscAtmIfVccPmBwdAverageClr0 OBJECT-TYPE
   SYNTAX     FixedPoint9 (0..1000000000)
   ACCESS     read-only
   STATUS     mandatory
   DESCRIPTION
     "This attribute indicates the average CLR for CLP=0 traffic 
      calculated for the total measurement interval."
::= { mscAtmIfVccPmBwdClrEntry 10 }

mscAtmIfVccPmBwdMaximumClr0 OBJECT-TYPE
   SYNTAX     FixedPoint9 (0..1000000000)
   ACCESS     read-only
   STATUS     mandatory
   DESCRIPTION
     "This attribute indicates the maximum CLR for CLP=0 traffi 
      calculated for the total measurement interval."
::= { mscAtmIfVccPmBwdClrEntry 11 }

mscAtmIfVccPmBwdMinimumClr0 OBJECT-TYPE
   SYNTAX     FixedPoint9 (0..1000000000)
   ACCESS     read-only
   STATUS     mandatory
   DESCRIPTION
     "This attribute indicates the minimum CLR for CLP=0 traffic 
      calculated for the total measurement interval."
::= { mscAtmIfVccPmBwdClrEntry 12 }

mscAtmIfVccPmBwdTotalUserCellsRx01 OBJECT-TYPE
   SYNTAX     PassportCounter64 
   ACCESS     read-only
   STATUS     mandatory
   DESCRIPTION
     "This attribute indicates the number of cells with CLP=0 received at 
      the local end over the total Cell Loss Ratio (CLR) measurement 
      interval."
::= { mscAtmIfVccPmBwdClrEntry 13 }

mscAtmIfVccPmBwdTotalUserCellsTx01 OBJECT-TYPE
   SYNTAX     PassportCounter64 
   ACCESS     read-only
   STATUS     mandatory
   DESCRIPTION
     "This attribute indicates the number of cells with CLP=0+1 
      transmitted from the remote end over the total Cell Loss Ratio 
      (CLR) measurement interval ."
::= { mscAtmIfVccPmBwdClrEntry 14 }

mscAtmIfVccPmBwdAverageClr01 OBJECT-TYPE
   SYNTAX     FixedPoint9 (0..1000000000)
   ACCESS     read-only
   STATUS     mandatory
   DESCRIPTION
     "This attribute displays the average CLR for CLP=0+1 traffic 
      calculated for the total measurement interval."
::= { mscAtmIfVccPmBwdClrEntry 15 }

mscAtmIfVccPmBwdMaximumClr01 OBJECT-TYPE
   SYNTAX     FixedPoint9 (0..1000000000)
   ACCESS     read-only
   STATUS     mandatory
   DESCRIPTION
     "This attribute indicates the maximum CLR for CLP=0+1 traffic 
      calculated for the total measurement interval."
::= { mscAtmIfVccPmBwdClrEntry 16 }

mscAtmIfVccPmBwdMinimumClr01 OBJECT-TYPE
   SYNTAX     FixedPoint9 (0..1000000000)
   ACCESS     read-only
   STATUS     mandatory
   DESCRIPTION
     "This attribute indicates the minimum CLR for CLP=0+1 traffic 
      calculated for the total measurement interval."
::= { mscAtmIfVccPmBwdClrEntry 17 }

mscAtmIfVccPmBwdPmCellDiscardCount OBJECT-TYPE
   SYNTAX     Unsigned32 (0..4294967295)
   ACCESS     read-only
   STATUS     mandatory
   DESCRIPTION
     "This attribute indicates the total number of Performance Monitoring 
      (PM) cells discarded."
::= { mscAtmIfVccPmBwdClrEntry 18 }

mscAtmIfVccPmArTable OBJECT-TYPE
   SYNTAX     SEQUENCE OF MscAtmIfVccPmArEntry
   ACCESS     not-accessible
   STATUS     mandatory
   DESCRIPTION
     "*** THIS TABLE CURRENTLY NOT IMPLEMENTED ***

      This group contains Availability Ratio (AR) measurements of the 
      connection."
::= { mscAtmIfVccPm 13 }

mscAtmIfVccPmArEntry OBJECT-TYPE
   SYNTAX     MscAtmIfVccPmArEntry
   ACCESS     not-accessible
   STATUS     mandatory
   DESCRIPTION
     "An entry in the mscAtmIfVccPmArTable."
   INDEX {
      mscAtmIfIndex,
      mscAtmIfVccIndex,
      mscAtmIfVccPmIndex }
::= { mscAtmIfVccPmArTable 1 }

MscAtmIfVccPmArEntry ::= SEQUENCE {
   mscAtmIfVccPmCurrentAvailabilityStatus
      INTEGER,
   mscAtmIfVccPmArTotalTime
      Unsigned32,
   mscAtmIfVccPmArAvailableTime
      Unsigned32,
   mscAtmIfVccPmArAvailabilityRatio
      FixedPoint7 }

mscAtmIfVccPmCurrentAvailabilityStatus OBJECT-TYPE
   SYNTAX     INTEGER  {
                 notApplicable(0),
                 available(1),
                 unavailable(2) }
   ACCESS     read-only
   STATUS     mandatory
   DESCRIPTION
     "This attribute indicates the current status of the bidirectional 
      connection for purposes of Availability Ratio (AR) computation.
      
      notApplicable means AR measurement was not requested on this 
      connection.
      available means AR is running and considers the connection 
      available (that is, the arAvailableTime attribute is being 
      incremented).
      unavailable means AR measurement was requested but the 
      connection is currently unavailable."
::= { mscAtmIfVccPmArEntry 1 }

mscAtmIfVccPmArTotalTime OBJECT-TYPE
   SYNTAX     Unsigned32 (0..4294967295)
   ACCESS     read-only
   STATUS     mandatory
   DESCRIPTION
     "This attribute indicates the total time used for calculating 
      Availability Ratio (AR) of the bi-directional connection."
::= { mscAtmIfVccPmArEntry 2 }

mscAtmIfVccPmArAvailableTime OBJECT-TYPE
   SYNTAX     Unsigned32 (0..4294967295)
   ACCESS     read-only
   STATUS     mandatory
   DESCRIPTION
     "This attribute indicates the total time the connection was available."
::= { mscAtmIfVccPmArEntry 3 }

mscAtmIfVccPmArAvailabilityRatio OBJECT-TYPE
   SYNTAX     FixedPoint7 (0..10000000)
   ACCESS     read-only
   STATUS     mandatory
   DESCRIPTION
     "This attribute indicates the ratio of network availability representing 
      the time to the total time of the connection."
::= { mscAtmIfVccPmArEntry 4 }


-- AtmIf/n NailedUpAccounting
-- This component represents the ATM accounting options for all 
-- nailed up connections (PVCs) on this ATM interface. The 
-- component must be provisioned in order to perform PVC ATM 
-- accounting on this ATM interface.

mscAtmIfNAcct OBJECT IDENTIFIER ::= { mscAtmIf 8 }



mscAtmIfNAcctRowStatusTable OBJECT-TYPE
   SYNTAX     SEQUENCE OF MscAtmIfNAcctRowStatusEntry
   ACCESS     not-accessible
   STATUS     mandatory
   DESCRIPTION
     "This entry controls the addition and deletion of 
      mscAtmIfNAcct components."
::= { mscAtmIfNAcct 1 }

mscAtmIfNAcctRowStatusEntry OBJECT-TYPE
   SYNTAX     MscAtmIfNAcctRowStatusEntry
   ACCESS     not-accessible
   STATUS     mandatory
   DESCRIPTION
     "A single entry in the table represents a single 
      mscAtmIfNAcct component."
   INDEX {
      mscAtmIfIndex,
      mscAtmIfNAcctIndex }
::= { mscAtmIfNAcctRowStatusTable 1 }

MscAtmIfNAcctRowStatusEntry ::= SEQUENCE {
   mscAtmIfNAcctRowStatus
      RowStatus,
   mscAtmIfNAcctComponentName
      DisplayString,
   mscAtmIfNAcctStorageType
      StorageType,
   mscAtmIfNAcctIndex
      NonReplicated }

mscAtmIfNAcctRowStatus OBJECT-TYPE
   SYNTAX     RowStatus 
   ACCESS     read-write
   STATUS     mandatory
   DESCRIPTION
     "This variable is used as the basis for SNMP naming of
      mscAtmIfNAcct components.
      These components can be added and deleted."
::= { mscAtmIfNAcctRowStatusEntry 1 }

mscAtmIfNAcctComponentName OBJECT-TYPE
   SYNTAX     DisplayString 
   ACCESS     read-only
   STATUS     mandatory
   DESCRIPTION
     "This variable provides the component's string name for
      use with the ASCII Console Interface"
::= { mscAtmIfNAcctRowStatusEntry 2 }

mscAtmIfNAcctStorageType OBJECT-TYPE
   SYNTAX     StorageType 
   ACCESS     read-only
   STATUS     mandatory
   DESCRIPTION
     "This variable represents the storage type value for the
      mscAtmIfNAcct tables."
::= { mscAtmIfNAcctRowStatusEntry 4 }

mscAtmIfNAcctIndex OBJECT-TYPE
   SYNTAX     NonReplicated 
   ACCESS     not-accessible
   STATUS     mandatory
   DESCRIPTION
     "This variable represents the index for the mscAtmIfNAcct tables."
::= { mscAtmIfNAcctRowStatusEntry 10 }

mscAtmIfNAcctProvTable OBJECT-TYPE
   SYNTAX     SEQUENCE OF MscAtmIfNAcctProvEntry
   ACCESS     not-accessible
   STATUS     mandatory
   DESCRIPTION
     "This group contains the provisionable attributes for PVC 
      accounting."
::= { mscAtmIfNAcct 10 }

mscAtmIfNAcctProvEntry OBJECT-TYPE
   SYNTAX     MscAtmIfNAcctProvEntry
   ACCESS     not-accessible
   STATUS     mandatory
   DESCRIPTION
     "An entry in the mscAtmIfNAcctProvTable."
   INDEX {
      mscAtmIfIndex,
      mscAtmIfNAcctIndex }
::= { mscAtmIfNAcctProvTable 1 }

MscAtmIfNAcctProvEntry ::= SEQUENCE {
   mscAtmIfNAcctAccountCollection
      OCTET STRING,
   mscAtmIfNAcctAccountConnectionType
      INTEGER,
   mscAtmIfNAcctAccountClass
      Unsigned32,
   mscAtmIfNAcctServiceExchange
      Unsigned32 }

mscAtmIfNAcctAccountCollection OBJECT-TYPE
   SYNTAX     OCTET STRING (SIZE (1))
   ACCESS     read-write
   STATUS     mandatory
   DESCRIPTION
     "This attribute specifies the reason(s) for which accounting data is 
      collected: billing, test, study, audit or force. 
      
      If the set of reasons is not empty then accounting records will be 
      generated by this interface in the following situations:
      - on a TODA (time of day accounting) changeover if TODA is 
      enabled;
      - every 12 hours (per connection) if TODA is disabled;
      - when the PVC is deleted (a call record is generated with final cell 
      counts).
      
      If none of the reasons is present, then accounting will be suppressed 
      for all PVCs on this interface. Accounting can be suppressed on 
      individual PVCs by specifying a null correlationTag attribute in the 
      AtmIf NAcct component.
      
      The reason for collection is recorded in the accounting record, in 
      the attribute callingCollectReason or calledCollectReason, as 
      appropriate.

      Description of bits:
      bill(0)
      test(1)
      study(2)
      audit(3)
      force(4)"
::= { mscAtmIfNAcctProvEntry 1 }

mscAtmIfNAcctAccountConnectionType OBJECT-TYPE
   SYNTAX     INTEGER  {
                 origTerm(0),
                 intermediate(1) }
   ACCESS     read-write
   STATUS     mandatory
   DESCRIPTION
     "This attribute specifies whether accounting records generated for 
      the PVCs on this interface should be marked as originating, 
      terminating or intermediate. This attribute, in combination with the 
      direction of the call, determines the value of attribute 
      connPointType of the accounting record. It may be used by 
      downstream accounting processing to correlate the records.
      
      If the value is origTerm then the value of attribute connPointType 
      in the accounting records generated for incoming calls will be 
      originating and records generated for outgoing calls will be 
      terminating.
      
      If the value is intermediate then the value of attribute 
      connPointType in the accounting records generated for all calls will 
      be intermediate."
   DEFVAL     { origTerm }
::= { mscAtmIfNAcctProvEntry 2 }

mscAtmIfNAcctAccountClass OBJECT-TYPE
   SYNTAX     Unsigned32 (0..255)
   ACCESS     read-write
   STATUS     mandatory
   DESCRIPTION
     "This attribute specifies the accounting class associated with the 
      PVCs on this interface. Its meaning is determined by the network 
      operator.
      
      Its value is recorded in the accounting records generated by this 
      interface, in the attributes, callingServiceType and 
      calledServiceType."
   DEFVAL     { 0 }
::= { mscAtmIfNAcctProvEntry 3 }

mscAtmIfNAcctServiceExchange OBJECT-TYPE
   SYNTAX     Unsigned32 (0..255)
   ACCESS     read-write
   STATUS     mandatory
   DESCRIPTION
     "This attribute specifies the data service exchange associated with 
      this interface. Its meaning is determined by the network operator.
      
      Its value is recorded in the accounting records generated by this 
      interface, in the attributes, callingDse and calledDse."
   DEFVAL     { 0 }
::= { mscAtmIfNAcctProvEntry 4 }


-- AtmIf/n VirtualPathTerminator/vpi
-- This component represents a virtual path terminator (VPT). The 
-- instance value defines the VPI value for this connectionfor 
-- example, Vpt/120 defines a terminator with a VPI of 120.

mscAtmIfVpt OBJECT IDENTIFIER ::= { mscAtmIf 9 }



mscAtmIfVptRowStatusTable OBJECT-TYPE
   SYNTAX     SEQUENCE OF MscAtmIfVptRowStatusEntry
   ACCESS     not-accessible
   STATUS     mandatory
   DESCRIPTION
     "This entry controls the addition and deletion of 
      mscAtmIfVpt components."
::= { mscAtmIfVpt 1 }

mscAtmIfVptRowStatusEntry OBJECT-TYPE
   SYNTAX     MscAtmIfVptRowStatusEntry
   ACCESS     not-accessible
   STATUS     mandatory
   DESCRIPTION
     "A single entry in the table represents a single 
      mscAtmIfVpt component."
   INDEX {
      mscAtmIfIndex,
      mscAtmIfVptIndex }
::= { mscAtmIfVptRowStatusTable 1 }

MscAtmIfVptRowStatusEntry ::= SEQUENCE {
   mscAtmIfVptRowStatus
      RowStatus,
   mscAtmIfVptComponentName
      DisplayString,
   mscAtmIfVptStorageType
      StorageType,
   mscAtmIfVptIndex
      Integer32 }

mscAtmIfVptRowStatus OBJECT-TYPE
   SYNTAX     RowStatus 
   ACCESS     read-write
   STATUS     mandatory
   DESCRIPTION
     "This variable is used as the basis for SNMP naming of
      mscAtmIfVpt components.
      These components can be added and deleted."
::= { mscAtmIfVptRowStatusEntry 1 }

mscAtmIfVptComponentName OBJECT-TYPE
   SYNTAX     DisplayString 
   ACCESS     read-only
   STATUS     mandatory
   DESCRIPTION
     "This variable provides the component's string name for
      use with the ASCII Console Interface"
::= { mscAtmIfVptRowStatusEntry 2 }

mscAtmIfVptStorageType OBJECT-TYPE
   SYNTAX     StorageType 
   ACCESS     read-only
   STATUS     mandatory
   DESCRIPTION
     "This variable represents the storage type value for the
      mscAtmIfVpt tables."
::= { mscAtmIfVptRowStatusEntry 4 }

mscAtmIfVptIndex OBJECT-TYPE
   SYNTAX     Integer32 (0..4095)
   ACCESS     not-accessible
   STATUS     mandatory
   DESCRIPTION
     "This variable represents the index for the mscAtmIfVpt tables."
::= { mscAtmIfVptRowStatusEntry 10 }

mscAtmIfVptStateTable OBJECT-TYPE
   SYNTAX     SEQUENCE OF MscAtmIfVptStateEntry
   ACCESS     not-accessible
   STATUS     mandatory
   DESCRIPTION
     "This group contains the three OSI State attributes. The descriptions 
      generically indicate what each state attribute implies about the 
      component. Note that not all the values and state combinations 
      described here are supported by every component which reuses this 
      group. For component-specific information and the valid state 
      combinations, refer to the appropriate NTP."
::= { mscAtmIfVpt 100 }

mscAtmIfVptStateEntry OBJECT-TYPE
   SYNTAX     MscAtmIfVptStateEntry
   ACCESS     not-accessible
   STATUS     mandatory
   DESCRIPTION
     "An entry in the mscAtmIfVptStateTable."
   INDEX {
      mscAtmIfIndex,
      mscAtmIfVptIndex }
::= { mscAtmIfVptStateTable 1 }

MscAtmIfVptStateEntry ::= SEQUENCE {
   mscAtmIfVptAdminState
      INTEGER,
   mscAtmIfVptOperationalState
      INTEGER,
   mscAtmIfVptUsageState
      INTEGER }

mscAtmIfVptAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock -force or 
      Lock command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscAtmIfVptStateEntry 1 }

mscAtmIfVptOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscAtmIfVptStateEntry 2 }

mscAtmIfVptUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscAtmIfVptStateEntry 3 }

mscAtmIfVptOperTable OBJECT-TYPE
   SYNTAX     SEQUENCE OF MscAtmIfVptOperEntry
   ACCESS     not-accessible
   STATUS     mandatory
   DESCRIPTION
     "This group contains operational information for a Vcc, Vpc, or Vpt 
      component."
::= { mscAtmIfVpt 110 }

mscAtmIfVptOperEntry OBJECT-TYPE
   SYNTAX     MscAtmIfVptOperEntry
   ACCESS     not-accessible
   STATUS     mandatory
   DESCRIPTION
     "An entry in the mscAtmIfVptOperTable."
   INDEX {
      mscAtmIfIndex,
      mscAtmIfVptIndex }
::= { mscAtmIfVptOperTable 1 }

MscAtmIfVptOperEntry ::= SEQUENCE {
   mscAtmIfVptConnectionPointType
      INTEGER }

mscAtmIfVptConnectionPointType OBJECT-TYPE
   SYNTAX     INTEGER  {
                 connectionEndPoint(0),
                 segmentEndPoint(1),
                 connectingPoint(2),
                 unknown(3) }
   ACCESS     read-only
   STATUS     mandatory
   DESCRIPTION
     "This attribute reflects the role of the connection component at this 
      interface.
      
      A value of connectionEndPoint indicates that user cells, end-to-end 
      OAM cells, and segment OAM cells are processed by the 
      connection component.
      
      A value of segmentEndPoint indicates that user cells and end-to-
      end OAM cells are relayed by the connection component, while 
      segment OAM cells are processed by the connection component.
      
      A value of connectingPoint indicates that user cells, end-to-end 
      OAM cells, and segment OAM cells are relayed by the connection 
      component.
      
      A value of unknown indicates that the connection component is 
      inactive."
::= { mscAtmIfVptOperEntry 10 }

mscAtmIfVptStatusTable OBJECT-TYPE
   SYNTAX     SEQUENCE OF MscAtmIfVptStatusEntry
   ACCESS     not-accessible
   STATUS     mandatory
   DESCRIPTION
     "This group contains operational status information for a Vcc, Vpc or 
      Vpt component."
::= { mscAtmIfVpt 120 }

mscAtmIfVptStatusEntry OBJECT-TYPE
   SYNTAX     MscAtmIfVptStatusEntry
   ACCESS     not-accessible
   STATUS     mandatory
   DESCRIPTION
     "An entry in the mscAtmIfVptStatusTable."
   INDEX {
      mscAtmIfIndex,
      mscAtmIfVptIndex }
::= { mscAtmIfVptStatusTable 1 }

MscAtmIfVptStatusEntry ::= SEQUENCE {
   mscAtmIfVptOperStatus
      INTEGER,
   mscAtmIfVptLocalFailureCause
      INTEGER,
   mscAtmIfVptTroubled
      INTEGER,
   mscAtmIfVptSegLinkSideLoopbackState
      INTEGER,
   mscAtmIfVptSegSwitchSideLoopbackState
      INTEGER,
   mscAtmIfVptEndToEndLoopbackState
      INTEGER,
   mscAtmIfVptRxOamCellCongestionState
      INTEGER,
   mscAtmIfVptAisState
      INTEGER,
   mscAtmIfVptRdiState
      INTEGER }

mscAtmIfVptOperStatus OBJECT-TYPE
   SYNTAX     INTEGER  {
                 unknown(0),
                 end2endUp(1),
                 end2endDown(2),
                 localUpEnd2endUnknown(3),
                 localDown(4) }
   ACCESS     read-only
   STATUS     mandatory
   DESCRIPTION
     "This attribute indicates the present operational status of the Vcc, 
      Vpc or Vpt component. Its value is dependent upon the current state 
      of the segLinkSideLoopbackState and endToEndLoopbackState 
      attributes.
      
      The value is end2endUp when the endToEndLoopbackState is good 
      and the segLinkSideLoopbackState is either good or unknown.
      
      The value is end2endDown when the endToEndLoopbackState is 
      bad and the segLinkSideLoopbackState is either good or unknown.
      
      The value is localUpEnd2endUnknown when the 
      endToEndLoopbackState is unknown and the 
      segLinkSideLoopbackState is good.
      
      The value is localDown when segLinkSideLoopbackState is bad.
      
      The value is localUpEnd2endUnknown when the 
      endToEndLoopbackState is notApplicable and the 
      segLinkSideLoopbackState is good.
      
      The value is unknown when the endToEndLoopbackState is either 
      unknown or notApplicable and the segLinkSideLoopbackState is 
      unknown."
::= { mscAtmIfVptStatusEntry 20 }

mscAtmIfVptLocalFailureCause OBJECT-TYPE
   SYNTAX     INTEGER  {
                 noFailure(0),
                 localBwLoss(1),
                 portDown(2),
                 notAdmitted(3),
                 appNotRegistered(4),
                 disabledByApp(5),
                 bwReduced(6),
                 vpDown(7) }
   ACCESS     read-only
   STATUS     mandatory
   DESCRIPTION
     "This attribute indicates the failure cause of the Vcc, Vpc or Vpt 
      component. noFailure indicates that there is currently no 
      bandwidth related failure for this connection. 
      
      portDown indicates that the interface corresponding to the parent 
      AtmIf is down. 
      
      localBwLoss indicates that the Ima corresponding to this AtmIf has 
      lost some, but not all bandwidth, and as a result, this connection has 
      been released.
      
      notAdmitted indicates that this connection has failed to be admitted 
      by the Connection Admission Control (CAC) algorithm.
      
      appNotRegistered indicates that there is no application registered to 
      use this connection. This may be the case, for example when there 
      is a Vcc Test application, but the test has not been started. Check the 
      status of the application to determine why it is not functional.
      
      disabledByApp indicates that the application using this connection 
      has requested that the connection be disabled. An example is a 
      connection used by a trunk application where the trunk has timed 
      out on an attempt to stage. Check the application to determine why 
      it is not fully functional.
      
      bwReduced indicates that this connection is operating in a reduced 
      bandwidth state. It is a bandwidth elastic connection which 
      currently has been allocated less than the requested (equivalent) 
      bandwidth.
      
      vpDown indicates that this connection has been notified of a fault 
      detected at the associated VP-layer. vpDown is applicable for Vpt 
      Vccs only."
::= { mscAtmIfVptStatusEntry 25 }

mscAtmIfVptTroubled OBJECT-TYPE
   SYNTAX     INTEGER  {
                 no(0),
                 yes(1) }
   ACCESS     read-only
   STATUS     mandatory
   DESCRIPTION
     "This attribute indicates whether or not the connection is in a 
      troubled state. Connections become troubled because of OAM 
      failures; when one of the attributes segLinkSideLoopbackState, 
      segSwitchSideLoopbackState, endToEndLoopbackState, aisState 
      (when receiving AIS cells only) or rdiState go bad, this attribute is 
      set to yes; otherwise it is set to no."
   DEFVAL     { no }
::= { mscAtmIfVptStatusEntry 28 }

mscAtmIfVptSegLinkSideLoopbackState OBJECT-TYPE
   SYNTAX     INTEGER  {
                 good(0),
                 bad(1),
                 unknown(2),
                 notApplicable(3) }
   ACCESS     read-only
   STATUS     mandatory
   DESCRIPTION
     "This attribute contains the current state of the link-side segment 
      loopback for this connection. Link-side segment loopback cells are 
      transmitted (inserted) by a connection component in the direction of 
      the link (port). The value of this attribute is dependent upon the 
      current setting of the segLinkSideLoopback provisionable attribute, 
      the connection point type as specified by the connectionPointType 
      attribute, and the current loopback state (if applicable).
      
      The value is notApplicable when the connectionPointType is a 
      connectingPoint. 
      
      The value is notApplicable when the distributionType is 
      pointToMultipoint.
      
      The value is good when the segLinkSideLoopback is on, the 
      connectionPointType is a segmentEndPoint or a 
      connectionEndPoint, and the segment link side loopback is 
      working.
      
      The value is bad when the segLinkSideLoopback is on, the 
      connectionPointType is a segmentEndPoint or a 
      connectionEndPoint, and the link side segment loopback is not 
      working.
      
      The value is unknown when the segLinkSideLoopback is off.
      
      The value is unknown when the segLinkSideLoopback is on, the 
      connectionPointType is a segmentEndPoint and the segment switch 
      side loopback has not yet been determined.
      
      The state of this attribute determines, in part, the value of the 
      operStatus attribute."
::= { mscAtmIfVptStatusEntry 30 }

mscAtmIfVptSegSwitchSideLoopbackState OBJECT-TYPE
   SYNTAX     INTEGER  {
                 good(0),
                 bad(1),
                 unknown(2),
                 notApplicable(3) }
   ACCESS     read-only
   STATUS     mandatory
   DESCRIPTION
     "This attribute contains the current state of the switch-side segment 
      loopback for this connection. Switch-side segment loopback cells 
      are transmitted (inserted) by a connection component in the 
      direction of the bus. The value of this attribute is dependent upon 
      the current setting of the segSwitchSideLoopback provisionable 
      attribute, the connection point type as specified by the 
      connectionPointType attribute, and the current loopback state (if 
      applicable).
      
      The value is only applicable when the connectionPointType is a 
      segmentEndPoint. 
      
      The value is notApplicable when the connectionPointType is a 
      connectingPoint or connectionEndPoint. 
      
      The value is notApplicable when the distributionType is 
      pointToMultipoint.
      
      The value is good when the segSwitchSideLoopback is on, the 
      connectionPointType is a segmentEndPoint and the segment switch 
      side loopback is working.
      
      The value is bad when the segSwitchSideLoopback is on, the 
      connectionPointType is a segmentEndPoint and the switch side 
      segment loopback is not working.
      
      The value is unknown when the segSwitchSideLoopback is off.
      
      The value is unknown when the segSwitchSideLoopback is on, the 
      connectionPointType is a segmentEndPoint and the segment switch 
      side loopback has not been determined."
::= { mscAtmIfVptStatusEntry 40 }

mscAtmIfVptEndToEndLoopbackState OBJECT-TYPE
   SYNTAX     INTEGER  {
                 good(0),
                 bad(1),
                 unknown(2),
                 notApplicable(3) }
   ACCESS     read-only
   STATUS     mandatory
   DESCRIPTION
     "This attribute contains the current state of the end-to-end loopback 
      for this connection. Its value is dependent upon the current setting 
      of the endToEndLoopback provisionable attribute and the 
      connection point type as specified by the connectionPointType 
      attribute.
      
      The value is only applicable when the connectionPointType is a 
      connectionEndPoint. 
      
      The value is notApplicable when the connectionPointType is a 
      connectingPoint or segmentEndPoint. 
      
      The value is notApplicable when the distributionType is a 
      pointToMultipoint.
      
      The value is good when the endToEndLoopback is on, the 
      connectionPointType is a connectionEndPoint and the end-to-end 
      loopback is working.
      
      The value is bad when the endToEndLoopback is on, the 
      connectionPointType is a connectionEndPoint and the end-to-end 
      loopback is not working.
      
      The value is unknown when the endToEndLoopback is off.
      
      The value is unknown when the endToEndLoopback is on, the 
      connectionPointType is a connectionEndPoint and the end-to-end 
      loopback status has not been determined.
      
      The state of this attribute determines, in part, the value of the 
      operStatus attribute."
::= { mscAtmIfVptStatusEntry 50 }

mscAtmIfVptRxOamCellCongestionState OBJECT-TYPE
   SYNTAX     INTEGER  {
                 good(0),
                 bad(1),
                 unknown(2),
                 notApplicable(3) }
   ACCESS     read-only
   STATUS     mandatory
   DESCRIPTION
     "This attribute contains the current state of the receive side OAM cell 
      congestion for this connection. Its value reflects whether the rate of 
      received OAM cells for this connection is below a specified 
      threshold. The connection maintains a count of the number of OAM 
      cells which are terminated per second. Once that count exceeds the 
      specified threshold, extraction of all OAM cells for this connection 
      is disabled for a period of one minute. This is a congestion 
      management mechanism to prevent the processor from being 
      overloaded with handling OAM cells for a particular connection. 
      This mechanism ensures that tasks, such as trunks obtain enough 
      processor cycles to remain in service, and are not adversely affected 
      by excessive rate of OAM cells on a particular connection.
      
      The value is good when the rate of received OAM cells is less than 
      the allowed threshold.
      
      The value is bad when the arrival rate has exceeded the allowed 
      threshold. It remains bad for one minute, before returning to good 
      again. During this timeout, extraction of all OAM cells is disabled 
      for this connection. As a result, other loopback failure conditions 
      may occur.
      
      The value is unknown when the application has not yet begun to 
      use this connection. An example is the Test component before a test 
      has been started.
      
      Each type of OAM cell is counted separately. The threshold for AIS 
      cells is three cells per second. If more than three AIS cells are 
      received within a one second interval, this attribute is set to bad. 
      The threshold for RDI cells and each loopback type is also three, 
      but the threshold for trace cells is 250 per second.
      
      The state of this attribute has no direct effect on the value of the 
      operStatus attribute or on the number of troubled connections."
::= { mscAtmIfVptStatusEntry 55 }

mscAtmIfVptAisState OBJECT-TYPE
   SYNTAX     INTEGER  {
                 good(0),
                 bad(1),
                 unknown(2),
                 notApplicable(3) }
   ACCESS     read-only
   STATUS     mandatory
   DESCRIPTION
     "This attribute contains the current state of the Alarm Indication 
      Signal for this connection.
      
      A value of good indicates that the connection's application is active 
      and no alarm has occurred.
      
      A value of bad indicates that the connection's application is active 
      and an alarm has occurred.
      
      A value of unknown indicates that the connection's application is 
      inactive.
      
      A value of notApplicable occurs when the connectionPointType is 
      either a segmentEndPoint or a connectingPoint."
::= { mscAtmIfVptStatusEntry 60 }

mscAtmIfVptRdiState OBJECT-TYPE
   SYNTAX     INTEGER  {
                 good(0),
                 bad(1),
                 unknown(2),
                 notApplicable(3) }
   ACCESS     read-only
   STATUS     mandatory
   DESCRIPTION
     "This attribute indicates the current state of the Remote Defect 
      Indication for this connection.
      
      A value of good indicates that the connection's application is active 
      and no alarm has occurred.
      
      A value of bad indicates that the connection's application is active 
      and an alarm has occurred.
      
      A value of unknown indicates that the connection's application is 
      inactive.
      
      A value of notApplicable occurs when the connectionPointType is 
      either a segmentEndPoint or a connectingPoint."
::= { mscAtmIfVptStatusEntry 70 }

mscAtmIfVptTrafficTable OBJECT-TYPE
   SYNTAX     SEQUENCE OF MscAtmIfVptTrafficEntry
   ACCESS     not-accessible
   STATUS     mandatory
   DESCRIPTION
     "This group is HISTORICAL. Please refer to the group AtmTmOper;
      
      This attribute group contains attributes for the Vcc and Vpc 
      components to reflect operational traffic attributes."
::= { mscAtmIfVpt 130 }

mscAtmIfVptTrafficEntry OBJECT-TYPE
   SYNTAX     MscAtmIfVptTrafficEntry
   ACCESS     not-accessible
   STATUS     mandatory
   DESCRIPTION
     "An entry in the mscAtmIfVptTrafficTable."
   INDEX {
      mscAtmIfIndex,
      mscAtmIfVptIndex }
::= { mscAtmIfVptTrafficTable 1 }

MscAtmIfVptTrafficEntry ::= SEQUENCE {
   mscAtmIfVptTxTrafficDescType
      INTEGER,
   mscAtmIfVptTxQosClass
      INTEGER,
   mscAtmIfVptFwdQosClass
      INTEGER,
   mscAtmIfVptTxQueueLength
      INTEGER,
   mscAtmIfVptTxQueueCongestionState
      INTEGER,
   mscAtmIfVptHoldingPriority
      INTEGER,
   mscAtmIfVptRxTrafficDescType
      INTEGER,
   mscAtmIfVptRxQosClass
      INTEGER,
   mscAtmIfVptBwdQosClass
      INTEGER,
   mscAtmIfVptAtmServiceCategory
      INTEGER,
   mscAtmIfVptTrafficShaping
      INTEGER,
   mscAtmIfVptBearerClassBbc
      INTEGER,
   mscAtmIfVptTransferCapabilityBbc
      INTEGER,
   mscAtmIfVptClippingBbc
      INTEGER,
   mscAtmIfVptUnshapedTransmitQueueing
      INTEGER,
   mscAtmIfVptBestEffort
      INTEGER,
   mscAtmIfVptUsageParameterControl
      INTEGER,
   mscAtmIfVptTxFrameDiscard
      OCTET STRING,
   mscAtmIfVptRxFrameDiscard
      OCTET STRING,
   mscAtmIfVptBandwidthElastic
      INTEGER,
   mscAtmIfVptBandwidthReduction
      INTEGER }

mscAtmIfVptTxTrafficDescType OBJECT-TYPE
   SYNTAX     INTEGER  {
                 n1(1),
                 n2(2),
                 n3(3),
                 n4(4),
                 n5(5),
                 n6(6),
                 n7(7),
                 n8(8) }
   ACCESS     read-only
   STATUS     obsolete
   DESCRIPTION
     "This attribute is HISTORICAL. Please refer to the attribute of the 
      same name in the group AtmTmOper.
      
      This attribute indicates the type of traffic management which is 
      applied to the transmit direction of this connection as defined in the 
      ATM Forum. The txTrafficDescType determines the number and 
      meaning of the parameters in the txTrafficDescParm attribute."
::= { mscAtmIfVptTrafficEntry 10 }

mscAtmIfVptTxQosClass OBJECT-TYPE
   SYNTAX     INTEGER  {
                 unspecified(0),
                 constantBitRate(1),
                 variableBitRate(2),
                 connectionOriented(3),
                 connectionless(4) }
   ACCESS     read-only
   STATUS     obsolete
   DESCRIPTION
     "This attribute indicates the quality of service for the transmit 
      direction for this connection.
      
      The constantBitRate class refers to traffic offered on services such 
      as a constant bit rate video service. This traffic is highest priority.
      
      The variableBitRate class refers to traffic offered on services such 
      as packetized audio and video.
      
      The connectionOriented class refers to connection-oriented traffic 
      such as Frame Relay or X.25 traffic. 
      
      The connectionless traffic refers to traffic offered through 
      connectionless trunks such as certain LAN protocols.
      
      The unspecified class supports a 'best effort' type of service, where 
      there is a minimum guarantee of bandwidth. This traffic is lowest 
      priority.
      
      This attribute is obsolete, replaced by the UNI 4.0 attribute 
      atmServiceCategory."
::= { mscAtmIfVptTrafficEntry 30 }

mscAtmIfVptFwdQosClass OBJECT-TYPE
   SYNTAX     INTEGER  {
                 n0(0),
                 n1(1),
                 n2(2),
                 n3(3),
                 n4(4),
                 notApplicable(14) }
   ACCESS     read-only
   STATUS     obsolete
   DESCRIPTION
     "This attribute is HISTORICAL. Please refer to the attribute of the 
      same name in the group AtmTmOper.
      
      This attribute indicates the quality of service for the calling to called 
      direction for this connection. This is only applicable to Soft PVC 
      and SVC connections. 
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified QOS class; no objective is specified for 
      the performance parameters.
      
      A value of notApplicable is displayed in the case of nailed-up PVCs 
      for which this attribute has no significance."
::= { mscAtmIfVptTrafficEntry 31 }

mscAtmIfVptTxQueueLength OBJECT-TYPE
   SYNTAX     INTEGER (0..30720)
   ACCESS     read-only
   STATUS     obsolete
   DESCRIPTION
     "This attribute is HISTORICAL. Please refer to the attribute of the 
      same name in the group AtmTmOper.
      
      This attribute indicates the current length of the transmit queue for 
      this connection. If this connection has traffic shaping disabled, then 
      this attribute displays the common queue length. If traffic shaping is 
      enabled, then this attribute displays the per-VC queue length."
::= { mscAtmIfVptTrafficEntry 32 }

mscAtmIfVptTxQueueCongestionState OBJECT-TYPE
   SYNTAX     INTEGER (0..3)
   ACCESS     read-only
   STATUS     obsolete
   DESCRIPTION
     "This attribute is HISTORICAL. Please refer to the attribute of the 
      same name in the group AtmTmOper.
      
      This attribute indicates the congestion state of the transmit queue 
      for this connection. If the connection has traffic shaping disabled, 
      then this attribute displays the common queue congestion state. If 
      traffic shaping is enabled, then this attribute displays the per-VC 
      queue congestion state.
      
      The congestion state of a queue is indicated by a numeric value 
      ranging from 0 to 3. When a queue is in a congested state x, only 
      traffic with discard priority (DP) 0 to x are enqueued. Traffic with 
      DP > x is discarded. 
      
      Therefore, if the congestion state is 3, there is no congestion and all 
      traffic is enqueued. Likewise, when the congestion state is 0, there 
      is maximum congestion and only traffic with DP=0 is enqueued on 
      that queue."
::= { mscAtmIfVptTrafficEntry 33 }

mscAtmIfVptHoldingPriority OBJECT-TYPE
   SYNTAX     INTEGER  {
                 n0(0),
                 n1(1),
                 n2(2),
                 n3(3),
                 n4(4),
                 notApplicable(6) }
   ACCESS     read-only
   STATUS     obsolete
   DESCRIPTION
     "This attribute is HISTORICAL. Please refer to the attribute of the 
      same name in the group AtmTmOper.
      
      This attribute indicates the actual holding priority in effect for this 
      connection. In a situation where the link bandwidth fluctuates, such 
      as over an IMA link, holding priority is used to determine which 
      connections are held and which are released. Holding priority 4 
      connections are the first to be released. Holding priority 0 
      connections are the last to be released. Some applications, for 
      example Vcc Test, may override the provisioned holding priority. 
      
      A value of notApplicable is displayed when this is an elastic 
      connection. Holding priority does not apply to bandwidth elastic 
      connections.
      
      Holding priority has no effect for ubr atmServiceCategory or 
      txTrafficDescriptorType 1 or 2 connections."
::= { mscAtmIfVptTrafficEntry 35 }

mscAtmIfVptRxTrafficDescType OBJECT-TYPE
   SYNTAX     INTEGER  {
                 n1(1),
                 n2(2),
                 n3(3),
                 n4(4),
                 n5(5),
                 n6(6),
                 n7(7),
                 n8(8) }
   ACCESS     read-only
   STATUS     obsolete
   DESCRIPTION
     "This attribute is HISTORICAL. Please refer to the attribute of the 
      same name in the group AtmTmOper.
      
      This attribute indicates the type of traffic management which is 
      applied to the receive direction of this connection as defined in the 
      ATM Forum. The rxTrafficDescType determines the number and 
      meaning of the parameters in the rxTrafficDescParm attribute."
::= { mscAtmIfVptTrafficEntry 40 }

mscAtmIfVptRxQosClass OBJECT-TYPE
   SYNTAX     INTEGER  {
                 unspecified(0),
                 constantBitRate(1),
                 variableBitRate(2),
                 connectionOriented(3),
                 connectionless(4) }
   ACCESS     read-only
   STATUS     obsolete
   DESCRIPTION
     "This attribute reflects the value of the provisioned attribute in the 
      Vcd or Vpd. Refer to that attribute for more detailed explanation. 
      
      This attribute is obsolete replaced by the UNI 4.0 attribute 
      atmServiceCategory."
::= { mscAtmIfVptTrafficEntry 60 }

mscAtmIfVptBwdQosClass OBJECT-TYPE
   SYNTAX     INTEGER  {
                 n0(0),
                 n1(1),
                 n2(2),
                 n3(3),
                 n4(4),
                 notApplicable(14) }
   ACCESS     read-only
   STATUS     obsolete
   DESCRIPTION
     "This attribute is HISTORICAL. Please refer to the attribute of the 
      same name in the group AtmTmOper.
      
      This attribute indicates the quality of service for the called to calling 
      direction for this connection. This is only applicable to Soft PVC 
      and SVC connections. 
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified QOS class; no objective is specified for 
      the performance parameters.
      
      A value of notApplicable is displayed in the case of nailed-up PVCs 
      for which this attribute has no significance."
::= { mscAtmIfVptTrafficEntry 61 }

mscAtmIfVptAtmServiceCategory OBJECT-TYPE
   SYNTAX     INTEGER  {
                 unspecifiedBitRate(0),
                 constantBitRate(1),
                 rtVariableBitRate(2),
                 nrtVariableBitRate(3) }
   ACCESS     read-only
   STATUS     obsolete
   DESCRIPTION
     "This attribute is HISTORICAL. Please refer to the attribute of the 
      same name in the group AtmTmOper.
      
      This attribute indicates the ATM service category used for traffic in 
      both directions of the connection. 
      
      The constantBitRate service category is intended for real time 
      applications, that is, those requiring tightly constrained delay and 
      delay variation, as would be appropriate for voice and video 
      applications. The consistent availability of a fixed quantity of 
      bandwidth is considered appropriate for CBR service. Cells which 
      are delayed beyond the value specified by Cell Transfer Delay are 
      assumed to have significantly reduced value of the application.
      
      The rtVariableBitRate service category is intended for real time 
      applications; that is those requiring tightly constrained delay and 
      delay variation, as would be appropriate for voice and video 
      applications. Sources are expected to transmit at a rate which varies 
      with time. Equivalently, the source can be described as 'bursty'. 
      Cells which are delayed beyond the value specified by Cell Transfer 
      Delay are assumed to be of significantly reduced value to the 
      application. Real time VBR service may support statistical 
      multiplexing of real time sources.
      
      The nrtVariableBitRate service category is intended for non-real 
      time applications which have bursty traffic characteristics and which 
      can be characterized in terms of a PCR, SCR, and MBS. For those 
      cells which are transferred within the traffic contract, the application 
      expects a low cell loss ratio. For all connections, it expects a bound 
      on the mean cell transfer delay. Non-real time VBR service may 
      support statistical multiplexing of connections.
      
      The unspecifiedBitRate service is intended for non-real time 
      applications, that is those not requiring tightly constrained delay 
      and delay variation. UBR sources are expected to be bursty. UBR 
      service supports a high degree of statistical multiplexing among 
      sources. UBR service does not specify traffic related service 
      guarantees. No numerical commitments are made with respect to 
      the cell loss ratio experienced by a UBR connection, or as to the 
      cell transfer delay experienced by cells on the connection."
::= { mscAtmIfVptTrafficEntry 62 }

mscAtmIfVptTrafficShaping OBJECT-TYPE
   SYNTAX     INTEGER  {
                 enabled(0),
                 disabled(1),
                 notApplicable(4) }
   ACCESS     read-only
   STATUS     obsolete
   DESCRIPTION
     "This attribute is HISTORICAL. Please refer to the attribute of the 
      same name in the group AtmTmOper.
      
      This attribute indicates the traffic shaping state of the connection.
      
      A value of notApplicable indicates that traffic shaping is not 
      applicable or not supported for this connection. This is the case 
      when the atmServiceCategory is constantBitRate, or when the 
      txTrafficDescType is 1 or 2. In these cases, the value of 
      notApplicable is set regardless of whether traffic shaping is enabled 
      or disabled in the provisioning data.
      
      A value of disabled indicates that traffic shaping is applicable and 
      supported for the type of connection but has been turned off in the 
      provisioning data.
      
      A value of enabled indicates that traffic shaping is applicable and 
      supported for the type of connection and has been turned on in the 
      provisioning data. This is the only case that indicates that traffic 
      shaping is performed on the connection. In this case, the actual 
      shaping rate is reflected in the txTrafficDescParm attribute, 
      parameter number 4."
::= { mscAtmIfVptTrafficEntry 70 }

mscAtmIfVptBearerClassBbc OBJECT-TYPE
   SYNTAX     INTEGER  {
                 a(1),
                 c(3),
                 x(16),
                 vp(24),
                 notApplicable(30) }
   ACCESS     read-only
   STATUS     obsolete
   DESCRIPTION
     "This attribute is HISTORICAL. Please refer to the attribute of the 
      same name in the group AtmTmOper.
      
      This attribute indicates the bearer capability for this connection.
      
      Class a service is a connection-oriented, constant bit rate ATM 
      transport service. Class a service has end to end timing 
      requirements and may require stringent cell loss, cell delay and cell 
      delay variation performance.When a is displayed, the user is 
      requesting more than an ATM only service. The network may look 
      at the AAL to provide interworking based upon its contents. 
      
      Class c service is a connection-oriented, variable bit rate ATM 
      transport service. Class c service has no end-to-end timing 
      requirements.When c is displayed, the user is requesting more than 
      an ATM only service. The network interworking function may look 
      at the AAL and provide service based on it.
      
      Class x service is a connection-oriented ATM transport service 
      where the AAL, trafficType (cbr or vbr) and timing requirements 
      are user defined (that is, transparent to the network). When the 
      value of this attribute is x, the user is requesting an ATM only 
      service from the network. In this case, the network shall not process 
      any higher layer protocol.
      
      Class vp service is used to indicate a transparent VP service when 
      the user is requesting an ATM only service from the network. In this 
      case, the network does not process any higher layer protocol. This 
      service differs from class x service in that with the class vp service 
      both the VCI field (except for VCI values 0, 3, 4, and 6 through 15) 
      and Payload Type field are transported transparently by the network. 
      This attribute value is only applicable to SPVP and SVP 
      connections.
      
      A value of notApplicable is displayed in the case of nailed-up PVCs 
      for which this attribute has no significance."
::= { mscAtmIfVptTrafficEntry 71 }

mscAtmIfVptTransferCapabilityBbc OBJECT-TYPE
   SYNTAX     INTEGER  {
                 n0(0),
                 n1(1),
                 n2(2),
                 n5(5),
                 n8(8),
                 n9(9),
                 n10(10),
                 notApplicable(30) }
   ACCESS     read-only
   STATUS     obsolete
   DESCRIPTION
     "This attribute is HISTORICAL. Please refer to the attribute of the 
      same name in the group AtmTmOper.
      
      This attribute indicates the transfer capability for this connection. 
      Uni 3.0/3.1 traffic type and end-to-end timing parameters are 
      mapped into this parameter as follows:
      <transferCapability: TrafficType, Timing>
      0: NoIndication, NoIndication
      1: NoIndication, yes
      2: NoIndication, no
      5: CBR, yes
      8: VBR, NoIndication
      9: VBR, yes
      10: VBR, no
      
      A value of notApplicable is displayed in the case of nailed-up PVCs 
      for which this attribute has no significance, or in the case that the 
      transfer capability in the call request was set to NoIndication.
      
      The CBR traffic type refers to traffic offered on services such as a 
      constant bit rate video service or a circuit emulation.
      
      The VBR traffic type refers to traffic offered on services such as 
      packetized audio and video, or data.
      
      The value NoIndication for traffic type is used if the user has not set 
      the traffic type; similarly for end-to-end timing.
      
      The value yes for end-to-end timing indicates that end-to-end 
      timing is required for the connection.
      
      The value no for end-to-end timing indicates that end-to-end timing 
      is not required for the connection."
::= { mscAtmIfVptTrafficEntry 72 }

mscAtmIfVptClippingBbc OBJECT-TYPE
   SYNTAX     INTEGER  {
                 no(0),
                 yes(1),
                 notApplicable(14) }
   ACCESS     read-only
   STATUS     obsolete
   DESCRIPTION
     "This attribute is HISTORICAL. Please refer to the attribute of the 
      same name in the group AtmTmOper.
      
      This attribute indicates the value of the clipping susceptibility 
      parameter in the BBC Information Element.
      
      Clipping is an impairment in which the first fraction of a second of 
      information to be transferred is lost. It occurs after a call is 
      answered and before an associated connection is switched through.
      
      A value of notApplicable is displayed in the case of nailed-up PVCs 
      for which this attribute has no significance."
::= { mscAtmIfVptTrafficEntry 74 }

mscAtmIfVptUnshapedTransmitQueueing OBJECT-TYPE
   SYNTAX     INTEGER  {
                 perVc(0),
                 common(1),
                 notApplicable(4) }
   ACCESS     read-only
   STATUS     obsolete
   DESCRIPTION
     "This attribute is HISTORICAL. Please refer to the attribute of the 
      same name in the group AtmTmOper.
      
      This attribute indicates the unshaped transmit queuing state of the 
      connection.
      
      A value of common indicates that transmit traffic is being enqueued 
      onto common transmit queues. 
      
      A value of perVc indicates that transmit traffic is being enqueued 
      onto a per-VC queue for this connection. This is the case when 
      trafficShaping is disabled, but per-VC queueing has been 
      configured for this connection. 
      
      A value of notApplicable indicates that transmit traffic is being 
      shaped for this connection. Transmit traffic for a shaped connection 
      is enqueued onto a per-VC queue, but this attribute is only 
      applicable for unshaped connections."
::= { mscAtmIfVptTrafficEntry 75 }

mscAtmIfVptBestEffort OBJECT-TYPE
   SYNTAX     INTEGER  {
                 indicated(0),
                 notIndicated(1),
                 notApplicable(14) }
   ACCESS     read-only
   STATUS     obsolete
   DESCRIPTION
     "This attribute is HISTORICAL. Please refer to the attribute of the 
      same name in the group AtmTmOper.
      
      This attribute indicates value of best effort parameter in the ATM 
      Traffic Descriptor Information Element.
      
      The value indicated implies that the quality of service for this 
      connection is not guaranteed.
      
      The value notIndicated implies that the quality of service for this 
      connection is guaranteed.
      
      A value of notApplicable is displayed in the case of nailed-up PVCs 
      for which this attribute has no significance."
::= { mscAtmIfVptTrafficEntry 76 }

mscAtmIfVptUsageParameterControl OBJECT-TYPE
   SYNTAX     INTEGER  {
                 enabled(0),
                 disabled(1),
                 notApplicable(3) }
   ACCESS     read-only
   STATUS     obsolete
   DESCRIPTION
     "This attribute is HISTORICAL. Please refer to the attribute of the 
      same name in the group AtmTmOper.
      
      This attribute indicates the UPC state of the connection.
      
      A value of notApplicable indicates that UPC is not applicable or not 
      supported for the connection. This is the case when the connection's 
      rxTrafficDescType is 1 or 2. A value of notApplicable is set 
      regardless of whether UPC is disabled or enabled in provisioning 
      data.
      
      A value of disabled indicates that UPC is applicable and supported 
      for the type of connection but has been turned off in the 
      provisioning data.
      
      A value of enabled indicates that UPC is applicable and supported 
      for the type of connection and has been turned on in the 
      provisioning data. This is the only case that indicates that UPC is 
      enforced on the connection. In this case the traffic descriptor 
      parameters used for UPC enforcement are reflected in the 
      rxTrafficDescParms of the connection."
::= { mscAtmIfVptTrafficEntry 80 }

mscAtmIfVptTxFrameDiscard OBJECT-TYPE
   SYNTAX     OCTET STRING (SIZE (1))
   ACCESS     read-only
   STATUS     obsolete
   DESCRIPTION
     "This attribute is HISTORICAL. Please refer to the attribute of the 
      same name in the group AtmTmOper.
      
      This attribute indicates the set of current frame discard functions in 
      effect in the transmit data direction at this connection point.
      
      A value of ppd indicates that the Partial Packet Discard (PPD) 
      function is in effect. PPD may be applied at an interim connecting 
      point for a connection which is transporting frame traffic (AAL5 at 
      the endpoint). PPD is controlled by provisioning for PVCs and 
      SPVCs, and by call setup parameters in the AAL and Traffic 
      Descriptor Information Elements.
      
      A value of epd indicates that the Early Packet Discard (EPD) 
      function is in effect at this connection endpoint. PPD and EPD are 
      enabled by default at a connection endpoint which is performing 
      AAL5 segmentation and assembly.
      
      Frame discard functions are not applicable for Virtual Path 
      Connections (VPCs).

      Description of bits:
      ppd(0)
      epd(1)"
::= { mscAtmIfVptTrafficEntry 85 }

mscAtmIfVptRxFrameDiscard OBJECT-TYPE
   SYNTAX     OCTET STRING (SIZE (1))
   ACCESS     read-only
   STATUS     obsolete
   DESCRIPTION
     "This attribute is HISTORICAL. Please refer to the attribute of the 
      same name in the group AtmTmOper.
      
      This attribute indicates the set of current frame discard functions in 
      effect in the receive data direction at this connection point.
      
      A value of ppd indicates that the Partial Packet Discard (PPD) 
      function is in effect. PPD may be applied at an interim connecting 
      point for a connection which is transporting frame traffic (AAL5 at 
      the endpoint). PPD is controlled by provisioning for PVCs and 
      SPVCs, and by call setup parameters in the AAL and Traffic 
      Descriptor Information Elements.
      
      A value of epd indicates that the Early Packet Discard (EPD) 
      function is in effect at this connection endpoint. PPD and EPD are 
      enabled by default at a connection endpoint which is performing 
      AAL5 segmentation and assembly.
      
      Frame discard functions are not applicable for Virtual Path 
      Connections (VPCs).

      Description of bits:
      ppd(0)
      epd(1)"
::= { mscAtmIfVptTrafficEntry 86 }

mscAtmIfVptBandwidthElastic OBJECT-TYPE
   SYNTAX     INTEGER  {
                 no(0),
                 yes(1) }
   ACCESS     read-only
   STATUS     obsolete
   DESCRIPTION
     "This attribute is HISTORICAL. Please refer to the attribute of the 
      same name in the group AtmTmOper.
      
      This attribute is only of importance for connections which are 
      carried on a link with a variable bandwidth. For example, the 
      bandwidth may be reduced in the event that one or more physical 
      links in the IMA group fail, such that the originally requested 
      bandwidth cannot be maintained. This attribute shows whether the 
      application (for example, Trunk) running on this connection can 
      continue to operate if the bandwidth is reduced. If the bandwidth is 
      reduced, the amount by which it is reduced is displayed in the 
      bandwidthReduction attribute. 
      
      A value of yes, indicates that this connection is elastic, and the 
      bandwidth may be reduced but the connection is not released. 
      
      A value of no indicates that the bandwidth for this connection is not 
      reduced in the event of link bandwidth reduction. However, this 
      connection may be released based on its holdingPriority.
      
      Bandwidth elasticity has no effect for ubr atmServiceCategory or 
      txTrafficDescriptorType 1 or 2 connections."
::= { mscAtmIfVptTrafficEntry 90 }

mscAtmIfVptBandwidthReduction OBJECT-TYPE
   SYNTAX     INTEGER (0..2147483647)
   ACCESS     read-only
   STATUS     obsolete
   DESCRIPTION
     "This attribute is HISTORICAL. Please refer to the attribute of the 
      same name in the group AtmTmOper.
      
      This attribute shows the amount by which the bandwidth has been 
      reduced for this connection. This value is non-zero only for 
      connections which have bandwidthElastic displayed as yes, and 
      which are also operating in a reduced bandwidth mode. This is 
      typically be the case for selected connections running over an IMA 
      link. This attribute takes a value from 0 (no reduction) up to the 
      ECR. All connections which are running at their full allocated 
      bandwidth, bwReduction have the value 0. Connections which have 
      been reduced in allocated bandwidth have a positive number for this 
      attribute. The bwReduction may be subtracted from the ECR (which 
      is displayed as txTrafficDescParm 5) to determine the actual 
      bandwidth allocated to this connection."
::= { mscAtmIfVptTrafficEntry 100 }

mscAtmIfVptStatsTable OBJECT-TYPE
   SYNTAX     SEQUENCE OF MscAtmIfVptStatsEntry
   ACCESS     not-accessible
   STATUS     mandatory
   DESCRIPTION
     "This group contains traffic statistics for a Vcc, Vpc, or Vpt 
      component."
::= { mscAtmIfVpt 140 }

mscAtmIfVptStatsEntry OBJECT-TYPE
   SYNTAX     MscAtmIfVptStatsEntry
   ACCESS     not-accessible
   STATUS     mandatory
   DESCRIPTION
     "An entry in the mscAtmIfVptStatsTable."
   INDEX {
      mscAtmIfIndex,
      mscAtmIfVptIndex }
::= { mscAtmIfVptStatsTable 1 }

MscAtmIfVptStatsEntry ::= SEQUENCE {
   mscAtmIfVptStatsTxCell
      PassportCounter64,
   mscAtmIfVptStatsTxCellClp
      PassportCounter64,
   mscAtmIfVptTxDiscard
      PassportCounter64,
   mscAtmIfVptTxDiscardClp
      PassportCounter64,
   mscAtmIfVptStatsTxCellDiscard
      PassportCounter64,
   mscAtmIfVptStatsTxCellDiscardClp
      PassportCounter64,
   mscAtmIfVptStatsTxFrameDiscard
      PassportCounter64,
   mscAtmIfVptStatsTxFrameDiscardClp
      PassportCounter64,
   mscAtmIfVptStatsRxCell
      PassportCounter64,
   mscAtmIfVptStatsRxCellClp
      PassportCounter64,
   mscAtmIfVptRxDiscard
      PassportCounter64,
   mscAtmIfVptRxDiscardClp
      PassportCounter64,
   mscAtmIfVptStatsRxCellDiscard
      PassportCounter64,
   mscAtmIfVptStatsRxCellDiscardClp
      PassportCounter64,
   mscAtmIfVptStatsRxFrameDiscard
      PassportCounter64,
   mscAtmIfVptStatsRxFrameDiscardClp
      PassportCounter64,
   mscAtmIfVptStatsRxUpcViolationOnEnforcer1
      PassportCounter64,
   mscAtmIfVptStatsRxUpcViolationOnEnforcer2
      PassportCounter64,
   mscAtmIfVptStatsRxAal5FrameError
      PassportCounter64,
   mscAtmIfVptStatsRxAal5FrameAbort
      PassportCounter64 }

mscAtmIfVptStatsTxCell OBJECT-TYPE
   SYNTAX     PassportCounter64 
   ACCESS     read-only
   STATUS     mandatory
   DESCRIPTION
     "This attribute counts the number of cells that have been transmitted 
      from the interface on this connection. The counter wraps to zero if it 
      exceeds its maximum value of (2**64)-1."
::= { mscAtmIfVptStatsEntry 10 }

mscAtmIfVptStatsTxCellClp OBJECT-TYPE
   SYNTAX     PassportCounter64 
   ACCESS     read-only
   STATUS     mandatory
   DESCRIPTION
     "This attribute counts the number of cells that have been transmitted 
      from the interface on this connection with the CLP=1. The counter 
      wraps to zero if it exceeds its maximum value of (2**64)-1."
::= { mscAtmIfVptStatsEntry 20 }

mscAtmIfVptTxDiscard OBJECT-TYPE
   SYNTAX     PassportCounter64 
   ACCESS     read-only
   STATUS     obsolete
   DESCRIPTION
     "This attribute is replaced by new attributes txCellDiscard and 
      txFrameDiscard.
      
      This attribute counts the number of cells or frames received from 
      the bus on this connection that have been discarded.
      
      If the connection segments frames into cells, the counter indicates 
      the number of frames discarded. Connections which segment 
      frames into cells have a connectionPointType of 
      connectionEndPoint.
      
      If the connection relays cells without adaptation, the counter 
      indicates the number of cells discarded. Connections which relay 
      cells without adaptation have a connectionPointType of 
      segmentEndPoint or connectingPoint.
      
      AAL1 connections are an exception to this rule; although they have 
      a connectionPointType of connectionEndPoint, they do not do 
      adaptation at this point. Thus, in the AAL1 case, this attribute 
      counts discarded cells.
      
      Discards are done due to congestion or when the connection's 
      interface is disabled.
      
      The counter wraps to zero if it exceeds its maximum value of 
      (2**64)-1."
::= { mscAtmIfVptStatsEntry 30 }

mscAtmIfVptTxDiscardClp OBJECT-TYPE
   SYNTAX     PassportCounter64 
   ACCESS     read-only
   STATUS     obsolete
   DESCRIPTION
     "This attribute is replaced by new attributes txCellDiscardClp and 
      txFrameDiscardClp.
      
      This attribute counts the number of cells or frames received from 
      the bus on this connection with CLP=1 that have been discarded.
      
      If the connection segments frames into cells, the counter indicates 
      the number of frames discarded. Connections which segment 
      frames into cells have a connectionPointType of 
      connectionEndPoint.
      
      If the connection relays cells without adaptation, the counter 
      indicates the number of cells discarded. Connections which relay 
      cells without adaptation have a connectionPointType of 
      segmentEndPoint or connectingPoint.
      
      AAL1 connections are an exception to this rule; although they have 
      a connectionPointType of connectionEndPoint, they do not do 
      adaptation at this point. Thus, in the AAL1 case, this attribute 
      counts discarded cells.
      
      Discards are done due to congestion or when the connection's 
      interface is disabled.
      
      The counter wraps to zero if it exceeds its maximum value of 
      (2**64)-1."
::= { mscAtmIfVptStatsEntry 40 }

mscAtmIfVptStatsTxCellDiscard OBJECT-TYPE
   SYNTAX     PassportCounter64 
   ACCESS     read-only
   STATUS     mandatory
   DESCRIPTION
     "This attribute counts the number of cells received from the bus on 
      this connection that have been discarded.
      
      Discarded cells are not counted in the txCell attribute.
      
      Cells are discarded due to transmit congestion, Partial Packet 
      Discard (PPD), Early Packet Discard (EPD), and Weighted Random 
      Early Detection (W-RED) mechanisms, or when the connection's 
      interface is disabled.
      
      For CQC-based ATM cards, this attribute is applicable only to 
      connections that relay cells without adaptation. Such connections 
      usually have a connectionPointType of segmentEndPoint or 
      connectingPoint. AAL1 connections are an exception to this rule; 
      although they have a connectionPointType of connectionEndPoint, 
      they do not do adaptation at this point. For Vpts, this attribute 
      provides an aggregated total of all txCellDiscard values for all such 
      connections associated with the Vpt.
      
      For Vccs on CQC-based ATM cards, if the connection segments 
      frames into cells, this attribute is not applicable and is not 
      displayed.
      
      The counter wraps to zero if it exceeds its maximum value of 
      (2**64)-1."
::= { mscAtmIfVptStatsEntry 42 }

mscAtmIfVptStatsTxCellDiscardClp OBJECT-TYPE
   SYNTAX     PassportCounter64 
   ACCESS     read-only
   STATUS     mandatory
   DESCRIPTION
     "This attribute counts the number of cells received from the bus on 
      this connection with CLP=1 that have been discarded.
      
      This count is included in the txCellDiscard attribute. Discarded 
      cells are not counted in the txCellClp attribute.
      
      Cells are discarded due to transmit congestion, Partial Packet 
      Discard (PPD), Early Packet Discard (EPD), and Weighted Random 
      Early Detection (W-RED) mechanisms, or when the connection's 
      interface is disabled.
      
      For CQC-based ATM cards, this attribute is applicable only to 
      connections that relay cells without adaptation. Such connections 
      have a connectionPointType of segmentEndPoint or 
      connectingPoint. AAL1 connections are an exception to this rule; 
      although they have a connectionPointType of connectionEndPoint, 
      they do not do adaptation at this point. For Vpts, this attribute 
      provides an aggregated total of all txCellDiscardClp values for all 
      such connections associated with the Vpt.
      
      For Vccs on CQC-based ATM cards, if the connection segments 
      frames into cells, this attribute is not applicable and is not 
      displayed.
      
      The counter wraps to zero if it exceeds its maximum value of 
      (2**64)-1."
::= { mscAtmIfVptStatsEntry 43 }

mscAtmIfVptStatsTxFrameDiscard OBJECT-TYPE
   SYNTAX     PassportCounter64 
   ACCESS     read-only
   STATUS     mandatory
   DESCRIPTION
     "This attribute counts the number of frames received from the bus on 
      this connection that have been discarded.
      
      Frames are discarded due to congestion, Partial Packet Discard 
      (PPD), Early Packet Discard (EPD), and Weighted Random Early 
      Detection (W-RED) mechanisms, or when the connection interface 
      is disabled.
      
      This count is independent of the txCell or txCellDiscard attribute.
      
      For CQC-based ATM cards, this attribute is applicable only to 
      connections that segment frames into cells. Such connections have a 
      connectionPointType of connectionEndPoint. AAL1 connections 
      are an exception to this rule; although they have a 
      connectionPointType of connectionEndPoint, they do not do 
      adaptation at this point. For Vpts, this attribute provides an 
      aggregated total of all txFrameDiscard values for all such 
      connections associated with the Vpt.
      
      For CQC-based ATM cards, for Vpcs, and Vccs that relay cells 
      without adaptation, this attribute is not applicable and is not 
      displayed.
      
      Discards due to EPD, PPD, and W-RED for a standard Vpt Vcc are 
      not included in this attribute. These discards are counted in the 
      Vcc's parent Vpt txFrameDiscard attribute.
      
      The counter wraps to zero if it exceeds its maximum value of 
      (2**64)-1."
::= { mscAtmIfVptStatsEntry 46 }

mscAtmIfVptStatsTxFrameDiscardClp OBJECT-TYPE
   SYNTAX     PassportCounter64 
   ACCESS     read-only
   STATUS     mandatory
   DESCRIPTION
     "This attribute counts the number of discarded frames on this 
      connection that were received from the bus and composed of one or 
      more CLP=1 cells.
      
      Frames are discarded due to congestion, Partial Packet Discard 
      (PPD), Early Packet Discard (EPD), and Weighted Random Early 
      Detection (W-RED) mechanisms, or when the connection interface 
      is disabled.
      
      This count is included in the txFrameDiscard attribute.
      
      For CQC-based ATM cards, this attribute is applicable only to 
      connections that segment frames into cells. Such connections have a 
      connectionPointType of connectionEndPoint. AAL1 connections 
      are an exception to this rule; although they have a 
      connectionPointType of connectionEndPoint, they do not do 
      adaptation at this point. For Vpts, this attribute provides an 
      aggregated total of all txFrameDiscardClp values for all such 
      connections associated with the Vpt.
      
      For CQC-based ATM cards, for Vpcs and Vccs that relay cells 
      without adaptation, this attribute is not applicable and is not 
      displayed.
      
      
      Discards due to EPD, PPD, and W-RED for a standard Vpt Vcc are 
      not included in this attribute. These discards are counted in the 
      Vcc's parent Vpt txFrameDiscardClp attribute.
      
      The counter wraps to zero if it exceeds its maximum value of 
      (2**64)-1."
::= { mscAtmIfVptStatsEntry 47 }

mscAtmIfVptStatsRxCell OBJECT-TYPE
   SYNTAX     PassportCounter64 
   ACCESS     read-only
   STATUS     mandatory
   DESCRIPTION
     "This attribute counts the number of cells that have been received 
      from the interface on this connection. The counter wraps to zero if it 
      exceeds its maximum value of (2**64)-1."
::= { mscAtmIfVptStatsEntry 50 }

mscAtmIfVptStatsRxCellClp OBJECT-TYPE
   SYNTAX     PassportCounter64 
   ACCESS     read-only
   STATUS     mandatory
   DESCRIPTION
     "This attribute counts the number of cells that have been received 
      from the interface on this connection with the CLP=1. The counter 
      wraps to zero if it exceeds its maximum value of (2**64)-1."
::= { mscAtmIfVptStatsEntry 60 }

mscAtmIfVptRxDiscard OBJECT-TYPE
   SYNTAX     PassportCounter64 
   ACCESS     read-only
   STATUS     obsolete
   DESCRIPTION
     "This attribute is replaced by new attributes rxCellDiscard and 
      rxFrameDiscard.
      
      This attribute counts the number of cells or frames received from 
      the interface on this connection that have been discarded.
      
      If the connection segments frames into cells, the counter indicates 
      the number of frames discarded. Connections which segment 
      frames into cells have a connectionPointType of 
      connectionEndPoint.
      
      If the connection relays cells without adaptation, the counter 
      indicates the number of cells discarded. Connections which relay 
      cells without adaptation have a connectionPointType of 
      segmentEndPoint or connectingPoint.
      
      AAL1 connections are an exception to this rule; although they have 
      a connectionPointType of connectionEndPoint, they do not do 
      adaptation at this point. Thus, in the AAL1 case, this attribute 
      counts discarded cells.
      
      Discards are done due to congestion, non-conformance with UPC or 
      AAL reassembly problems.
      
      The counter wraps to zero if it exceeds its maximum value of 
      (2**64)-1."
::= { mscAtmIfVptStatsEntry 70 }

mscAtmIfVptRxDiscardClp OBJECT-TYPE
   SYNTAX     PassportCounter64 
   ACCESS     read-only
   STATUS     obsolete
   DESCRIPTION
     "This attribute is replaced by new attributes rxCellDiscardClp and 
      rxFrameDiscardClp.
      
      This attribute counts the number of cells or frames received from 
      the interface on this connection with CLP=1 that have been 
      discarded.
      
      If the connection segments frames into cells, the counter indicates 
      the number of frames discarded. Connections which segment 
      frames into cells have a connectionPointType of 
      connectionEndPoint.
      
      If the connection relays cells without adaptation, the counter 
      indicates the number of cells discarded. Connections which relay 
      cells without adaptation have a connectionPointType of 
      segmentEndPoint or connectingPoint.
      
      AAL1 connections are an exception to this rule; although they have 
      a connectionPointType of connectionEndPoint, they do not do 
      adaptation at this point. Thus, in the AAL1 case, this attribute 
      counts discarded cells.
      
      Discards are done due to congestion, non-conformance with UPC or 
      AAL reassembly problems.
      
      The counter wraps to zero if it exceeds its maximum value of 
      (2**64)-1."
::= { mscAtmIfVptStatsEntry 80 }

mscAtmIfVptStatsRxCellDiscard OBJECT-TYPE
   SYNTAX     PassportCounter64 
   ACCESS     read-only
   STATUS     mandatory
   DESCRIPTION
     "This attribute counts the number of cells received from the interface 
      on this connection that have been discarded. This count is included 
      in the rxCell attribute.
      
      This count includes cells discarded due to non-conformance with 
      UPC, cells which are part of a frame which has been discarded due 
      to an AAL5 frame reassembly error, cells which are discarded due 
      to congestion, or cells which are received while the next hop 
      connection to which the traffic is directed across the backplane is 
      down. The next hop connection is the Vcc or Vpc identified by the 
      nextHop attribute of the Nrp or Rp component. 
      
      For CQC-based ATM cards, this attribute is applicable only to 
      connections that relay cells without adaptation. Such connections 
      have a connectionPointType of connectionEndPoint or 
      connectingPoint. AAL1 connections are an exception to this rule; 
      although they have a connectionPointType of connectionEndPoint, 
      they do not do adaptation at this point. For Vpts, this attribute 
      provides an aggregated total of all rxCellDiscard values for all such 
      connections associated with the Vpt.
      
      For CQC-based ATM cards, for Vpcs, and Vccs that relay cells 
      without adaptation, this attribute is not applicable and is not 
      displayed.
      
      Discards due to non-conformance with UPC at the VP layer, for a 
      standard Vpt Vcc, are not included in this attribute. These discards 
      are counted in the Vcc's parent Vpt rxCellDiscard attribute. 
      
      The counter wraps to zero if it exceeds its maximum value of 
      (2**64)-1."
::= { mscAtmIfVptStatsEntry 82 }

mscAtmIfVptStatsRxCellDiscardClp OBJECT-TYPE
   SYNTAX     PassportCounter64 
   ACCESS     read-only
   STATUS     mandatory
   DESCRIPTION
     "This attribute counts the number of cells received from the interface 
      on this connection with CLP=1 that have been discarded. This count 
      is included in the rxCell and rxCellDiscard attributes.
      
      This count includes cells discarded due to non-conformance with 
      UPC, cells which are part of a frame which has been discarded due 
      to an AAL5 frame reassembly error, cells which are discarded due 
      to congestion, or cells which are received while the next hop 
      connection to which the traffic is directed across the backplane is 
      down. The next hop connection is the Vcc or Vpc identified by the 
      nextHop attribute of the Nrp or Rp component. 
      
      For CQC-based ATM cards, this attribute is applicable only to 
      connections that relay cells without adaptation. Such connections 
      have a connectionPointType of connectionEndPoint or 
      connectingPoint. AAL1 connections are an exception to this rule; 
      although they have a connectionPointType of connectionEndPoint, 
      they do not do adaptation at this point. For Vpts, this attribute 
      provides an aggregated total of all rxCellDiscard values for all such 
      connections associated with the Vpt.
      
      For CQC-based ATM cards, for Vpcs, and Vccs that relay cells 
      without adaptation, this attribute is not applicable and is not 
      displayed.
      
      Discards due to non-conformance with UPC at the VP layer, for a 
      standard Vpt Vcc, are not included in this attribute. These discards 
      are counted in the Vcc's parent Vpt rxCellDiscard attribute.
      
      The counter wraps to zero if it exceeds its maximum value of 
      (2**64)-1."
::= { mscAtmIfVptStatsEntry 83 }

mscAtmIfVptStatsRxFrameDiscard OBJECT-TYPE
   SYNTAX     PassportCounter64 
   ACCESS     read-only
   STATUS     mandatory
   DESCRIPTION
     "This attribute counts the number of frames received from the 
      interface on this connection that have been discarded. This count is 
      independent of the rxCellDiscard attribute.
      
      This count includes frames discarded due to an AAL5 frame 
      reassembly error, frames discarded due to early packet discard 
      (EPD), and frames discarded due to processor (CPU) congestion. 
      This attribute is applicable only to connections that reassemble 
      incoming cells into frames. Connections which reassemble cells 
      into frames have a connectionPointType of connectionEndPoint. 
      AAL1 connections are an exception to this rule; even though they 
      have a connectionPointType of connectionEndPoint, they do not 
      do adaptation at this point. For Vpts, this attribute provides an 
      aggregated total of all rxFrameDiscard values for all applicable 
      connections associated with the Vpt.
      
      For Vpcs and for Vccs that relay cells without adaptation, this 
      attribute is not applicable and is not displayed.
      
      The counter wraps to zero if it exceeds its maximum value of 
      (2**64)-1."
::= { mscAtmIfVptStatsEntry 86 }

mscAtmIfVptStatsRxFrameDiscardClp OBJECT-TYPE
   SYNTAX     PassportCounter64 
   ACCESS     read-only
   STATUS     mandatory
   DESCRIPTION
     "This attribute counts the number of discarded frames on this 
      connection that were received from the interface and composed of 
      one or more CLP1 cells. This count is included in the 
      rxFrameDiscard attribute. It is independent of the rxCellDiscard 
      attribute.
      
      This count includes frames discarded due to an AAL5 frame 
      reassembly error, frames discarded due to early packet discard 
      (EPD), and frames discarded due to processor (CPU) congestion. 
      This attribute is applicable only to connections that reassemble 
      incoming cells into frames. Such connections have a 
      connectionPointType of connectionEndPoint. AAL1 connections 
      are an exception to this rule; although they have a 
      connectionPointType of connectionEndPoint, they do not do 
      adaptation at this point. For Vpts, this attribute provides an 
      aggregated total of all rxFrameDiscardClp values for all applicable 
      connections associated with the Vpt.
      
      For Vpcs and for Vccs that relay cells without adaptation, this 
      attribute is not applicable and is not displayed.
      
      The counter wraps to zero if it exceeds its maximum value of 
      (2**64)-1."
::= { mscAtmIfVptStatsEntry 88 }

mscAtmIfVptStatsRxUpcViolationOnEnforcer1 OBJECT-TYPE
   SYNTAX     PassportCounter64 
   ACCESS     read-only
   STATUS     mandatory
   DESCRIPTION
     "This attribute counts the number of UPC violations observed by the 
      Generic Cell Rate Algorithm (GCRA) Enforcer 1. This attribute is 
      only applicable if UPC is enforced or monitored. This attribute is 
      not applicable for standard Vpt Vccs. This attribute is not applicable 
      and is not displayed on CQC-based ATM cards.
      
      When the value of rxTrafficDescType for this connection is 3, 4, 5, 
      6, 7 or 8, Enforcer 1 enforces conformance of traffic received from 
      the interface to PCR CLP0+1.
      
      When the value of rxTrafficDescType for this connection is 9, 
      Enforcer 1 performs the Dynamic Generic Cell Rate Algorithm 
      (DGCRA) used for the Available Bit Rate (ABR) service category.
      
      If UPC is enforced all non-conforming cells are discarded by this 
      enforcer. These discarded cells are included in rxCellDiscard. 
      
      For basic Vpts, this attribute provides an aggregated total of all 
      rxUpcViolationOnEnforcer1 values for the Vccs associated with the 
      Vpt.
      
      The counter wraps to zero if it exceeds its maximum value of 
      (2**64)-1."
::= { mscAtmIfVptStatsEntry 90 }

mscAtmIfVptStatsRxUpcViolationOnEnforcer2 OBJECT-TYPE
   SYNTAX     PassportCounter64 
   ACCESS     read-only
   STATUS     mandatory
   DESCRIPTION
     "This attribute counts the number of UPC violations observed by the 
      Generic Cell Rate Algorithm (GCRA) Enforcer 2. This attribute is 
      only applicable if UPC is enforced or monitored. This attribute is 
      not applicable for standard Vpt Vccs. This attribute is not applicable 
      and is not displayed on CQC-based ATM cards.
      
      Enforcer2 is applicable only if the rxTrafficDescType for this 
      connection is 4, 5, 6, 7 or 8.
      
      When the value of rxTrafficDescType 4 or 5, Enforcer 2 enforces 
      conformance of traffic received from the interface to PCR CLP0.
      
      When the value of rxTrafficDescType 6, Enforcer 2 enforces 
      conformance of traffic received from the interface to SCR CLP0+1.
      
      When the value of rxTrafficDescType 7 or 8, Enforcer 2 enforces 
      conformance of traffic received from the interface to SCR CLP0.
      
      If UPC is enforced, enforcer 2 discards non-conforming cells for 
      rxTrafficDescType values of 4, 6 and 7. It tags non-conforming cells 
      for rxTrafficDescType values of 5 and 8. Discarded cells are 
      counted in the rxCellDiscard attribute. 
      
      For basic Vpts, this attribute provides an aggregated total of all 
      rxUpcViolationOnEnforcer2 values for the Vccs associated with 
      the Vpt.
      
      The counter wraps to zero if it exceeds its maximum value of 
      (2**64)-1."
::= { mscAtmIfVptStatsEntry 92 }

mscAtmIfVptStatsRxAal5FrameError OBJECT-TYPE
   SYNTAX     PassportCounter64 
   ACCESS     read-only
   STATUS     mandatory
   DESCRIPTION
     "This attribute counts the number of frames received from the 
      interface on this connection that have AAL5 length errors or AAL5 
      CRC errors. 
      
      This attribute is not applicable and is not displayed on CQC-based 
      ATM cards.
      
      AAL5 length or CRC errors typically occur because of cell discards 
      due to congestion, UPC, or due to corruption of data between the 
      AAL5 segmentation and reassembly end points.
      
      This attribute is applicable only to connections that reassemble 
      incoming cells into frames. Such connections have a 
      connectionPointType of connectionEndPoint. AAL1 connections 
      are an exception to this rule; although they have a 
      connectionPointType of connectionEndPoint, they do not do 
      adaptation at this point. For Vpts, this attribute provides an 
      aggregated total of all rxAal5FrameError values for all applicable 
      connections associated with the Vpt.
      
      For Vpcs and for Vccs that relay cells without adaptation, this 
      attribute is not applicable and is not displayed.
      
      The counter wraps to zero if it exceeds its maximum value of 
      (2**64)-1."
::= { mscAtmIfVptStatsEntry 100 }

mscAtmIfVptStatsRxAal5FrameAbort OBJECT-TYPE
   SYNTAX     PassportCounter64 
   ACCESS     read-only
   STATUS     mandatory
   DESCRIPTION
     "This attribute counts the number of frames received from the 
      interface on this connection that have the AAL5 length field set to 
      zero. 
      
      This attribute is not applicable and is not displayed for CQC-based 
      ATM cards.
      
      An AAL5 length of zero is an indication by the far end 
      segmentation point to this reassembly point that the frame is to be 
      discarded without reassembly. This mechanism is typically used by 
      a segmentation point if it detects an error in a frame after some of 
      the cells belonging to that frame have already been transmitted.
      
      This attribute is applicable only to connections that reassemble 
      incoming cells into frames. Such connections have a 
      connectionPointType of connectionEndPoint. AAL1 connections 
      are an exception to this rule; although they have a 
      connectionPointType of connectionEndPoint, they do not do 
      adaptation at this point. For Vpts, this attribute provides an 
      aggregated total of all rxAal5FrameAbort values for all applicable 
      connections associated with the Vpt.
      
      For Vpcs and for Vccs that relay cells without adaptation, this 
      attribute is not applicable and is not displayed.
      
      The counter wraps to zero if it exceeds its maximum value of 
      (2**64)-1."
::= { mscAtmIfVptStatsEntry 102 }

mscAtmIfVptTxTdpTable OBJECT-TYPE
   SYNTAX     SEQUENCE OF MscAtmIfVptTxTdpEntry
   ACCESS     not-accessible
   STATUS     obsolete
   DESCRIPTION
     "This attribute is HISTORICAL. Please refer to the attribute of the 
      same name in the group AtmTmOper.
      
      This attribute is a vector of five transmit traffic parameters. The first 
      three elements reflect the settings of the first three elements of the 
      txTrafficDescParm attribute in the AtmTrafficProv group. 
      
      When txTrafficDescType is 1 or 2, parameters 1 through 5 are 
      unused.
      
      In this description, PCR is the greater of either the PCR or the 
      requested shaping rate (parameter 1 or parameter 5) specified in the 
      Traffic group under the Vcd or Vpd.
      
      When txTrafficDescType is 3, parameter 1 represents the PCR for 
      CLP equal to 0 or 1 traffic; parameters 2 and 3 are unused.
      
      When txTrafficDescType is 4, parameter 1 represents the PCR for 
      CLP equal to 0 and 1 traffic; parameter 2 represents the PCR for 
      CLP equal to 0 traffic with cell discard.
      
      When txTrafficDescType is 5, parameter 1 represents the PCR for 
      CLP equal to 0 and 1 traffic; parameter 2 represents the PCR for 
      CLP equal to 0 traffic with cell tagging.
      
      When txTrafficDescType is 6, parameter 1 represents the PCR for 
      CLP equal to 0 and 1 traffic; parameter 2 represents the SCR for 
      CLP equal to 0 and 1 traffic; parameter 3 represents the MBS for 
      CLP equal to 0 and 1 traffic.
      
      When txTrafficDescType is 7, parameter 1 represents the PCR for 
      CLP equal to 0 and 1 traffic; parameter 2 represents the SCR for 
      CLP equal to 0 traffic with cell discard; parameter 3 represents the 
      MBS for CLP equal to 0 traffic.
      
      When txTrafficDescType is 8, parameter 1 represents the PCR for 
      CLP equal to 0 and 1 traffic; parameter 2 represents the SCR for 
      CLP equal to 0 traffic with cell tagging; parameter 3 represents the 
      MBS for CLP equal to 0 traffic
      
      When txTrafficDescType is 3, 4, 5, 6, 7 or 8, parameter 4 reflects 
      the actual shaping rate in cell/s for this connection. This rate is one 
      of the set of available shaping rates for this type of ATM-FP, based 
      on the number of interfaces doing shaping (attribute 
      perVcQueueInterfaces), the provisioned cell rate, the 
      shapingScalingFactor attribute of the AtmResourceControl 
      component, and whether traffic shaping is enabled. A rate of zero 
      (0) indicates that shaping is not performed. 
      
      When txTrafficDescType is 3, 4, 5, 6, 7 or 8, parameter 5 reflects 
      the equivalent cell rate in cell/s for this connection as determined by 
      the Connection Admission Control (CAC) algorithm. The 
      equivalent cell rate is useful in determining the admission 
      characteristics of this connection."
::= { mscAtmIfVpt 294 }

mscAtmIfVptTxTdpEntry OBJECT-TYPE
   SYNTAX     MscAtmIfVptTxTdpEntry
   ACCESS     not-accessible
   STATUS     obsolete
   DESCRIPTION
     "An entry in the mscAtmIfVptTxTdpTable."
   INDEX {
      mscAtmIfIndex,
      mscAtmIfVptIndex,
      mscAtmIfVptTxTdpIndex }
::= { mscAtmIfVptTxTdpTable 1 }

MscAtmIfVptTxTdpEntry ::= SEQUENCE {
   mscAtmIfVptTxTdpIndex
      Integer32,
   mscAtmIfVptTxTdpValue
      Unsigned32 }

mscAtmIfVptTxTdpIndex OBJECT-TYPE
   SYNTAX     Integer32 (1..5)
   ACCESS     not-accessible
   STATUS     obsolete
   DESCRIPTION
     "This variable represents the mscAtmIfVptTxTdpTable
      specific index for the mscAtmIfVptTxTdpTable."
::= { mscAtmIfVptTxTdpEntry 1 }

mscAtmIfVptTxTdpValue OBJECT-TYPE
   SYNTAX     Unsigned32 (0..2147483647)
   ACCESS     read-only
   STATUS     obsolete
   DESCRIPTION
     "This variable represents an individual value for the
      mscAtmIfVptTxTdpTable."
::= { mscAtmIfVptTxTdpEntry 2 }

mscAtmIfVptRxTdpTable OBJECT-TYPE
   SYNTAX     SEQUENCE OF MscAtmIfVptRxTdpEntry
   ACCESS     not-accessible
   STATUS     obsolete
   DESCRIPTION
     "This attribute is HISTORICAL. Please refer to the attribute of the 
      same name in the group AtmTmOper.
      
      This attribute is a vector of four traffic parameters whose meanings 
      are defined by the rxTrafficDescType attribute. The values of peak 
      cell rate (PCR), sustained cell rate (SCR) are expressed in cells/s. 
      Maximum burst size (MBS) is expressed in cells. Cell Delay 
      Variation Tolerance (CDVT) is expressed in microseconds.
      
      When rxTrafficDescType is 1 or 2, none of the parameters are used.
      
      When rxTrafficDescType is 3, parameter 1 represents the PCR for 
      CLP equal to 0 and 1 traffic; parameter 4 represents the CDVT.
      
      When rxTrafficDescType is 4, parameter 1 represents the PCR for 
      CLP equal to 0 and 1 traffic; parameter 2 represents the PCR for 
      CLP equal to 0 traffic with cell discard; parameter 4 represents the 
      CDVT.
      
      When rxTrafficDescType is 5, parameter 1 represents the PCR for 
      CLP equal to 0 and 1 traffic; parameter 2 represents the PCR for 
      CLP equal to 0 traffic with cell tagging; parameter 4 represents the 
      CDVT.
      
      When rxTrafficDescType is a 6, parameter 1 represents the PCR for 
      CLP equal to 0 and 1 traffic; parameter 2 represents the SCR for 
      CLP equal to 0 and 1 traffic; parameter 3 represents the MBS for 
      CLP equal to 0 and 1 traffic; parameter 4 represents the CDVT. 
      
      When rxTrafficDescType is 7, parameter 1 represents the PCR for 
      CLP equal to 0 and 1 traffic; parameter 2 represents the SCR for 
      CLP equal to 0 traffic with cell discard; parameter 3 represents the 
      MBS for CLP equal to 0 traffic; parameter 4 represents the CDVT.
      
      When rxTrafficDescType is 8, parameter 1 represents the PCR for 
      CLP equal to 0 and 1 traffic; parameter 2 represents the SCR for 
      CLP equal to 0 traffic with cell tagging; parameter 3 represents the 
      MBS for CLP equal to 0 traffic; parameter 4 represents the CDVT. 
      
      If Upc is disabled for this connection, the values of PCR, SCR, 
      MBS and CDVT is a combination of provisioned parameters. If Upc 
      is enabled, the values of PCR, SCR, MBS, and CDVT is exactly the 
      values used by the usage parameter control hardware in policing the 
      arriving traffic. These may vary slightly from the provisioned values 
      due to granularity of the hardware. In the case where the PCR is 
      equal to the SCR, the effective MBS is zero."
::= { mscAtmIfVpt 295 }

mscAtmIfVptRxTdpEntry OBJECT-TYPE
   SYNTAX     MscAtmIfVptRxTdpEntry
   ACCESS     not-accessible
   STATUS     obsolete
   DESCRIPTION
     "An entry in the mscAtmIfVptRxTdpTable."
   INDEX {
      mscAtmIfIndex,
      mscAtmIfVptIndex,
      mscAtmIfVptRxTdpIndex }
::= { mscAtmIfVptRxTdpTable 1 }

MscAtmIfVptRxTdpEntry ::= SEQUENCE {
   mscAtmIfVptRxTdpIndex
      Integer32,
   mscAtmIfVptRxTdpValue
      Unsigned32 }

mscAtmIfVptRxTdpIndex OBJECT-TYPE
   SYNTAX     Integer32 (1..4)
   ACCESS     not-accessible
   STATUS     obsolete
   DESCRIPTION
     "This variable represents the mscAtmIfVptRxTdpTable
      specific index for the mscAtmIfVptRxTdpTable."
::= { mscAtmIfVptRxTdpEntry 1 }

mscAtmIfVptRxTdpValue OBJECT-TYPE
   SYNTAX     Unsigned32 (0..2147483647)
   ACCESS     read-only
   STATUS     obsolete
   DESCRIPTION
     "This variable represents an individual value for the
      mscAtmIfVptRxTdpTable."
::= { mscAtmIfVptRxTdpEntry 2 }

mscAtmIfVptTxQThreshTable OBJECT-TYPE
   SYNTAX     SEQUENCE OF MscAtmIfVptTxQThreshEntry
   ACCESS     not-accessible
   STATUS     obsolete
   DESCRIPTION
     "This attribute is HISTORICAL. Please refer to the attribute of the 
      same name in the group AtmTmOper.
      
      This attribute indicates the queue limit and the discard thresholds 
      for the transmit queue of this connection. 
      
      The first element indicates the queue limit. Depending upon the 
      atmServiceCategory of the connection, the provisioned value of the 
      transmit queue limit is derived from the txQueueLimit attribute 
      under one of the subcomponents of the AtmIf CA component. If the 
      connection has traffic shaping disabled, then this attribute relates to 
      the common queue. If traffic shaping is enabled, then this attribute 
      relates to the per-VC queue.
      
      The second element is the threshold that marks the transition from 
      congestion state 1 to congestion state 0. This is the threshold at 
      which traffic with discard priority (DP) = 1 is discarded. This 
      threshold is set approximately at 90 percent of the first parameter, 
      the operational queue limit.
      
      The third element is the threshold that marks the transition from 
      congestion state 2 to congestion state 1. This is the threshold at 
      which traffic with DP = 2 is discarded. This threshold is set 
      approximately at 75 percent of the first parameter, the operational 
      queue limit.
      
      The fourth element is the threshold that marks the transition from 
      congestion state 3 to congestion state 2. This is the threshold at 
      which traffic with DP = 3 is discarded. This threshold is set 
      approximately at 35 percent of the first parameter, the operational 
      queue limit."
::= { mscAtmIfVpt 352 }

mscAtmIfVptTxQThreshEntry OBJECT-TYPE
   SYNTAX     MscAtmIfVptTxQThreshEntry
   ACCESS     not-accessible
   STATUS     obsolete
   DESCRIPTION
     "An entry in the mscAtmIfVptTxQThreshTable."
   INDEX {
      mscAtmIfIndex,
      mscAtmIfVptIndex,
      mscAtmIfVptTxQThreshIndex }
::= { mscAtmIfVptTxQThreshTable 1 }

MscAtmIfVptTxQThreshEntry ::= SEQUENCE {
   mscAtmIfVptTxQThreshIndex
      Integer32,
   mscAtmIfVptTxQThreshValue
      Unsigned32 }

mscAtmIfVptTxQThreshIndex OBJECT-TYPE
   SYNTAX     Integer32 (0..3)
   ACCESS     not-accessible
   STATUS     obsolete
   DESCRIPTION
     "This variable represents the mscAtmIfVptTxQThreshTable
      specific index for the mscAtmIfVptTxQThreshTable."
::= { mscAtmIfVptTxQThreshEntry 1 }

mscAtmIfVptTxQThreshValue OBJECT-TYPE
   SYNTAX     Unsigned32 (0..30720)
   ACCESS     read-only
   STATUS     obsolete
   DESCRIPTION
     "This variable represents an individual value for the
      mscAtmIfVptTxQThreshTable."
::= { mscAtmIfVptTxQThreshEntry 2 }

mscAtmIfVptFqpTable OBJECT-TYPE
   SYNTAX     SEQUENCE OF MscAtmIfVptFqpEntry
   ACCESS     not-accessible
   STATUS     obsolete
   DESCRIPTION
     "This attribute is HISTORICAL. Please refer to the attribute of the 
      same name in the group AtmTmOper.
      
      This attribute is a vector of three elements that indicate the quality 
      of service parameters for the forward direction for this connection. 
      This attribute is used for SPVC and SVC connections on a PNNI 
      interface.
      
      The cdv element indicates the acceptable peak-to-peak Cell Delay 
      Variation (CDV) of real-time connections (CBR, and rt-VBR). 
      
      The ctd element indicates the acceptable maximum Cell Transfer 
      Delay (maxCtd) of real-time connections (CBR, and rt-VBR). 
      
      The clr element indicates the acceptable Cell Loss Ratio (CLR) of 
      CBR, rt-VBR, and nrt-VBR connections."
::= { mscAtmIfVpt 357 }

mscAtmIfVptFqpEntry OBJECT-TYPE
   SYNTAX     MscAtmIfVptFqpEntry
   ACCESS     not-accessible
   STATUS     obsolete
   DESCRIPTION
     "An entry in the mscAtmIfVptFqpTable."
   INDEX {
      mscAtmIfIndex,
      mscAtmIfVptIndex,
      mscAtmIfVptFqpIndex }
::= { mscAtmIfVptFqpTable 1 }

MscAtmIfVptFqpEntry ::= SEQUENCE {
   mscAtmIfVptFqpIndex
      INTEGER,
   mscAtmIfVptFqpValue
      Unsigned32 }

mscAtmIfVptFqpIndex OBJECT-TYPE
   SYNTAX     INTEGER  {
                 cdv(0),
                 ctd(1),
                 clr(2) }
   ACCESS     not-accessible
   STATUS     obsolete
   DESCRIPTION
     "This variable represents the mscAtmIfVptFqpTable
      specific index for the mscAtmIfVptFqpTable."
::= { mscAtmIfVptFqpEntry 1 }

mscAtmIfVptFqpValue OBJECT-TYPE
   SYNTAX     Unsigned32 (0..2147483647)
   ACCESS     read-only
   STATUS     obsolete
   DESCRIPTION
     "This variable represents an individual value for the
      mscAtmIfVptFqpTable."
::= { mscAtmIfVptFqpEntry 2 }

mscAtmIfVptBqpTable OBJECT-TYPE
   SYNTAX     SEQUENCE OF MscAtmIfVptBqpEntry
   ACCESS     not-accessible
   STATUS     obsolete
   DESCRIPTION
     "This attribute is HISTORICAL. Please refer to the attribute of the 
      same name in the group AtmTmOper.
      
      This attribute is a vector of three elements that indicate the quality 
      of service parameters for the backward direction for this 
      connection. This attribute is used for SPVC and SVC connections 
      on a PNNI interface.
      
      The cdv element indicates the acceptable peak-to-peak Cell Delay 
      Variation (CDV) of real-time connections (CBR, and rt-VBR). 
      
      The ctd element indicates the acceptable maximum Cell Transfer 
      Delay (maxCtd) of real-time connections (CBR, and rt-VBR). 
      
      The clr element indicates the acceptable Cell Loss Ratio (CLR) of 
      CBR, rt-VBR, and nrt-VBR connections."
::= { mscAtmIfVpt 358 }

mscAtmIfVptBqpEntry OBJECT-TYPE
   SYNTAX     MscAtmIfVptBqpEntry
   ACCESS     not-accessible
   STATUS     obsolete
   DESCRIPTION
     "An entry in the mscAtmIfVptBqpTable."
   INDEX {
      mscAtmIfIndex,
      mscAtmIfVptIndex,
      mscAtmIfVptBqpIndex }
::= { mscAtmIfVptBqpTable 1 }

MscAtmIfVptBqpEntry ::= SEQUENCE {
   mscAtmIfVptBqpIndex
      INTEGER,
   mscAtmIfVptBqpValue
      Unsigned32 }

mscAtmIfVptBqpIndex OBJECT-TYPE
   SYNTAX     INTEGER  {
                 cdv(0),
                 ctd(1),
                 clr(2) }
   ACCESS     not-accessible
   STATUS     obsolete
   DESCRIPTION
     "This variable represents the mscAtmIfVptBqpTable
      specific index for the mscAtmIfVptBqpTable."
::= { mscAtmIfVptBqpEntry 1 }

mscAtmIfVptBqpValue OBJECT-TYPE
   SYNTAX     Unsigned32 (0..2147483647)
   ACCESS     read-only
   STATUS     obsolete
   DESCRIPTION
     "This variable represents an individual value for the
      mscAtmIfVptBqpTable."
::= { mscAtmIfVptBqpEntry 2 }


-- AtmIf/n Vpt/vpi Vpd
-- The VptVpd component contains provisioning information about its 
-- parent Vpt component.

mscAtmIfVptVpd OBJECT IDENTIFIER ::= { mscAtmIfVpt 2 }



mscAtmIfVptVpdRowStatusTable OBJECT-TYPE
   SYNTAX     SEQUENCE OF MscAtmIfVptVpdRowStatusEntry
   ACCESS     not-accessible
   STATUS     mandatory
   DESCRIPTION
     "This entry controls the addition and deletion of 
      mscAtmIfVptVpd components."
::= { mscAtmIfVptVpd 1 }

mscAtmIfVptVpdRowStatusEntry OBJECT-TYPE
   SYNTAX     MscAtmIfVptVpdRowStatusEntry
   ACCESS     not-accessible
   STATUS     mandatory
   DESCRIPTION
     "A single entry in the table represents a single 
      mscAtmIfVptVpd component."
   INDEX {
      mscAtmIfIndex,
      mscAtmIfVptIndex,
      mscAtmIfVptVpdIndex }
::= { mscAtmIfVptVpdRowStatusTable 1 }

MscAtmIfVptVpdRowStatusEntry ::= SEQUENCE {
   mscAtmIfVptVpdRowStatus
      RowStatus,
   mscAtmIfVptVpdComponentName
      DisplayString,
   mscAtmIfVptVpdStorageType
      StorageType,
   mscAtmIfVptVpdIndex
      NonReplicated }

mscAtmIfVptVpdRowStatus OBJECT-TYPE
   SYNTAX     RowStatus 
   ACCESS     read-only
   STATUS     mandatory
   DESCRIPTION
     "This variable is used as the basis for SNMP naming of
      mscAtmIfVptVpd components.
      These components cannot be added nor deleted."
::= { mscAtmIfVptVpdRowStatusEntry 1 }

mscAtmIfVptVpdComponentName OBJECT-TYPE
   SYNTAX     DisplayString 
   ACCESS     read-only
   STATUS     mandatory
   DESCRIPTION
     "This variable provides the component's string name for
      use with the ASCII Console Interface"
::= { mscAtmIfVptVpdRowStatusEntry 2 }

mscAtmIfVptVpdStorageType OBJECT-TYPE
   SYNTAX     StorageType 
   ACCESS     read-only
   STATUS     mandatory
   DESCRIPTION
     "This variable represents the storage type value for the
      mscAtmIfVptVpd tables."
::= { mscAtmIfVptVpdRowStatusEntry 4 }

mscAtmIfVptVpdIndex OBJECT-TYPE
   SYNTAX     NonReplicated 
   ACCESS     not-accessible
   STATUS     mandatory
   DESCRIPTION
     "This variable represents the index for the mscAtmIfVptVpd tables."
::= { mscAtmIfVptVpdRowStatusEntry 10 }

mscAtmIfVptVpdLbkTable OBJECT-TYPE
   SYNTAX     SEQUENCE OF MscAtmIfVptVpdLbkEntry
   ACCESS     not-accessible
   STATUS     mandatory
   DESCRIPTION
     "This group contains the provisionable loopback attributes for a Vcc, 
      Vpc, or Vpt component.
      
      Note that certain loopback requests may not be possible on a given 
      connection. In such cases, the corresponding operational loopback 
      attribute in the Status group of the Vcc, Vpc, or Vpt component is 
      set to notApplicable and the requested loopback is not performed.
      
      If loopbacks are provisioned to be on, and for any reason the 
      segment or end-to-end OAM loopback cells are not relayed, the 
      connection component becomes troubled, and user cell traffic may 
      be discarded. If loopbacks are provisioned to be on, all of the nodes 
      in the segment, and external networks which are in the end-to-end 
      connection must relay the OAM loopback cells."
::= { mscAtmIfVptVpd 100 }

mscAtmIfVptVpdLbkEntry OBJECT-TYPE
   SYNTAX     MscAtmIfVptVpdLbkEntry
   ACCESS     not-accessible
   STATUS     mandatory
   DESCRIPTION
     "An entry in the mscAtmIfVptVpdLbkTable."
   INDEX {
      mscAtmIfIndex,
      mscAtmIfVptIndex,
      mscAtmIfVptVpdIndex }
::= { mscAtmIfVptVpdLbkTable 1 }

MscAtmIfVptVpdLbkEntry ::= SEQUENCE {
   mscAtmIfVptVpdSegLinkSideLoopback
      INTEGER,
   mscAtmIfVptVpdSegSwitchSideLoopback
      INTEGER,
   mscAtmIfVptVpdEndToEndLoopback
      INTEGER,
   mscAtmIfVptVpdMCastConnectionType
      INTEGER }

mscAtmIfVptVpdSegLinkSideLoopback OBJECT-TYPE
   SYNTAX     INTEGER  {
                 on(0),
                 off(1),
                 sameAsInterface(2) }
   ACCESS     read-write
   STATUS     mandatory
   DESCRIPTION
     "This attribute specifies whether link-side segment loopback 
      insertion should be performed on this connection. 
      
      When sameAsInterface is selected, the link-side segment loopback 
      insertion for the connection is based on the segLinkSideLoopback 
      attribute of the connection's parent AtmIf componentif the ATM 
      interface has link-side segment loopback insertion turned on, then 
      link-side segment loopback insertion is also on for the connection. 
      
      When on or off is selected, link-side segment loopback insertion is 
      turned on or off respectively for the connection regardless of the 
      provisioning of the parent AtmIf component.
      
      Note that link-side segment loopback insertion is not possible if the 
      connectionPointType attribute of the Vcc or Vpc component is 
      connectingPoint. Link-side segment loopback insertion is also not 
      possible if the distributionType of the Vcc is pointToMultipoint. In 
      such cases, the associated segLinkSideLoopbackState attribute 
      indicates notApplicable and link-side segment loopback insertion is 
      not performed. Link-side segment loopback insertion is always 
      possible on a Vpt."
   DEFVAL     { sameAsInterface }
::= { mscAtmIfVptVpdLbkEntry 10 }

mscAtmIfVptVpdSegSwitchSideLoopback OBJECT-TYPE
   SYNTAX     INTEGER  {
                 on(0),
                 off(1),
                 sameAsInterface(2) }
   ACCESS     read-write
   STATUS     mandatory
   DESCRIPTION
     "This attribute specifies whether switch-side segment loopback 
      insertion should be performed on this connection.
      
      When sameAsInterface is selected, the switch-side segment 
      loopback for the connection is based on the segSwitchSideLoopback 
      attribute of the connection's parent AtmIf componentif the ATM 
      interface has switch-side segment loopback insertion turned on, 
      then switch-side segment loopback insertion is also on for the 
      connection. 
      
      When on or off is selected, switch-side segment loopback insertion 
      is turned on or off respectively for the connection regardless of the 
      provisioning of the parent AtmIf component.
      
      Note that switch-side segment loopback insertion is not possible if 
      the connectionPointType attribute of the Vcc or Vpc component is 
      connectingPoint or connectionEndPoint. Switch-side segment 
      loopback insertion is also not possible if the distributionType of the 
      Vcc is pointToMultipoint In such cases, the associated 
      segSwitchSideLoopbackState attribute indicates notApplicable and 
      switch-side segment loopback insertion is not performed. Switch-
      side segment loopback is never possible on a Vpt."
   DEFVAL     { sameAsInterface }
::= { mscAtmIfVptVpdLbkEntry 20 }

mscAtmIfVptVpdEndToEndLoopback OBJECT-TYPE
   SYNTAX     INTEGER  {
                 on(0),
                 off(1),
                 sameAsInterface(2) }
   ACCESS     read-write
   STATUS     mandatory
   DESCRIPTION
     "This attribute specifies whether end-to-end loopback insertion 
      should be performed on this connection.
      
      When sameAsInterface is selected, the end-to-end loopback for the 
      connection is based on the endToEndLoopback attribute of the 
      connection's parent AtmIf componentif the ATM interface has 
      end-to-end loopback insertion turned on, then end-to-end loopback 
      insertion is also on for the connection. 
      
      When on or off is selected, end-to-end loopback insertion is turned 
      on or off respectively for the connection regardless of the 
      provisioning of the parent AtmIf component.
      
      Note that end-to-end loopback insertion is not possible if the 
      connectionPointType attribute of the Vcc or Vpc component is 
      connectingPoint or segmentEndPoint. End-to-end loopback 
      insertion is also not possible if the distributionType of the Vcc is 
      pointToMultipoint. In such cases, the associated 
      endToEndLoopbackState attribute indicates notApplicable and end-
      to-end loopback insertion is not performed. End-to-end loopback 
      insertion is always possible on a Vpt."
   DEFVAL     { sameAsInterface }
::= { mscAtmIfVptVpdLbkEntry 30 }

mscAtmIfVptVpdMCastConnectionType OBJECT-TYPE
   SYNTAX     INTEGER  {
                 pointToPoint(0),
                 pointToMultipointRoot(1),
                 pointToMultipointLeaf(2) }
   ACCESS     read-write
   STATUS     mandatory
   DESCRIPTION
     "This attribute is introduced to exist temporarily to pass to AtmIf the 
      connection type defined under Vcc or Vpc. This attribute will be 
      obsoleted once a more elegant solution is available."
   DEFVAL     { pointToPoint }
::= { mscAtmIfVptVpdLbkEntry 50 }

mscAtmIfVptVpdTrafficTable OBJECT-TYPE
   SYNTAX     SEQUENCE OF MscAtmIfVptVpdTrafficEntry
   ACCESS     not-accessible
   STATUS     mandatory
   DESCRIPTION
     "This group contains traffic related provisionable attributes for the 
      Vcc and Vpc components. The attributes' operational values are 
      reflected in the Traffic group for these components. Changing any 
      of the attributes in this group causes a service interruption on the 
      Vcc or Vpc component."
::= { mscAtmIfVptVpd 110 }

mscAtmIfVptVpdTrafficEntry OBJECT-TYPE
   SYNTAX     MscAtmIfVptVpdTrafficEntry
   ACCESS     not-accessible
   STATUS     mandatory
   DESCRIPTION
     "An entry in the mscAtmIfVptVpdTrafficTable."
   INDEX {
      mscAtmIfIndex,
      mscAtmIfVptIndex,
      mscAtmIfVptVpdIndex }
::= { mscAtmIfVptVpdTrafficTable 1 }

MscAtmIfVptVpdTrafficEntry ::= SEQUENCE {
   mscAtmIfVptVpdTxTrafficDescType
      INTEGER,
   mscAtmIfVptVpdTxQosClass
      INTEGER,
   mscAtmIfVptVpdFwdQosClass
      INTEGER,
   mscAtmIfVptVpdHoldingPriority
      INTEGER,
   mscAtmIfVptVpdRxTrafficDescType
      INTEGER,
   mscAtmIfVptVpdRxQosClass
      INTEGER,
   mscAtmIfVptVpdBwdQosClass
      INTEGER,
   mscAtmIfVptVpdAtmServiceCategory
      INTEGER,
   mscAtmIfVptVpdTrafficShaping
      INTEGER,
   mscAtmIfVptVpdUnshapedTransmitQueueing
      INTEGER,
   mscAtmIfVptVpdUsageParameterControl
      INTEGER,
   mscAtmIfVptVpdBearerClassBbc
      INTEGER,
   mscAtmIfVptVpdTransferCapabilityBbc
      INTEGER,
   mscAtmIfVptVpdClippingBbc
      INTEGER,
   mscAtmIfVptVpdBestEffort
      INTEGER,
   mscAtmIfVptVpdFwdFrameDiscard
      INTEGER,
   mscAtmIfVptVpdBwdFrameDiscard
      INTEGER }

mscAtmIfVptVpdTxTrafficDescType OBJECT-TYPE
   SYNTAX     INTEGER  {
                 n1(1),
                 n2(2),
                 n3(3),
                 n4(4),
                 n5(5),
                 n6(6),
                 n7(7),
                 n8(8),
                 n9(9) }
   ACCESS     read-write
   STATUS     obsolete
   DESCRIPTION
     "This attribute is migrated to the AtmTmProv group.
      
      This attribute specifies the type of traffic management which is 
      applied to the transmit direction of this connection as defined in the 
      ATM Forum. The txTrafficDescType determines the number and 
      meaning of the parameters in the txTrafficDescParm attribute."
   DEFVAL     { n1 }
::= { mscAtmIfVptVpdTrafficEntry 10 }

mscAtmIfVptVpdTxQosClass OBJECT-TYPE
   SYNTAX     INTEGER  {
                 unspecified(0),
                 constantBitRate(1),
                 variableBitRate(2),
                 connectionOriented(3),
                 connectionless(4) }
   ACCESS     read-write
   STATUS     obsolete
   DESCRIPTION
     "This attribute specifies the quality of service for the transmit 
      direction for this connection.
      
      The constantBitRate class refers to traffic offered on services such 
      as a constant bit rate video service. This traffic is highest priority.
      
      The variableBitRate class refers to traffic offered on services such 
      as packetized audio and video.
      
      The connectionOriented class refers to connection-oriented traffic 
      such as Frame Relay or X.25 traffic. 
      
      The connectionless traffic refers to traffic offered through 
      connectionless trunks such as certain LAN protocols.
      
      The unspecified class supports a 'best effort' type of service, where 
      there is a minimum guarantee of bandwidth. This traffic is lowest 
      priority.
      
      This attribute is obsolete. The value is migrated into 
      atmServiceCategory. The atmServiceCategory applies in both 
      transmit and receive directions.
      
      unspecified maps to unspecifiedBitRate;
      constantBitRate maps to constantBitRate;
      variableBitRate maps to variableBitRateRt;
      connectionOriented maps to variableBitRateNrt
      connectionless maps to variableBitRateNrt"
   DEFVAL     { connectionOriented }
::= { mscAtmIfVptVpdTrafficEntry 20 }

mscAtmIfVptVpdFwdQosClass OBJECT-TYPE
   SYNTAX     INTEGER  {
                 n0(0),
                 n1(1),
                 n2(2),
                 n3(3),
                 n4(4) }
   ACCESS     read-write
   STATUS     obsolete
   DESCRIPTION
     "This attribute is migrated to the AtmTmProv group.
      
      This attribute specifies the quality of service for the forward 
      direction for this connection. This attribute is only used for SPVC 
      connections.
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified bit rate QOS class; no objective is 
      specified for the performance parameters."
   DEFVAL     { n0 }
::= { mscAtmIfVptVpdTrafficEntry 21 }

mscAtmIfVptVpdHoldingPriority OBJECT-TYPE
   SYNTAX     INTEGER  {
                 n0(0),
                 n1(1),
                 n2(2),
                 n3(3),
                 n4(4) }
   ACCESS     read-write
   STATUS     obsolete
   DESCRIPTION
     "This attribute is migrated to the AtmTmProv group.
      
      This attribute specifies the holding priority of this connection. In a 
      situation where the link bandwidth fluctuates, such as over an IMA 
      link, holding priority is used to determine which connections are 
      held and which are released. Holding priority 4 connections are the 
      first to be released. Holding priority 0 connections are the last to be 
      released. This value provisioned in the Vcd or Vpd may be 
      overridden by certain applications, for example Vcc Test, which run 
      over this connection. The default holding priority for a provisioned 
      connection is higher then default holding priorities for dynamic 
      (SVC) connections."
   DEFVAL     { n2 }
::= { mscAtmIfVptVpdTrafficEntry 25 }

mscAtmIfVptVpdRxTrafficDescType OBJECT-TYPE
   SYNTAX     INTEGER  {
                 n1(1),
                 n2(2),
                 n3(3),
                 n4(4),
                 n5(5),
                 n6(6),
                 n7(7),
                 n8(8),
                 sameAsTx(15) }
   ACCESS     read-write
   STATUS     obsolete
   DESCRIPTION
     "This attribute is migrated to the AtmTmProv group.
      
      This attribute specifies the type of traffic management which is 
      applied to the receive direction of this connection as defined in the 
      ATM Forum. The rxTrafficDescType determines the number and 
      meaning of the parameters in the rxTrafficDescParm attribute
      
      When sameAsTx is selected, the rxTrafficDescType as well as the 
      rxTrafficDescParm are taken from the transmit values."
   DEFVAL     { sameAsTx }
::= { mscAtmIfVptVpdTrafficEntry 30 }

mscAtmIfVptVpdRxQosClass OBJECT-TYPE
   SYNTAX     INTEGER  {
                 unspecified(0),
                 constantBitRate(1),
                 variableBitRate(2),
                 connectionOriented(3),
                 connectionless(4),
                 sameAsTx(15) }
   ACCESS     read-write
   STATUS     obsolete
   DESCRIPTION
     "This attribute specifies the quality of service for the receive 
      direction for this connection.
      
      The constantBitRate class refers to traffic offered on services such 
      as a constant bit rate video service. 
      
      The variableBitRate class refers to traffic offered on services such 
      as packetized audio and video. 
      
      The connectionOriented class refers to connection-oriented traffic.
      
      The connectionless traffic refers to traffic offered through 
      connectionless trunks. 
      
      The unspecified class supports a 'best effort' type of service, where 
      there is a minimum guarantee of bandwidth. 
      
      The sameAsTx selection sets the receive quality of service to be the 
      same as the transmit quality of service.
      
      This attribute is obsolete. The value of txQosClass is migrated into 
      atmServiceCategory. The value of this attribute is ignored. 
      AtmServiceCategory applies in both transmit and receive directions."
   DEFVAL     { sameAsTx }
::= { mscAtmIfVptVpdTrafficEntry 40 }

mscAtmIfVptVpdBwdQosClass OBJECT-TYPE
   SYNTAX     INTEGER  {
                 n0(0),
                 n1(1),
                 n2(2),
                 n3(3),
                 n4(4),
                 sameAsFwd(15) }
   ACCESS     read-write
   STATUS     obsolete
   DESCRIPTION
     "This attribute is migrated to the AtmTmProv group.
      
      This attribute specifies the quality of service for the backward 
      direction for this connection. This attribute is only used for SPVC 
      connections.
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified bit rate QOS class; no objective is 
      specified for the performance parameters.
      
      The sameAsFwd selection sets the backward quality of service to 
      be the same as the forward quality of service."
   DEFVAL     { sameAsFwd }
::= { mscAtmIfVptVpdTrafficEntry 41 }

mscAtmIfVptVpdAtmServiceCategory OBJECT-TYPE
   SYNTAX     INTEGER  {
                 unspecifiedBitRate(0),
                 constantBitRate(1),
                 rtVariableBitRate(2),
                 nrtVariableBitRate(3),
                 derivedFromBBC(15) }
   ACCESS     read-write
   STATUS     obsolete
   DESCRIPTION
     "This attribute is migrated to the AtmTmProv group.
      
      This attribute specifies the ATM service category for both directions 
      of the connection. 
      
      The value derivedFromBBC may only be used if the SrcPvc 
      component is provisioned under this Vcc.Otherwise a specific ATM 
      service category must be specified. 
      
      If this attribute is set to derivedFromBBC, the Broadband Bearer 
      Capability (BBC) and bestEffort attributes are used to determine the 
      atmServiceCategory of this connection. 
      
      If this attribute is set to other than derivedFromBBC, the value of 
      this attribute is used to override the provisioned BBC Information 
      Element parameters. In those cases, the BBC attributes are not used. 
      
      The constantBitRate service category is intended for real time 
      applications, that is those requiring tightly constrained delay and 
      delay variation, as would be appropriate for voice and video 
      applications. The consistent availability of a fixed quantity of 
      bandwidth is considered appropriate for CBR service. Cells which 
      are delayed beyond the value specified by Cell Transfer Delay are 
      assumed to be of significantly reduce value to the application.
      
      The rtVariableBitRate service category is intended for real time 
      applications, that is those requiring tightly constrained delay and 
      delay variation, as would be appropriate for voice and video 
      applications. Sources are expected to transmit at a rate which varies 
      with time. Equivalently, the source can be described as 'bursty'. 
      Cells which are delayed beyond the value specified by CTD are 
      assumed to be of significantly reduced value to the application. Real 
      time VBR service may support statistical multiplexing of real time 
      sources.
      
      The nrtVariableBitRate service category is intended for non-real 
      time applications which have bursty traffic characteristics and which 
      can be characterized in terms of a PCR, SCR, and MBS. For those 
      cells which are transferred within the traffic contract, the application 
      expects a low cell loss ratio. For all connections, it expects a bound 
      on the mean cell transfer delay. Non-real time VBR service may 
      support statistical multiplexing of connections.
      
      The unspecifiedBitRate service is intended for non-real time 
      applications; that is, those not requiring tightly constrained delay 
      and delay variation. UBR sources are expected to be bursty. UBR 
      service supports a high degree of statistical multiplexing among 
      sources. UBR service does not specify traffic related service 
      guarantees. No numerical commitments are made with respect to 
      the cell loss ratio experienced by a UBR connection, or as to the 
      cell transfer delay experienced by cells on the connection."
   DEFVAL     { unspecifiedBitRate }
::= { mscAtmIfVptVpdTrafficEntry 42 }

mscAtmIfVptVpdTrafficShaping OBJECT-TYPE
   SYNTAX     INTEGER  {
                 disabled(1),
                 sameAsInterface(2) }
   ACCESS     read-write
   STATUS     obsolete
   DESCRIPTION
     "This attribute is migrated to the AtmTmProv group.
      
      This attribute specifies whether this connection uses traffic shaping 
      when transmitting traffic to the ATM interface.
      
      When sameAsInterface is selected, traffic shaping for the 
      connection is based on the trafficShaping attribute of the 
      connection's parent AtmIf componentif the ATM interface has 
      traffic shaping enabled, then traffic shaping is enabled for the 
      connection. Note that enabling traffic shaping may have no effect 
      under certain cases. These cases are listed in the description of the 
      trafficShaping operational attribute, which is under the Vcc and Vpc 
      components.
      
      When disabled is selected, traffic shaping for this connection is 
      disabled regardless of the provisioning of the parent AtmIf 
      component."
   DEFVAL     { sameAsInterface }
::= { mscAtmIfVptVpdTrafficEntry 50 }

mscAtmIfVptVpdUnshapedTransmitQueueing OBJECT-TYPE
   SYNTAX     INTEGER  {
                 common(1),
                 sameAsInterface(3) }
   ACCESS     read-write
   STATUS     obsolete
   DESCRIPTION
     "This attribute is migrated to the AtmTmProv group.
      
      This attribute only applies when this connection is unshaped. This 
      attribute defines the transmit queueing method for this connection if 
      it is unshaped. Refer to the unshapedTransmitQueueing attribute 
      under the AtmIf for more details on the meaning of this attribute. 
      
      When this attribute is set to sameAsInterface, the value from the 
      AtmIf is used. 
      
      When this attribute is set to common, transmit traffic on this 
      unshaped connection is destined for the common queue."
   DEFVAL     { sameAsInterface }
::= { mscAtmIfVptVpdTrafficEntry 60 }

mscAtmIfVptVpdUsageParameterControl OBJECT-TYPE
   SYNTAX     INTEGER  {
                 disabled(1),
                 sameAsInterface(2) }
   ACCESS     read-write
   STATUS     obsolete
   DESCRIPTION
     "This attribute is migrated to the AtmTmProv group.
      
      This attribute specifies whether this connection enforces usage 
      parameter control when receiving traffic from the ATM interface.
      
      When sameAsInterface is selected, UPC for the connection is 
      based on the usageParameterControl attribute of the connection's 
      parent AtmIf componentif the ATM interface has UPC enabled, 
      then UPC is enabled for the connection. Note that enabling UPC 
      may have no effect under certain cases. These cases are listed in the 
      description of the usageParameterControl operational attribute, 
      which is under the Vcc and Vpc components.
      
      When disabled is selected, UPC for this connection is disabled 
      regardless of the provisioning of the parent AtmIf component."
   DEFVAL     { sameAsInterface }
::= { mscAtmIfVptVpdTrafficEntry 70 }

mscAtmIfVptVpdBearerClassBbc OBJECT-TYPE
   SYNTAX     INTEGER  {
                 a(1),
                 c(3),
                 x(16),
                 vp(24),
                 derivedFromServiceCategory(31) }
   ACCESS     read-write
   STATUS     obsolete
   DESCRIPTION
     "This attribute is migrated to the AtmTmProv group.
      
      This attribute specifies the bearer capability. This attribute is only 
      used for SPVC and SPVP connections. It is one of the Broadband 
      Bearer Capability (BBC) attributes. The purpose of the BBC 
      information element is to indicate a requested broadband 
      connection-oriented bearer service to be provided by the network.
      
      The value derivedFromServiceCategory specifies that the actual 
      value which is used for this connection is derived from the value of 
      the atmServiceCategory. Either, this attribute must be set to 
      derivedFromServiceCategory, or the atmServiceCategory attribute 
      must be set to derivedFromBBC, but not both.
      
      Class a service is a connection-oriented, constant bit rate ATM 
      transport service. Class a service has end to end timing 
      requirements and may require stringent cell loss, cell delay and cell 
      delay variation performance.When a is set, the user is requesting 
      more than an ATM only service. The network may look at the AAL 
      to provide interworking based upon its contents. 
      
      Class c service is a connection-oriented, variable bit rate ATM 
      transport service. Class c service has no end-to-end timing 
      requirements. When c is set, the user is requesting more than an 
      ATM only service. The network interworking function may look at 
      the AAL and provide service based on it.
      
      Class x service is a connection-oriented ATM transport service 
      where the AAL, trafficType (vbr or cbr) and timing requirements 
      are user defined (that is, transparent to the network).When x is set 
      the user is requesting an ATM only service from the network.
      
      Class vp service is used to specify a transparent VP service. When 
      the value of this attribute is vp, the user is requesting an ATM only 
      service from the network. In this case, the network shall not process 
      any higher layer protocol. This service differs from class x service 
      in that with the class vp service both the VCI field (except or VCI 
      values 0, 3, 4, and 6 through 15) and Payload Type field are 
      transported transparently by the network. This attribute value is 
      only applicable to SPVP connections."
   DEFVAL     { derivedFromServiceCategory }
::= { mscAtmIfVptVpdTrafficEntry 71 }

mscAtmIfVptVpdTransferCapabilityBbc OBJECT-TYPE
   SYNTAX     INTEGER  {
                 n0(0),
                 n1(1),
                 n2(2),
                 n5(5),
                 n8(8),
                 n9(9),
                 n10(10),
                 notApplicable(30),
                 derivedFromServiceCategory(31) }
   ACCESS     read-write
   STATUS     obsolete
   DESCRIPTION
     "This attribute is migrated to the AtmTmProv group.
      
      This attribute specifies the transfer capability for this connection. 
      Uni 3.0/3.1 traffic type and end-to-end timing parameters are 
      mapped into this parameter as follows:
      <transferCapability: TrafficType, Timing>
      0: NoIndication, NoIndication
      1: NoIndication, yes
      2: NoIndication, no
      5: CBR, yes
      8: VBR, NoIndication
      9: VBR, yes
      10: VBR, no
      
      NotApplicable specifies that the user does not want to specify the 
      transfer capability.
      
      The CBR traffic type refers to traffic offered on services such as a 
      constant bit rate video service or a circuit emulation.
      
      The VBR traffic type refers to traffic offered on services such as 
      packetized audio and video, or data.
      
      The value no indication for traffic type is used if the user has not set 
      the traffic type; similarly for end-to-end timing.
      
      The value yes for end-to-end timing indicates that end-to-end 
      timing is required.
      
      The value no for end-to-end timing indicates that end-to-end timing 
      is not required.
      
      The value derivedFromServiceCategory specifies that the actual 
      value which is used for this connection is derived from the value of 
      the atmServiceCategory. Either, this attribute must be set to 
      derivedFromServiceCategory, or the atmServiceCategory attribute 
      must be set to derivedFromBBC, but not both."
   DEFVAL     { derivedFromServiceCategory }
::= { mscAtmIfVptVpdTrafficEntry 72 }

mscAtmIfVptVpdClippingBbc OBJECT-TYPE
   SYNTAX     INTEGER  {
                 no(0),
                 yes(1) }
   ACCESS     read-write
   STATUS     obsolete
   DESCRIPTION
     "This attribute is migrated to the AtmTmProv group.
      
      This attribute specifies the value for the clipping susceptibility 
      parameter in the BBC Information Element. This attribute is only 
      used for SPVC connections. It is one of the Broadband Bearer 
      Capability attributes.
      
      Clipping is an impairment in which the first fraction of a second of 
      information to be transferred is lost. It occurs after a call is 
      answered and before an associated connection is switched through."
   DEFVAL     { no }
::= { mscAtmIfVptVpdTrafficEntry 74 }

mscAtmIfVptVpdBestEffort OBJECT-TYPE
   SYNTAX     INTEGER  {
                 indicated(0),
                 notIndicated(1),
                 derivedFromServiceCategory(15) }
   ACCESS     read-write
   STATUS     obsolete
   DESCRIPTION
     "This attribute is migrated to the AtmTmProv group.
      
      This attribute specifies the value of the best effort parameter in the 
      ATM Traffic Descriptor Information Element. This attribute is only 
      used for Soft PVC connections. It is one of the Broadband Bearer 
      Capability attributes.
      
      The value indicated implies that the quality of service for this 
      connection is not guaranteed.
      
      The value notIndicated implies that the quality of service for this 
      connection is guaranteed.
      
      The value derivedFromServiceCategory specifies that the actual 
      value which is used for this connection is derived from the value of 
      the atmServiceCategory. Either, this attribute must be set to 
      derivedFromServiceCategory, or the atmServiceCategory attribute 
      must be set to derivedFromBBC, but not both."
   DEFVAL     { derivedFromServiceCategory }
::= { mscAtmIfVptVpdTrafficEntry 75 }

mscAtmIfVptVpdFwdFrameDiscard OBJECT-TYPE
   SYNTAX     INTEGER  {
                 notIndicated(0),
                 indicated(1) }
   ACCESS     read-write
   STATUS     obsolete
   DESCRIPTION
     "This attribute specifies the activation of frame discard functionality 
      in the forward data direction, at relay points, for this connection. It 
      applies to each hop of the connection. Frame discard functions 
      should not be requested if this connection is not transferring frame 
      (AAL5) traffic. Setting the value to indicated for any other traffic 
      type results in all traffic being discarded.
      
      If this connection point is a permanent (provisioned) VCC mid-
      point, this attribute specifies whether the Partial Packet 
      Discard (PPD) function is to be enabled or disabled in the transmit 
      direction at this connecting point. The PPD function allows the 
      connecting point to discard the remainder of a cell-forwarded AAL5 
      frame if one cell of this frame has been discarded. The PPD 
      function increases the 'goodput' of the link, since cells which are 
      only going to be discarded by the AAL5 reassembly are not 
      transmitted.
      
      At a permanent VCC connecting point which is not a connection 
      endpoint, when this attribute is set to indicated, the PPD function is 
      applied to transmit traffic at this connecting point. It should not be 
      indicated for connections whose end points are not performing 
      AAL5 segmentation and reassembly. When this attribute is set to 
      notIndicated, the PPD feature is not applied to transmit traffic at 
      this connecting point.
      
      At a SPVC origin on a PNNI interface, a value of indicated 
      specifies that frame discard is requested in the forward direction. 
      The frame discard function for SPVCs consists of PPD at the SPVC 
      origin and at all intermediate connecting points. When this attribute 
      is set to notIndicated, forward frame discard is not requested in the 
      SPVC call setup. Thus PPD is not enabled at the SPVC origin nor at 
      any intermediate connecting point.
      
      At all points along a VPC, this setting is ignored.
      
      At a permanent VCC connection endpoint, this value is ignored. If 
      AAL5 segmentation and reassembly has been requested, PPD and 
      Early Packet Discard (EPD) are automatically enabled.
      
      This attribute has been migrated to txFrameDiscard."
   DEFVAL     { notIndicated }
::= { mscAtmIfVptVpdTrafficEntry 76 }

mscAtmIfVptVpdBwdFrameDiscard OBJECT-TYPE
   SYNTAX     INTEGER  {
                 notIndicated(0),
                 indicated(1) }
   ACCESS     read-write
   STATUS     obsolete
   DESCRIPTION
     "This attribute specifies the activation of frame discard functionality 
      in the backward data direction, at relay points, for this connection. 
      It applies to each hop of the connection. Frame discard functions 
      should not be requested if this connection is not transferring frame 
      (AAL5) traffic. Setting the value to indicated for any other traffic 
      type results in all traffic being discarded.
      
      If this connection point is a permanent (provisioned) VCC mid-
      point, this attribute specifies whether the Partial Packet Discard 
      (PPD) function is to be enabled or disabled in the receive direction 
      at this connecting point. The PPD function allows the connecting 
      point to discard the remainder of a cell-forwarded AAL5 frame if 
      one cell of this frame has been discarded. The PPD function 
      increases the 'goodput' of the link, since cells which are only going 
      to be discarded by the AAL5 reassembly are not received.
      
      At a permanent VCC connecting point which is not a connection 
      endpoint, when this attribute is set to indicated, the PPD function is 
      applied to receive traffic at this connecting point. It should not be 
      indicated for connections whose end points are not performing 
      AAL5 segmentation and reassembly. When this attribute is set to 
      notIndicated, the PPD feature is not applied to receive traffic at this 
      connecting point.
      
      At a SPVC origin on a PNNI interface, a value of indicated 
      specifies that frame discard is requested in the backward direction. 
      The frame discard function for SPVCs consists of PPD at the SPVC 
      origin and at all intermediate connecting points. When this attribute 
      is set to notIndicated, backwards frame discard is not requested in 
      the SPVC call setup. Thus PPD is not enabled at the SPVC origin 
      nor at any intermediate connecting point.
      
      At all points along a VPC, this setting is ignored.
      
      At a permanent VCC connection endpoint, this value is ignored. If 
      AAL5 segmentation and reassembly has been requested, PPD and 
      Early Packet Discard (EPD) are automatically enabled.
      
      This attribute has been migrated to rxFrameDiscard."
   DEFVAL     { notIndicated }
::= { mscAtmIfVptVpdTrafficEntry 77 }

mscAtmIfVptVpdAcctTable OBJECT-TYPE
   SYNTAX     SEQUENCE OF MscAtmIfVptVpdAcctEntry
   ACCESS     not-accessible
   STATUS     mandatory
   DESCRIPTION
     "This group contains the provisionable ATM accounting attributes 
      for a Vcc, Vpc, or Vpt component."
::= { mscAtmIfVptVpd 111 }

mscAtmIfVptVpdAcctEntry OBJECT-TYPE
   SYNTAX     MscAtmIfVptVpdAcctEntry
   ACCESS     not-accessible
   STATUS     mandatory
   DESCRIPTION
     "An entry in the mscAtmIfVptVpdAcctTable."
   INDEX {
      mscAtmIfIndex,
      mscAtmIfVptIndex,
      mscAtmIfVptVpdIndex }
::= { mscAtmIfVptVpdAcctTable 1 }

MscAtmIfVptVpdAcctEntry ::= SEQUENCE {
   mscAtmIfVptVpdCorrelationTag
      AsciiString }

mscAtmIfVptVpdCorrelationTag OBJECT-TYPE
   SYNTAX     AsciiString (SIZE (0..32))
   ACCESS     read-write
   STATUS     mandatory
   DESCRIPTION
     "This attribute specifies a unique indentifier for each end of a PVC. It 
      that may be used by downstream processing systems to correlate 
      accounting records issued at different nodes in the network. The 
      attribute can be up to 32 bytes long. If it is less than 32 bytes, it is 
      zero filled on the right to create a 32 byte value. The resulting value 
      is recorded in the attribute callConnId for this PVC's ATM 
      accounting records.
      If the attribute is a null string then this PVC does not have any 
      accounting records generated for it."
   DEFVAL     { ''H }  -- ""
::= { mscAtmIfVptVpdAcctEntry 10 }

mscAtmIfVptVpdProvTable OBJECT-TYPE
   SYNTAX     SEQUENCE OF MscAtmIfVptVpdProvEntry
   ACCESS     not-accessible
   STATUS     mandatory
   DESCRIPTION
     "This group contains the provisionable ATM Virtual Path Descriptor 
      attributes for a Vpt component."
::= { mscAtmIfVptVpd 112 }

mscAtmIfVptVpdProvEntry OBJECT-TYPE
   SYNTAX     MscAtmIfVptVpdProvEntry
   ACCESS     not-accessible
   STATUS     mandatory
   DESCRIPTION
     "An entry in the mscAtmIfVptVpdProvTable."
   INDEX {
      mscAtmIfIndex,
      mscAtmIfVptIndex,
      mscAtmIfVptVpdIndex }
::= { mscAtmIfVptVpdProvTable 1 }

MscAtmIfVptVpdProvEntry ::= SEQUENCE {
   mscAtmIfVptVpdVptType
      INTEGER }

mscAtmIfVptVpdVptType OBJECT-TYPE
   SYNTAX     INTEGER  {
                 basic(0),
                 standard(1) }
   ACCESS     read-write
   STATUS     mandatory
   DESCRIPTION
     "This attribute specifies the type of the Vpt.
      
      On CQC-based ATM FPs all Vpts must be basic. Vpts on ATM IP 
      FPs may be of any type.
      
      A value of basic configures one level of traffic management (TM) 
      for the VPT, at the VC level. VCs within the VP are treated like 
      independent VCC connections, and thus, are scheduled the same as 
      other VCs under the AtmIf, with no scheduling done for the VP 
      itself.
      
      A value of standard configures two levels of TM for the VPT, one 
      level for VP TM and one level for VC level TM. VCs within the VP 
      use weighted fair queueing (standard VPT VCC scheduling) to 
      schedule VCs within the VPT, with VCs differentiated as either 
      real-time (CBR, rt-VBR) or non-real-time (nrt-VBR, UBR) 
      connections. The VP itself has a full range of emission scheduling 
      and service category differentiation available between itself and the 
      other connections under the AtmIf."
   DEFVAL     { basic }
::= { mscAtmIfVptVpdProvEntry 10 }

mscAtmIfVptVpdTxTdpTable OBJECT-TYPE
   SYNTAX     SEQUENCE OF MscAtmIfVptVpdTxTdpEntry
   ACCESS     not-accessible
   STATUS     obsolete
   DESCRIPTION
     "This attribute is migrated to the AtmTmProv group.
      
      This attribute is a vector of five traffic parameters whose meanings 
      are defined by the txTrafficDescType attribute. The values of peak 
      cell rate (PCR), sustained cell rate (SCR) and requested shaping rate 
      are expressed in cell/s. Maximum burst size (MBS) is expressed in 
      cells. CDVT is expressed in microseconds. The values of PCR, 
      SCR, MBS and CDVT are used for connection admission control 
      (CAC). The value of CDVT is only used for connections where the 
      atmServiceCategory is constantBitRate. For all other values of 
      atmServiceCategory, CDVT is ignored. The values of PCR, SCR 
      and requested shaping rate are used to determine the actual shaping 
      rate where traffic shaping is enabled.
      
      When txTrafficDescType is 1 or 2, all of the parameters must be set 
      to zero.
      
      When txTrafficDescType is 3, parameter 1 represents the PCR for 
      CLP equal to 0 and 1 traffic; parameter 4 represents the CDVT; and 
      parameter 5 represents the requested shaping rate. A non-zero value 
      in parameter 5 overrides any value in parameter 1. This result is 
      used as the PCR. Parameter 1 must be non-zero. Parameters 2 and 3 
      must be zero.
      
      When txTrafficDescType is 4, parameter 1 represents the PCR for 
      CLP equal to 0 and 1 traffic with cell discard; parameter 2 
      represents the PCR for CLP equal to 0 traffic; parameter 4 
      represents the CDVT; and parameter 5 represents the requested 
      shaping rate. A non-zero value in parameter 5 overrides any value in 
      parameter 1. This result is used as the PCR. Parameter 1 must be 
      greater than or equal to parameter 2. Parameters 1 and 2 must be 
      non-zero. Parameter 3 must be zero.
      
      When txTrafficDescType is 5, parameter 1 represents the PCR for 
      CLP equal to 0 and 1 traffic with cell tagging; parameter 2 
      represents the PCR for CLP equal to 0 traffic; parameter 4 
      represents the CDVT; and parameter 5 represents the requested 
      shaping rate. A non-zero value in parameter 5 overrides any value in 
      parameter 1. This result is used as the PCR. Parameter 1 must be 
      greater than or equal to parameter 2. Parameters 1 and 2 must be 
      non-zero. Parameter 3 must be zero.
      
      When txTrafficDescType is 6, parameter 1 represents the PCR for 
      CLP equal to 0 and 1 traffic; parameter 2 represents the SCR for 
      CLP equal to 0 and 1 traffic; parameter 3 represents the MBS for 
      CLP equal to 0 and 1 traffic; parameter 4 represents the CDVT; and 
      parameter 5 represents the requested shaping rate. A non-zero value 
      in parameter 5 overrides any value in parameter 1. This result is 
      used as the PCR. Parameters 1, 2 and 3 must be non-zero. 
      Parameter 1 must be greater than or equal to parameter 2. Parameter 
      5, must either be zero (unused) or greater than or equal to parameter 
      2.
      
      When txTrafficDescType is 7, parameter 1 represents the PCR for 
      CLP equal to 0 and 1 traffic; parameter 2 represents the SCR for 
      CLP equal to 0 with cell discard; parameter 3 represents the MBS 
      for CLP equal to 0 traffic; parameter 4 represents the CDVT; and 
      parameter 5 represents the requested shaping rate. A non-zero value 
      in parameter 5 overrides any value in parameter 1. This result is 
      used as the PCR. Parameters 1, 2 and 3 must be non-zero. 
      Parameter 1 must be greater than or equal to parameter 2. Parameter 
      5, must either be zero (unused) or greater than or equal to parameter 
      2.
      
      When txTrafficDescType is 8, parameter 1 represents the PCR for 
      CLP equal to 0 and 1 traffic; parameter 2 represents the SCR for 
      CLP equal to 0 traffic with cell tagging; parameter 3 represents the 
      MBS for CLP equal to 0 traffic; parameter 4 represents the CDVT; 
      and parameter 5 represents the requested shaping rate. A non-zero 
      value in parameter 5 overrides any value in parameter 1. This result 
      is used as the PCR. Parameters 1, 2 and 3 must be non-zero. 
      Parameter 1 must be greater than or equal to parameter 2. Parameter 
      5, must either be zero (unused) or greater than or equal to parameter 
      2.
      
      Whenever it is valid for PCR to be specified, parameter 5 may also 
      be used to specify a requested shaping rate. A non-zero value in 
      parameter 5 overrides the value in parameter 1 and is used as the 
      peak cell rate in calculations of CAC and shaping rate.
      
      For txTrafficDescType 3, 4 and 5, the transmit traffic is shaped at 
      the next rate less than the PCR. 
      
      For txTrafficDescType 6, 7 and 8, the transmit traffic is shaped at 
      the highest available rate which is between PCR and SCR. 
      However, if there is no available shaping rate between PCR and 
      SCR, traffic is shaped at the next rate above the PCR."
::= { mscAtmIfVptVpd 297 }

mscAtmIfVptVpdTxTdpEntry OBJECT-TYPE
   SYNTAX     MscAtmIfVptVpdTxTdpEntry
   ACCESS     not-accessible
   STATUS     obsolete
   DESCRIPTION
     "An entry in the mscAtmIfVptVpdTxTdpTable."
   INDEX {
      mscAtmIfIndex,
      mscAtmIfVptIndex,
      mscAtmIfVptVpdIndex,
      mscAtmIfVptVpdTxTdpIndex }
::= { mscAtmIfVptVpdTxTdpTable 1 }

MscAtmIfVptVpdTxTdpEntry ::= SEQUENCE {
   mscAtmIfVptVpdTxTdpIndex
      Integer32,
   mscAtmIfVptVpdTxTdpValue
      Unsigned32 }

mscAtmIfVptVpdTxTdpIndex OBJECT-TYPE
   SYNTAX     Integer32 (1..5)
   ACCESS     not-accessible
   STATUS     obsolete
   DESCRIPTION
     "This variable represents the mscAtmIfVptVpdTxTdpTable
      specific index for the mscAtmIfVptVpdTxTdpTable."
::= { mscAtmIfVptVpdTxTdpEntry 1 }

mscAtmIfVptVpdTxTdpValue OBJECT-TYPE
   SYNTAX     Unsigned32 (0..2147483647)
   ACCESS     read-write
   STATUS     obsolete
   DESCRIPTION
     "This variable represents an individual value for the
      mscAtmIfVptVpdTxTdpTable."
::= { mscAtmIfVptVpdTxTdpEntry 2 }

mscAtmIfVptVpdRxTdpTable OBJECT-TYPE
   SYNTAX     SEQUENCE OF MscAtmIfVptVpdRxTdpEntry
   ACCESS     not-accessible
   STATUS     obsolete
   DESCRIPTION
     "This attribute is migrated to the AtmTmProv group.
      
      This attribute is a vector of four traffic parameters whose meanings 
      are defined by the rxTrafficDescType attribute. The values of peak 
      cell rate (PCR) and sustained cell rate (SCR) are expressed in 
      cell/s. Maximum burst size (MBS) is expressed in cells. The value 
      of CDVT is expressed in microseconds. The values of PCR, SCR, 
      MBS and CDVT are used for usage parameter control (UPC).
      
      When rxTrafficDescType is 1 or 2, all of the parameters must be set 
      to zero (unused).
      
      When rxTrafficDescType is 3, parameter 1 represents the PCR for 
      CLP equal to 0 and 1 traffic. Parameter 1 must be non-zero. 
      Parameters 2 and 3 must be set to zero (unused).
      
      When rxTrafficDescType is 4, parameter 1 represents the PCR for 
      CLP equal to 0 and 1 traffic; parameter 2 represents the PCR for 
      CLP equal to 0 traffic with cell discard. Parameters 1 and 2 must be 
      non-zero. Parameter 3 must be set to zero (unused). Parameter 1 
      must be greater than or equal to parameter 2.
      
      When rxTrafficDescType is 5, parameter 1 represents the PCR for 
      CLP equal to 0 and 1 traffic; parameter 2 represents the PCR for 
      CLP equal to 0 traffic with cell tagging. Parameters 1 and 2 must be 
      non-zero. Parameter 3 must be set to zero (unused). Parameter 1 
      must be greater than or equal to parameter 2.
      
      When rxTrafficDescType is a 6, parameter 1 represents the PCR for 
      CLP equal to 0 and 1 traffic; parameter 2 represents the SCR for 
      CLP equal to 0 and 1 traffic; parameter 3 represents the MBS for 
      CLP equal to 0 and 1 traffic. Parameters 1, 2 and 3 must be non-
      zero. Parameter 1 must be greater than or equal to Parameter 2. 
      
      When rxTrafficDescType is 7, parameter 1 represents the PCR for 
      CLP equal to 0 and 1 traffic; parameter 2 represents the SCR for 
      CLP equal to 0 traffic with cell discard; parameter 3 represents the 
      MBS for CLP equal to 0 traffic. Parameters 1, 2 and 3 must be non-
      zero. Parameter 1 must be greater than or equal to parameter 2. 
      
      When rxTrafficDescType is 8, parameter 1 represents the PCR for 
      CLP equal to 0 and 1 traffic; parameter 2 represents the SCR for 
      CLP equal to 0 traffic with cell tagging; parameter 3 represents the 
      MBS for CLP equal to 0 traffic. Parameter 1, 2 and 3 must be non-
      zero. Parameter 1 must be greater than or equal to parameter 2.
      
      When rxTrafficDescType is any value from 3 through 8, parameter 
      4 represents the CDVT. If this value is zero, the CDVT is taken 
      from the ConnectionAdministrator defaults for the particular 
      atmServiceCategory of this connection.
      
      When rxTrafficDescriptorType is 3 through 8, there are certain 
      extreme combinations of rxTrafficDescParm which are outside the 
      capabilities of the UPC hardware. The check prov command detects 
      such cases and generates an error message. If this happens, adjust 
      the parameters until they fall within the supported limits. 
      
      To calculate the limits, use the following formulae:
      I1 = 1 000 000 000 / PCR
      L1 = CDVT * 1000
      I2 = 1 000 000 000 / SCR
      L2 = CDVT + (MBS - 1) * (I2 - I1)
      I1 and I2 must be less than or equal to 335 523 840. I1 + L1 must 
      be less than or equal to 1 342 156 800. I2 + L2 must be less than or 
      equal to 1 342 156 800. Note that I2 and L2 only apply when the 
      rxTrafficDescriptorType is 6 through 8.
      
      If the values of I1, L1, I2 or L2 are closer to the limits described 
      above, a further restriction applies. Specifically, if either:
      I1 > 41 940 480 or
      I2 > 41 940 480 or
      I1 + L1 > 167 769 600 or
      I2 + L2 > 167 769 600
      then both I1 and I2 must be greater than 20 480. 
      
      Parameter 5 of the rxTrafficDescParm is always unused. 
      
      If the rxTrafficDescType is sameAsTx, the values in this attribute 
      are taken from the txTrafficDescParm."
::= { mscAtmIfVptVpd 298 }

mscAtmIfVptVpdRxTdpEntry OBJECT-TYPE
   SYNTAX     MscAtmIfVptVpdRxTdpEntry
   ACCESS     not-accessible
   STATUS     obsolete
   DESCRIPTION
     "An entry in the mscAtmIfVptVpdRxTdpTable."
   INDEX {
      mscAtmIfIndex,
      mscAtmIfVptIndex,
      mscAtmIfVptVpdIndex,
      mscAtmIfVptVpdRxTdpIndex }
::= { mscAtmIfVptVpdRxTdpTable 1 }

MscAtmIfVptVpdRxTdpEntry ::= SEQUENCE {
   mscAtmIfVptVpdRxTdpIndex
      Integer32,
   mscAtmIfVptVpdRxTdpValue
      Unsigned32 }

mscAtmIfVptVpdRxTdpIndex OBJECT-TYPE
   SYNTAX     Integer32 (1..5)
   ACCESS     not-accessible
   STATUS     obsolete
   DESCRIPTION
     "This variable represents the mscAtmIfVptVpdRxTdpTable
      specific index for the mscAtmIfVptVpdRxTdpTable."
::= { mscAtmIfVptVpdRxTdpEntry 1 }

mscAtmIfVptVpdRxTdpValue OBJECT-TYPE
   SYNTAX     Unsigned32 (0..2147483647)
   ACCESS     read-write
   STATUS     obsolete
   DESCRIPTION
     "This variable represents an individual value for the
      mscAtmIfVptVpdRxTdpTable."
::= { mscAtmIfVptVpdRxTdpEntry 2 }

mscAtmIfVptVpdFqpTable OBJECT-TYPE
   SYNTAX     SEQUENCE OF MscAtmIfVptVpdFqpEntry
   ACCESS     not-accessible
   STATUS     obsolete
   DESCRIPTION
     "This attribute is migrated to the AtmTmProv group.
      
      This attribute is a vector of three elements that specify the quality of 
      service parameters for the forward direction for this connection. 
      This attribute is used for SPVC connections.
      
      The cdv element specifies the acceptable peak-to-peak Cell Delay 
      Variation (CDV) of real-time connections (CBR, and rt-VBR). It is 
      signalled through the extended QoS information element.
      
      The ctd specifies the acceptable maximum Cell Transfer Delay 
      (maxCtd) of real-time connections (CBR, and rt-VBR). 
      It is signalled through the end to end transit delay information 
      element.
      
      The clr specifies the acceptable Cell Loss Ratio (CLR) of CBR, rt-
      VBR, and nrt-VBR connections. It is signalled through the extended 
      QoS information element."
::= { mscAtmIfVptVpd 359 }

mscAtmIfVptVpdFqpEntry OBJECT-TYPE
   SYNTAX     MscAtmIfVptVpdFqpEntry
   ACCESS     not-accessible
   STATUS     obsolete
   DESCRIPTION
     "An entry in the mscAtmIfVptVpdFqpTable."
   INDEX {
      mscAtmIfIndex,
      mscAtmIfVptIndex,
      mscAtmIfVptVpdIndex,
      mscAtmIfVptVpdFqpIndex }
::= { mscAtmIfVptVpdFqpTable 1 }

MscAtmIfVptVpdFqpEntry ::= SEQUENCE {
   mscAtmIfVptVpdFqpIndex
      INTEGER,
   mscAtmIfVptVpdFqpValue
      Unsigned32 }

mscAtmIfVptVpdFqpIndex OBJECT-TYPE
   SYNTAX     INTEGER  {
                 cdv(0),
                 ctd(1),
                 clr(2) }
   ACCESS     not-accessible
   STATUS     obsolete
   DESCRIPTION
     "This variable represents the mscAtmIfVptVpdFqpTable
      specific index for the mscAtmIfVptVpdFqpTable."
::= { mscAtmIfVptVpdFqpEntry 1 }

mscAtmIfVptVpdFqpValue OBJECT-TYPE
   SYNTAX     Unsigned32 (0..2147483647)
   ACCESS     read-write
   STATUS     obsolete
   DESCRIPTION
     "This variable represents an individual value for the
      mscAtmIfVptVpdFqpTable."
::= { mscAtmIfVptVpdFqpEntry 2 }

mscAtmIfVptVpdBqpTable OBJECT-TYPE
   SYNTAX     SEQUENCE OF MscAtmIfVptVpdBqpEntry
   ACCESS     not-accessible
   STATUS     obsolete
   DESCRIPTION
     "This attribute is migrated to the AtmTmProv group.
      
      This attribute is a vector of three elements that specify the quality of 
      service parameters for the backward direction for this connection. 
      This attribute is used for SPVC connections.
      
      The cdv element specifies the acceptable peak-to-peak Cell Delay 
      Variation (CDV) of real-time connections (CBR, and rt-VBR). 
      
      It is signalled through the extended QoS information element.
      
      The ctd specifies the acceptable maximum Cell Transfer Delay 
      (maxCtd) of real-time connections (CBR, and rt-VBR). It is 
      signalled through the end to end transit delay information element.
      
      The clr specifies the acceptable Cell Loss Ratio (CLR) of CBR, rt-
      VBR, and nrt-VBR connections. It is signalled through the extended 
      QoS information element."
::= { mscAtmIfVptVpd 360 }

mscAtmIfVptVpdBqpEntry OBJECT-TYPE
   SYNTAX     MscAtmIfVptVpdBqpEntry
   ACCESS     not-accessible
   STATUS     obsolete
   DESCRIPTION
     "An entry in the mscAtmIfVptVpdBqpTable."
   INDEX {
      mscAtmIfIndex,
      mscAtmIfVptIndex,
      mscAtmIfVptVpdIndex,
      mscAtmIfVptVpdBqpIndex }
::= { mscAtmIfVptVpdBqpTable 1 }

MscAtmIfVptVpdBqpEntry ::= SEQUENCE {
   mscAtmIfVptVpdBqpIndex
      INTEGER,
   mscAtmIfVptVpdBqpValue
      Unsigned32 }

mscAtmIfVptVpdBqpIndex OBJECT-TYPE
   SYNTAX     INTEGER  {
                 cdv(0),
                 ctd(1),
                 clr(2) }
   ACCESS     not-accessible
   STATUS     obsolete
   DESCRIPTION
     "This variable represents the mscAtmIfVptVpdBqpTable
      specific index for the mscAtmIfVptVpdBqpTable."
::= { mscAtmIfVptVpdBqpEntry 1 }

mscAtmIfVptVpdBqpValue OBJECT-TYPE
   SYNTAX     Unsigned32 (0..2147483647)
   ACCESS     read-write
   STATUS     obsolete
   DESCRIPTION
     "This variable represents an individual value for the
      mscAtmIfVptVpdBqpTable."
::= { mscAtmIfVptVpdBqpEntry 2 }


-- AtmIf/n Vcc/vpi.vci Vcd TrafficManagement, 
-- AtmIf/n Vpc/vci Vpd TrafficManagement,
-- AtmIf/n Vpt/vpi Vpd TrafficManagement,
-- AtmIf/n Vpt/vpi Vcc/vci Vcd TrafficManagement
-- This component contains provisioned traffic management attributes 
-- of a connection. It is added automatically when a Vcc, Vpc, or Vpt is 
-- added in provisioning mode. It is a mandatory subcomponent of the 
-- Vcd or Vpd component.

mscAtmIfVptVpdTm OBJECT IDENTIFIER ::= { mscAtmIfVptVpd 2 }



mscAtmIfVptVpdTmRowStatusTable OBJECT-TYPE
   SYNTAX     SEQUENCE OF MscAtmIfVptVpdTmRowStatusEntry
   ACCESS     not-accessible
   STATUS     mandatory
   DESCRIPTION
     "This entry controls the addition and deletion of 
      mscAtmIfVptVpdTm components."
::= { mscAtmIfVptVpdTm 1 }

mscAtmIfVptVpdTmRowStatusEntry OBJECT-TYPE
   SYNTAX     MscAtmIfVptVpdTmRowStatusEntry
   ACCESS     not-accessible
   STATUS     mandatory
   DESCRIPTION
     "A single entry in the table represents a single 
      mscAtmIfVptVpdTm component."
   INDEX {
      mscAtmIfIndex,
      mscAtmIfVptIndex,
      mscAtmIfVptVpdIndex,
      mscAtmIfVptVpdTmIndex }
::= { mscAtmIfVptVpdTmRowStatusTable 1 }

MscAtmIfVptVpdTmRowStatusEntry ::= SEQUENCE {
   mscAtmIfVptVpdTmRowStatus
      RowStatus,
   mscAtmIfVptVpdTmComponentName
      DisplayString,
   mscAtmIfVptVpdTmStorageType
      StorageType,
   mscAtmIfVptVpdTmIndex
      NonReplicated }

mscAtmIfVptVpdTmRowStatus OBJECT-TYPE
   SYNTAX     RowStatus 
   ACCESS     read-only
   STATUS     mandatory
   DESCRIPTION
     "This variable is used as the basis for SNMP naming of
      mscAtmIfVptVpdTm components.
      These components cannot be added nor deleted."
::= { mscAtmIfVptVpdTmRowStatusEntry 1 }

mscAtmIfVptVpdTmComponentName OBJECT-TYPE
   SYNTAX     DisplayString 
   ACCESS     read-only
   STATUS     mandatory
   DESCRIPTION
     "This variable provides the component's string name for
      use with the ASCII Console Interface"
::= { mscAtmIfVptVpdTmRowStatusEntry 2 }

mscAtmIfVptVpdTmStorageType OBJECT-TYPE
   SYNTAX     StorageType 
   ACCESS     read-only
   STATUS     mandatory
   DESCRIPTION
     "This variable represents the storage type value for the
      mscAtmIfVptVpdTm tables."
::= { mscAtmIfVptVpdTmRowStatusEntry 4 }

mscAtmIfVptVpdTmIndex OBJECT-TYPE
   SYNTAX     NonReplicated 
   ACCESS     not-accessible
   STATUS     mandatory
   DESCRIPTION
     "This variable represents the index for the mscAtmIfVptVpdTm tables."
::= { mscAtmIfVptVpdTmRowStatusEntry 10 }

mscAtmIfVptVpdTmProvTable OBJECT-TYPE
   SYNTAX     SEQUENCE OF MscAtmIfVptVpdTmProvEntry
   ACCESS     not-accessible
   STATUS     mandatory
   DESCRIPTION
     "This group contains traffic related provisionable attributes for the 
      Vcc, Vpc, and Vpt components. Changing any of the attributes in 
      this group causes a service interruption on the Vcc, Vpc, or Vpt 
      component."
::= { mscAtmIfVptVpdTm 100 }

mscAtmIfVptVpdTmProvEntry OBJECT-TYPE
   SYNTAX     MscAtmIfVptVpdTmProvEntry
   ACCESS     not-accessible
   STATUS     mandatory
   DESCRIPTION
     "An entry in the mscAtmIfVptVpdTmProvTable."
   INDEX {
      mscAtmIfIndex,
      mscAtmIfVptIndex,
      mscAtmIfVptVpdIndex,
      mscAtmIfVptVpdTmIndex }
::= { mscAtmIfVptVpdTmProvTable 1 }

MscAtmIfVptVpdTmProvEntry ::= SEQUENCE {
   mscAtmIfVptVpdTmTxTrafficDescType
      INTEGER,
   mscAtmIfVptVpdTmFwdQosClass
      INTEGER,
   mscAtmIfVptVpdTmTxQueueLimit
      Unsigned32,
   mscAtmIfVptVpdTmHoldingPriority
      INTEGER,
   mscAtmIfVptVpdTmRxTrafficDescType
      INTEGER,
   mscAtmIfVptVpdTmBwdQosClass
      INTEGER,
   mscAtmIfVptVpdTmAtmServiceCategory
      INTEGER,
   mscAtmIfVptVpdTmTrafficShaping
      INTEGER,
   mscAtmIfVptVpdTmUnshapedTransmitQueueing
      INTEGER,
   mscAtmIfVptVpdTmWeight
      Unsigned32,
   mscAtmIfVptVpdTmForceTagging
      INTEGER,
   mscAtmIfVptVpdTmUsageParameterControl
      INTEGER,
   mscAtmIfVptVpdTmBearerClassBbc
      INTEGER,
   mscAtmIfVptVpdTmTransferCapabilityBbc
      INTEGER,
   mscAtmIfVptVpdTmClippingBbc
      INTEGER,
   mscAtmIfVptVpdTmBestEffort
      INTEGER,
   mscAtmIfVptVpdTmTxPacketWiseDiscard
      INTEGER,
   mscAtmIfVptVpdTmRxPacketWiseDiscard
      INTEGER,
   mscAtmIfVptVpdTmAbrConnectionType
      INTEGER }

mscAtmIfVptVpdTmTxTrafficDescType OBJECT-TYPE
   SYNTAX     INTEGER  {
                 n1(1),
                 n2(2),
                 n3(3),
                 n4(4),
                 n5(5),
                 n6(6),
                 n7(7),
                 n8(8),
                 n9(9) }
   ACCESS     read-write
   STATUS     mandatory
   DESCRIPTION
     "This attribute specifies the type of traffic management which is 
      applied to the transmit direction of this connection as defined in the 
      ATM Forum. The txTrafficDescType determines the number and 
      meaning of the parameters in the txTrafficDescParm attribute.
      
      This attribute can have a value of 9 if and only if the 
      atmServiceCategory is availableBitRate."
   DEFVAL     { n1 }
::= { mscAtmIfVptVpdTmProvEntry 10 }

mscAtmIfVptVpdTmFwdQosClass OBJECT-TYPE
   SYNTAX     INTEGER  {
                 n0(0),
                 n1(1),
                 n2(2),
                 n3(3),
                 n4(4) }
   ACCESS     read-write
   STATUS     mandatory
   DESCRIPTION
     "This attribute specifies the quality of service for the forward 
      direction for this connection. This attribute is only used for SPVC 
      connections.
      
      Class 1 supports a QOS that meets Service Class A performance 
      requirements (circuit emulation, constant bit rate video).
      
      Class 2 supports a QOS that meets Service Class B performance 
      requirements (variable bit rate audio and video).
      
      Class 3 supports a QOS that meets Service Class C performance 
      requirements (Connection-Oriented Data Transfer).
      
      Class 4 supports a QOS that meets Service Class D performance 
      requirements (Connectionless Data Transfer).
      
      Class 0 is the unspecified bit rate QOS class; no objective is 
      specified for the performance parameters."
   DEFVAL     { n0 }
::= { mscAtmIfVptVpdTmProvEntry 21 }

mscAtmIfVptVpdTmTxQueueLimit OBJECT-TYPE
   SYNTAX     Unsigned32 (0 | 5..512000)
   ACCESS     read-write
   STATUS     mandatory
   DESCRIPTION
     "This attribute specifies an override to the default transmit queue 
      limit for this connection. An value other than sameAsCa may be 
      specified only for ATM IP and 1pOC48SmSrAtm cards. This 
      attribute is not applicable for basic Vpts.
      
      A value of sameAsCa means to use the default common or per-VC 
      transmit queue limit as defined by the CA service category for this 
      connection. 
      
      A value from 5 to 63,488 indicates that a specific transmit queue 
      limit is requested which differs from the default which is defined 
      under the CA component for this service category. A specific value 
      is ignored for connections where common queuing is specified for 
      the service category. 
      
      For the 1pOC48SmSrAtm card, this attribute is used to set the per 
      VC utilization limit.
      
      The actual transmit queue limit for a connection is visible in the Vcc 
      Tm, Vpc Tm or Vpt txQueueThresholds attribute.

      VALUES (

      0 = sameAsCa

      )"
   DEFVAL     { 0 }
::= { mscAtmIfVptVpdTmProvEntry 22 }

mscAtmIfVptVpdTmHoldingPriority OBJECT-TYPE
   SYNTAX     INTEGER  {
                 n0(0),
                 n1(1),
                 n2(2),
                 n3(3),
                 n4(4) }
   ACCESS     read-write
   STATUS     mandatory
   DESCRIPTION
     "This attribute specifies the holding priority of this connection. In a 
      situation where the link bandwidth fluctuates, such as over an IMA 
      link, holding priority is used to determine which connections are 
      held and which are released. Holding priority 4 connections are the 
      first to be released. Holding priority 0 connections are the last to be 
      released. This value provisioned in the Vcd or Vpd may be 
      overridden by certain applications, for example Vcc Test, which run 
      over this connection. The default holding priority for a provisioned 
      connection is higher then default holding priorities for dynamic 
      (SVC) connections. 
      
      This attribute is not applicable for Vpt Vccs."
   DEFVAL     { n2 }
::= { mscAtmIfVptVpdTmProvEntry 25 }

mscAtmIfVptVpdTmRxTrafficDescType OBJECT-TYPE
   SYNTAX     INTEGER  {
                 n1(1),
                 n2(2),
                 n3(3),
                 n4(4),
                 n5(5),
                 n6(6),
                 n7(7),
                 n8(8),
                 n9(9),
                 sameAsTx(15) }
   ACCESS     read-write
   STATUS     mandatory
   DESCRIPTION
     "This attribute specifies the type of traffic management which is 
      applied to the receive direction of this connection as defined in the 
      ATM Forum. The rxTrafficDescType determines the number and 
      meaning of the parameters in the rxTrafficDescParm attribute.
      
      When this attribute is set to sameAsTx, the rxTrafficDescType as 
      well as the rxTrafficDescParm are taken from the 
      txTrafficDescType and txTrafficDescParm values."
   DEFVAL     { sameAsTx }
::= { mscAtmIfVptVpdTmProvEntry 30 }

mscAtmIfVptVpdTmBwdQosClass OBJECT-TYPE
   SYNTAX     INTEGER  {
                 n0(0),
                 n1(1),
                 n2(2),
                 n3(3),
                 n4(4),
                 sameAsFwd(15) }
   ACCESS     read-write
   STATUS     mandatory
   DESCRIPTION
     "This attribute specifies the quality of service for the backward 
      direction for this connection. This attribute is only used for SPVC 
      connections.
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified bit rate QOS class; no objective is 
      specified for the performance parameters.
      
      The sameAsFwd selection sets the backward quality of service to 
      be the same as the forward quality of service."
   DEFVAL     { sameAsFwd }
::= { mscAtmIfVptVpdTmProvEntry 41 }

mscAtmIfVptVpdTmAtmServiceCategory OBJECT-TYPE
   SYNTAX     INTEGER  {
                 unspecifiedBitRate(0),
                 constantBitRate(1),
                 rtVariableBitRate(2),
                 nrtVariableBitRate(3),
                 availableBitRate(4),
                 derivedFromBBC(15) }
   ACCESS     read-write
   STATUS     mandatory
   DESCRIPTION
     "This attribute specifies the ATM service category for both directions 
      of the connection. 
      
      The value derivedFromBBC may only be used if the SrcPvc 
      component is provisioned under this Vcc. Otherwise a specific 
      ATM service category must be specified. 
      
      If this attribute is set to derivedFromBBC, the Broadband Bearer 
      Capability (BBC) and bestEffort attributes are used to determine the 
      atmServiceCategory of this connection. 
      
      If this attribute is set to other than derivedFromBBC, the value of 
      this attribute is used to override the provisioned BBC Information 
      Element parameters. In those cases, the BBC attributes are not used. 
      
      The constantBitRate service category is intended for real time 
      applications, that is those requiring tightly constrained delay and 
      delay variation, as would be appropriate for voice and video 
      applications. The consistent availability of a fixed quantity of 
      bandwidth is considered appropriate for CBR service. Cells which 
      are delayed beyond the value specified by Cell Transfer Delay are 
      assumed to be of significantly reduced value to the application.
      
      The rtVariableBitRate service category is intended for real time 
      applications, that is those requiring tightly constrained delay and 
      delay variation, as would be appropriate for voice and video 
      applications. Sources are expected to transmit at a rate which varies 
      with time. Equivalently, the source can be described as 'bursty'. 
      Cells which are delayed beyond the value specified by CTD are 
      assumed to be of significantly reduced value to the application. Real 
      time VBR service may support statistical multiplexing of real time 
      sources.
      
      The nrtVariableBitRate service category is intended for non-real 
      time applications which have bursty traffic characteristics and which 
      can be characterized in terms of a PCR, SCR, and MBS. For those 
      cells which are transferred within the traffic contract, the application 
      expects a low cell loss ratio. For all connections, it expects a bound 
      on the mean cell transfer delay. Non-real time VBR service may 
      support statistical multiplexing of connections. 
      
      The availableBitRate service is an ATM layer service category for 
      which the limiting ATM layer transfer characteristics provided by 
      the network may change subsequent to connection establishment. 
      ABR service has a flow control mechanism which supports several 
      types of feedback to control the source rate in response to changing 
      ATM layer transfer characteristics. ABR service is not intended to 
      support real-time applications. 
      
      The unspecifiedBitRate service is intended for non-real time 
      applications; that is, those not requiring tightly constrained delay 
      and delay variation. UBR sources are expected to be bursty. UBR 
      service supports a high degree of statistical multiplexing among 
      sources. UBR service does not specify traffic related service 
      guarantees. No numerical commitments are made with respect to 
      the cell loss ratio experienced by a UBR connection, or as to the 
      cell transfer delay experienced by cells on the connection."
   DEFVAL     { unspecifiedBitRate }
::= { mscAtmIfVptVpdTmProvEntry 42 }

mscAtmIfVptVpdTmTrafficShaping OBJECT-TYPE
   SYNTAX     INTEGER  {
                 disabled(1),
                 sameAsCa(2) }
   ACCESS     read-write
   STATUS     mandatory
   DESCRIPTION
     "This attribute specifies whether this connection uses traffic shaping 
      when transmitting traffic to the ATM interface.
      
      This attribute is ignored if the atmServiceCategory is 
      availableBitRate.
      
      Traffic shaping is not available on the 1pOC12SmLrAtm card, 
      therefore this attribute is ignored.
      
      When sameAsCa is selected, traffic shaping for the connection is 
      based on the trafficShaping attribute of the connection's service 
      category component under the CA. If the service category has 
      trafficShaping set to enabled or inverseUpc, then traffic shaping is 
      enabled for the connection. Note that enabling traffic shaping may 
      have no effect under certain cases. These cases are listed in the 
      description of the trafficShaping operational attribute, which is 
      under the Vcc Tm, Vpc Tm, or Vpt Tm components.
      
      When disabled is selected, traffic shaping for this connection is 
      disabled regardless of the provisioning of the connection's service 
      category component."
   DEFVAL     { sameAsCa }
::= { mscAtmIfVptVpdTmProvEntry 50 }

mscAtmIfVptVpdTmUnshapedTransmitQueueing OBJECT-TYPE
   SYNTAX     INTEGER  {
                 common(1),
                 sameAsCa(3) }
   ACCESS     read-write
   STATUS     mandatory
   DESCRIPTION
     "This attribute only applies when this connection is unshaped. This 
      attribute specifies the transmit queueing method for this connection 
      if it is unshaped. The two possible methods are per-VC queuing and 
      common queuing. 
      
      On ATM IP FPs, this attribute must be set to sameAsCa. 
      
      This attribute is ignored in the following situations:
      - if the connection has trafficShaping enabled or inverseUpc, or 
      - if the atmServiceCategory is availableBitRate, or
      - if the atmServiceCategory is constantBitRate and this is a CQC-
      based ATM FP.
      - for basic Vpts and standard Vpt Vccs
      
      When this attribute is set to sameAsCa, the transmit queueing 
      method for the connection is based on the 
      unshapedTransmitQueueing attribute of the connection's service 
      category component under the CA. 
      
      When this attribute is set to common, transmit traffic on this 
      unshaped connection is destined for the common queue."
   DEFVAL     { sameAsCa }
::= { mscAtmIfVptVpdTmProvEntry 60 }

mscAtmIfVptVpdTmWeight OBJECT-TYPE
   SYNTAX     Unsigned32 (0 | 1..4095 | 65535)
   ACCESS     read-write
   STATUS     mandatory
   DESCRIPTION
     "This attribute specifies an override for the weight of this unshaped 
      connection. This attribute is ignored for shaped connections, for 
      ABR connections, for connections on a CQC-based ATM FP and 
      basic Vpts.
      
      When the value is set to sameAsCa, the weight is determined by the 
      fairnessWeight attribute under the CA service category component 
      for all but standard Vpt Vccs. For standard Vpt Vccs, the weight is 
      determined by the Vcc's service category, when the value is set to 
      sameAsCa.
      
      When this attribute is set to a value from 1 to 4095, that value is 
      used for the fairness weight of this connection relative to other 
      connections. For all but standard Vpt Vccs, fairness weight 
      determines the proportion of transmit cell opportunities which are 
      allocated to this connection, compared to other connections in the 
      same service category. For standard Vpt Vccs, fairness weight 
      determines the proportion of transmit cell opportunities which are 
      allocated to this connection, compared to other connections 
      associated with the Vpt.
      
      When the value is set to upToQueueLimit, the fairness weight is 
      limited only by the txQueueLimit.

      VALUES (

      0 = upToQueueLimit

      65535 = sameAsCa

      )"
   DEFVAL     { 65535 }
::= { mscAtmIfVptVpdTmProvEntry 61 }

mscAtmIfVptVpdTmForceTagging OBJECT-TYPE
   SYNTAX     INTEGER  {
                 enabled(0),
                 disabled(1),
                 sameAsCa(2) }
   ACCESS     read-write
   STATUS     mandatory
   DESCRIPTION
     "This attribute specifies whether force tagging is enforced for this 
      connection for cells in the transmit direction. 
      
      On CQC-based ATM cards and for Vpts, this attribute is not 
      applicable and is ignored. 
      
      When the value is set to sameAsCa, the force tagging functionality 
      is determined by the forceTagging attribute under the CA service 
      category component. 
      
      When the value is set to enabled, force tagging is enabled for cells 
      in the transmit direction on this connection. When this option is 
      selected, the CLP bit is set to 1 for all cells in the transmit direction. 
      Cells which are tagged are counted in the txCellClp attribute. 
      
      When the value is set to disabled, force tagging is disabled for cells 
      in the transmit direction on this connection. When this option is 
      selected, the CLP bit is unchanged for cells in the transmit 
      direction."
   DEFVAL     { sameAsCa }
::= { mscAtmIfVptVpdTmProvEntry 62 }

mscAtmIfVptVpdTmUsageParameterControl OBJECT-TYPE
   SYNTAX     INTEGER  {
                 enforced(0),
                 disabled(1),
                 sameAsCa(2),
                 monitored(4) }
   ACCESS     read-write
   STATUS     mandatory
   DESCRIPTION
     "This attribute specifies whether this connection enforces usage 
      parameter control when receiving traffic from the ATM interface.
      
      When sameAsCa is selected, UPC for the connection is based on 
      the usageParameterControl attribute of the service category 
      component under the AtmIf CA. If the service category has UPC 
      enforced or monitored, then UPC is set to that value for the 
      connection. 
      
      When disabled is selected, UPC for this connection is disabled 
      regardless of the provisioning of the service category. 
      
      When enforced is selected, UPC for this connection is enforced 
      regardless of the provisioning of the service category. 
      
      Note that setting UPC to enforced or monitored may have no effect 
      under certain cases. These cases are listed in the description of the 
      usageParameterControl operational attribute, which is under the 
      Vcc, Vpc, and Vpt components."
   DEFVAL     { sameAsCa }
::= { mscAtmIfVptVpdTmProvEntry 70 }

mscAtmIfVptVpdTmBearerClassBbc OBJECT-TYPE
   SYNTAX     INTEGER  {
                 a(1),
                 c(3),
                 x(16),
                 vp(24),
                 derivedFromServiceCategory(31) }
   ACCESS     read-write
   STATUS     mandatory
   DESCRIPTION
     "This attribute specifies the bearer capability. This attribute is only 
      used for SPVC and SPVP connections. It is one of the Broadband 
      Bearer Capability (BBC) attributes. The purpose of the BBC 
      information element is to indicate a requested broadband 
      connection-oriented bearer service to be provided by the network.
      
      The value derivedFromServiceCategory specifies that the actual 
      value which is used for this connection is derived from the value of 
      the atmServiceCategory. Either, this attribute must be set to 
      derivedFromServiceCategory, or the atmServiceCategory attribute 
      must be set to derivedFromBBC, but not both.
      
      Class a service is a connection-oriented, constant bit rate ATM 
      transport service. Class a service has end to end timing 
      requirements and may require stringent cell loss, cell delay and cell 
      delay variation performance.When a is set, the user is requesting 
      more than an ATM only service. The network may look at the AAL 
      to provide interworking based upon its contents. 
      
      Class c service is a connection-oriented, variable bit rate ATM 
      transport service. Class c service has no end-to-end timing 
      requirements. When c is set, the user is requesting more than an 
      ATM only service. The network interworking function may look at 
      the AAL and provide service based on it.
      
      Class x service is a connection-oriented ATM transport service 
      where the AAL, trafficType (vbr or cbr) and timing requirements 
      are user defined (that is, transparent to the network).When x is set 
      the user is requesting an ATM only service from the network. In this 
      case, the network shall not process any higher layer protocol.
      
      Class vp service is used to specify a transparent VP service. When 
      the value of this attribute is vp, the user is requesting an ATM only 
      service from the network. In this case, the network shall not process 
      any higher layer protocol. This service differs from class x service 
      in that with the class vp service both the VCI field (except or VCI 
      values 0, 3, 4, and 6 through 15) and Payload Type field are 
      transported transparently by the network. This attribute value is 
      only applicable to SPVP connections."
   DEFVAL     { derivedFromServiceCategory }
::= { mscAtmIfVptVpdTmProvEntry 71 }

mscAtmIfVptVpdTmTransferCapabilityBbc OBJECT-TYPE
   SYNTAX     INTEGER  {
                 n0(0),
                 n1(1),
                 n2(2),
                 n5(5),
                 n8(8),
                 n9(9),
                 n10(10),
                 notApplicable(30),
                 derivedFromServiceCategory(31) }
   ACCESS     read-write
   STATUS     mandatory
   DESCRIPTION
     "This attribute specifies the transfer capability for this connection. 
      Uni 3.0/3.1 traffic type and end-to-end timing parameters are 
      mapped into this parameter as follows:
      <transferCapability: TrafficType, Timing>
      0: NoIndication, NoIndication
      1: NoIndication, yes
      2: NoIndication, no
      5: CBR, yes
      8: VBR, NoIndication
      9: VBR, yes
      10: VBR, no
      
      notApplicable specifies that the user does not want to specify the 
      transfer capability.
      
      The CBR traffic type refers to traffic offered on services such as a 
      constant bit rate video service or a circuit emulation.
      The VBR traffic type refers to traffic offered on services such as 
      packetized audio and video, or data.
      
      The value no indication for traffic type is used if the user has not set 
      the traffic type; similarly for end-to-end timing.
      
      The value yes for end-to-end timing indicates that end-to-end 
      timing is required.
      
      The value no for end-to-end timing indicates that end-to-end timing 
      is not required.
      
      The value derivedFromServiceCategory specifies that the actual 
      value which is used for this connection is derived from the value of 
      the atmServiceCategory. Either, this attribute must be set to 
      derivedFromServiceCategory, or the atmServiceCategory attribute 
      must be set to derivedFromBBC, but not both."
   DEFVAL     { derivedFromServiceCategory }
::= { mscAtmIfVptVpdTmProvEntry 72 }

mscAtmIfVptVpdTmClippingBbc OBJECT-TYPE
   SYNTAX     INTEGER  {
                 no(0),
                 yes(1) }
   ACCESS     read-write
   STATUS     mandatory
   DESCRIPTION
     "This attribute specifies the value for the clipping susceptibility 
      parameter in the BBC Information Element. This attribute is only 
      used for SPVC connections. It is one of the Broadband Bearer 
      Capability attributes.
      
      Clipping is an impairment in which the first fraction of a second of 
      information to be transferred is lost. It occurs after a call is 
      answered and before an associated connection is switched through."
   DEFVAL     { no }
::= { mscAtmIfVptVpdTmProvEntry 74 }

mscAtmIfVptVpdTmBestEffort OBJECT-TYPE
   SYNTAX     INTEGER  {
                 indicated(0),
                 notIndicated(1),
                 derivedFromServiceCategory(15) }
   ACCESS     read-write
   STATUS     mandatory
   DESCRIPTION
     "This attribute specifies the value of the best effort parameter in the 
      ATM Traffic Descriptor Information Element. This attribute is only 
      used for Soft PVC connections. It is one of the Broadband Bearer 
      Capability attributes.
      
      The value indicated implies that the quality of service for this 
      connection is not guaranteed.
      
      The value notIndicated implies that the quality of service for this 
      connection is guaranteed.
      
      The value derivedFromServiceCategory specifies that the actual 
      value which is used for this connection is derived from the value of 
      the atmServiceCategory. Either, this attribute must be set to 
      derivedFromServiceCategory, or the atmServiceCategory attribute 
      must be set to derivedFromBBC, but not both."
   DEFVAL     { derivedFromServiceCategory }
::= { mscAtmIfVptVpdTmProvEntry 75 }

mscAtmIfVptVpdTmTxPacketWiseDiscard OBJECT-TYPE
   SYNTAX     INTEGER  {
                 disabled(0),
                 enabled(1) }
   ACCESS     read-write
   STATUS     mandatory
   DESCRIPTION
     "This attribute specifies whether packet-wise discard functions are to 
      be enabled or disabled in the transmit data direction for this 
      connection. Packet-wise discard functions should only be requested 
      if this connection is transferring AAL5 frame traffic. This attribute 
      is not applicable for Vpts.
      
      Packet-wise functions increase the 'goodput' of the link. The 
      transmit packet-wise functions are Early Packet Discard (EPD) and 
      Partial Packet Discard (PPD). 
      
      EPD allows the connection to discard an entire frame once the 
      transmit queue has reached the EPD threshold. EPD increases the 
      'goodput' of a link, since discarding an entire frame means that 
      some queue capacity is guarded for some other frame which is 
      already partially transmitted. All cells of the frame are discarded 
      from the Beginning of Message (BOM) cell up to and including the 
      End of Message (EOM) cell. 
      
      PPD allows the connection to discard the remainder of a cell-
      forwarded AAL5 frame if one cell of this frame has been discarded. 
      All cells are discarded up to but not including the EOM cell. The 
      PPD function increases the 'goodput' of the link, since cells which 
      are only going to be discarded at the AAL5 reassembly point are 
      not transmitted.
      
      On CQC-based ATM cards, the packet-wise discard functions are 
      PPD and EPD. PPD is available at VCC cell-transfer points. PPD is 
      not applicable at frame-cell conversion points, and is not applicable 
      for Vpcs. PPD is configured by this attribute. Packet-wise discard 
      should only be enabled for connections carrying AAL5 
      segmentation traffic. Setting the value to enabled for any other 
      traffic type may result in all traffic being discarded. On CQC-based 
      ATM FPs, EPD is automatically enabled at frame-to-cell conversion 
      points, independent of the setting of this attribute. 
      
      On CQC-based ATM cards, at a permanent VCC connection 
      endpoint, this attribute is not applicable and is ignored. If AAL5 
      segmentation and reassembly has been requested, PPD and Early 
      Packet Discard (EPD) are automatically enabled.
      
      On ATM IP cards, packet-wise discard functions include EPD and 
      PPD. PPD and EPD apply to individual VCCs and VCCs within 
      VPCs at all connection points, including tandem VPC connections. 
      Both PPD and EPD are controlled by this attribute. This attribute 
      may safely be set to enabled for any connection (Vcc or Vpc) on 
      ATM IP FPs since they have the ability to automatically detect 
      AAL5-segmented traffic on a connection, and only enable packet-
      wise discards if AAL5-segmented traffic is detected.
      
      When this attribute is set to enabled, packet-wise discard functions 
      are applied to transmit traffic at this connection point. When this 
      attribute is set to disabled, packet-wise discard functions are not 
      applied to transmit traffic at this connection point.
      
      At a SPVC origin on a PNNI interface, a value of enabled specifies 
      that frame discard is requested in the backward direction. When this 
      attribute is set to disabled, backward frame discard is not requested 
      in the SPVC call setup. 
      
      The transmit packet-wise discard functions that are active are 
      visible in the Vcc/Vpc Tm txPacketWiseDiscard operational 
      attribute."
   DEFVAL     { disabled }
::= { mscAtmIfVptVpdTmProvEntry 76 }

mscAtmIfVptVpdTmRxPacketWiseDiscard OBJECT-TYPE
   SYNTAX     INTEGER  {
                 disabled(0),
                 enabled(1) }
   ACCESS     read-write
   STATUS     mandatory
   DESCRIPTION
     "This attribute specifies whether packet-wise discard functions are to 
      be enabled or disabled in the receive data direction for this 
      connection. Packet-wise discard functions should only be requested 
      if this connection is transferring AAL5 frame traffic. This attribute 
      is not applicable for Vpts.
      
      Packet-wise functions increase the 'goodput' of the link. The 
      receive packet-wise function is Partial Packet Discard (PPD). 
      
      PPD allows the connection to discard the remainder of a cell-
      forwarded AAL5 frame if one cell of this frame has been discarded, 
      for example due to UPC. All cells are discarded up to but not 
      including the EOM cell. The PPD function increases the 'goodput' 
      of the link, since cells which are only going to be discarded at the 
      AAL5 reassembly point are not transmitted.
      
      PPD is available at all VCC connection points where UPC may be 
      activated. PPD is not applicable for Vpcs. 
      
      On CQC-based ATM FPs, packet-wise discards should only be 
      enabled for connections carrying AAL5 segmentation traffic. 
      Setting the value to enabled for any other traffic type may result in 
      traffic being discarded. 
      
      On CQC-based ATM cards, at a permanent VCC connection 
      endpoint, this attribute is not applicable and is ignored. If AAL5 
      segmentation and reassembly has been requested, PPD and Early 
      Packet Discard (EPD) are automatically enabled.
      
      On ATM IP cards, this attribute may safely be set to enabled for any 
      connection (Vcc or Vpc) since they have the ability to automatically 
      detect AAL5-segmented traffic on a connection, and only enables 
      packet-wise discards if AAL5-segmented traffic is detected.
      
      When this attribute is set to enabled, packet-wise discard functions 
      are applied to receive traffic at this connection point. When this 
      attribute is set to disabled, packet-wise discard functions are not 
      applied to receive traffic at this connection point.
      
      At a SPVC origin on a PNNI interface, a value of enabled specifies 
      that frame discard is requested in the forward direction. When this 
      attribute is set to disabled, forward frame discard is not requested in 
      the SPVC call setup. 
      
      The receive packet-wise discard functions that are active are visible 
      in the Vcc/Vpc Tm rxPacketWiseDiscard operational attribute."
   DEFVAL     { disabled }
::= { mscAtmIfVptVpdTmProvEntry 78 }

mscAtmIfVptVpdTmAbrConnectionType OBJECT-TYPE
   SYNTAX     INTEGER  {
                 abrSwitch(0),
                 virtualSourceDest(3),
                 sourceDest(4),
                 nonAbrInterworking(5),
                 sameAsCa(14) }
   ACCESS     read-write
   STATUS     mandatory
   DESCRIPTION
     "This attribute specifies the type of ABR behavior which is to be 
      enforced at this connection. This attribute is only applicable if the 
      atmServiceCategory attribute is availableBitRate. If the 
      atmServicecategory attribute is not availableBitRate, this attribute 
      value is ignored.
      
      The actual ABR functionality which is in effect is visible in the 
      Vcc/Vpc/Vpt Tm abrConnectionType operational attribute.
      
      For CQC-based ATM cards, the only allowable values are 
      sameAsCa, nonAbrInterworking or abrSwitch. If abrSwitch is 
      selected, the CQC implements EFCI marking behavior.
      
      For the 1pOC12SmLrAtm card, the only allowable values are 
      sameAsCa or abrSwitch. If abrSwitch is selected, EFCI marking 
      behavior is implemented.
      
      sameAsCa is used to request the default behavior as specified in the 
      CA Abr component for this Vcc. Otherwise, this attribute overrides 
      the default behavior. 
      
      virtualSourceDest is used to request that this connection point 
      function as a virtual source/virtual destination. VS/VD functionality 
      is only supported on ATM IP FPs.
      
      sourceDest requires that this connection point function as a S/D for 
      RM cells. S/D mode is automatically invoked at this connection 
      point either if this is a connection end point, or if the next hop 
      connection point is configured as nonAbrInterworking.
      
      nonAbrInterworking is used to request that this connection point 
      function as an interworking between ABR and non-ABR service 
      categories. This means that there are no RM cells on the link side of 
      this connection, and that the next hop connection point is 
      performing as an ABR sourceDest.
      
      abrSwitch is used to request ABR switch behavior for this 
      connection point. The ABR switch behavior is first, to confirm to 
      virtualSourceDest or nonAbrInterworking setting on the next hop, 
      and otherwise to implement ABR ER switch behavior. For CQC-
      based FPs, ABR switch behavior is implemented as EFCI marking."
   DEFVAL     { sameAsCa }
::= { mscAtmIfVptVpdTmProvEntry 90 }

mscAtmIfVptVpdTmTxTdpTable OBJECT-TYPE
   SYNTAX     SEQUENCE OF MscAtmIfVptVpdTmTxTdpEntry
   ACCESS     not-accessible
   STATUS     mandatory
   DESCRIPTION
     "This attribute is a vector of five traffic parameters whose meanings 
      are defined by the txTrafficDescType attribute. 
      
      The values of peak cell rate (PCR), sustained cell rate (SCR), 
      Minimum Cell Rate (MCR) and requested shaping rate are 
      expressed in cell/s. Maximum burst size (MBS) is expressed in 
      cells. CDVT is expressed in microseconds. The values of PCR, 
      SCR, MCR, MBS and CDVT are used for connection admission 
      control (CAC). The value of CDVT is only used for connections 
      where the atmServiceCategory is constantBitRate. For all other 
      values of atmServiceCategory, CDVT is ignored. The values of 
      PCR, SCR, MCR and requested shaping rate are used to determine 
      the actual shaping rate where traffic shaping is enabled.
      
      When txTrafficDescType is 1 or 2, all of the parameters must be set 
      to zero.
      
      When txTrafficDescType is 3, parameter 1 represents the PCR for 
      CLP equal to 0 and 1 traffic; parameter 4 represents the CDVT; and 
      parameter 5 represents the requested shaping rate. A non-zero value 
      in parameter 5 overrides any value in parameter 1. This result is 
      used as the PCR. Parameter 1 must be non-zero. Parameters 2 and 3 
      must be zero.
      
      When txTrafficDescType is 4, parameter 1 represents the PCR for 
      CLP equal to 0 and 1 traffic with cell discard; parameter 2 
      represents the PCR for CLP equal to 0 traffic; parameter 4 
      represents the CDVT; and parameter 5 represents the requested 
      shaping rate. A non-zero value in parameter 5 overrides any value in 
      parameter 1. This result is used as the PCR. Parameter 1 must be 
      greater than or equal to parameter 2. Parameters 1 and 2 must be 
      non-zero. Parameter 3 must be zero.
      
      When txTrafficDescType is 5, parameter 1 represents the PCR for 
      CLP equal to 0 and 1 traffic with cell tagging; parameter 2 
      represents the PCR for CLP equal to 0 traffic; parameter 4 
      represents the CDVT; and parameter 5 represents the requested 
      shaping rate. A non-zero value in parameter 5 overrides any value in 
      parameter 1. This result is used as the PCR. Parameter 1 must be 
      greater than or equal to parameter 2. Parameters 1 and 2 must be 
      non-zero. Parameter 3 must be zero.
      
      When txTrafficDescType is 6, parameter 1 represents the PCR for 
      CLP equal to 0 and 1 traffic; parameter 2 represents the SCR for 
      CLP equal to 0 and 1 traffic; parameter 3 represents the MBS for 
      CLP equal to 0 and 1 traffic; parameter 4 represents the CDVT; and 
      parameter 5 represents the requested shaping rate. A non-zero value 
      in parameter 5 overrides any value in parameter 1. This result is 
      used as the PCR. Parameters 1, 2 and 3 must be non-zero. 
      Parameter 1 must be greater than or equal to parameter 2. Parameter 
      5, must either be zero (unused) or greater than or equal to parameter 
      2.
      
      When txTrafficDescType is 7, parameter 1 represents the PCR for 
      CLP equal to 0 and 1 traffic; parameter 2 represents the SCR for 
      CLP equal to 0 with cell discard; parameter 3 represents the MBS 
      for CLP equal to 0 traffic; parameter 4 represents the CDVT; and 
      parameter 5 represents the requested shaping rate. A non-zero value 
      in parameter 5 overrides any value in parameter 1. This result is 
      used as the PCR. Parameters 1, 2 and 3 must be non-zero. 
      Parameter 1 must be greater than or equal to parameter 2. Parameter 
      5, must either be zero (unused) or greater than or equal to parameter 
      2.
      
      When txTrafficDescType is 8, parameter 1 represents the PCR for 
      CLP equal to 0 and 1 traffic; parameter 2 represents the SCR for 
      CLP equal to 0 traffic with cell tagging; parameter 3 represents the 
      MBS for CLP equal to 0 traffic; parameter 4 represents the CDVT; 
      and parameter 5 represents the requested shaping rate. A non-zero 
      value in parameter 5 overrides any value in parameter 1. This result 
      is used as the PCR. Parameters 1, 2 and 3 must be non-zero. 
      Parameter 1 must be greater than or equal to parameter 2. Parameter 
      5, must either be zero (unused) or greater than or equal to parameter 
      2.
      
      When txTrafficDescType is 9, parameter 1 represents the PCR; 
      parameter 2 represents the CDVT; parameter 3 represents the MCR; 
      parameter 4 and parameter 5 represent are not used and must be 
      zero. Parameter 1 must be non-zero and must be greater than or 
      equal to parameter 3. Parameter 3 may be optionally zero.
      
      Whenever it is valid for PCR to be specified, parameter 5 may also 
      be used to specify a requested shaping rate. A non-zero value in 
      parameter 5 overrides the value in parameter 1 and is used as the 
      peak cell rate in calculations of CAC and shaping rate. When the 
      atmServiceCategory is availableBitRate (ABR), the shaping rate is 
      dynamically chosen, based on the ABR flow control mechanism, as 
      a value between the MCR and the PCR or the requested shaping 
      rate if applicable.
      
      For txTrafficDescType 3, 4 and 5, the transmit traffic is shaped at 
      the next available shaping rate less than the PCR. 
      
      For txTrafficDescType 6, 7 and 8 if linear traffic shaping is selected, 
      the transmit traffic is shaped at the highest available rate which is 
      between PCR and SCR. However, if there is no available shaping 
      rate between PCR and SCR, traffic is shaped at the next rate above 
      the PCR. 
      
      For txTrafficDescType 6, 7 and 8 if inverse-UPC traffic shaping is 
      selected, the transmit traffic is shaped at a variable rate which 
      conforms to the PCR, SCR and MBS of the connection traffic 
      descriptor. Inverse-UPC traffic shaping is available only on ATM IP 
      cards."
::= { mscAtmIfVptVpdTm 456 }

mscAtmIfVptVpdTmTxTdpEntry OBJECT-TYPE
   SYNTAX     MscAtmIfVptVpdTmTxTdpEntry
   ACCESS     not-accessible
   STATUS     mandatory
   DESCRIPTION
     "An entry in the mscAtmIfVptVpdTmTxTdpTable."
   INDEX {
      mscAtmIfIndex,
      mscAtmIfVptIndex,
      mscAtmIfVptVpdIndex,
      mscAtmIfVptVpdTmIndex,
      mscAtmIfVptVpdTmTxTdpIndex }
::= { mscAtmIfVptVpdTmTxTdpTable 1 }

MscAtmIfVptVpdTmTxTdpEntry ::= SEQUENCE {
   mscAtmIfVptVpdTmTxTdpIndex
      Integer32,
   mscAtmIfVptVpdTmTxTdpValue
      Unsigned32 }

mscAtmIfVptVpdTmTxTdpIndex OBJECT-TYPE
   SYNTAX     Integer32 (1..5)
   ACCESS     not-accessible
   STATUS     mandatory
   DESCRIPTION
     "This variable represents the mscAtmIfVptVpdTmTxTdpTable
      specific index for the mscAtmIfVptVpdTmTxTdpTable."
::= { mscAtmIfVptVpdTmTxTdpEntry 1 }

mscAtmIfVptVpdTmTxTdpValue OBJECT-TYPE
   SYNTAX     Unsigned32 (0..2147483647)
   ACCESS     read-write
   STATUS     mandatory
   DESCRIPTION
     "This variable represents an individual value for the
      mscAtmIfVptVpdTmTxTdpTable."
::= { mscAtmIfVptVpdTmTxTdpEntry 2 }

mscAtmIfVptVpdTmRxTdpTable OBJECT-TYPE
   SYNTAX     SEQUENCE OF MscAtmIfVptVpdTmRxTdpEntry
   ACCESS     not-accessible
   STATUS     mandatory
   DESCRIPTION
     "This attribute is a vector of four traffic parameters whose meanings 
      are defined by the rxTrafficDescType attribute. The values of peak 
      cell rate (PCR), sustained cell rate (SCR) and Minimum Cell Rate 
      (MCR) are expressed in cell/s. Maximum burst size (MBS) is 
      expressed in cells. The value of CDVT is expressed in 
      microseconds. The values of PCR, SCR, MCR, MBS and CDVT 
      are used for usage parameter control (UPC).
      
      When rxTrafficDescType is 1 or 2, all of the parameters must be set 
      to zero (unused).
      
      When rxTrafficDescType is 3, parameter 1 represents the PCR for 
      CLP equal to 0 and 1 traffic. Parameter 1 must be non-zero. 
      Parameters 2 and 3 must be set to zero (unused).
      
      When rxTrafficDescType is 4, parameter 1 represents the PCR 
      for CLP equal to 0 and 1 traffic; parameter 2 represents the PCR for 
      CLP equal to 0 traffic with cell discard. Parameters 1 and 2 must be 
      non-zero. Parameter 3 must be set to zero (unused). Parameter 1 
      must be greater than or equal to parameter 2.
      
      When rxTrafficDescType is 5, parameter 1 represents the PCR for 
      CLP equal to 0 and 1 traffic; parameter 2 represents the PCR for 
      CLP equal to 0 traffic with cell tagging. Parameters 1 and 2 must be 
      non-zero. Parameter 3 must be set to zero (unused). Parameter 1 
      must be greater than or equal to parameter 2.
      
      When rxTrafficDescType is a 6, parameter 1 represents the PCR for 
      CLP equal to 0 and 1 traffic; parameter 2 represents the SCR for 
      CLP equal to 0 and 1 traffic; parameter 3 represents the MBS for 
      CLP equal to 0 and 1 traffic. Parameters 1, 2 and 3 must be non-
      zero. Parameter 1 must be greater than or equal to Parameter 2. 
      
      When rxTrafficDescType is 7, parameter 1 represents the PCR for 
      CLP equal to 0 and 1 traffic; parameter 2 represents the SCR for 
      CLP equal to 0 traffic with cell discard; parameter 3 represents the 
      MBS for CLP equal to 0 traffic. Parameters 1, 2 and 3 must be non-
      zero. Parameter 1 must be greater than or equal to parameter 2. 
      
      When rxTrafficDescType is 8, parameter 1 represents the PCR for 
      CLP equal to 0 and 1 traffic; parameter 2 represents the SCR for 
      CLP equal to 0 traffic with cell tagging; parameter 3 represents the 
      MBS for CLP equal to 0 traffic. Parameter 1, 2 and 3 must be non-
      zero. Parameter 1 must be greater than or equal to parameter 2.
      
      When rxTrafficDescType is 9, parameter 1 represents the PCR; 
      parameter 2 represents the CDVT; parameter 3 represents the MCR. 
      Parameter 4 is not used and must be zero. Parameter 1,must be non-
      zero and must be greater than or equal to parameter 3. Parameter 3 
      may optionally be zero.
      
      When rxTrafficDescType is any value from 3 through 8, parameter 
      4 represents the CDVT. 
      
      If the value of CDVT either in parameter 2 or in parameter 4 is zero, 
      the CDVT is taken from the CA defaults for the particular 
      atmServiceCategory of this connection.
      
      On a CQC-based ATM card, when rxTrafficDescriptorType is 3 
      through 8, there are certain extreme combinations of 
      rxTrafficDescParm which are outside the capabilities of the UPC 
      hardware. The check prov command detects such cases and 
      generates an error message. If this happens, adjust the parameters 
      until they fall within the supported limits. 
      
      To calculate the limits, use the following formulae:
      I1 = 1 000 000 000 / PCR
      L1 = CDVT * 1000
      I2 = 1,000,000,000 / SCR
      L2 = CDVT + (MBS - 1) * (I2 - I1)
      I1 and I2 must be less than or equal to 335,523,840. I1 + L1 must 
      be less than or equal to 1,342,156,800. I2 + L2 must be less than or 
      equal to 1,342,156,800. Note that I2 and L2 only apply when the 
      rxTrafficDescriptorType is 6 through 8.
      
      If the values of I1, L1, I2 or L2 are closer to the limits described 
      above, a further restriction applies. Specifically, if either:
      I1 > 41,940,480 or
      I2 > 41,940,480 or
      I1 + L1 > 167,769,600 or
      I2 + L2 > 167,769,600
      then both I1 and I2 must be greater than 20,480. 
      
      Parameter 5 of the rxTrafficDescParm is always unused. 
      
      If the rxTrafficDescType is sameAsTx, the values provisioned in 
      this attribute are ignored. The traffic parameters for the receive 
      direction are taken from the txTrafficDescParm."
::= { mscAtmIfVptVpdTm 457 }

mscAtmIfVptVpdTmRxTdpEntry OBJECT-TYPE
   SYNTAX     MscAtmIfVptVpdTmRxTdpEntry
   ACCESS     not-accessible
   STATUS     mandatory
   DESCRIPTION
     "An entry in the mscAtmIfVptVpdTmRxTdpTable."
   INDEX {
      mscAtmIfIndex,
      mscAtmIfVptIndex,
      mscAtmIfVptVpdIndex,
      mscAtmIfVptVpdTmIndex,
      mscAtmIfVptVpdTmRxTdpIndex }
::= { mscAtmIfVptVpdTmRxTdpTable 1 }

MscAtmIfVptVpdTmRxTdpEntry ::= SEQUENCE {
   mscAtmIfVptVpdTmRxTdpIndex
      Integer32,
   mscAtmIfVptVpdTmRxTdpValue
      Unsigned32 }

mscAtmIfVptVpdTmRxTdpIndex OBJECT-TYPE
   SYNTAX     Integer32 (1..5)
   ACCESS     not-accessible
   STATUS     mandatory
   DESCRIPTION
     "This variable represents the mscAtmIfVptVpdTmRxTdpTable
      specific index for the mscAtmIfVptVpdTmRxTdpTable."
::= { mscAtmIfVptVpdTmRxTdpEntry 1 }

mscAtmIfVptVpdTmRxTdpValue OBJECT-TYPE
   SYNTAX     Unsigned32 (0..2147483647)
   ACCESS     read-write
   STATUS     mandatory
   DESCRIPTION
     "This variable represents an individual value for the
      mscAtmIfVptVpdTmRxTdpTable."
::= { mscAtmIfVptVpdTmRxTdpEntry 2 }

mscAtmIfVptVpdTmFqpTable OBJECT-TYPE
   SYNTAX     SEQUENCE OF MscAtmIfVptVpdTmFqpEntry
   ACCESS     not-accessible
   STATUS     mandatory
   DESCRIPTION
     "This attribute is a vector of three elements that specify the quality of 
      service parameters for the forward direction for this connection. 
      This attribute is used for SPVC connections.
      
      The cdv element specifies the acceptable peak-to-peak Cell Delay 
      Variation (CDV) of real-time connections (CBR and rt-VBR). It is 
      signalled through the extended QoS information element.
      
      The ctd specifies the acceptable maximum Cell Transfer Delay 
      (maxCtd) of real-time connections (CBR and rt-VBR). 
      It is signalled through the end to end transit delay information 
      element.
      
      The clr specifies the acceptable Cell Loss Ratio (CLR) of CBR, rt-
      VBR, and nrt-VBR connections. It is signalled through the extended 
      QoS information element."
::= { mscAtmIfVptVpdTm 458 }

mscAtmIfVptVpdTmFqpEntry OBJECT-TYPE
   SYNTAX     MscAtmIfVptVpdTmFqpEntry
   ACCESS     not-accessible
   STATUS     mandatory
   DESCRIPTION
     "An entry in the mscAtmIfVptVpdTmFqpTable."
   INDEX {
      mscAtmIfIndex,
      mscAtmIfVptIndex,
      mscAtmIfVptVpdIndex,
      mscAtmIfVptVpdTmIndex,
      mscAtmIfVptVpdTmFqpIndex }
::= { mscAtmIfVptVpdTmFqpTable 1 }

MscAtmIfVptVpdTmFqpEntry ::= SEQUENCE {
   mscAtmIfVptVpdTmFqpIndex
      INTEGER,
   mscAtmIfVptVpdTmFqpValue
      Unsigned32 }

mscAtmIfVptVpdTmFqpIndex OBJECT-TYPE
   SYNTAX     INTEGER  {
                 cdv(0),
                 ctd(1),
                 clr(2) }
   ACCESS     not-accessible
   STATUS     mandatory
   DESCRIPTION
     "This variable represents the mscAtmIfVptVpdTmFqpTable
      specific index for the mscAtmIfVptVpdTmFqpTable."
::= { mscAtmIfVptVpdTmFqpEntry 1 }

mscAtmIfVptVpdTmFqpValue OBJECT-TYPE
   SYNTAX     Unsigned32 (0..2147483647)
   ACCESS     read-write
   STATUS     mandatory
   DESCRIPTION
     "This variable represents an individual value for the
      mscAtmIfVptVpdTmFqpTable."
::= { mscAtmIfVptVpdTmFqpEntry 2 }

mscAtmIfVptVpdTmBqpTable OBJECT-TYPE
   SYNTAX     SEQUENCE OF MscAtmIfVptVpdTmBqpEntry
   ACCESS     not-accessible
   STATUS     mandatory
   DESCRIPTION
     "This attribute is a vector of three elements that specify the quality of 
      service parameters for the backward direction for this connection. 
      This attribute is used for SPVC connections.
      
      The cdv element specifies the acceptable peak-to-peak Cell Delay 
      Variation (CDV) of real-time connections (CBR and rt-VBR).
      It is signalled through the extended QoS information element.
      
      The ctd specifies the acceptable maximum Cell Transfer Delay 
      (maxCtd) of real-time connections (CBR and rt-VBR). It is 
      signalled through the end to end transit delay information element.
      
      The clr specifies the acceptable Cell Loss Ratio (CLR) of CBR, rt-
      VBR, and nrt-VBR connections. It is signalled through the extended 
      QoS information element."
::= { mscAtmIfVptVpdTm 459 }

mscAtmIfVptVpdTmBqpEntry OBJECT-TYPE
   SYNTAX     MscAtmIfVptVpdTmBqpEntry
   ACCESS     not-accessible
   STATUS     mandatory
   DESCRIPTION
     "An entry in the mscAtmIfVptVpdTmBqpTable."
   INDEX {
      mscAtmIfIndex,
      mscAtmIfVptIndex,
      mscAtmIfVptVpdIndex,
      mscAtmIfVptVpdTmIndex,
      mscAtmIfVptVpdTmBqpIndex }
::= { mscAtmIfVptVpdTmBqpTable 1 }

MscAtmIfVptVpdTmBqpEntry ::= SEQUENCE {
   mscAtmIfVptVpdTmBqpIndex
      INTEGER,
   mscAtmIfVptVpdTmBqpValue
      Unsigned32 }

mscAtmIfVptVpdTmBqpIndex OBJECT-TYPE
   SYNTAX     INTEGER  {
                 cdv(0),
                 ctd(1),
                 clr(2) }
   ACCESS     not-accessible
   STATUS     mandatory
   DESCRIPTION
     "This variable represents the mscAtmIfVptVpdTmBqpTable
      specific index for the mscAtmIfVptVpdTmBqpTable."
::= { mscAtmIfVptVpdTmBqpEntry 1 }

mscAtmIfVptVpdTmBqpValue OBJECT-TYPE
   SYNTAX     Unsigned32 (0..2147483647)
   ACCESS     read-write
   STATUS     mandatory
   DESCRIPTION
     "This variable represents an individual value for the
      mscAtmIfVptVpdTmBqpTable."
::= { mscAtmIfVptVpdTmBqpEntry 2 }


-- AtmIf/n Vcc/vpi.vci Vcd Tm AvailableBitRate, 
-- AtmIf/n Vpc/vci Vpd Tm AvailableBitRate,
-- AtmIf/n Vpt/vpi Vpd Tm AvailableBitRate,
-- AtmIf/n Vpt/vpi Vcc/vci Vcd Tm AvailableBitRate
-- This component contains provisioned ABR-related attributes of a 
-- connection. It is an optional subcomponent of the Vcd Tm and Vpd 
-- Tm component. It is used to override DGCRA-related defaults in 
-- the CA Abr component. It contains the specific configuration for the 
-- ABR connection at this connection point. If this is the source of an 
-- SPVC connection, this component also contains the ABR 
-- parameters required for the SPVC call request.

mscAtmIfVptVpdTmAbr OBJECT IDENTIFIER ::= { mscAtmIfVptVpdTm 2 }



mscAtmIfVptVpdTmAbrRowStatusTable OBJECT-TYPE
   SYNTAX     SEQUENCE OF MscAtmIfVptVpdTmAbrRowStatusEntry
   ACCESS     not-accessible
   STATUS     mandatory
   DESCRIPTION
     "This entry controls the addition and deletion of 
      mscAtmIfVptVpdTmAbr components."
::= { mscAtmIfVptVpdTmAbr 1 }

mscAtmIfVptVpdTmAbrRowStatusEntry OBJECT-TYPE
   SYNTAX     MscAtmIfVptVpdTmAbrRowStatusEntry
   ACCESS     not-accessible
   STATUS     mandatory
   DESCRIPTION
     "A single entry in the table represents a single 
      mscAtmIfVptVpdTmAbr component."
   INDEX {
      mscAtmIfIndex,
      mscAtmIfVptIndex,
      mscAtmIfVptVpdIndex,
      mscAtmIfVptVpdTmIndex,
      mscAtmIfVptVpdTmAbrIndex }
::= { mscAtmIfVptVpdTmAbrRowStatusTable 1 }

MscAtmIfVptVpdTmAbrRowStatusEntry ::= SEQUENCE {
   mscAtmIfVptVpdTmAbrRowStatus
      RowStatus,
   mscAtmIfVptVpdTmAbrComponentName
      DisplayString,
   mscAtmIfVptVpdTmAbrStorageType
      StorageType,
   mscAtmIfVptVpdTmAbrIndex
      NonReplicated }

mscAtmIfVptVpdTmAbrRowStatus OBJECT-TYPE
   SYNTAX     RowStatus 
   ACCESS     read-write
   STATUS     mandatory
   DESCRIPTION
     "This variable is used as the basis for SNMP naming of
      mscAtmIfVptVpdTmAbr components.
      These components can be added and deleted."
::= { mscAtmIfVptVpdTmAbrRowStatusEntry 1 }

mscAtmIfVptVpdTmAbrComponentName OBJECT-TYPE
   SYNTAX     DisplayString 
   ACCESS     read-only
   STATUS     mandatory
   DESCRIPTION
     "This variable provides the component's string name for
      use with the ASCII Console Interface"
::= { mscAtmIfVptVpdTmAbrRowStatusEntry 2 }

mscAtmIfVptVpdTmAbrStorageType OBJECT-TYPE
   SYNTAX     StorageType 
   ACCESS     read-only
   STATUS     mandatory
   DESCRIPTION
     "This variable represents the storage type value for the
      mscAtmIfVptVpdTmAbr tables."
::= { mscAtmIfVptVpdTmAbrRowStatusEntry 4 }

mscAtmIfVptVpdTmAbrIndex OBJECT-TYPE
   SYNTAX     NonReplicated 
   ACCESS     not-accessible
   STATUS     mandatory
   DESCRIPTION
     "This variable represents the index for the mscAtmIfVptVpdTmAbr tables."
::= { mscAtmIfVptVpdTmAbrRowStatusEntry 10 }

mscAtmIfVptVpdTmAbrProvTable OBJECT-TYPE
   SYNTAX     SEQUENCE OF MscAtmIfVptVpdTmAbrProvEntry
   ACCESS     not-accessible
   STATUS     mandatory
   DESCRIPTION
     "This group contains provisioned attributes for the ABR ATM 
      connections configured on an ATM interface."
::= { mscAtmIfVptVpdTmAbr 110 }

mscAtmIfVptVpdTmAbrProvEntry OBJECT-TYPE
   SYNTAX     MscAtmIfVptVpdTmAbrProvEntry
   ACCESS     not-accessible
   STATUS     mandatory
   DESCRIPTION
     "An entry in the mscAtmIfVptVpdTmAbrProvTable."
   INDEX {
      mscAtmIfIndex,
      mscAtmIfVptIndex,
      mscAtmIfVptVpdIndex,
      mscAtmIfVptVpdTmIndex,
      mscAtmIfVptVpdTmAbrIndex }
::= { mscAtmIfVptVpdTmAbrProvTable 1 }

MscAtmIfVptVpdTmAbrProvEntry ::= SEQUENCE {
   mscAtmIfVptVpdTmAbrInitialCellRate
      Unsigned32,
   mscAtmIfVptVpdTmAbrTransientBufferExposure
      Unsigned32,
   mscAtmIfVptVpdTmAbrFixedRoundTripTime
      Unsigned32,
   mscAtmIfVptVpdTmAbrRateDecreaseFactor
      Unsigned32,
   mscAtmIfVptVpdTmAbrRateIncreaseFactor
      Unsigned32,
   mscAtmIfVptVpdTmAbrMaxCellPerRmCell
      Unsigned32,
   mscAtmIfVptVpdTmAbrMaxTimeBetweenRmCells
      Unsigned32,
   mscAtmIfVptVpdTmAbrCutoffDecreaseFactor
      Unsigned32,
   mscAtmIfVptVpdTmAbrAcrDecreaseTimeFactor
      Unsigned32,
   mscAtmIfVptVpdTmAbrDgcraMaximumDelay
      Unsigned32,
   mscAtmIfVptVpdTmAbrDgcraMinimumDelay
      Unsigned32,
   mscAtmIfVptVpdTmAbrFarEndAcrDecreaseTimeFactor
      Unsigned32,
   mscAtmIfVptVpdTmAbrFarEndInitialCellRate
      Unsigned32 }

mscAtmIfVptVpdTmAbrInitialCellRate OBJECT-TYPE
   SYNTAX     Unsigned32 (0..16777215 | 16777216 | 16777217 | 16777218)
   ACCESS     read-write
   STATUS     mandatory
   DESCRIPTION
     "This attribute specifies the Initial Cell Rate (ICR) parameter for this 
      connection. ICR is the rate at which a source should send initially 
      and after an idle period.
      
      When this attribute is set to sameAsCa, the initial cell rate is 
      determined by the AtmIf CA Abr/0 icr attribute. When the value of 
      this attribute is set to useMcr, ICR is set to the same value as the 
      Minimum Cell Rate (MCR) for the connection.
      
      When the value of this attribute is set to usePcr, ICR is set to the 
      same value as the Peak Cell Rate (PCR) for the connection.
      
      If this attribute is specified less than the MCR of the connection, 
      then the MCR is used as the ICR. If this attribute is specified more 
      than PCR of the connection, then PCR is used as the ICR.
      
      This attribute is ignored under all conditions where the operational 
      attribute abrConnectionType indicates erSwitch or efciSwitch.

      VALUES (

      16777216 = sameAsCa

      16777217 = useMcr

      16777218 = usePcr

      )"
   DEFVAL     { 16777216 }
::= { mscAtmIfVptVpdTmAbrProvEntry 10 }

mscAtmIfVptVpdTmAbrTransientBufferExposure OBJECT-TYPE
   SYNTAX     Unsigned32 (0..16777215)
   ACCESS     read-write
   STATUS     mandatory
   DESCRIPTION
     "This attribute specifies the Transient Buffer Exposure (TBE) for this 
      connection. TBE is the negotiated number of cells that the network 
      would like to limit the source to send during start-up periods, before 
      the first Resource Management (RM) cell returns.
      
      TBE divided by fixedRoundTripTime determines an upper bound 
      for the operational value of initialCellRate, the rate at which a 
      source should send initially and after an idle period.
      
      TBE divided by maxCellsPerRmCell specifies the operational value 
      of forwardRmCellLimit, the limit of the number of forward 
      Resource Management (RM) cells which may be sent in the 
      absence of received backward RM cells.
      
      This attribute is ignored under all conditions where the operational 
      attribute abrConnectionType is set to erSwitch."
   DEFVAL     { 16777215 }
::= { mscAtmIfVptVpdTmAbrProvEntry 11 }

mscAtmIfVptVpdTmAbrFixedRoundTripTime OBJECT-TYPE
   SYNTAX     Unsigned32 (0..16700000)
   ACCESS     read-write
   STATUS     mandatory
   DESCRIPTION
     "This attribute specifies the Fixed Round-Trip Time (FRTT) 
      parameter for this connection. FRTT is the sum of the fixed and 
      propagation delays from the source to a destination and back.
      
      The value of transientBufferExposure divided by the value of FRTT 
      (in seconds) determines an upper bound for the operational value of 
      initialCellRate, the rate at which a source should send initially and 
      after an idle period.
      
      This attribute is ignored under all conditions where the operational 
      attribute abrConnectionType indicates erSwitch or efciSwitch."
   DEFVAL     { 5000000 }
::= { mscAtmIfVptVpdTmAbrProvEntry 12 }

mscAtmIfVptVpdTmAbrRateDecreaseFactor OBJECT-TYPE
   SYNTAX     Unsigned32 (0..15 | 16777216)
   ACCESS     read-write
   STATUS     mandatory
   DESCRIPTION
     "This attribute specifies the Rate Decrease Factor (RDF) for this 
      connection. The RDF value is computed by using the provisioned 
      value of this attribute, n, as 2 to the inverse power n. For example, if 
      the value of this attribute is 8, RDF is 2E-8 = 1/256.
      
      RDF controls the amount by which the cell transmission rate may 
      decrease upon receipt of a backward Resource Management (RM) 
      cell. For example, if a backward RM cell is received with the 
      Congestion Indication (CI) field set to 1, the Allowed Cell Rate 
      (ACR) value would be reduced by the amount (RDF*ACR). The 
      ACR is not allowed to fall below the Minimum Cell Rate (MCR), in 
      which case the ACR is set to MCR.
      
      This attribute is ignored under all conditions where the operational 
      attribute abrConnectionType has the value erSwitch.

      VALUES (

      16777216 = sameAsCa

      )"
   DEFVAL     { 16777216 }
::= { mscAtmIfVptVpdTmAbrProvEntry 13 }

mscAtmIfVptVpdTmAbrRateIncreaseFactor OBJECT-TYPE
   SYNTAX     Unsigned32 (0..15 | 16777216)
   ACCESS     read-write
   STATUS     mandatory
   DESCRIPTION
     "This attribute specifies the Rate Increase Factor (RIF) for this 
      connection. The RIF value is computed by using the provisioned 
      value of this attribute, n, as 2 to the inverse power n. For example, if 
      the value of this attribute is 6, RIF is 2E-6 = 1/64.
      
      RIF controls the amount by which the cell transmission rate may 
      increase upon receipt of a backward Resource Management (RM) 
      cell. For example, if a backward RM cell is received with the 
      Congestion Indication (CI) and the No Increase (NI) fields both set 
      to 0, the Allowed Cell Rate (ACR) value would be increased by the 
      amount (RIF*ACR). The ACR is not allowed to exceed the Peak 
      Cell Rate (PCR), in which case the ACR is set to PCR.
      
      This attribute is ignored under all conditions where the operational 
      attribute abrConnectionType has the value erSwitch.

      VALUES (

      16777216 = sameAsCa

      )"
   DEFVAL     { 16777216 }
::= { mscAtmIfVptVpdTmAbrProvEntry 14 }

mscAtmIfVptVpdTmAbrMaxCellPerRmCell OBJECT-TYPE
   SYNTAX     Unsigned32 (2 | 4 | 8 | 16 | 32 | 64 | 128 | 256 | 16777216)
   ACCESS     read-write
   STATUS     mandatory
   DESCRIPTION
     "This attribute specifies the maximum number of cells an ABR 
      source may transmit for each forward Resource Management (RM) 
      cell. The count of the cells transmitted includes data cells, OAM 
      cells, backward RM cells, and the forward RM cell.
      
      A value of 2 is not recommended although it is permitted according 
      to the ATM Forum standard. When this attribute is set to a value of 
      2, it is possible that only one forward and one backward RM cell 
      are repeatedly transmitted, and all data traffic is queued up 
      indefinitely.
      
      This attribute is ignored under all conditions where the operational 
      attribute abrConnectionType has the value erSwitch.

      VALUES (

      16777216 = sameAsCa

      )"
   DEFVAL     { 16777216 }
::= { mscAtmIfVptVpdTmAbrProvEntry 15 }

mscAtmIfVptVpdTmAbrMaxTimeBetweenRmCells OBJECT-TYPE
   SYNTAX     Unsigned32 (781 | 1563 | 3125 | 6250 | 12500 | 25000 | 50000 | 100000 | 16777216)
   ACCESS     read-write
   STATUS     mandatory
   DESCRIPTION
     "This attribute specifies the TRM parameter for this connection.
      
      TRM provides an lower bound on the time interval between forward 
      Resource Management (RM) cells for an ABR source. Since the last 
      forward RM cell was sent, if at least TRM time has elapsed since 
      and at least two other cells have been sent, then the next cell to be 
      transmitted would be a forward RM cell.
      
      This attribute is ignored under all conditions where the operational 
      attribute abrConnectionType has the value erSwitch.
      
      The provisioned value of 781 is signalled as TRM = 0, in the ABR 
      Additional Parameters Information Element. 
      1563 is signalled as TRM = 1. 
      3125 is signalled as TRM = 2. 
      6250 is signalled as TRM = 3. 
      12500 is signalled as TRM = 4 
      25000 is signalled as TRM = 5. 
      50000 is signalled as TRM = 6. 
      100000 is signalled as TRM = 7.

      VALUES (

      16777216 = sameAsCa

      )"
   DEFVAL     { 16777216 }
::= { mscAtmIfVptVpdTmAbrProvEntry 16 }

mscAtmIfVptVpdTmAbrCutoffDecreaseFactor OBJECT-TYPE
   SYNTAX     Unsigned32 (0 | 1 | 2 | 4 | 8 | 16 | 32 | 64 | 16777216)
   ACCESS     read-write
   STATUS     mandatory
   DESCRIPTION
     "This attribute specifies the Cutoff Decrease Factor (CDF) parameter 
      for this connection. When the value of this attribute is non-zero, 
      CDF is computed as the inverse of the value. For example, if the 
      value is 32, the value of CDF is 1/32. When the value of this 
      attribute is 0, CDF is also zero.
      
      CDF controls the decrease in the Allowed Cell Rate (ACR) 
      associated with the CRM parameter, the limit of the number of 
      forward Resource Management (RM) cells which may be sent in 
      the absence of received backward RM cells. When this limit is 
      crossed, the ACR value would be decreased by the amount 
      (CDF*ACR). The ACR is not allowed to fall below the Minimum 
      Cell Rate (MCR), in which case the ACR is set to MCR.
      
      The value of CRM is indicated by the forwardRmCellLimit 
      attribute.
      
      This attribute is ignored under all conditions where the operational 
      attribute abrConnectionType indicates erSwitch or efciSwitch.

      VALUES (

      16777216 = sameAsCa

      )"
   DEFVAL     { 16777216 }
::= { mscAtmIfVptVpdTmAbrProvEntry 17 }

mscAtmIfVptVpdTmAbrAcrDecreaseTimeFactor OBJECT-TYPE
   SYNTAX     Unsigned32 (0..1023 | 16777216)
   ACCESS     read-write
   STATUS     mandatory
   DESCRIPTION
     "This attribute specifies the Allowed Cell Rate Decrease Time Factor 
      (ADTF) parameter for this connection.
      
      ADTF is the maximum time interval permitted between sending 
      forward Resource Management (RM) cells before the Allowed Cell 
      Rate (ACR) is decreased to initialCellRate. In other words, if the 
      source does not transit a forward RM cell for the period specified by 
      adtf, it reduces its ACR to the value of its initialCellRate.
      
      This attribute is ignored under all conditions where the operational 
      attribute abrConnectionType indicates erSwitch or efciSwitch.

      VALUES (

      16777216 = sameAsCa

      )"
   DEFVAL     { 16777216 }
::= { mscAtmIfVptVpdTmAbrProvEntry 18 }

mscAtmIfVptVpdTmAbrDgcraMaximumDelay OBJECT-TYPE
   SYNTAX     Unsigned32 (1..16700000 | 16777216)
   ACCESS     read-write
   STATUS     mandatory
   DESCRIPTION
     "This attribute specifies an upper bound on the delay after which the 
      rate change induced by a backward Resource Management (RM) 
      cell departing from this connection point (in the backward 
      direction) is expected to be observed at this connection point (in the 
      forward direction).
      
      This upper bound may be approximated as the sum of the round trip 
      fixed and propagation delays and the maximum queuing delays 
      between the ABR source and this interface.
      
      The value of this attribute is used in policing an ABR connection 
      using the Dynamic General Cell Rate Algorithm (DGCRA). A 
      larger value for this attribute implies a more lenient policer. When 
      there is a reduction in the Allowed Cell Rate (ACR), the policer 
      waits for a correspondingly longer period of time before it enforces 
      at the new cell rate.
      
      The value of this attribute must not be less than the 
      dgcraMinimumDelay attribute.

      VALUES (

      16777216 = sameAsCa

      )"
   DEFVAL     { 16777216 }
::= { mscAtmIfVptVpdTmAbrProvEntry 19 }

mscAtmIfVptVpdTmAbrDgcraMinimumDelay OBJECT-TYPE
   SYNTAX     Unsigned32 (1..16700000 | 16777216)
   ACCESS     read-write
   STATUS     mandatory
   DESCRIPTION
     "This attribute specifies a lower bound on the delay after which the 
      rate change induced by a backward Resource Management (RM) 
      cell departing from this connection point (in the backward 
      direction) is expected to be observed at this connection point (in the 
      forward connection).
      
      This lower bound may be approximated as the sum of the round trip 
      fixed and propagation delays between the ABR source and this 
      interface.
      
      The value of this attribute is used in policing an ABR connection 
      using the Dynamic General Cell Rate Algorithm (DGCRA). A 
      smaller value for this attribute implies a more lenient policer. When 
      there is a increase in the Allowed Cell Rate (ACR), the policer waits 
      for a correspondingly shorter period of time before it enforces at the 
      new cell rate.

      VALUES (

      16777216 = sameAsCa

      )"
   DEFVAL     { 16777216 }
::= { mscAtmIfVptVpdTmAbrProvEntry 20 }

mscAtmIfVptVpdTmAbrFarEndAcrDecreaseTimeFactor OBJECT-TYPE
   SYNTAX     Unsigned32 (0..1023)
   ACCESS     read-write
   STATUS     mandatory
   DESCRIPTION
     "This attribute specifies the Allowed Cell Rate Decrease Time Factor 
      (ADTF) of the far end ABR source. The value specified should be 
      the same as the ADTF parameter at the far end of this ABR 
      connection. 
      
      The value of this attribute is used in policing an ABR connection 
      using the Dynamic Generic Cell Rate Algorithm (DGCRA). A 
      larger value for this attribute implies a more lenient policer. When 
      the delay between two consecutive forward Resource Management 
      (RM) cells received at this interface corresponds to a value greater 
      than the value of this attribute, the policer begins to limit enforce 
      the incoming traffic at the initial cell rate (ICR) of the far end, as 
      specified by the farEndInitialCellRate attribute."
   DEFVAL     { 50 }
::= { mscAtmIfVptVpdTmAbrProvEntry 21 }

mscAtmIfVptVpdTmAbrFarEndInitialCellRate OBJECT-TYPE
   SYNTAX     Unsigned32 (0..16777215)
   ACCESS     read-write
   STATUS     mandatory
   DESCRIPTION
     "This attribute specifies the Initial Cell Rate (ICR) of the far end 
      ABR source. The value specified should be the same as the ICR 
      parameter at the far end of this ABR connection. 
      
      The value of this attribute is used in policing an ABR connection 
      using the Dynamic Generic Cell Rate Algorithm (DGCRA). A 
      larger value for this attribute implies a more lenient policer. When 
      the delay between two consecutive forward Resource Management 
      (RM) cells received at this interface corresponds to a value greater 
      than the farEndAcrDecreaseTimeFactor attribute, the policer begins 
      to enforce the incoming traffic at the value of this attribute.
      
      If this attribute is specified less than the MCR of the connection, 
      then the MCR is used as the feIcr. If this attribute is more than the 
      PCR of the connection, then PCR is used as the feIcr."
   DEFVAL     { 0 }
::= { mscAtmIfVptVpdTmAbrProvEntry 22 }


-- AtmIf/n Vpt/n ConnectionAdministrator 
-- This component controls connection admission, and reports 
-- statistics about the ATM connections which have been admitted on 
-- this Virtual Path Terminator (VPT).
-- 
-- If the VPT does not have the optional CA component, all 
-- connections associated with the given VPT attempt their admission 
-- through the AtmIf CA.
-- 
-- The provisionable attributes of this ConnectionAdministrator 
-- override those of the AtmIf CA, for all connections associated with 
-- this Vpt. Any attributes of the AtmIf CA that cannot be overridden in 
-- the Vpt CA affect all connections, including Vpt Vccs.

mscAtmIfVptCA OBJECT IDENTIFIER ::= { mscAtmIfVpt 5 }



mscAtmIfVptCARowStatusTable OBJECT-TYPE
   SYNTAX     SEQUENCE OF MscAtmIfVptCARowStatusEntry
   ACCESS     not-accessible
   STATUS     mandatory
   DESCRIPTION
     "This entry controls the addition and deletion of 
      mscAtmIfVptCA components."
::= { mscAtmIfVptCA 1 }

mscAtmIfVptCARowStatusEntry OBJECT-TYPE
   SYNTAX     MscAtmIfVptCARowStatusEntry
   ACCESS     not-accessible
   STATUS     mandatory
   DESCRIPTION
     "A single entry in the table represents a single 
      mscAtmIfVptCA component."
   INDEX {
      mscAtmIfIndex,
      mscAtmIfVptIndex,
      mscAtmIfVptCAIndex }
::= { mscAtmIfVptCARowStatusTable 1 }

MscAtmIfVptCARowStatusEntry ::= SEQUENCE {
   mscAtmIfVptCARowStatus
      RowStatus,
   mscAtmIfVptCAComponentName
      DisplayString,
   mscAtmIfVptCAStorageType
      StorageType,
   mscAtmIfVptCAIndex
      NonReplicated }

mscAtmIfVptCARowStatus OBJECT-TYPE
   SYNTAX     RowStatus 
   ACCESS     read-write
   STATUS     mandatory
   DESCRIPTION
     "This variable is used as the basis for SNMP naming of
      mscAtmIfVptCA components.
      These components can be added and deleted."
::= { mscAtmIfVptCARowStatusEntry 1 }

mscAtmIfVptCAComponentName OBJECT-TYPE
   SYNTAX     DisplayString 
   ACCESS     read-only
   STATUS     mandatory
   DESCRIPTION
     "This variable provides the component's string name for
      use with the ASCII Console Interface"
::= { mscAtmIfVptCARowStatusEntry 2 }

mscAtmIfVptCAStorageType OBJECT-TYPE
   SYNTAX     StorageType 
   ACCESS     read-only
   STATUS     mandatory
   DESCRIPTION
     "This variable represents the storage type value for the
      mscAtmIfVptCA tables."
::= { mscAtmIfVptCARowStatusEntry 4 }

mscAtmIfVptCAIndex OBJECT-TYPE
   SYNTAX     NonReplicated 
   ACCESS     not-accessible
   STATUS     mandatory
   DESCRIPTION
     "This variable represents the index for the mscAtmIfVptCA tables."
::= { mscAtmIfVptCARowStatusEntry 10 }

mscAtmIfVptCAProvTable OBJECT-TYPE
   SYNTAX     SEQUENCE OF MscAtmIfVptCAProvEntry
   ACCESS     not-accessible
   STATUS     mandatory
   DESCRIPTION
     "This group contains provisioned attributes which control 
      Connection Admission Control (CAC) attributes for the ATM 
      connections associated with a Virtual Path Terminator. Note that the 
      names of some of the attributes follow the conventions of UNI 4.0 
      for forward compatibility reasons. This does not imply conformance 
      in general with the UNI 4.0 specification. 
      
      The provisioned attributes of this ConnectionAdministrator will 
      override those of the AtmIf CA, for all connections associated with 
      this Vpt. Any attributes of the AtmIf CA that cannot be overridden in 
      the Vpt CA affect all connections, including Vpt Vccs."
::= { mscAtmIfVptCA 100 }

mscAtmIfVptCAProvEntry OBJECT-TYPE
   SYNTAX     MscAtmIfVptCAProvEntry
   ACCESS     not-accessible
   STATUS     mandatory
   DESCRIPTION
     "An entry in the mscAtmIfVptCAProvTable."
   INDEX {
      mscAtmIfIndex,
      mscAtmIfVptIndex,
      mscAtmIfVptCAIndex }
::= { mscAtmIfVptCAProvTable 1 }

MscAtmIfVptCAProvEntry ::= SEQUENCE {
   mscAtmIfVptCAMaxVccs
      Unsigned32,
   mscAtmIfVptCAPermittedAtmServiceCategories
      OCTET STRING }

mscAtmIfVptCAMaxVccs OBJECT-TYPE
   SYNTAX     Unsigned32 (0..16384 | 65535)
   ACCESS     read-write
   STATUS     mandatory
   DESCRIPTION
     "This attribute specifies the maximum number of Vccs that can be 
      associated with this Vpt. The value must not exceed the maxVccs 
      attribute of the Atmif CA.
      
      If this attribute is set to autoConfigure, then on 32 port Multi-
      Service Access cards its value is configured as 100, and on all other 
      cards it is 255.

      VALUES (

      65535 = autoConfigure

      )"
   DEFVAL     { 65535 }
::= { mscAtmIfVptCAProvEntry 6 }

mscAtmIfVptCAPermittedAtmServiceCategories OBJECT-TYPE
   SYNTAX     OCTET STRING (SIZE (1))
   ACCESS     read-write
   STATUS     mandatory
   DESCRIPTION
     "This attribute specifies which ATM service categories are permitted 
      on this Vpt for SVCs. The value of this attribute does not affect 
      control Vccs, such as signalling and ILMI channels. If the value is 
      empty, no SVCs are permitted to use this Vpt.

      Description of bits:
      unspecifiedBitRate(0)
      constantBitRate(1)
      rtVariableBitRate(2)
      nrtVariableBitRate(3)"
   DEFVAL     { 'f0'H }
::= { mscAtmIfVptCAProvEntry 25 }

mscAtmIfVptCAOperTable OBJECT-TYPE
   SYNTAX     SEQUENCE OF MscAtmIfVptCAOperEntry
   ACCESS     not-accessible
   STATUS     mandatory
   DESCRIPTION
     "This group contains operational attributes giving statistics about the 
      ATM connections associated with a Virtual Path Terminator (VPT)."
::= { mscAtmIfVptCA 110 }

mscAtmIfVptCAOperEntry OBJECT-TYPE
   SYNTAX     MscAtmIfVptCAOperEntry
   ACCESS     not-accessible
   STATUS     mandatory
   DESCRIPTION
     "An entry in the mscAtmIfVptCAOperTable."
   INDEX {
      mscAtmIfIndex,
      mscAtmIfVptIndex,
      mscAtmIfVptCAIndex }
::= { mscAtmIfVptCAOperTable 1 }

MscAtmIfVptCAOperEntry ::= SEQUENCE {
   mscAtmIfVptCAActualMaxVccs
      Unsigned32,
   mscAtmIfVptCAPermanentVccs
      Unsigned32,
   mscAtmIfVptCASwitchedVccs
      Gauge32,
   mscAtmIfVptCATroubledVccs
      Unsigned32,
   mscAtmIfVptCAConnectionPoolUsage
      Gauge32 }

mscAtmIfVptCAActualMaxVccs OBJECT-TYPE
   SYNTAX     Unsigned32 (0..16384)
   ACCESS     read-only
   STATUS     mandatory
   DESCRIPTION
     "This attribute indicates the maximum number of VCC connections 
      that can be supported on this Vpt. The value includes both 
      provisioned and dynamic connections. The value is determined 
      from the provisioned attribute maxVccs."
::= { mscAtmIfVptCAOperEntry 6 }

mscAtmIfVptCAPermanentVccs OBJECT-TYPE
   SYNTAX     Unsigned32 (0..16384)
   ACCESS     read-only
   STATUS     mandatory
   DESCRIPTION
     "This attribute indicates the number of permanent Vccs that are 
      currently associated with this Vpt."
::= { mscAtmIfVptCAOperEntry 20 }

mscAtmIfVptCASwitchedVccs OBJECT-TYPE
   SYNTAX     Gauge32 (0..16384)
   ACCESS     read-only
   STATUS     mandatory
   DESCRIPTION
     "This attribute indicates the number of switched Vccs that are 
      currently associated with this Vpt."
::= { mscAtmIfVptCAOperEntry 30 }

mscAtmIfVptCATroubledVccs OBJECT-TYPE
   SYNTAX     Unsigned32 (0..16384)
   ACCESS     read-only
   STATUS     mandatory
   DESCRIPTION
     "This attribute indicates the number of troubled Vccs associated with 
      this Vpt. A Vcc is 'troubled' if its operational troubled attribute has 
      the value yes."
::= { mscAtmIfVptCAOperEntry 70 }

mscAtmIfVptCAConnectionPoolUsage OBJECT-TYPE
   SYNTAX     Gauge32 (0..10752)
   ACCESS     read-only
   STATUS     mandatory
   DESCRIPTION
     "This attribute indicates the number of allocated VCCs associated 
      with this VPT.
      
      Each of these VCCs uses a connection out of the pool defined by 
      the Arc totalConnectionPoolAvailable attribute."
::= { mscAtmIfVptCAOperEntry 81 }

mscAtmIfVptCAPoolAvailBwTable OBJECT-TYPE
   SYNTAX     SEQUENCE OF MscAtmIfVptCAPoolAvailBwEntry
   ACCESS     not-accessible
   STATUS     mandatory
   DESCRIPTION
     "This attribute indicates the total available bandwidth in the 
      corresponding bandwidthPool. A non-zero number indicates that 
      there is still bandwidth available in the pool which has not been 
      allocated."
::= { mscAtmIfVptCA 460 }

mscAtmIfVptCAPoolAvailBwEntry OBJECT-TYPE
   SYNTAX     MscAtmIfVptCAPoolAvailBwEntry
   ACCESS     not-accessible
   STATUS     mandatory
   DESCRIPTION
     "An entry in the mscAtmIfVptCAPoolAvailBwTable."
   INDEX {
      mscAtmIfIndex,
      mscAtmIfVptIndex,
      mscAtmIfVptCAIndex,
      mscAtmIfVptCAPoolAvailBwIndex }
::= { mscAtmIfVptCAPoolAvailBwTable 1 }

MscAtmIfVptCAPoolAvailBwEntry ::= SEQUENCE {
   mscAtmIfVptCAPoolAvailBwIndex
      Integer32,
   mscAtmIfVptCAPoolAvailBwValue
      INTEGER }

mscAtmIfVptCAPoolAvailBwIndex OBJECT-TYPE
   SYNTAX     Integer32 (1..5)
   ACCESS     not-accessible
   STATUS     mandatory
   DESCRIPTION
     "This variable represents the mscAtmIfVptCAPoolAvailBwTable
      specific index for the mscAtmIfVptCAPoolAvailBwTable."
::= { mscAtmIfVptCAPoolAvailBwEntry 1 }

mscAtmIfVptCAPoolAvailBwValue OBJECT-TYPE
   SYNTAX     INTEGER (0..2147483647)
   ACCESS     read-only
   STATUS     mandatory
   DESCRIPTION
     "This variable represents an individual value for the
      mscAtmIfVptCAPoolAvailBwTable."
::= { mscAtmIfVptCAPoolAvailBwEntry 2 }

mscAtmIfVptCABwPoolTable OBJECT-TYPE
   SYNTAX     SEQUENCE OF MscAtmIfVptCABwPoolEntry
   ACCESS     not-accessible
   STATUS     mandatory
   DESCRIPTION
     "Total bandwidth capacity is partitioned into five bandwidth pools. 
      This attribute specifies the percentage of Vpt bandwidth that is 
      allowed for each pool. The percentage for each pool ranges from 
      0% to 12,800%. This allows for both under and over subscription of 
      the VPT bandwidth. Under subscription occurs when the sum of the 
      percentages assigned to the five pools is less than 100%. Over 
      subscription occurs when the sum of the percentages for the five 
      pools exceeds 100%."
::= { mscAtmIfVptCA 461 }

mscAtmIfVptCABwPoolEntry OBJECT-TYPE
   SYNTAX     MscAtmIfVptCABwPoolEntry
   ACCESS     not-accessible
   STATUS     mandatory
   DESCRIPTION
     "An entry in the mscAtmIfVptCABwPoolTable."
   INDEX {
      mscAtmIfIndex,
      mscAtmIfVptIndex,
      mscAtmIfVptCAIndex,
      mscAtmIfVptCABwPoolIndex }
::= { mscAtmIfVptCABwPoolTable 1 }

MscAtmIfVptCABwPoolEntry ::= SEQUENCE {
   mscAtmIfVptCABwPoolIndex
      Integer32,
   mscAtmIfVptCABwPoolValue
      Unsigned32 }

mscAtmIfVptCABwPoolIndex OBJECT-TYPE
   SYNTAX     Integer32 (1..5)
   ACCESS     not-accessible
   STATUS     mandatory
   DESCRIPTION
     "This variable represents the mscAtmIfVptCABwPoolTable
      specific index for the mscAtmIfVptCABwPoolTable."
::= { mscAtmIfVptCABwPoolEntry 1 }

mscAtmIfVptCABwPoolValue OBJECT-TYPE
   SYNTAX     Unsigned32 (0..12800)
   ACCESS     read-write
   STATUS     mandatory
   DESCRIPTION
     "This variable represents an individual value for the
      mscAtmIfVptCABwPoolTable."
::= { mscAtmIfVptCABwPoolEntry 2 }

mscAtmIfVptCAPoolProvBwTable OBJECT-TYPE
   SYNTAX     SEQUENCE OF MscAtmIfVptCAPoolProvBwEntry
   ACCESS     not-accessible
   STATUS     mandatory
   DESCRIPTION
     "This attribute indicates the total provisioned bandwidth from the 
      corresponding bandwidthPool. Its value is the sum of the equivalent 
      cell rates (ECR) of the provisioned connections."
::= { mscAtmIfVptCA 462 }

mscAtmIfVptCAPoolProvBwEntry OBJECT-TYPE
   SYNTAX     MscAtmIfVptCAPoolProvBwEntry
   ACCESS     not-accessible
   STATUS     mandatory
   DESCRIPTION
     "An entry in the mscAtmIfVptCAPoolProvBwTable."
   INDEX {
      mscAtmIfIndex,
      mscAtmIfVptIndex,
      mscAtmIfVptCAIndex,
      mscAtmIfVptCAPoolProvBwIndex }
::= { mscAtmIfVptCAPoolProvBwTable 1 }

MscAtmIfVptCAPoolProvBwEntry ::= SEQUENCE {
   mscAtmIfVptCAPoolProvBwIndex
      Integer32,
   mscAtmIfVptCAPoolProvBwValue
      Gauge32 }

mscAtmIfVptCAPoolProvBwIndex OBJECT-TYPE
   SYNTAX     Integer32 (1..5)
   ACCESS     not-accessible
   STATUS     mandatory
   DESCRIPTION
     "This variable represents the mscAtmIfVptCAPoolProvBwTable
      specific index for the mscAtmIfVptCAPoolProvBwTable."
::= { mscAtmIfVptCAPoolProvBwEntry 1 }

mscAtmIfVptCAPoolProvBwValue OBJECT-TYPE
   SYNTAX     Gauge32 (0..2147483647)
   ACCESS     read-only
   STATUS     mandatory
   DESCRIPTION
     "This variable represents an individual value for the
      mscAtmIfVptCAPoolProvBwTable."
::= { mscAtmIfVptCAPoolProvBwEntry 2 }

mscAtmIfVptCAPoolRequBwTable OBJECT-TYPE
   SYNTAX     SEQUENCE OF MscAtmIfVptCAPoolRequBwEntry
   ACCESS     not-accessible
   STATUS     mandatory
   DESCRIPTION
     "This attribute indicates the total requested bandwidth from the 
      corresponding bandwidthPool. This attribute does not include the 
      bandwidth for ATM networking signalling connections. Its value is 
      the sum of the equivalent cell rates (ECR) for connections which 
      are admitted and connections which are requesting admission, but 
      have not yet been admitted."
::= { mscAtmIfVptCA 463 }

mscAtmIfVptCAPoolRequBwEntry OBJECT-TYPE
   SYNTAX     MscAtmIfVptCAPoolRequBwEntry
   ACCESS     not-accessible
   STATUS     mandatory
   DESCRIPTION
     "An entry in the mscAtmIfVptCAPoolRequBwTable."
   INDEX {
      mscAtmIfIndex,
      mscAtmIfVptIndex,
      mscAtmIfVptCAIndex,
      mscAtmIfVptCAPoolRequBwIndex }
::= { mscAtmIfVptCAPoolRequBwTable 1 }

MscAtmIfVptCAPoolRequBwEntry ::= SEQUENCE {
   mscAtmIfVptCAPoolRequBwIndex
      Integer32,
   mscAtmIfVptCAPoolRequBwValue
      Gauge32 }

mscAtmIfVptCAPoolRequBwIndex OBJECT-TYPE
   SYNTAX     Integer32 (1..5)
   ACCESS     not-accessible
   STATUS     mandatory
   DESCRIPTION
     "This variable represents the mscAtmIfVptCAPoolRequBwTable
      specific index for the mscAtmIfVptCAPoolRequBwTable."
::= { mscAtmIfVptCAPoolRequBwEntry 1 }

mscAtmIfVptCAPoolRequBwValue OBJECT-TYPE
   SYNTAX     Gauge32 (0..2147483647)
   ACCESS     read-only
   STATUS     mandatory
   DESCRIPTION
     "This variable represents an individual value for the
      mscAtmIfVptCAPoolRequBwTable."
::= { mscAtmIfVptCAPoolRequBwEntry 2 }

mscAtmIfVptCAPoolAdmitBwTable OBJECT-TYPE
   SYNTAX     SEQUENCE OF MscAtmIfVptCAPoolAdmitBwEntry
   ACCESS     not-accessible
   STATUS     mandatory
   DESCRIPTION
     "This attribute indicates the total admitted bandwidth in the 
      corresponding bandwidthPool. Its value is the sum of the equivalent 
      cell rates (ECR) of the admitted connections. This attribute does not 
      include the bandwidth for ATM networking signalling connections."
::= { mscAtmIfVptCA 464 }

mscAtmIfVptCAPoolAdmitBwEntry OBJECT-TYPE
   SYNTAX     MscAtmIfVptCAPoolAdmitBwEntry
   ACCESS     not-accessible
   STATUS     mandatory
   DESCRIPTION
     "An entry in the mscAtmIfVptCAPoolAdmitBwTable."
   INDEX {
      mscAtmIfIndex,
      mscAtmIfVptIndex,
      mscAtmIfVptCAIndex,
      mscAtmIfVptCAPoolAdmitBwIndex }
::= { mscAtmIfVptCAPoolAdmitBwTable 1 }

MscAtmIfVptCAPoolAdmitBwEntry ::= SEQUENCE {
   mscAtmIfVptCAPoolAdmitBwIndex
      Integer32,
   mscAtmIfVptCAPoolAdmitBwValue
      Gauge32 }

mscAtmIfVptCAPoolAdmitBwIndex OBJECT-TYPE
   SYNTAX     Integer32 (1..5)
   ACCESS     not-accessible
   STATUS     mandatory
   DESCRIPTION
     "This variable represents the mscAtmIfVptCAPoolAdmitBwTable
      specific index for the mscAtmIfVptCAPoolAdmitBwTable."
::= { mscAtmIfVptCAPoolAdmitBwEntry 1 }

mscAtmIfVptCAPoolAdmitBwValue OBJECT-TYPE
   SYNTAX     Gauge32 (0..2147483647)
   ACCESS     read-only
   STATUS     mandatory
   DESCRIPTION
     "This variable represents an individual value for the
      mscAtmIfVptCAPoolAdmitBwTable."
::= { mscAtmIfVptCAPoolAdmitBwEntry 2 }

mscAtmIfVptCAPoolAdmConnsTable OBJECT-TYPE
   SYNTAX     SEQUENCE OF MscAtmIfVptCAPoolAdmConnsEntry
   ACCESS     not-accessible
   STATUS     mandatory
   DESCRIPTION
     "This attribute indicates the total number of connections which are 
      currently admitted in the corresponding bandwidthPool. This 
      attribute does not include ATM networking signalling connections."
::= { mscAtmIfVptCA 465 }

mscAtmIfVptCAPoolAdmConnsEntry OBJECT-TYPE
   SYNTAX     MscAtmIfVptCAPoolAdmConnsEntry
   ACCESS     not-accessible
   STATUS     mandatory
   DESCRIPTION
     "An entry in the mscAtmIfVptCAPoolAdmConnsTable."
   INDEX {
      mscAtmIfIndex,
      mscAtmIfVptIndex,
      mscAtmIfVptCAIndex,
      mscAtmIfVptCAPoolAdmConnsIndex }
::= { mscAtmIfVptCAPoolAdmConnsTable 1 }

MscAtmIfVptCAPoolAdmConnsEntry ::= SEQUENCE {
   mscAtmIfVptCAPoolAdmConnsIndex
      Integer32,
   mscAtmIfVptCAPoolAdmConnsValue
      Gauge32 }

mscAtmIfVptCAPoolAdmConnsIndex OBJECT-TYPE
   SYNTAX     Integer32 (1..5)
   ACCESS     not-accessible
   STATUS     mandatory
   DESCRIPTION
     "This variable represents the mscAtmIfVptCAPoolAdmConnsTable
      specific index for the mscAtmIfVptCAPoolAdmConnsTable."
::= { mscAtmIfVptCAPoolAdmConnsEntry 1 }

mscAtmIfVptCAPoolAdmConnsValue OBJECT-TYPE
   SYNTAX     Gauge32 (0..16384)
   ACCESS     read-only
   STATUS     mandatory
   DESCRIPTION
     "This variable represents an individual value for the
      mscAtmIfVptCAPoolAdmConnsTable."
::= { mscAtmIfVptCAPoolAdmConnsEntry 2 }

mscAtmIfVptCAPoolWaitAdmConnsTable OBJECT-TYPE
   SYNTAX     SEQUENCE OF MscAtmIfVptCAPoolWaitAdmConnsEntry
   ACCESS     not-accessible
   STATUS     mandatory
   DESCRIPTION
     "This attribute indicates the total number of connections which are 
      currently admitted in the corresponding bandwidthPool. This 
      attribute does not include ATM networking signalling connections."
::= { mscAtmIfVptCA 466 }

mscAtmIfVptCAPoolWaitAdmConnsEntry OBJECT-TYPE
   SYNTAX     MscAtmIfVptCAPoolWaitAdmConnsEntry
   ACCESS     not-accessible
   STATUS     mandatory
   DESCRIPTION
     "An entry in the mscAtmIfVptCAPoolWaitAdmConnsTable."
   INDEX {
      mscAtmIfIndex,
      mscAtmIfVptIndex,
      mscAtmIfVptCAIndex,
      mscAtmIfVptCAPoolWaitAdmConnsIndex }
::= { mscAtmIfVptCAPoolWaitAdmConnsTable 1 }

MscAtmIfVptCAPoolWaitAdmConnsEntry ::= SEQUENCE {
   mscAtmIfVptCAPoolWaitAdmConnsIndex
      Integer32,
   mscAtmIfVptCAPoolWaitAdmConnsValue
      Gauge32 }

mscAtmIfVptCAPoolWaitAdmConnsIndex OBJECT-TYPE
   SYNTAX     Integer32 (1..5)
   ACCESS     not-accessible
   STATUS     mandatory
   DESCRIPTION
     "This variable represents the mscAtmIfVptCAPoolWaitAdmConnsTable
      specific index for the mscAtmIfVptCAPoolWaitAdmConnsTable."
::= { mscAtmIfVptCAPoolWaitAdmConnsEntry 1 }

mscAtmIfVptCAPoolWaitAdmConnsValue OBJECT-TYPE
   SYNTAX     Gauge32 (0..16384)
   ACCESS     read-only
   STATUS     mandatory
   DESCRIPTION
     "This variable represents an individual value for the
      mscAtmIfVptCAPoolWaitAdmConnsTable."
::= { mscAtmIfVptCAPoolWaitAdmConnsEntry 2 }


-- AtmIf/n Vpt/n CA ConstantBitRate/n 
-- This component controls default characteristics of the constant bit 
-- rate (CBR) service category, for Vccs administered by this CA. Any 
-- attributes of the AtmIf CA Cbr that cannot be overridden in the Vpt 
-- CA Cbr affect all connections, including Vpt Vccs.

mscAtmIfVptCACbr OBJECT IDENTIFIER ::= { mscAtmIfVptCA 2 }



mscAtmIfVptCACbrRowStatusTable OBJECT-TYPE
   SYNTAX     SEQUENCE OF MscAtmIfVptCACbrRowStatusEntry
   ACCESS     not-accessible
   STATUS     mandatory
   DESCRIPTION
     "This entry controls the addition and deletion of 
      mscAtmIfVptCACbr components."
::= { mscAtmIfVptCACbr 1 }

mscAtmIfVptCACbrRowStatusEntry OBJECT-TYPE
   SYNTAX     MscAtmIfVptCACbrRowStatusEntry
   ACCESS     not-accessible
   STATUS     mandatory
   DESCRIPTION
     "A single entry in the table represents a single 
      mscAtmIfVptCACbr component."
   INDEX {
      mscAtmIfIndex,
      mscAtmIfVptIndex,
      mscAtmIfVptCAIndex,
      mscAtmIfVptCACbrIndex }
::= { mscAtmIfVptCACbrRowStatusTable 1 }

MscAtmIfVptCACbrRowStatusEntry ::= SEQUENCE {
   mscAtmIfVptCACbrRowStatus
      RowStatus,
   mscAtmIfVptCACbrComponentName
      DisplayString,
   mscAtmIfVptCACbrStorageType
      StorageType,
   mscAtmIfVptCACbrIndex
      Integer32 }

mscAtmIfVptCACbrRowStatus OBJECT-TYPE
   SYNTAX     RowStatus 
   ACCESS     read-write
   STATUS     mandatory
   DESCRIPTION
     "This variable is used as the basis for SNMP naming of
      mscAtmIfVptCACbr components.
      These components can be added."
::= { mscAtmIfVptCACbrRowStatusEntry 1 }

mscAtmIfVptCACbrComponentName OBJECT-TYPE
   SYNTAX     DisplayString 
   ACCESS     read-only
   STATUS     mandatory
   DESCRIPTION
     "This variable provides the component's string name for
      use with the ASCII Console Interface"
::= { mscAtmIfVptCACbrRowStatusEntry 2 }

mscAtmIfVptCACbrStorageType OBJECT-TYPE
   SYNTAX     StorageType 
   ACCESS     read-only
   STATUS     mandatory
   DESCRIPTION
     "This variable represents the storage type value for the
      mscAtmIfVptCACbr tables."
::= { mscAtmIfVptCACbrRowStatusEntry 4 }

mscAtmIfVptCACbrIndex OBJECT-TYPE
   SYNTAX     Integer32 (0)
   ACCESS     not-accessible
   STATUS     mandatory
   DESCRIPTION
     "This variable represents the index for the mscAtmIfVptCACbr tables."
::= { mscAtmIfVptCACbrRowStatusEntry 10 }

mscAtmIfVptCACbrProvTable OBJECT-TYPE
   SYNTAX     SEQUENCE OF MscAtmIfVptCACbrProvEntry
   ACCESS     not-accessible
   STATUS     mandatory
   DESCRIPTION
     "This group contains provisioned attributes which control 
      Connection Admission Control (CAC) and Usage Parameter 
      Control (UPC) attributes for the CBR ATM connections managed 
      by this Vpt. Any attributes of the AtmIf CA Cbr that cannot be 
      overridden in the Vpt CA Cbr affect all connections, including Vpt 
      Vccs."
::= { mscAtmIfVptCACbr 100 }

mscAtmIfVptCACbrProvEntry OBJECT-TYPE
   SYNTAX     MscAtmIfVptCACbrProvEntry
   ACCESS     not-accessible
   STATUS     mandatory
   DESCRIPTION
     "An entry in the mscAtmIfVptCACbrProvTable."
   INDEX {
      mscAtmIfIndex,
      mscAtmIfVptIndex,
      mscAtmIfVptCAIndex,
      mscAtmIfVptCACbrIndex }
::= { mscAtmIfVptCACbrProvTable 1 }

MscAtmIfVptCACbrProvEntry ::= SEQUENCE {
   mscAtmIfVptCACbrPool
      INTEGER,
   mscAtmIfVptCACbrCdvt
      Unsigned32,
   mscAtmIfVptCACbrCdv
      Unsigned32,
   mscAtmIfVptCACbrMaxCtd
      Unsigned32,
   mscAtmIfVptCACbrCellLossRatio
      Unsigned32 }

mscAtmIfVptCACbrPool OBJECT-TYPE
   SYNTAX     INTEGER  {
                 pool1(1),
                 pool2(2),
                 pool3(3),
                 pool4(4),
                 pool5(5) }
   ACCESS     read-write
   STATUS     mandatory
   DESCRIPTION
     "This attribute specifies the bandwidth pool which is to be used to 
      support the constant bit rate (CBR) service category. The percentage 
      of Vpt bandwidth capacity reserved for the given bandwidth pool is 
      the maximum bandwidth that can be allocated to CBR traffic. The 
      percentage allocated to each bandwidth pool can be provisioned 
      through the bandwidthPool attribute under the CA."
   DEFVAL     { pool1 }
::= { mscAtmIfVptCACbrProvEntry 10 }

mscAtmIfVptCACbrCdvt OBJECT-TYPE
   SYNTAX     Unsigned32 (1..10000)
   ACCESS     read-write
   STATUS     mandatory
   DESCRIPTION
     "This attribute specifies the default cell delay variation tolerance 
      (CDVT) for connections of the CBR service category. An override 
      to this default may be specified for a provisioned connection under 
      the Vcd Tm or Vpd Tm component.
      
      This attribute is used by the CAC function to compute the 
      equivalent cell rate (ECR) required by a given CBR connection. The 
      larger the value of CDVT, the larger is its ECR. 
      
      If Usage Parameter Control (UPC) is enabled for a connection, 
      CDVT is used by the UPC function on the ingress to decide whether 
      a cell is conforming or non-conforming based on the connection's 
      traffic descriptor type. The larger the CDVT value, the more tolerant 
      is the UPC of bandwidth usage beyond the traffic contract."
   DEFVAL     { 250 }
::= { mscAtmIfVptCACbrProvEntry 20 }

mscAtmIfVptCACbrCdv OBJECT-TYPE
   SYNTAX     Unsigned32 (0..2147483647)
   ACCESS     read-write
   STATUS     mandatory
   DESCRIPTION
     "This attribute specifies the peak-to-peak cell delay variation (CDV) 
      which is contributed to connections associated with this Vpt for 
      CBR traffic. 
      
      The CDV is a measure of the delay jitter introduced mostly by 
      traffic buffering and cell scheduling. 
      
      The value of this attribute is used by PNNI in the Resource 
      Availability Information Group (RAIG) topology updates and route 
      selection. It is also used by CAC at connection set-up time to 
      determine whether this Vpt can meet the ATM connection's CDV 
      requirement. If so, the value of this attribute is added to the 
      cumulative CDV field of the extended QoS information element."
   DEFVAL     { 250 }
::= { mscAtmIfVptCACbrProvEntry 30 }

mscAtmIfVptCACbrMaxCtd OBJECT-TYPE
   SYNTAX     Unsigned32 (0..2147483647)
   ACCESS     read-write
   STATUS     mandatory
   DESCRIPTION
     "This attribute specifies the maximum cell transfer delay (MaxCTD) 
      which is applied to all connections associated with this Vpt for CBR 
      traffic.
      
      MaxCTD is the sum of the fixed delay and the CDV. The 
      components of the fixed delay include propagation delay through 
      the physical media, delays induced by the transmission system, and 
      fixed components of switch processing delay. 
      
      This attribute is used by PNNI in the Resource Availability 
      Information Group (RAIG) topology updates and route selection. It 
      is also used by CAC at connection set-up time to determine whether 
      this Vpt can meet the ATM connection's MaxCTD requirement."
   DEFVAL     { 1000 }
::= { mscAtmIfVptCACbrProvEntry 40 }

mscAtmIfVptCACbrCellLossRatio OBJECT-TYPE
   SYNTAX     Unsigned32 (0..15)
   ACCESS     read-write
   STATUS     mandatory
   DESCRIPTION
     "This attribute specifies the tolerable cell loss ratio (CLR) for CBR 
      traffic. The number is the negative logarithm (base 10) of the CLR. 
      For example, if the target CLR = 1E-10 then Cbr cellLossRatio = 
      10. This number must be the same as the RtVbr cellLossRatio since 
      CBR and rt-VBR traffic have the same discard priority. The Cbr 
      cellLossRatio is used by the Connection Admission Control (CAC) 
      algorithm to compute the required (equivalent) cell rate for CBR 
      connections. 
      
      There is a trade-off between the service category CLR and the 
      achievable Vpt bandwidth utilization. To guarantee an excellent 
      service category, the CLR should be as small as possible (e.g., 1E-
      10). However, a smaller CLR results in a larger equivalent cell rate 
      for a given connection and hence a lower Vpt bandwidth utilization.
      
      Setting this attribute to 0 means that a CLR of 1 can be tolerated. In 
      this case, no bandwidth is reserved for CBR connections, and CAC 
      is effectively turned off. All CBR connections are admitted."
   DEFVAL     { 10 }
::= { mscAtmIfVptCACbrProvEntry 50 }


-- AtmIf/n Vpt/n CA RealTimeVariableBitRate/n 
-- This component controls default characteristics of the real-time 
-- variable bit rate (rt-VBR) service category, for Vccs administered by 
-- this CA. Any attributes of the AtmIf CA RtVbr that cannot be 
-- overridden in the Vpt CA RtVbr affect all connections, including Vpt 
-- Vccs.

mscAtmIfVptCARtVbr OBJECT IDENTIFIER ::= { mscAtmIfVptCA 3 }



mscAtmIfVptCARtVbrRowStatusTable OBJECT-TYPE
   SYNTAX     SEQUENCE OF MscAtmIfVptCARtVbrRowStatusEntry
   ACCESS     not-accessible
   STATUS     mandatory
   DESCRIPTION
     "This entry controls the addition and deletion of 
      mscAtmIfVptCARtVbr components."
::= { mscAtmIfVptCARtVbr 1 }

mscAtmIfVptCARtVbrRowStatusEntry OBJECT-TYPE
   SYNTAX     MscAtmIfVptCARtVbrRowStatusEntry
   ACCESS     not-accessible
   STATUS     mandatory
   DESCRIPTION
     "A single entry in the table represents a single 
      mscAtmIfVptCARtVbr component."
   INDEX {
      mscAtmIfIndex,
      mscAtmIfVptIndex,
      mscAtmIfVptCAIndex,
      mscAtmIfVptCARtVbrIndex }
::= { mscAtmIfVptCARtVbrRowStatusTable 1 }

MscAtmIfVptCARtVbrRowStatusEntry ::= SEQUENCE {
   mscAtmIfVptCARtVbrRowStatus
      RowStatus,
   mscAtmIfVptCARtVbrComponentName
      DisplayString,
   mscAtmIfVptCARtVbrStorageType
      StorageType,
   mscAtmIfVptCARtVbrIndex
      Integer32 }

mscAtmIfVptCARtVbrRowStatus OBJECT-TYPE
   SYNTAX     RowStatus 
   ACCESS     read-write
   STATUS     mandatory
   DESCRIPTION
     "This variable is used as the basis for SNMP naming of
      mscAtmIfVptCARtVbr components.
      These components can be added."
::= { mscAtmIfVptCARtVbrRowStatusEntry 1 }

mscAtmIfVptCARtVbrComponentName OBJECT-TYPE
   SYNTAX     DisplayString 
   ACCESS     read-only
   STATUS     mandatory
   DESCRIPTION
     "This variable provides the component's string name for
      use with the ASCII Console Interface"
::= { mscAtmIfVptCARtVbrRowStatusEntry 2 }

mscAtmIfVptCARtVbrStorageType OBJECT-TYPE
   SYNTAX     StorageType 
   ACCESS     read-only
   STATUS     mandatory
   DESCRIPTION
     "This variable represents the storage type value for the
      mscAtmIfVptCARtVbr tables."
::= { mscAtmIfVptCARtVbrRowStatusEntry 4 }

mscAtmIfVptCARtVbrIndex OBJECT-TYPE
   SYNTAX     Integer32 (0)
   ACCESS     not-accessible
   STATUS     mandatory
   DESCRIPTION
     "This variable represents the index for the mscAtmIfVptCARtVbr tables."
::= { mscAtmIfVptCARtVbrRowStatusEntry 10 }

mscAtmIfVptCARtVbrProvTable OBJECT-TYPE
   SYNTAX     SEQUENCE OF MscAtmIfVptCARtVbrProvEntry
   ACCESS     not-accessible
   STATUS     mandatory
   DESCRIPTION
     "This group contains provisioned attributes which control 
      Connection Admission Control (CAC) and UPC attributes for the rt-
      VBR ATM connections associated with this Vpt. Any attributes of 
      the AtmIf CA RtVbr that cannot be overridden in the Vpt CA RtVbr 
      affect all connections, including Vpt Vccs."
::= { mscAtmIfVptCARtVbr 100 }

mscAtmIfVptCARtVbrProvEntry OBJECT-TYPE
   SYNTAX     MscAtmIfVptCARtVbrProvEntry
   ACCESS     not-accessible
   STATUS     mandatory
   DESCRIPTION
     "An entry in the mscAtmIfVptCARtVbrProvTable."
   INDEX {
      mscAtmIfIndex,
      mscAtmIfVptIndex,
      mscAtmIfVptCAIndex,
      mscAtmIfVptCARtVbrIndex }
::= { mscAtmIfVptCARtVbrProvTable 1 }

MscAtmIfVptCARtVbrProvEntry ::= SEQUENCE {
   mscAtmIfVptCARtVbrPool
      INTEGER,
   mscAtmIfVptCARtVbrCdv
      Unsigned32,
   mscAtmIfVptCARtVbrMaxCtd
      Unsigned32,
   mscAtmIfVptCARtVbrCellLossRatio
      Unsigned32 }

mscAtmIfVptCARtVbrPool OBJECT-TYPE
   SYNTAX     INTEGER  {
                 pool1(1),
                 pool2(2),
                 pool3(3),
                 pool4(4),
                 pool5(5) }
   ACCESS     read-write
   STATUS     mandatory
   DESCRIPTION
     "This attribute specifies the bandwidth pool which is to be used to 
      support the real-time variable bit rate (rt-VBR) service category. 
      The percentage of Vpt capacity reserved for the given bandwidth 
      pool is the maximum bandwidth that can be allocated to rt-VBR 
      traffic. The percentage allocated to each bandwidth pool can be 
      provisioned through the bandwidthPool attribute under the Vpt CA."
   DEFVAL     { pool1 }
::= { mscAtmIfVptCARtVbrProvEntry 10 }

mscAtmIfVptCARtVbrCdv OBJECT-TYPE
   SYNTAX     Unsigned32 (0..2147483647)
   ACCESS     read-write
   STATUS     mandatory
   DESCRIPTION
     "This attribute specifies the peak-to-peak cell delay variation (CDV) 
      which is contributed to all rt-VBR connections associated with this 
      Vpt. 
      
      The CDV is a measure of the delay jitter introduced mostly by 
      traffic buffering and cell scheduling.
      
      The value of this attribute is used by PNNI in the Resource 
      Availability Information Group (RAIG) topology updates and route 
      selection. It is also used by CAC at connection set-up time to 
      determine whether this Vpt can meet the CDV requirement for that 
      connection. If so, the value of this attribute is added to the 
      cumulative CDV field of the extended QoS information element."
   DEFVAL     { 1268 }
::= { mscAtmIfVptCARtVbrProvEntry 30 }

mscAtmIfVptCARtVbrMaxCtd OBJECT-TYPE
   SYNTAX     Unsigned32 (0..2147483647)
   ACCESS     read-write
   STATUS     mandatory
   DESCRIPTION
     "This attribute specifies the maximum cell transfer delay (MaxCTD) 
      which is applied to all rt-VBR connections associated with this Vpt.
      
      MaxCTD is the sum of the fixed delay and the CDV. The 
      components of the fixed delay include propagation delay through 
      the physical media, delays induced by the transmission system, and 
      fixed components of switch processing delay.
      
      This attribute is used by PNNI in the Resource Availability 
      Information Group (RAIG) topology updates and route selection. It 
      is also used by CAC at connection set-up time to determine whether 
      this Vpt can meet the ATM connection's MaxCTD requirement."
   DEFVAL     { 2000 }
::= { mscAtmIfVptCARtVbrProvEntry 40 }

mscAtmIfVptCARtVbrCellLossRatio OBJECT-TYPE
   SYNTAX     Unsigned32 (0..15)
   ACCESS     read-write
   STATUS     mandatory
   DESCRIPTION
     "This attribute specifies the tolerable cell loss ratio (CLR) for rt-
      VBR traffic. The number is the negative logarithm (base 10) of the 
      CLR. For example, if the target CLR = 1E-10 then RtVbr 
      cellLossRatio = 10. This number must be the same as the Cbr 
      cellLossRatio since CBR and rt-VBR traffic have the same discard 
      priority. The RtVbr cellLossRatio is used by the Connection 
      Admission Control (CAC) algorithm to compute the required 
      (equivalent) cell rate for rt-VBR connections. This number must be 
      less than or equal to the NrtVbr cellLossRatio, since rt-VBR traffic 
      has a higher discard priority.
      
      There is a trade-off between the service category CLR and the 
      achievable Vpt bandwidth utilization. To guarantee an excellent 
      service category, the CLR should be as small as possible (e.g., 1E-
      10). However, a smaller CLR results in a larger equivalent cell rate 
      for a given connection and hence a lower Vpt bandwidth utilization. 
      
      Setting this attribute to 0 means that a CLR of 1 can be tolerated. In 
      this case, no bandwidth is reserved for rt-VBR connections and 
      CAC is effectively turned off. All rt-VBR connections are admitted."
   DEFVAL     { 10 }
::= { mscAtmIfVptCARtVbrProvEntry 50 }


-- AtmIf/n Vpt/n CA NonRealTimeVariableBitRate/n 
-- This component controls default characteristics of the non-real-time 
-- variable bit rate (nrt-VBR) service category, for Vccs administered 
-- by this CA. Any attributes of the AtmIf CA NrtVbr that cannot be 
-- overridden in the Vpt CA NrtVbr affect all connections, including 
-- Vpt Vccs.

mscAtmIfVptCANrtVbr OBJECT IDENTIFIER ::= { mscAtmIfVptCA 4 }



mscAtmIfVptCANrtVbrRowStatusTable OBJECT-TYPE
   SYNTAX     SEQUENCE OF MscAtmIfVptCANrtVbrRowStatusEntry
   ACCESS     not-accessible
   STATUS     mandatory
   DESCRIPTION
     "This entry controls the addition and deletion of 
      mscAtmIfVptCANrtVbr components."
::= { mscAtmIfVptCANrtVbr 1 }

mscAtmIfVptCANrtVbrRowStatusEntry OBJECT-TYPE
   SYNTAX     MscAtmIfVptCANrtVbrRowStatusEntry
   ACCESS     not-accessible
   STATUS     mandatory
   DESCRIPTION
     "A single entry in the table represents a single 
      mscAtmIfVptCANrtVbr component."
   INDEX {
      mscAtmIfIndex,
      mscAtmIfVptIndex,
      mscAtmIfVptCAIndex,
      mscAtmIfVptCANrtVbrIndex }
::= { mscAtmIfVptCANrtVbrRowStatusTable 1 }

MscAtmIfVptCANrtVbrRowStatusEntry ::= SEQUENCE {
   mscAtmIfVptCANrtVbrRowStatus
      RowStatus,
   mscAtmIfVptCANrtVbrComponentName
      DisplayString,
   mscAtmIfVptCANrtVbrStorageType
      StorageType,
   mscAtmIfVptCANrtVbrIndex
      Integer32 }

mscAtmIfVptCANrtVbrRowStatus OBJECT-TYPE
   SYNTAX     RowStatus 
   ACCESS     read-write
   STATUS     mandatory
   DESCRIPTION
     "This variable is used as the basis for SNMP naming of
      mscAtmIfVptCANrtVbr components.
      These components can be added."
::= { mscAtmIfVptCANrtVbrRowStatusEntry 1 }

mscAtmIfVptCANrtVbrComponentName OBJECT-TYPE
   SYNTAX     DisplayString 
   ACCESS     read-only
   STATUS     mandatory
   DESCRIPTION
     "This variable provides the component's string name for
      use with the ASCII Console Interface"
::= { mscAtmIfVptCANrtVbrRowStatusEntry 2 }

mscAtmIfVptCANrtVbrStorageType OBJECT-TYPE
   SYNTAX     StorageType 
   ACCESS     read-only
   STATUS     mandatory
   DESCRIPTION
     "This variable represents the storage type value for the
      mscAtmIfVptCANrtVbr tables."
::= { mscAtmIfVptCANrtVbrRowStatusEntry 4 }

mscAtmIfVptCANrtVbrIndex OBJECT-TYPE
   SYNTAX     Integer32 (0)
   ACCESS     not-accessible
   STATUS     mandatory
   DESCRIPTION
     "This variable represents the index for the mscAtmIfVptCANrtVbr tables."
::= { mscAtmIfVptCANrtVbrRowStatusEntry 10 }

mscAtmIfVptCANrtVbrProvTable OBJECT-TYPE
   SYNTAX     SEQUENCE OF MscAtmIfVptCANrtVbrProvEntry
   ACCESS     not-accessible
   STATUS     mandatory
   DESCRIPTION
     "This group contains provisioned attributes which control 
      Connection Admission Control (CAC) and UPC attributes for the 
      nrt-VBR ATM connections associated with this Vpt. Any attributes 
      of the AtmIf CA NrtVbr that cannot be overridden in the Vpt CA 
      NrtVbr affect all connections, including Vpt Vccs."
::= { mscAtmIfVptCANrtVbr 100 }

mscAtmIfVptCANrtVbrProvEntry OBJECT-TYPE
   SYNTAX     MscAtmIfVptCANrtVbrProvEntry
   ACCESS     not-accessible
   STATUS     mandatory
   DESCRIPTION
     "An entry in the mscAtmIfVptCANrtVbrProvTable."
   INDEX {
      mscAtmIfIndex,
      mscAtmIfVptIndex,
      mscAtmIfVptCAIndex,
      mscAtmIfVptCANrtVbrIndex }
::= { mscAtmIfVptCANrtVbrProvTable 1 }

MscAtmIfVptCANrtVbrProvEntry ::= SEQUENCE {
   mscAtmIfVptCANrtVbrPool
      INTEGER,
   mscAtmIfVptCANrtVbrCellLossRatio
      Unsigned32 }

mscAtmIfVptCANrtVbrPool OBJECT-TYPE
   SYNTAX     INTEGER  {
                 pool1(1),
                 pool2(2),
                 pool3(3),
                 pool4(4),
                 pool5(5) }
   ACCESS     read-write
   STATUS     mandatory
   DESCRIPTION
     "This attribute specifies the bandwidth pool which is to be used to 
      support the non-real time variable bit rate (nrt-VBR) service 
      category. The percentage of Vpt bandwidth capacity reserved for the 
      given bandwidth pool is the maximum bandwidth that can be 
      allocated to nrt-VBR traffic. The percentage allocated to each 
      bandwidth pool can be provisioned through the bandwidthPool 
      attribute under the CA."
   DEFVAL     { pool1 }
::= { mscAtmIfVptCANrtVbrProvEntry 1 }

mscAtmIfVptCANrtVbrCellLossRatio OBJECT-TYPE
   SYNTAX     Unsigned32 (0..15)
   ACCESS     read-write
   STATUS     mandatory
   DESCRIPTION
     "This attribute specifies the tolerable cell loss ratio (CLR) for nrt-
      VBR traffic. The number is the negative logarithm (base 10) of the 
      CLR. In other words if the target CLR = 1E-10 then NrtVbr 
      cellLossRatio = 10. This number must be greater than or equal to 
      RtVbr cellLossRatio since rt-VBR traffic has a higher discard 
      priority. The NrtVbr cellLossRatio is used by the Connection 
      Admission Control (CAC) algorithm to compute the required 
      (equivalent) cell rate for nrt-VBR connections. 
      
      There is a trade-off between the service category CLR and the 
      achievable Vpt bandwidth utilization. To guarantee an excellent 
      service category, the CLR should be as small as possible (e.g., 1E-
      10). However, a smaller CLR results in a larger equivalent cell rate 
      for a given connection and hence a lower Vpt bandwidth utilization. 
      
      Setting this attribute to 0 means that a CLR of 1 can be tolerated. In 
      this case, no bandwidth is reserved for nrt-VBR connections, and 
      CAC is effectively turned off. All nrt-VBR connections are 
      admitted."
   DEFVAL     { 7 }
::= { mscAtmIfVptCANrtVbrProvEntry 3 }


-- AtmIf/n Vpt/n CA AvailableBitRate/n 
-- This component controls default characteristics of the available bit 
-- rate (ABR) service category, for Vccs administered by this CA. Any 
-- attributes of the AtmIf CA Abr that cannot be overridden in the Vpt 
-- CA Abr affect all connections, including Vpt Vccs.

mscAtmIfVptCAAbr OBJECT IDENTIFIER ::= { mscAtmIfVptCA 5 }



mscAtmIfVptCAAbrRowStatusTable OBJECT-TYPE
   SYNTAX     SEQUENCE OF MscAtmIfVptCAAbrRowStatusEntry
   ACCESS     not-accessible
   STATUS     mandatory
   DESCRIPTION
     "This entry controls the addition and deletion of 
      mscAtmIfVptCAAbr components."
::= { mscAtmIfVptCAAbr 1 }

mscAtmIfVptCAAbrRowStatusEntry OBJECT-TYPE
   SYNTAX     MscAtmIfVptCAAbrRowStatusEntry
   ACCESS     not-accessible
   STATUS     mandatory
   DESCRIPTION
     "A single entry in the table represents a single 
      mscAtmIfVptCAAbr component."
   INDEX {
      mscAtmIfIndex,
      mscAtmIfVptIndex,
      mscAtmIfVptCAIndex,
      mscAtmIfVptCAAbrIndex }
::= { mscAtmIfVptCAAbrRowStatusTable 1 }

MscAtmIfVptCAAbrRowStatusEntry ::= SEQUENCE {
   mscAtmIfVptCAAbrRowStatus
      RowStatus,
   mscAtmIfVptCAAbrComponentName
      DisplayString,
   mscAtmIfVptCAAbrStorageType
      StorageType,
   mscAtmIfVptCAAbrIndex
      Integer32 }

mscAtmIfVptCAAbrRowStatus OBJECT-TYPE
   SYNTAX     RowStatus 
   ACCESS     read-write
   STATUS     mandatory
   DESCRIPTION
     "This variable is used as the basis for SNMP naming of
      mscAtmIfVptCAAbr components.
      These components can be added."
::= { mscAtmIfVptCAAbrRowStatusEntry 1 }

mscAtmIfVptCAAbrComponentName OBJECT-TYPE
   SYNTAX     DisplayString 
   ACCESS     read-only
   STATUS     mandatory
   DESCRIPTION
     "This variable provides the component's string name for
      use with the ASCII Console Interface"
::= { mscAtmIfVptCAAbrRowStatusEntry 2 }

mscAtmIfVptCAAbrStorageType OBJECT-TYPE
   SYNTAX     StorageType 
   ACCESS     read-only
   STATUS     mandatory
   DESCRIPTION
     "This variable represents the storage type value for the
      mscAtmIfVptCAAbr tables."
::= { mscAtmIfVptCAAbrRowStatusEntry 4 }

mscAtmIfVptCAAbrIndex OBJECT-TYPE
   SYNTAX     Integer32 (0)
   ACCESS     not-accessible
   STATUS     mandatory
   DESCRIPTION
     "This variable represents the index for the mscAtmIfVptCAAbr tables."
::= { mscAtmIfVptCAAbrRowStatusEntry 10 }

mscAtmIfVptCAAbrProvTable OBJECT-TYPE
   SYNTAX     SEQUENCE OF MscAtmIfVptCAAbrProvEntry
   ACCESS     not-accessible
   STATUS     mandatory
   DESCRIPTION
     "This group contains provisioned attributes which control 
      Connection Admission Control (CAC) attributes for ABR 
      connections associated with this Vpt. Any attributes of the AtmIf CA 
      Abr that cannot be overridden in the Vpt CA Abr affect all 
      connections, including Vpt Vccs."
::= { mscAtmIfVptCAAbr 100 }

mscAtmIfVptCAAbrProvEntry OBJECT-TYPE
   SYNTAX     MscAtmIfVptCAAbrProvEntry
   ACCESS     not-accessible
   STATUS     mandatory
   DESCRIPTION
     "An entry in the mscAtmIfVptCAAbrProvTable."
   INDEX {
      mscAtmIfIndex,
      mscAtmIfVptIndex,
      mscAtmIfVptCAIndex,
      mscAtmIfVptCAAbrIndex }
::= { mscAtmIfVptCAAbrProvTable 1 }

MscAtmIfVptCAAbrProvEntry ::= SEQUENCE {
   mscAtmIfVptCAAbrPool
      INTEGER }

mscAtmIfVptCAAbrPool OBJECT-TYPE
   SYNTAX     INTEGER  {
                 pool1(1),
                 pool2(2),
                 pool3(3),
                 pool4(4),
                 pool5(5) }
   ACCESS     read-write
   STATUS     mandatory
   DESCRIPTION
     "This attribute specifies the bandwidth pool which is to be used to 
      support the available bit rate (ABR) service category. The 
      percentage of Vpt bandwidth capacity reserved for the given 
      bandwidth pool is the maximum bandwidth that can be allocated to 
      ABR traffic. The percentage allocated to each bandwidth pool can 
      be provisioned through the bandwidthPool attribute under the CA."
   DEFVAL     { pool1 }
::= { mscAtmIfVptCAAbrProvEntry 10 }


-- AtmIf/n Vpt/n CA UnspecifiedBitRate/n 
-- This component controls default characteristics of the unspecified 
-- bit rate (UBR) service category, for Vccs administered by this CA. 
-- Any attributes of the AtmIf CA Ubr that cannot be overridden in the 
-- Vpt CA Ubr affect all connections, including Vpt Vccs.

mscAtmIfVptCAUbr OBJECT IDENTIFIER ::= { mscAtmIfVptCA 6 }



mscAtmIfVptCAUbrRowStatusTable OBJECT-TYPE
   SYNTAX     SEQUENCE OF MscAtmIfVptCAUbrRowStatusEntry
   ACCESS     not-accessible
   STATUS     mandatory
   DESCRIPTION
     "This entry controls the addition and deletion of 
      mscAtmIfVptCAUbr components."
::= { mscAtmIfVptCAUbr 1 }

mscAtmIfVptCAUbrRowStatusEntry OBJECT-TYPE
   SYNTAX     MscAtmIfVptCAUbrRowStatusEntry
   ACCESS     not-accessible
   STATUS     mandatory
   DESCRIPTION
     "A single entry in the table represents a single 
      mscAtmIfVptCAUbr component."
   INDEX {
      mscAtmIfIndex,
      mscAtmIfVptIndex,
      mscAtmIfVptCAIndex,
      mscAtmIfVptCAUbrIndex }
::= { mscAtmIfVptCAUbrRowStatusTable 1 }

MscAtmIfVptCAUbrRowStatusEntry ::= SEQUENCE {
   mscAtmIfVptCAUbrRowStatus
      RowStatus,
   mscAtmIfVptCAUbrComponentName
      DisplayString,
   mscAtmIfVptCAUbrStorageType
      StorageType,
   mscAtmIfVptCAUbrIndex
      Integer32 }

mscAtmIfVptCAUbrRowStatus OBJECT-TYPE
   SYNTAX     RowStatus 
   ACCESS     read-write
   STATUS     mandatory
   DESCRIPTION
     "This variable is used as the basis for SNMP naming of
      mscAtmIfVptCAUbr components.
      These components can be added."
::= { mscAtmIfVptCAUbrRowStatusEntry 1 }

mscAtmIfVptCAUbrComponentName OBJECT-TYPE
   SYNTAX     DisplayString 
   ACCESS     read-only
   STATUS     mandatory
   DESCRIPTION
     "This variable provides the component's string name for
      use with the ASCII Console Interface"
::= { mscAtmIfVptCAUbrRowStatusEntry 2 }

mscAtmIfVptCAUbrStorageType OBJECT-TYPE
   SYNTAX     StorageType 
   ACCESS     read-only
   STATUS     mandatory
   DESCRIPTION
     "This variable represents the storage type value for the
      mscAtmIfVptCAUbr tables."
::= { mscAtmIfVptCAUbrRowStatusEntry 4 }

mscAtmIfVptCAUbrIndex OBJECT-TYPE
   SYNTAX     Integer32 (0)
   ACCESS     not-accessible
   STATUS     mandatory
   DESCRIPTION
     "This variable represents the index for the mscAtmIfVptCAUbr tables."
::= { mscAtmIfVptCAUbrRowStatusEntry 10 }

mscAtmIfVptCAUbrProvTable OBJECT-TYPE
   SYNTAX     SEQUENCE OF MscAtmIfVptCAUbrProvEntry
   ACCESS     not-accessible
   STATUS     mandatory
   DESCRIPTION
     "This group contains provisioned attributes which control 
      Connection Admission Control (CAC) attributes for UBR 
      connections associated with this Vpt. Any attributes of the AtmIf CA 
      Ubr that cannot be overridden in the Vpt CA Ubr affect all 
      connections, including Vpt Vccs."
::= { mscAtmIfVptCAUbr 100 }

mscAtmIfVptCAUbrProvEntry OBJECT-TYPE
   SYNTAX     MscAtmIfVptCAUbrProvEntry
   ACCESS     not-accessible
   STATUS     mandatory
   DESCRIPTION
     "An entry in the mscAtmIfVptCAUbrProvTable."
   INDEX {
      mscAtmIfIndex,
      mscAtmIfVptIndex,
      mscAtmIfVptCAIndex,
      mscAtmIfVptCAUbrIndex }
::= { mscAtmIfVptCAUbrProvTable 1 }

MscAtmIfVptCAUbrProvEntry ::= SEQUENCE {
   mscAtmIfVptCAUbrMaxVccs
      Unsigned32,
   mscAtmIfVptCAUbrPool
      INTEGER,
   mscAtmIfVptCAUbrMinimumCellRate
      Unsigned32 }

mscAtmIfVptCAUbrMaxVccs OBJECT-TYPE
   SYNTAX     Unsigned32 (0..16384 | 16385)
   ACCESS     read-write
   STATUS     mandatory
   DESCRIPTION
     "This attribute specifies the maximum number of UBR Vccs that can 
      be configured associated with this Vpt. The value must not exceed 
      the maxVccs attribute of the parent Vpt CA component.
      
      If this attribute is set to sameAsCa, the maximum number of UBR 
      Vccs is the same as specified by the maxVccs attribute of the Vpt 
      CA.
      
      Changes to this attribute are not critical to the Vpt. If the value is 
      changed to a number smaller than the current number of active 
      VCCs, no new VCCs can be admitted until the number of active 
      VCCs drops below the value of this attribute. The current number of 
      active VCCs is indicated by the sum of the permanentVccs and 
      switchedVccs operational attribute under the Vpt CA component.

      VALUES (

      16385 = sameAsCa

      )"
   DEFVAL     { 16385 }
::= { mscAtmIfVptCAUbrProvEntry 6 }

mscAtmIfVptCAUbrPool OBJECT-TYPE
   SYNTAX     INTEGER  {
                 pool1(1),
                 pool2(2),
                 pool3(3),
                 pool4(4),
                 pool5(5) }
   ACCESS     read-write
   STATUS     mandatory
   DESCRIPTION
     "This attribute specifies the bandwidth pool which is to be used to 
      support the unspecified bit rate (UBR) service category. The 
      percentage of Vpt bandwidth capacity reserved for the given 
      bandwidth pool is the maximum bandwidth that can be allocated to 
      UBR traffic. The percentage allocated to each bandwidth pool can 
      be provisioned through the bandwidthPool attribute under the CA."
   DEFVAL     { pool1 }
::= { mscAtmIfVptCAUbrProvEntry 10 }

mscAtmIfVptCAUbrMinimumCellRate OBJECT-TYPE
   SYNTAX     Unsigned32 (0..2147483647)
   ACCESS     read-write
   STATUS     mandatory
   DESCRIPTION
     "This attribute specifies the default minimum cell rate (MCR) which 
      is allocated from the UBR pool bandwidth for each UBR 
      connection which is admitted. UBR connections normally are 
      serviced on a best effort basis, but this attribute allows allocation of 
      a default minimum bandwidth for each connection."
   DEFVAL     { 0 }
::= { mscAtmIfVptCAUbrProvEntry 11 }

mscAtmIfVptCAUbrOperTable OBJECT-TYPE
   SYNTAX     SEQUENCE OF MscAtmIfVptCAUbrOperEntry
   ACCESS     not-accessible
   STATUS     mandatory
   DESCRIPTION
     "This group contains operational attributes which show operational 
      attributes for UBR connections associated with this Vpt."
::= { mscAtmIfVptCAUbr 110 }

mscAtmIfVptCAUbrOperEntry OBJECT-TYPE
   SYNTAX     MscAtmIfVptCAUbrOperEntry
   ACCESS     not-accessible
   STATUS     mandatory
   DESCRIPTION
     "An entry in the mscAtmIfVptCAUbrOperTable."
   INDEX {
      mscAtmIfIndex,
      mscAtmIfVptIndex,
      mscAtmIfVptCAIndex,
      mscAtmIfVptCAUbrIndex }
::= { mscAtmIfVptCAUbrOperTable 1 }

MscAtmIfVptCAUbrOperEntry ::= SEQUENCE {
   mscAtmIfVptCAUbrVccUsage
      Unsigned32 }

mscAtmIfVptCAUbrVccUsage OBJECT-TYPE
   SYNTAX     Unsigned32 (0..16384)
   ACCESS     read-only
   STATUS     mandatory
   DESCRIPTION
     "This attribute indicates the number of active UBR Vccs under this 
      Vpt. It includes switched and permanent connections."
::= { mscAtmIfVptCAUbrOperEntry 12 }


-- AtmIf/n Vpc/vpi TrafficManagement, 
-- AtmIf/n Vcc/vpi.vci TrafficManagement,
-- AtmIf/n Vpt/vpi TrafficManagement,
-- AtmIf/n Vpt/vpi Vcc/vci TrafficManagement
-- The Tm subcomponent contains the operational traffic management 
-- attributes of a connection. It is created dynamically for each 
-- activated Vcc, Vpc, or Vpt component.

mscAtmIfVptTm OBJECT IDENTIFIER ::= { mscAtmIfVpt 9 }



mscAtmIfVptTmRowStatusTable OBJECT-TYPE
   SYNTAX     SEQUENCE OF MscAtmIfVptTmRowStatusEntry
   ACCESS     not-accessible
   STATUS     mandatory
   DESCRIPTION
     "This entry controls the addition and deletion of 
      mscAtmIfVptTm components."
::= { mscAtmIfVptTm 1 }

mscAtmIfVptTmRowStatusEntry OBJECT-TYPE
   SYNTAX     MscAtmIfVptTmRowStatusEntry
   ACCESS     not-accessible
   STATUS     mandatory
   DESCRIPTION
     "A single entry in the table represents a single 
      mscAtmIfVptTm component."
   INDEX {
      mscAtmIfIndex,
      mscAtmIfVptIndex,
      mscAtmIfVptTmIndex }
::= { mscAtmIfVptTmRowStatusTable 1 }

MscAtmIfVptTmRowStatusEntry ::= SEQUENCE {
   mscAtmIfVptTmRowStatus
      RowStatus,
   mscAtmIfVptTmComponentName
      DisplayString,
   mscAtmIfVptTmStorageType
      StorageType,
   mscAtmIfVptTmIndex
      NonReplicated }

mscAtmIfVptTmRowStatus OBJECT-TYPE
   SYNTAX     RowStatus 
   ACCESS     read-only
   STATUS     mandatory
   DESCRIPTION
     "This variable is used as the basis for SNMP naming of
      mscAtmIfVptTm components.
      These components cannot be added nor deleted."
::= { mscAtmIfVptTmRowStatusEntry 1 }

mscAtmIfVptTmComponentName OBJECT-TYPE
   SYNTAX     DisplayString 
   ACCESS     read-only
   STATUS     mandatory
   DESCRIPTION
     "This variable provides the component's string name for
      use with the ASCII Console Interface"
::= { mscAtmIfVptTmRowStatusEntry 2 }

mscAtmIfVptTmStorageType OBJECT-TYPE
   SYNTAX     StorageType 
   ACCESS     read-only
   STATUS     mandatory
   DESCRIPTION
     "This variable represents the storage type value for the
      mscAtmIfVptTm tables."
::= { mscAtmIfVptTmRowStatusEntry 4 }

mscAtmIfVptTmIndex OBJECT-TYPE
   SYNTAX     NonReplicated 
   ACCESS     not-accessible
   STATUS     mandatory
   DESCRIPTION
     "This variable represents the index for the mscAtmIfVptTm tables."
::= { mscAtmIfVptTmRowStatusEntry 10 }

mscAtmIfVptTmOperTable OBJECT-TYPE
   SYNTAX     SEQUENCE OF MscAtmIfVptTmOperEntry
   ACCESS     not-accessible
   STATUS     mandatory
   DESCRIPTION
     "This group contains attributes for the Tm component to reflect 
      operational traffic attributes."
::= { mscAtmIfVptTm 100 }

mscAtmIfVptTmOperEntry OBJECT-TYPE
   SYNTAX     MscAtmIfVptTmOperEntry
   ACCESS     not-accessible
   STATUS     mandatory
   DESCRIPTION
     "An entry in the mscAtmIfVptTmOperTable."
   INDEX {
      mscAtmIfIndex,
      mscAtmIfVptIndex,
      mscAtmIfVptTmIndex }
::= { mscAtmIfVptTmOperTable 1 }

MscAtmIfVptTmOperEntry ::= SEQUENCE {
   mscAtmIfVptTmTxTrafficDescType
      INTEGER,
   mscAtmIfVptTmTxQosClass
      INTEGER,
   mscAtmIfVptTmTxQueueLength
      Unsigned32,
   mscAtmIfVptTmTxQueueCongestionState
      Unsigned32,
   mscAtmIfVptTmHoldingPriority
      INTEGER,
   mscAtmIfVptTmRxTrafficDescType
      INTEGER,
   mscAtmIfVptTmRxQosClass
      INTEGER,
   mscAtmIfVptTmAtmServiceCategory
      INTEGER,
   mscAtmIfVptTmTrafficShaping
      INTEGER,
   mscAtmIfVptTmBearerClassBbc
      INTEGER,
   mscAtmIfVptTmTransferCapabilityBbc
      INTEGER,
   mscAtmIfVptTmClippingBbc
      INTEGER,
   mscAtmIfVptTmUnshapedTransmitQueueing
      INTEGER,
   mscAtmIfVptTmBestEffort
      INTEGER,
   mscAtmIfVptTmForceTagging
      INTEGER,
   mscAtmIfVptTmWeight
      Unsigned32,
   mscAtmIfVptTmUsageParameterControl
      INTEGER,
   mscAtmIfVptTmTxPacketWiseDiscard
      OCTET STRING,
   mscAtmIfVptTmRxPacketWiseDiscard
      OCTET STRING,
   mscAtmIfVptTmBandwidthElastic
      INTEGER,
   mscAtmIfVptTmBandwidthReduction
      Unsigned32,
   mscAtmIfVptTmAbrConnectionType
      INTEGER }

mscAtmIfVptTmTxTrafficDescType OBJECT-TYPE
   SYNTAX     INTEGER  {
                 n1(1),
                 n2(2),
                 n3(3),
                 n4(4),
                 n5(5),
                 n6(6),
                 n7(7),
                 n8(8),
                 n9(9) }
   ACCESS     read-only
   STATUS     mandatory
   DESCRIPTION
     "T his attribute indicates the type of traffic management which is 
      applied to the transmit direction of this connection as defined in the 
      ATM Forum. The txTrafficDescType determines the number and 
      meaning of the parameters in the txTrafficDescParm attribute."
::= { mscAtmIfVptTmOperEntry 10 }

mscAtmIfVptTmTxQosClass OBJECT-TYPE
   SYNTAX     INTEGER  {
                 n0(0),
                 n1(1),
                 n2(2),
                 n3(3),
                 n4(4),
                 notApplicable(14) }
   ACCESS     read-only
   STATUS     mandatory
   DESCRIPTION
     "This attribute indicates the quality of service for the calling to called 
      direction for this connection. This is only applicable to Soft PVC 
      and SVC connections. 
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified QOS class; no objective is specified for 
      the performance parameters.
      
      A value of notApplicable is displayed in the case of nailed-up PVCs 
      for which this attribute has no significance."
::= { mscAtmIfVptTmOperEntry 31 }

mscAtmIfVptTmTxQueueLength OBJECT-TYPE
   SYNTAX     Unsigned32 (0..30720)
   ACCESS     read-only
   STATUS     mandatory
   DESCRIPTION
     "This attribute indicates the current number of cells in the transmit 
      queue for this connection. 
      
      If this connection has unshapedTransmitQueueing attribute 
      displayed as common, this attribute displays the length of the 
      common queue which is used for this atm service category. 
      
      If this connection has unshapedTransmitQueueing attribute 
      displayed as fifo, this attribute indicates the number of cells for this 
      connection which are enqueued in a first-in-first-out queuing 
      method for this atm service category. This will only occur for 
      connections on ATM IP cards with atmServiceCategory of nrtVbr 
      or ubr. 
      
      If this connection has unshapedTransmitQueueing attribute 
      displayed as perVc or as notApplicable, this attribute displays the 
      length of the per-VC queue.
      
      For the 1pOC48SmSrAtm card, this attribute displays the current 
      number of cells in the link class queue used by this connection to 
      buffer its traffic.
      
      
      This attribute does not apply to basic Vpts."
::= { mscAtmIfVptTmOperEntry 32 }

mscAtmIfVptTmTxQueueCongestionState OBJECT-TYPE
   SYNTAX     Unsigned32 (0..3)
   ACCESS     read-only
   STATUS     mandatory
   DESCRIPTION
     "This attribute indicates the congestion state of the transmit queue 
      for this connection. 
      
      If this connection has unshapedTransmitQueueing attribute 
      displayed as common, this attribute displays the congestion state of 
      the common queue. If this connection has 
      unshapedTransmitQueueing attribute displayed as perVc or as 
      notApplicable, this attribute displays the congestion state of the per-
      VC queue.
      
      For the 1pOC48SmSrAtm card, this attribute displays the current 
      congestion state of the link class queue used by this connection to 
      buffer its traffic.
      
      The congestion state of a queue is indicated by a numeric value 
      ranging from 0 to 3. When a queue is in a congested state x, only 
      traffic with discard priority (DP) 0 to x are enqueued. Traffic with 
      DP > x is discarded. 
      
      For example, if the congestion state is 3, there is no congestion and 
      all traffic is enqueued. Likewise, when the congestion state is 0, 
      there is maximum congestion and only traffic with DP=0 is 
      enqueued on that queue.
      
      This attribute does not apply to basic Vpts."
::= { mscAtmIfVptTmOperEntry 33 }

mscAtmIfVptTmHoldingPriority OBJECT-TYPE
   SYNTAX     INTEGER  {
                 n0(0),
                 n1(1),
                 n2(2),
                 n3(3),
                 n4(4),
                 notApplicable(6) }
   ACCESS     read-only
   STATUS     mandatory
   DESCRIPTION
     "This attribute indicates the actual holding priority in effect for this 
      connection. In a situation where the link bandwidth fluctuates, such 
      as over an IMA link, holding priority is used to determine which 
      connections are held and which are released. Holding priority 4 
      connections are the first to be released. Holding priority 0 
      connections are the last to be released. Some applications, for 
      example Vcc Test, may override the provisioned holding priority. 
      
      A value of notApplicable is displayed when this is an elastic 
      connection. Holding priority does not apply to bandwidth elastic 
      connections.
      
      Holding priority has no effect if the equivalent cell rate (ECR) for a 
      connection is zero.
      
      This attribute does not apply to Vpt Vccs."
::= { mscAtmIfVptTmOperEntry 35 }

mscAtmIfVptTmRxTrafficDescType OBJECT-TYPE
   SYNTAX     INTEGER  {
                 n1(1),
                 n2(2),
                 n3(3),
                 n4(4),
                 n5(5),
                 n6(6),
                 n7(7),
                 n8(8),
                 n9(9) }
   ACCESS     read-only
   STATUS     mandatory
   DESCRIPTION
     "This attribute indicates the type of traffic management which is 
      applied to the receive direction of this connection as defined in the 
      ATM Forum. The rxTrafficDescType determines the number and 
      meaning of the parameters in the rxTrafficDescParm attribute."
::= { mscAtmIfVptTmOperEntry 40 }

mscAtmIfVptTmRxQosClass OBJECT-TYPE
   SYNTAX     INTEGER  {
                 n0(0),
                 n1(1),
                 n2(2),
                 n3(3),
                 n4(4),
                 notApplicable(14),
                 sameAsFwd(15) }
   ACCESS     read-only
   STATUS     mandatory
   DESCRIPTION
     "This attribute indicates the quality of service for the called to calling 
      direction for this connection. This is only applicable to Soft PVC 
      and SVC connections. 
      
      Class 1 supports a QOS that meets Service Class A performance 
      requirements (circuit emulation, constant bit rate video).
      
      Class 2 supports a QOS that meets Service Class B performance 
      requirements (variable bit rate audio and video).
      
      Class 3 supports a QOS that meets Service Class C performance 
      requirements (Connection-Oriented Data Transfer).
      
      Class 4 supports a QOS that meets Service Class D performance 
      requirements (Connectionless Data Transfer).
      
      Class 0 is the unspecified QOS class; no objective is specified for 
      the performance parameters.
      
      A value of notApplicable is displayed in the case of nailed-up PVCs 
      for which this attribute has no significance."
::= { mscAtmIfVptTmOperEntry 61 }

mscAtmIfVptTmAtmServiceCategory OBJECT-TYPE
   SYNTAX     INTEGER  {
                 unspecifiedBitRate(0),
                 constantBitRate(1),
                 rtVariableBitRate(2),
                 nrtVariableBitRate(3),
                 availableBitRate(4) }
   ACCESS     read-only
   STATUS     mandatory
   DESCRIPTION
     "This attribute indicates the ATM service category used for traffic in 
      both directions of the connection. 
      
      The constantBitRate service category is intended for real time 
      applications, that is, those requiring tightly constrained delay and 
      delay variation, as would be appropriate for voice and video 
      applications. The consistent availability of a fixed quantity of 
      bandwidth is considered appropriate for CBR service. Cells which 
      are delayed beyond the value specified by Cell Transfer Delay are 
      assumed to have significantly reduced value for the application.
      
      The rtVariableBitRate service category is intended for real time 
      applications; that is those requiring tightly constrained delay and 
      delay variation, as would be appropriate for voice and video 
      applications. Sources are expected to transmit at a rate which varies 
      with time. Equivalently, the source can be described as 'bursty'. 
      Cells which are delayed beyond the value specified by Cell Transfer 
      Delay are assumed to be of significantly reduced value to the 
      application. Real time VBR service may support statistical 
      multiplexing of real time sources.
      
      The nrtVariableBitRate service category is intended for non-real 
      time applications which have bursty traffic characteristics and which 
      can be characterized in terms of a PCR, SCR, and MBS. For those 
      cells which are transferred within the traffic contract, the application 
      expects a low cell loss ratio. For all connections, it expects a bound 
      on the mean cell transfer delay. Non-real time VBR service may 
      support statistical multiplexing of connections.
      
      The availableBitRate service is an ATM layer service category for 
      which the limiting ATM layer transfer characteristics provided by 
      the network may change subsequent to connection establishment. 
      ABR service has a flow control mechanism which supports several 
      types of feedback to control the source rate in response to changing 
      ATM layer transfer characteristics. ABR service is not intended to 
      support real-time applications.
      
      The unspecifiedBitRate service is intended for non-real time 
      applications, that is those not requiring tightly constrained delay 
      and delay variation. UBR sources are expected to be bursty. UBR 
      service supports a high degree of statistical multiplexing among 
      sources. UBR service does not specify traffic related service 
      guarantees. No numerical commitments are made with respect to 
      the cell loss ratio experienced by a UBR connection, or as to the 
      cell transfer delay experienced by cells on the connection."
::= { mscAtmIfVptTmOperEntry 62 }

mscAtmIfVptTmTrafficShaping OBJECT-TYPE
   SYNTAX     INTEGER  {
                 disabled(1),
                 notApplicable(4),
                 linear(5),
                 inverseUpc(6) }
   ACCESS     read-only
   STATUS     mandatory
   DESCRIPTION
     "This attribute indicates the traffic shaping state of the connection.
      
      A value of notApplicable indicates that traffic shaping is not 
      applicable or not supported for this connection. This is the case:
      - when the txTrafficDescType is 1 or 2.
      - for standard Vpt Vccs and basic Vpts.
      - for CQC-based ATM cards, when the atmServiceCategory is 
      constantBitRate.
      
      In these cases, the value of notApplicable is set regardless of 
      whether traffic shaping is enabled or disabled in the provisioning 
      data.
      
      For the 1pOC12SmLrAtm card, traffic shaping is not available, 
      therefore this attribute is always notApplicable.
      
      A value of disabled indicates that traffic shaping is applicable and 
      supported for the type of connection but has been turned off in the 
      provisioning data.
      
      A value of linear or inverseUpc indicates that traffic shaping is 
      applicable and supported for the type of connection and has been 
      turned on in the provisioning data. This is the only case that 
      indicates that traffic shaping is performed on the connection. In this 
      case, the actual shaping rate is reflected in the txTrafficDescParm 
      attribute, parameter number 4. A value of linear indicates that 
      traffic is being shaped at the constant rate indicated in 
      txTrafficDescParm 4.
      
      A value of inverseUpc is possible only on ATM IP cards. This value 
      indicates that the shaper strictly conforms to the requirements of a 
      dual leaky bucket UPC enforcer. This value is indicated if traffic 
      shaping is enabled, and the txTrafficDescType for this connection is 
      6, 7 or 8.
      
      Traffic shaping for connections with atmServiceCategory as 
      availableBitRate (txTrafficDescType 9) depends upon the 
      abrConnectionType attribute. If abrConnectionType is sourceDest 
      or virtualSourceDest, the value of this attribute is linear. If 
      abrConnectionType is erSwitch or efciSwitch, this attribute is 
      notApplicable."
::= { mscAtmIfVptTmOperEntry 70 }

mscAtmIfVptTmBearerClassBbc OBJECT-TYPE
   SYNTAX     INTEGER  {
                 a(1),
                 c(3),
                 x(16),
                 vp(24),
                 notApplicable(30) }
   ACCESS     read-only
   STATUS     mandatory
   DESCRIPTION
     "This attribute indicates the bearer capability for this connection.
      
      Class a service is a connection-oriented, constant bit rate ATM 
      transport service. Class a service has end to end timing 
      requirements and may require stringent cell loss, cell delay and cell 
      delay variation performance.When a is displayed, the user is 
      requesting more than an ATM only service. The network may look 
      at the AAL to provide interworking based upon its contents. 
      
      Class c service is a connection-oriented, variable bit rate ATM 
      transport service. Class c service has no end-to-end timing 
      requirements.When c is displayed, the user is requesting more than 
      an ATM only service. The network interworking function may look 
      at the AAL and provide service based on it.
      
      Class x service is a connection-oriented ATM transport service 
      where the AAL, trafficType (cbr or vbr), and timing requirements 
      are user defined (that is, transparent to the network). When the 
      value of this attribute is x, the user is requesting an ATM only 
      service from the network. In this case, the network shall not process 
      any higher layer protocol.
      
      Class vp service is used to indicate a transparent VP service when 
      the user is requesting an ATM only service from the network. In this 
      case, the network does not process any higher layer protocol. This 
      service differs from class x service in that with the class vp service 
      both the VCI field (except for VCI values 0, 3, 4, and 6 through 15) 
      and Payload Type field are transported transparently by the network. 
      This attribute value is only applicable to SPVP and SVP 
      connections.
      
      A value of notApplicable is displayed in the case of nailed-up PVCs 
      for which this attribute has no significance."
::= { mscAtmIfVptTmOperEntry 71 }

mscAtmIfVptTmTransferCapabilityBbc OBJECT-TYPE
   SYNTAX     INTEGER  {
                 n0(0),
                 n1(1),
                 n2(2),
                 n5(5),
                 n8(8),
                 n9(9),
                 n10(10),
                 notApplicable(30) }
   ACCESS     read-only
   STATUS     mandatory
   DESCRIPTION
     "This attribute indicates the transfer capability for this connection. 
      Uni 3.0/3.1 traffic type and end-to-end timing parameters are 
      mapped into this parameter as follows:
      <transferCapability: TrafficType, Timing>
      0: NoIndication, NoIndication
      1: NoIndication, yes
      2: NoIndication, no
      5: CBR, yes
      8: VBR, NoIndication
      9: VBR, yes
      10: VBR, no
      
      A value of notApplicable is displayed in the case of nailed-up PVCs 
      for which this attribute has no significance, or in the case that the 
      transfer capability in the call request was set to NoIndication.
      
      The CBR traffic type refers to traffic offered on services such as a 
      constant bit rate video service or a circuit emulation.
      
      The VBR traffic type refers to traffic offered on services such as 
      packetized audio and video, or data.
      
      The value NoIndication for traffic type is used if the user has not set 
      the traffic type; similarly for end-to-end timing.
      
      The value yes for end-to-end timing indicates that end-to-end 
      timing is required for the connection.
      
      The value no for end-to-end timing indicates that end-to-end timing 
      is not required for the connection."
::= { mscAtmIfVptTmOperEntry 72 }

mscAtmIfVptTmClippingBbc OBJECT-TYPE
   SYNTAX     INTEGER  {
                 no(0),
                 yes(1),
                 notApplicable(14) }
   ACCESS     read-only
   STATUS     mandatory
   DESCRIPTION
     "This attribute indicates the value of the clipping susceptibility 
      parameter in the broadband bearer capability (BBC) Information 
      Element.
      
      Clipping is an impairment in which the first fraction of a second of 
      information to be transferred is lost. It occurs after a call is 
      answered and before an associated connection is switched through.
      
      A value of notApplicable is displayed in the case of nailed-up PVCs 
      for which this attribute has no significance."
::= { mscAtmIfVptTmOperEntry 74 }

mscAtmIfVptTmUnshapedTransmitQueueing OBJECT-TYPE
   SYNTAX     INTEGER  {
                 perVc(0),
                 common(1),
                 notApplicable(4),
                 fifo(5) }
   ACCESS     read-only
   STATUS     mandatory
   DESCRIPTION
     "This attribute indicates the unshaped transmit queuing state of the 
      connection.
      
      A value of common indicates that transmit traffic is being enqueued 
      onto the common transmit queue for this service category. 
      The txQueueLength attribute indicates the current length of the 
      common transmit queue.
      
      A value of fifo indicates that transmit traffic is being queued in a 
      first-in-first-out basis for this service category. This is similar to 
      common queueing, but the txQueueLength attribute indicates the 
      number of cells in this connection queue. A value of fifo will only 
      be indicated for connections on ATM IP cards with 
      atmServiceCategory of nrtVbr or ubr. 
      
      A value of perVc indicates that transmit traffic is being enqueued 
      onto a per-VC queue for this connection. 
      
      A value of notApplicable indicates that transmit traffic is being 
      shaped for this connection, or that unshaped transmit queuing is not 
      applicable for this type of connection. Transmit traffic for a shaped 
      connection is enqueued onto a per-VC queue, but this attribute is 
      only applicable for unshaped connections. Unshaped transmit 
      queuing is not applicable for basic Vpts.
      
      For 1pOC12SmLrAtm cards, perVc queueing is not available thus 
      this attribute only indicates common or notApplicable."
::= { mscAtmIfVptTmOperEntry 75 }

mscAtmIfVptTmBestEffort OBJECT-TYPE
   SYNTAX     INTEGER  {
                 indicated(0),
                 notIndicated(1),
                 notApplicable(14) }
   ACCESS     read-only
   STATUS     mandatory
   DESCRIPTION
     "This attribute indicates value of best effort parameter in the ATM 
      Traffic Descriptor Information Element.
      
      The value indicated implies that the quality of service for this 
      connection is not guaranteed.
      
      The value notIndicated implies that the quality of service for this 
      connection is guaranteed.
      
      A value of notApplicable is displayed in the case of nailed-up PVCs 
      for which this attribute has no significance."
::= { mscAtmIfVptTmOperEntry 76 }

mscAtmIfVptTmForceTagging OBJECT-TYPE
   SYNTAX     INTEGER  {
                 enabled(0),
                 disabled(1) }
   ACCESS     read-only
   STATUS     mandatory
   DESCRIPTION
     "This attribute indicates the state of force tagging option for this 
      connection. Force tagging refers to setting the CLP bit for all cells 
      on a connection. 
      
      For CQC-based ATM cards, this attribute is not applicable and is 
      not displayed.
      
      A value of enabled indicates that the CLP bit is being set to 1 for all 
      cells in the transmit direction on this connection. 
      
      A value of disabled indicates that the CLP bit is unchanged for cells 
      in the transmit direction on this connection. disabled is always 
      displayed for Vpts since forced tagging is applied on a per Vpt Vcc 
      basis."
::= { mscAtmIfVptTmOperEntry 78 }

mscAtmIfVptTmWeight OBJECT-TYPE
   SYNTAX     Unsigned32 (0 | 1..4095 | 65534)
   ACCESS     read-only
   STATUS     mandatory
   DESCRIPTION
     "This attribute indicates the relative weight of this unshaped 
      connection. Connections with a larger weight get a larger proportion 
      of the link bandwidth or in the case of standard Vpt Vccs, the Vpt 
      bandwidth.
      
      For all but standard Vpt Vccs, the default connection weight is 
      determined by the weight policy for a service category and the 
      traffic descriptor for a connection. For standard Vpt Vccs, the 
      default connection weight is determined by the Vcc's service 
      category.
      
      For CQC-based ATM cards, this attribute is not applicable and is 
      not displayed.
      
      A value from 1 to 4095 indicates an actual weight. The value 
      upToQueueLimit indicates that the weight of a connection is up to 
      the transmit queue limit for this connection. upToQueueLimit is 
      used with common (first-in-first-out) queueing. 
      
      This attribute is displayed as notApplicable if:
      - this connection has trafficShaping displayed as linear or 
      inverseUpc.
      - this is a basic Vpt.

      VALUES (

      0 = upToQueueLimit

      65534 = notApplicable

      )"
::= { mscAtmIfVptTmOperEntry 79 }

mscAtmIfVptTmUsageParameterControl OBJECT-TYPE
   SYNTAX     INTEGER  {
                 enforced(0),
                 disabled(1),
                 notApplicable(3),
                 monitored(4) }
   ACCESS     read-only
   STATUS     mandatory
   DESCRIPTION
     "This attribute indicates the UPC state of the connection.
      
      A value of notApplicable indicates that UPC is not applicable or not 
      supported for the connection. This is the case:
      - when the connection's rxTrafficDescType is 1 or 2. 
      - for standard Vpt Vccs and basic Vpts.
      
      A value of notApplicable is set regardless of whether UPC is 
      disabled or enabled in provisioning data.
      
      A value of disabled indicates that UPC is applicable and supported 
      for the type of connection but has been turned off in the 
      provisioning data.
      
      A value of enforced indicates that UPC is actively checking 
      conformance for the connection and is discarding or tagging cells 
      which do not conform to the connection traffic contract. The traffic 
      descriptor parameters used for UPC conformance are reflected in 
      the rxTrafficDescParms of the connection. On ATM IP cards, the 
      counts of UPC violations are visible in the Vcc, Vpc or Vpt 
      rxUpcViolationsOnEnforcer1 or rxUpcViolationsOnEnforcer2 
      attributes. 
      
      ATM IP cards provide the ability to monitor UPC violations without 
      tagging or discarding. A value of monitored indicates that UPC is 
      actively checking conformance for the connection and counting the 
      violations, but is not discarding or tagging cells which do not 
      conform to the connection traffic contract. The traffic descriptor 
      parameters used for UPC conformance are reflected in the 
      rxTrafficDescParms of the connection. The counts of UPC 
      violations are visible in the Vcc, Vpc or Vpt. 
      rxUpcViolationsOnEnforcer1 or rxUpcViolationsOnEnforcer2 
      attributes. The value of monitored appears only on ATM IP cards. 
      
      If the atmServiceCategory for this connection is availableBitRate, a 
      value of enforced indicates that Dynamic Generic Cell Rate 
      Algorithm (DGCRA) is active for the connection. The traffic 
      descriptor parameters used for DGCRA enforcement are reflected in 
      the rxTrafficDescParm of the connection."
::= { mscAtmIfVptTmOperEntry 80 }

mscAtmIfVptTmTxPacketWiseDiscard OBJECT-TYPE
   SYNTAX     OCTET STRING (SIZE (1))
   ACCESS     read-only
   STATUS     mandatory
   DESCRIPTION
     "This attribute indicates the current set of packet-wise discard 
      functions in effect in the transmit data direction at this connection 
      point.
      
      A value of ppd indicates that the Partial Packet Discard (PPD) 
      function is in effect. PPD may be applied at an intermediate 
      connecting point for a connection which is transporting frame traffic 
      (AAL5 at the endpoint). PPD is controlled by provisioning for 
      PVCs and SPVCs, and by call setup parameters in the AAL and 
      Traffic Descriptor Information Elements.
      
      A value of epd indicates that the Early Packet Discard (EPD) 
      function is in effect at this connection endpoint. On CQC-based 
      ATM cards, PPD and EPD are enabled by default at a connection 
      endpoint which is performing AAL5 segmentation and assembly.
      
      A value of wred indicates that Weighted Random Early Detection is 
      in effect at this connection point. W-RED can be enabled by 
      provisioning for PVCs and SPVCs.
      
      On ATM IP cards, all packet-wise discard functions also apply to 
      provisioned virtual path connections (VPCs). On CQC-based ATM 
      cards, packet-wise functions are not applicable for VPCs.
      
      This attribute is not applicable for Vpts.

      Description of bits:
      ppd(0)
      epd(1)
      wred(2)"
::= { mscAtmIfVptTmOperEntry 85 }

mscAtmIfVptTmRxPacketWiseDiscard OBJECT-TYPE
   SYNTAX     OCTET STRING (SIZE (1))
   ACCESS     read-only
   STATUS     mandatory
   DESCRIPTION
     "This attribute indicates the current set of packet-wise discard 
      functions in effect in the receive data direction at this connection 
      point.
      
      A value of ppd indicates that the Partial Packet Discard (PPD) 
      function is in effect. PPD may be applied at an intermediate 
      connecting point for a connection which is transporting frame traffic 
      (AAL5 at the endpoint). PPD is controlled by provisioning for 
      PVCs and SPVCs, and by call setup parameters in the AAL and 
      Traffic Descriptor Information Elements.
      
      A value of epd indicates that the Early Packet Discard (EPD) 
      function is in effect at this connection endpoint. PPD and EPD are 
      enabled by default at a connection endpoint which is performing 
      AAL5 segmentation and assembly.
      
      On ATM IP cards, all packet-wise discard functions also apply to 
      provisioned virtual path connections (VPCs). On CQC-based ATM 
      cards, packet-wise functions are not applicable for VPCs.
      
      This attribute is not applicable for Vpts.

      Description of bits:
      ppd(0)
      epd(1)"
::= { mscAtmIfVptTmOperEntry 86 }

mscAtmIfVptTmBandwidthElastic OBJECT-TYPE
   SYNTAX     INTEGER  {
                 no(0),
                 yes(1) }
   ACCESS     read-only
   STATUS     mandatory
   DESCRIPTION
     "This attribute is only of importance for connections which are 
      carried on a link with a variable bandwidth. For example, the 
      bandwidth may be reduced in the event that one or more physical 
      links in the IMA group fail, such that the originally requested 
      bandwidth cannot be maintained. This attribute shows whether the 
      application (for example, Trunk) running on this connection can 
      continue to operate if the bandwidth is reduced. If the bandwidth is 
      reduced, the amount by which it is reduced is displayed in the 
      bandwidthReduction attribute. 
      
      A value of yes, indicates that this connection is elastic, and the 
      bandwidth may be reduced but the connection is not released. 
      
      A value of no indicates that the bandwidth for this connection is not 
      reduced in the event of link bandwidth reduction. However, this 
      connection may be released based on its holdingPriority.
      
      Bandwidth elasticity has no effect for connections which have an 
      equivalent cell rate (ECR) of zero. 
      
      This attribute is not applicable for Vpts and Vpt Vccs."
::= { mscAtmIfVptTmOperEntry 90 }

mscAtmIfVptTmBandwidthReduction OBJECT-TYPE
   SYNTAX     Unsigned32 (0..2147483647)
   ACCESS     read-only
   STATUS     mandatory
   DESCRIPTION
     "This attribute shows the amount by which the bandwidth has been 
      reduced for this connection. This value is non-zero only for 
      connections which have bandwidthElastic displayed as yes, and 
      which are also operating in a reduced bandwidth mode. This is 
      typically the case for selected connections running over an IMA 
      link. This attribute takes a value from 0 (no reduction) up to the 
      ECR. For all connections which are running at their full allocated 
      bandwidth, bwReduction has the value 0. Connections which have 
      been reduced in allocated bandwidth have a positive number for this 
      attribute. The bwReduction may be subtracted from the ECR (which 
      is displayed as txTrafficDescParm 5) to determine the actual 
      bandwidth allocated to this connection."
::= { mscAtmIfVptTmOperEntry 100 }

mscAtmIfVptTmAbrConnectionType OBJECT-TYPE
   SYNTAX     INTEGER  {
                 erSwitch(1),
                 efciSwitch(2),
                 virtualSourceDest(3),
                 sourceDest(4),
                 nonAbrInterworking(5),
                 notApplicable(15) }
   ACCESS     read-only
   STATUS     mandatory
   DESCRIPTION
     "This attribute indicates the type of ABR behavior which is in effect 
      at this connection. This attribute is only applicable if the 
      atmServiceCategory attribute is availableBitRate. If the 
      atmServiceCategory attribute is not availableBitRate, this attribute 
      value is set to notApplicable.
      
      For CQC-based ATM cards and the 1pOC12SmLrAtm card, the 
      notApplicable, efciSwitch or nonAbrInterworking. In EFCI 
      marking mode, the Explicit Forward Congestion Indication (EFCI) 
      field in the data cell headers is used to indicate transmit queue 
      congestion. 
      
      For ATM IP cards other than 1pOC12SmLrAtm, if the displayed as 
      connectionEndPoint, this attribute has the value sourceDest. In this 
      mode, the ABR Source and Destination behavior is in effect at this 
      connection. This attribute is also sourceDest in the case where the 
      next hop connection is specified as nonAbrInterworking. The next 
      hop connection is the Vcc or Vpc identified by the nextHop attribute 
      of the Nrp or Rp component. 
      
      If the connectionPointType is not connectionEndPoint, the value of 
      this attribute depends upon the abrConnectionType provisioning 
      and the card type to which the traffic is forwarded on the backplane. 
      The default abrConnectionType is provisioned at the CA Abr 
      abrConnectionType attribute, and may be overridden for a 
      provisioned connection in the Vcd Tm abrConnectionType or Vpd 
      Tm abrConnectionType attribute. If the CA Abr abrConnectionType 
      attribute is virtualSourceDest at either one of the two connection 
      points, and if both the connection points are defined on ATM IP 
      cards, virtual source and destination behavior is applied to the 
      connection. In this instance, the attribute displays the value 
      virtualSourceDest.
      
      This attribute has the value erSwitch if ABR explicit rate 
      functionality is in effect at this connection. In this mode, the switch 
      may modify the Explicit Rate (ER) field of backward Resource 
      Management (RM) cells to indicate the status of congestion at this 
      connection point.
      
      This attribute has the value nonAbrInterworking in the case where 
      this connection point is functioning as an SPVC origin for an ABR 
      connection where the link side of this connection is configured as a 
      non-ABR ATM service category. This means that there are no RM 
      cells on the link side of this connection, and that the next hop 
      connection point is performing as an ABR sourceDest."
::= { mscAtmIfVptTmOperEntry 110 }

mscAtmIfVptTmTxTdpTable OBJECT-TYPE
   SYNTAX     SEQUENCE OF MscAtmIfVptTmTxTdpEntry
   ACCESS     not-accessible
   STATUS     mandatory
   DESCRIPTION
     "This attribute is a vector of five transmit traffic parameters whose 
      mapping is defined by the txTrafficDescType attribute. 
      
      The values of peak cell rate (PCR), sustained cell rate (SCR), 
      Minimum Cell Rate (MCR), actual cell rate (ACR), explicit rate 
      (ER), equivalent cell rate (ECR), and actual shaping rate are 
      expressed in cell/s. Maximum burst size (MBS) is expressed in 
      cells. CDVT is expressed in microseconds. 
      
      When txTrafficDescType is 1 or 2, parameters 1 through 5 are 
      unused.
      
      In this description, PCR is the greater of either the PCR or the 
      requested shaping rate (parameter 1 or parameter 5) specified in the 
      txTrafficDescParm attribute under the Vcd Tm or Vpd Tm 
      component.
      
      When txTrafficDescType is 3, parameter 1 represents the PCR for 
      CLP equal to 0 or 1 traffic; parameters 2 and 3 are unused.
      
      When txTrafficDescType is 4, parameter 1 represents the PCR for 
      CLP equal to 0 and 1 traffic; parameter 2 represents the PCR for 
      CLP equal to 0 traffic with cell discard.
      
      When txTrafficDescType is 5, parameter 1 represents the PCR for 
      CLP equal to 0 and 1 traffic; parameter 2 represents the PCR for 
      CLP equal to 0 traffic with cell tagging.
      
      When txTrafficDescType is 6, parameter 1 represents the PCR for 
      CLP equal to 0 and 1 traffic; parameter 2 represents the SCR for 
      CLP equal to 0 and 1 traffic; parameter 3 represents the MBS for 
      CLP equal to 0 and 1 traffic.
      
      When txTrafficDescType is 7, parameter 1 represents the PCR for 
      CLP equal to 0 and 1 traffic; parameter 2 represents the SCR for 
      CLP equal to 0 traffic with cell discard; parameter 3 represents the 
      MBS for CLP equal to 0 traffic.
      
      When txTrafficDescType is 8, parameter 1 represents the PCR for 
      CLP equal to 0 and 1 traffic; parameter 2 represents the SCR for 
      CLP equal to 0 traffic with cell tagging; parameter 3 represents the 
      MBS for CLP equal to 0 traffic.
      
      When txTrafficDescType is 3, 4, 5, 6, 7, or 8, parameter 4 reflects 
      the actual shaping rate in cell/s for this connection. For CQC-based 
      ATM cards, the set of available shaping rates is based on the 
      number of interfaces doing shaping (attribute 
      perVcQueueInterfaces), and the shapingScalingFactor attribute of 
      the Arc Cqc Override component. A rate of zero (0) indicates that 
      shaping is not performed, or that the interface is down. 
      
      When txTrafficDescType is 9, parameter 1 represents the PCR; 
      parameter 2 represents the Cell Delay Variation Toleration (CDVT); 
      parameter 3 represents the Minimum Cell Rate (MCR); the meaning 
      of parameter 4 depends upon the value of the abrConnectionType 
      attribute. if abrConnectionType is sourceDest or 
      virtualSourceDest, parameter 4 represents the Allowed Cell Rate 
      (ACR); If abrConnectionType is erSwitch, parameter 4 represents 
      the Explicit Rate (ER); and if abrConnectionType is efciSwitch, 
      parameter 4 reflects the actual shaping rate in cell/s for this 
      connection.
      
      When txTrafficDescType is 3, 4, 5, 6, 7, 8, or 9, parameter 5 reflects 
      the equivalent cell rate in cell/s for this connection as determined by 
      the Connection Admission Control (CAC) algorithm. The 
      equivalent cell rate is useful in determining the admission 
      characteristics of this connection."
::= { mscAtmIfVptTm 451 }

mscAtmIfVptTmTxTdpEntry OBJECT-TYPE
   SYNTAX     MscAtmIfVptTmTxTdpEntry
   ACCESS     not-accessible
   STATUS     mandatory
   DESCRIPTION
     "An entry in the mscAtmIfVptTmTxTdpTable."
   INDEX {
      mscAtmIfIndex,
      mscAtmIfVptIndex,
      mscAtmIfVptTmIndex,
      mscAtmIfVptTmTxTdpIndex }
::= { mscAtmIfVptTmTxTdpTable 1 }

MscAtmIfVptTmTxTdpEntry ::= SEQUENCE {
   mscAtmIfVptTmTxTdpIndex
      Integer32,
   mscAtmIfVptTmTxTdpValue
      Unsigned32 }

mscAtmIfVptTmTxTdpIndex OBJECT-TYPE
   SYNTAX     Integer32 (1..5)
   ACCESS     not-accessible
   STATUS     mandatory
   DESCRIPTION
     "This variable represents the mscAtmIfVptTmTxTdpTable
      specific index for the mscAtmIfVptTmTxTdpTable."
::= { mscAtmIfVptTmTxTdpEntry 1 }

mscAtmIfVptTmTxTdpValue OBJECT-TYPE
   SYNTAX     Unsigned32 (0..2147483647)
   ACCESS     read-only
   STATUS     mandatory
   DESCRIPTION
     "This variable represents an individual value for the
      mscAtmIfVptTmTxTdpTable."
::= { mscAtmIfVptTmTxTdpEntry 2 }

mscAtmIfVptTmTxQThreshTable OBJECT-TYPE
   SYNTAX     SEQUENCE OF MscAtmIfVptTmTxQThreshEntry
   ACCESS     not-accessible
   STATUS     mandatory
   DESCRIPTION
     "This attribute indicates the queue limit and the discard thresholds 
      for the transmit queue of this connection. 
      
      If this connection has unshapedTransmitQueueing attribute 
      displayed as common, this attribute displays the thresholds of the 
      common queue. If this connection has unshapedTransmitQueueing 
      attribute displayed as perVc or as notApplicable, this attribute 
      displays the thresholds of the per-VC queue.
      
      The first element indicates the queue limit. The provisioned value of 
      the transmit queue limit is derived from the txQueueLimit attribute 
      under the service category subcomponents of the CA component for 
      the service category of this connection. 
      
      The second element is the threshold that marks the transition from 
      congestion state 1 to congestion state 0. This is the threshold at 
      which traffic with discard priority (DP) = 1 is discarded. This 
      threshold is set at approximately 90 percent of the first parameter, 
      the operational queue limit.
      
      The third element is the threshold that marks the transition from 
      congestion state 2 to congestion state 1. This is the threshold at 
      which traffic with DP = 2 is discarded. This threshold is set at 
      approximately 75 percent of the first parameter, the operational 
      queue limit.
      
      The fourth element is the threshold that marks the transition from 
      congestion state 3 to congestion state 2. This is the threshold at 
      which traffic with DP = 3 is discarded. This threshold is set at 
      approximately 35 percent of the first parameter, the operational 
      queue limit.
      
      This attribute does not apply to basic Vpts."
::= { mscAtmIfVptTm 452 }

mscAtmIfVptTmTxQThreshEntry OBJECT-TYPE
   SYNTAX     MscAtmIfVptTmTxQThreshEntry
   ACCESS     not-accessible
   STATUS     mandatory
   DESCRIPTION
     "An entry in the mscAtmIfVptTmTxQThreshTable."
   INDEX {
      mscAtmIfIndex,
      mscAtmIfVptIndex,
      mscAtmIfVptTmIndex,
      mscAtmIfVptTmTxQThreshIndex }
::= { mscAtmIfVptTmTxQThreshTable 1 }

MscAtmIfVptTmTxQThreshEntry ::= SEQUENCE {
   mscAtmIfVptTmTxQThreshIndex
      Integer32,
   mscAtmIfVptTmTxQThreshValue
      Unsigned32 }

mscAtmIfVptTmTxQThreshIndex OBJECT-TYPE
   SYNTAX     Integer32 (0..3)
   ACCESS     not-accessible
   STATUS     mandatory
   DESCRIPTION
     "This variable represents the mscAtmIfVptTmTxQThreshTable
      specific index for the mscAtmIfVptTmTxQThreshTable."
::= { mscAtmIfVptTmTxQThreshEntry 1 }

mscAtmIfVptTmTxQThreshValue OBJECT-TYPE
   SYNTAX     Unsigned32 (0..512000)
   ACCESS     read-only
   STATUS     mandatory
   DESCRIPTION
     "This variable represents an individual value for the
      mscAtmIfVptTmTxQThreshTable."
::= { mscAtmIfVptTmTxQThreshEntry 2 }

mscAtmIfVptTmRxTdpTable OBJECT-TYPE
   SYNTAX     SEQUENCE OF MscAtmIfVptTmRxTdpEntry
   ACCESS     not-accessible
   STATUS     mandatory
   DESCRIPTION
     "This attribute is a vector of four traffic parameters whose meanings 
      are defined by the rxTrafficDescType attribute. The values of peak 
      cell rate (PCR), sustained cell rate (SCR), minimum cell rate 
      (MCR) are expressed in cell/s. Maximum burst size (MBS) is 
      expressed in cells. Cell delay variation tolerance (CDVT) is 
      expressed in microseconds.
      
      When rxTrafficDescType is 1 or 2, none of the parameters are used.
      
      When rxTrafficDescType is 3, parameter 1 represents the PCR for 
      CLP equal to 0 and 1 traffic; parameter 4 represents the CDVT.
      
      When rxTrafficDescType is 4, parameter 1 represents the PCR for 
      CLP equal to 0 and 1 traffic; parameter 2 represents the PCR for 
      CLP equal to 0 traffic with cell discard; parameter 4 represents the 
      CDVT.
      
      When rxTrafficDescType is 5, parameter 1 represents the PCR for 
      CLP equal to 0 and 1 traffic; parameter 2 represents the PCR for 
      CLP equal to 0 traffic with cell tagging; parameter 4 represents the 
      CDVT.
      
      When rxTrafficDescType is 6, parameter 1 represents the PCR for 
      CLP equal to 0 and 1 traffic; parameter 2 represents the SCR for 
      CLP equal to 0 and 1 traffic; parameter 3 represents the MBS for 
      CLP equal to 0 and 1 traffic; parameter 4 represents the CDVT. 
      
      When rxTrafficDescType is 7, parameter 1 represents the PCR for 
      CLP equal to 0 and 1 traffic; parameter 2 represents the SCR for 
      CLP equal to 0 traffic with cell discard; parameter 3 represents the 
      MBS for CLP equal to 0 traffic; parameter 4 represents the CDVT.
      
      When rxTrafficDescType is 8, parameter 1 represents the PCR for 
      CLP equal to 0 and 1 traffic; parameter 2 represents the SCR for 
      CLP equal to 0 traffic with cell tagging; parameter 3 represents the 
      MBS for CLP equal to 0 traffic; parameter 4 represents the CDVT. 
      
      When rxTrafficDescType is 9, parameter 1 represents the PCR; 
      parameter 2 represents CDVT; parameter 3 represents the MCR; 
      parameter 4 is not used.
      
      If upc is disabled for this connection, the values of PCR, SCR, 
      MBS and CDVT are the provisioned parameters.
      
      If upc is enabled, the values of PCR, SCR, MBS, and CDVT are 
      exactly the values used by the usage parameter control hardware in 
      policing the arriving traffic. These may vary slightly from the 
      provisioned values due to granularity of the hardware. In the case 
      where the PCR is equal to the SCR, the effective MBS is zero."
::= { mscAtmIfVptTm 453 }

mscAtmIfVptTmRxTdpEntry OBJECT-TYPE
   SYNTAX     MscAtmIfVptTmRxTdpEntry
   ACCESS     not-accessible
   STATUS     mandatory
   DESCRIPTION
     "An entry in the mscAtmIfVptTmRxTdpTable."
   INDEX {
      mscAtmIfIndex,
      mscAtmIfVptIndex,
      mscAtmIfVptTmIndex,
      mscAtmIfVptTmRxTdpIndex }
::= { mscAtmIfVptTmRxTdpTable 1 }

MscAtmIfVptTmRxTdpEntry ::= SEQUENCE {
   mscAtmIfVptTmRxTdpIndex
      Integer32,
   mscAtmIfVptTmRxTdpValue
      Unsigned32 }

mscAtmIfVptTmRxTdpIndex OBJECT-TYPE
   SYNTAX     Integer32 (1..4)
   ACCESS     not-accessible
   STATUS     mandatory
   DESCRIPTION
     "This variable represents the mscAtmIfVptTmRxTdpTable
      specific index for the mscAtmIfVptTmRxTdpTable."
::= { mscAtmIfVptTmRxTdpEntry 1 }

mscAtmIfVptTmRxTdpValue OBJECT-TYPE
   SYNTAX     Unsigned32 (0..2147483647)
   ACCESS     read-only
   STATUS     mandatory
   DESCRIPTION
     "This variable represents an individual value for the
      mscAtmIfVptTmRxTdpTable."
::= { mscAtmIfVptTmRxTdpEntry 2 }

mscAtmIfVptTmTqpTable OBJECT-TYPE
   SYNTAX     SEQUENCE OF MscAtmIfVptTmTqpEntry
   ACCESS     not-accessible
   STATUS     mandatory
   DESCRIPTION
     "This attribute is a vector of three elements that indicate the quality 
      of service parameters for the forward direction for this connection. 
      This attribute is used for SPVC and SVC connections on a PNNI 
      interface.
      
      The cdv element indicates the acceptable peak-to-peak Cell Delay 
      Variation (CDV) of real-time connections (CBR and rt-VBR). 
      
      The ctd element indicates the acceptable maximum Cell Transfer 
      Delay (maxCtd) of real-time connections (CBR and rt-VBR). 
      
      The clr element indicates the acceptable Cell Loss Ratio (CLR) of 
      CBR, rt-VBR, and nrt-VBR connections."
::= { mscAtmIfVptTm 454 }

mscAtmIfVptTmTqpEntry OBJECT-TYPE
   SYNTAX     MscAtmIfVptTmTqpEntry
   ACCESS     not-accessible
   STATUS     mandatory
   DESCRIPTION
     "An entry in the mscAtmIfVptTmTqpTable."
   INDEX {
      mscAtmIfIndex,
      mscAtmIfVptIndex,
      mscAtmIfVptTmIndex,
      mscAtmIfVptTmTqpIndex }
::= { mscAtmIfVptTmTqpTable 1 }

MscAtmIfVptTmTqpEntry ::= SEQUENCE {
   mscAtmIfVptTmTqpIndex
      INTEGER,
   mscAtmIfVptTmTqpValue
      Unsigned32 }

mscAtmIfVptTmTqpIndex OBJECT-TYPE
   SYNTAX     INTEGER  {
                 cdv(0),
                 ctd(1),
                 clr(2) }
   ACCESS     not-accessible
   STATUS     mandatory
   DESCRIPTION
     "This variable represents the mscAtmIfVptTmTqpTable
      specific index for the mscAtmIfVptTmTqpTable."
::= { mscAtmIfVptTmTqpEntry 1 }

mscAtmIfVptTmTqpValue OBJECT-TYPE
   SYNTAX     Unsigned32 (0..2147483647)
   ACCESS     read-only
   STATUS     mandatory
   DESCRIPTION
     "This variable represents an individual value for the
      mscAtmIfVptTmTqpTable."
::= { mscAtmIfVptTmTqpEntry 2 }

mscAtmIfVptTmRqpTable OBJECT-TYPE
   SYNTAX     SEQUENCE OF MscAtmIfVptTmRqpEntry
   ACCESS     not-accessible
   STATUS     mandatory
   DESCRIPTION
     "This attribute is a vector of three elements that indicate the quality 
      of service parameters for the backward direction for this 
      connection. This attribute is used for SPVC and SVC connections 
      on a PNNI interface.
      
      The cdv element indicates the acceptable peak-to-peak Cell Delay 
      Variation (CDV) of real-time connections (CBR and rt-VBR). 
      
      The ctd element indicates the acceptable maximum Cell Transfer 
      Delay (maxCtd) of real-time connections (CBR and rt-VBR). 
      
      The clr element indicates the acceptable Cell Loss Ratio (CLR) of 
      CBR, rt-VBR, and nrt-VBR connections."
::= { mscAtmIfVptTm 455 }

mscAtmIfVptTmRqpEntry OBJECT-TYPE
   SYNTAX     MscAtmIfVptTmRqpEntry
   ACCESS     not-accessible
   STATUS     mandatory
   DESCRIPTION
     "An entry in the mscAtmIfVptTmRqpTable."
   INDEX {
      mscAtmIfIndex,
      mscAtmIfVptIndex,
      mscAtmIfVptTmIndex,
      mscAtmIfVptTmRqpIndex }
::= { mscAtmIfVptTmRqpTable 1 }

MscAtmIfVptTmRqpEntry ::= SEQUENCE {
   mscAtmIfVptTmRqpIndex
      INTEGER,
   mscAtmIfVptTmRqpValue
      Unsigned32 }

mscAtmIfVptTmRqpIndex OBJECT-TYPE
   SYNTAX     INTEGER  {
                 cdv(0),
                 ctd(1),
                 clr(2) }
   ACCESS     not-accessible
   STATUS     mandatory
   DESCRIPTION
     "This variable represents the mscAtmIfVptTmRqpTable
      specific index for the mscAtmIfVptTmRqpTable."
::= { mscAtmIfVptTmRqpEntry 1 }

mscAtmIfVptTmRqpValue OBJECT-TYPE
   SYNTAX     Unsigned32 (0..2147483647)
   ACCESS     read-only
   STATUS     mandatory
   DESCRIPTION
     "This variable represents an individual value for the
      mscAtmIfVptTmRqpTable."
::= { mscAtmIfVptTmRqpEntry 2 }


-- AtmIf/n Vpc/vpi Tm AvailableBitRate, 
-- AtmIf/n Vcc/vpi.vci Tm AvailableBitRate,
-- AtmIf/n Vpt/vpi Tm AvailableBitRate,
-- AtmIf/n Vpt/vpi Vcc/vci Tm AvailableBitRate
-- This component contains ABR-related operational attributes of a 
-- connection. It is dynamically created for connections where the 
-- atmServiceCategory is availableBitRate, and where 
-- abrConnectionType is sourceDest or virtualSourceDest.

mscAtmIfVptTmAbr OBJECT IDENTIFIER ::= { mscAtmIfVptTm 2 }



mscAtmIfVptTmAbrRowStatusTable OBJECT-TYPE
   SYNTAX     SEQUENCE OF MscAtmIfVptTmAbrRowStatusEntry
   ACCESS     not-accessible
   STATUS     mandatory
   DESCRIPTION
     "This entry controls the addition and deletion of 
      mscAtmIfVptTmAbr components."
::= { mscAtmIfVptTmAbr 1 }

mscAtmIfVptTmAbrRowStatusEntry OBJECT-TYPE
   SYNTAX     MscAtmIfVptTmAbrRowStatusEntry
   ACCESS     not-accessible
   STATUS     mandatory
   DESCRIPTION
     "A single entry in the table represents a single 
      mscAtmIfVptTmAbr component."
   INDEX {
      mscAtmIfIndex,
      mscAtmIfVptIndex,
      mscAtmIfVptTmIndex,
      mscAtmIfVptTmAbrIndex }
::= { mscAtmIfVptTmAbrRowStatusTable 1 }

MscAtmIfVptTmAbrRowStatusEntry ::= SEQUENCE {
   mscAtmIfVptTmAbrRowStatus
      RowStatus,
   mscAtmIfVptTmAbrComponentName
      DisplayString,
   mscAtmIfVptTmAbrStorageType
      StorageType,
   mscAtmIfVptTmAbrIndex
      NonReplicated }

mscAtmIfVptTmAbrRowStatus OBJECT-TYPE
   SYNTAX     RowStatus 
   ACCESS     read-only
   STATUS     mandatory
   DESCRIPTION
     "This variable is used as the basis for SNMP naming of
      mscAtmIfVptTmAbr components.
      These components cannot be added nor deleted."
::= { mscAtmIfVptTmAbrRowStatusEntry 1 }

mscAtmIfVptTmAbrComponentName OBJECT-TYPE
   SYNTAX     DisplayString 
   ACCESS     read-only
   STATUS     mandatory
   DESCRIPTION
     "This variable provides the component's string name for
      use with the ASCII Console Interface"
::= { mscAtmIfVptTmAbrRowStatusEntry 2 }

mscAtmIfVptTmAbrStorageType OBJECT-TYPE
   SYNTAX     StorageType 
   ACCESS     read-only
   STATUS     mandatory
   DESCRIPTION
     "This variable represents the storage type value for the
      mscAtmIfVptTmAbr tables."
::= { mscAtmIfVptTmAbrRowStatusEntry 4 }

mscAtmIfVptTmAbrIndex OBJECT-TYPE
   SYNTAX     NonReplicated 
   ACCESS     not-accessible
   STATUS     mandatory
   DESCRIPTION
     "This variable represents the index for the mscAtmIfVptTmAbr tables."
::= { mscAtmIfVptTmAbrRowStatusEntry 10 }

mscAtmIfVptTmAbrOperTable OBJECT-TYPE
   SYNTAX     SEQUENCE OF MscAtmIfVptTmAbrOperEntry
   ACCESS     not-accessible
   STATUS     mandatory
   DESCRIPTION
     "This group contains operational attributes for connections using 
      ABR service category."
::= { mscAtmIfVptTmAbr 110 }

mscAtmIfVptTmAbrOperEntry OBJECT-TYPE
   SYNTAX     MscAtmIfVptTmAbrOperEntry
   ACCESS     not-accessible
   STATUS     mandatory
   DESCRIPTION
     "An entry in the mscAtmIfVptTmAbrOperTable."
   INDEX {
      mscAtmIfIndex,
      mscAtmIfVptIndex,
      mscAtmIfVptTmIndex,
      mscAtmIfVptTmAbrIndex }
::= { mscAtmIfVptTmAbrOperTable 1 }

MscAtmIfVptTmAbrOperEntry ::= SEQUENCE {
   mscAtmIfVptTmAbrInitialCellRate
      Unsigned32,
   mscAtmIfVptTmAbrTransientBufferExposure
      Unsigned32,
   mscAtmIfVptTmAbrFixedRoundTripTime
      Unsigned32,
   mscAtmIfVptTmAbrRateDecreaseFactor
      Unsigned32,
   mscAtmIfVptTmAbrRateIncreaseFactor
      Unsigned32,
   mscAtmIfVptTmAbrMaxCellPerRmCell
      Unsigned32,
   mscAtmIfVptTmAbrMaxTimeBetweenRmCell
      Unsigned32,
   mscAtmIfVptTmAbrCutoffDecreaseFactor
      Unsigned32,
   mscAtmIfVptTmAbrAcrDecreaseTimeFactor
      Unsigned32,
   mscAtmIfVptTmAbrForwardRmCellLimit
      Unsigned32,
   mscAtmIfVptTmAbrTxRateChangeInfo
      INTEGER,
   mscAtmIfVptTmAbrAcrRateChangeInfo
      INTEGER,
   mscAtmIfVptTmAbrTxFwdRmCells
      Unsigned32,
   mscAtmIfVptTmAbrRxEfci
      INTEGER }

mscAtmIfVptTmAbrInitialCellRate OBJECT-TYPE
   SYNTAX     Unsigned32 (0..16777215)
   ACCESS     read-only
   STATUS     mandatory
   DESCRIPTION
     "This attribute indicates the Initial Cell Rate (ICR) parameter for this 
      connection. ICR is the rate at which a source should send initially 
      and after an idle period.
      
      For nailed-up connections, this attribute is determined by the 
      provisioned value of the initialCellRate attribute. For signalled 
      connections, it is indicated in the ABR Setup Parameters 
      Information Element.
      
      The ICR for a connection is a value between the MCR and the PCR. 
      Furthermore, ICR has an upper bound determined by the 
      transientBufferExposure divided by fixedRoundTripTime."
::= { mscAtmIfVptTmAbrOperEntry 10 }

mscAtmIfVptTmAbrTransientBufferExposure OBJECT-TYPE
   SYNTAX     Unsigned32 (0..16777215)
   ACCESS     read-only
   STATUS     mandatory
   DESCRIPTION
     "This attribute indicates the Transient Buffer Exposure (TBE) for 
      this connection. TBE is the negotiated number of cells that the 
      network would like to limit the resource to send during start-up 
      periods, before the first Resource Management (RM) cell returns.
      
      For nailed-up connections, this attribute is determined by the 
      provisioned value of the transientBufferExposure attribute. For 
      signalled connections, it is indicated in the ABR Setup Parameters 
      Information Element."
::= { mscAtmIfVptTmAbrOperEntry 11 }

mscAtmIfVptTmAbrFixedRoundTripTime OBJECT-TYPE
   SYNTAX     Unsigned32 (0..16700000)
   ACCESS     read-only
   STATUS     mandatory
   DESCRIPTION
     "This attribute indicates the Fixed Round-Trip Time (FRTT) 
      parameter for this connection. FRTT is the sum of the fixed and 
      propagation delays from the source to a destination and back.
      
      For nailed-up connections, this attribute is determined by the 
      provisioned value of the fixedRoundTripTime attribute. For 
      signalled connections, it is indicated in the ABR Setup Parameters 
      Information Element."
::= { mscAtmIfVptTmAbrOperEntry 12 }

mscAtmIfVptTmAbrRateDecreaseFactor OBJECT-TYPE
   SYNTAX     Unsigned32 (0..15)
   ACCESS     read-only
   STATUS     mandatory
   DESCRIPTION
     "This attribute indicates the Rate Decrease Factor (RDF) for this 
      connection. The RDF value is computed by using the operational 
      value of this attribute, n, as 2 to the inverse power n. For example, if 
      the value of this attribute is 8, RDF is 2E-8 = 1/256.
      
      RDF controls the amount by which the cell transmission rate may 
      decrease upon receipt of a backward Resource Management (RM) 
      cell. For example, if a backward RM cell is received with the 
      Congestion Indication (CI) field set to 1, the Allowed Cell Rate 
      (ACR) value would be reduced by the amount (RDF*ACR). The 
      ACR is not allowed to fall below the Minimum Cell Rate (MCR), in 
      which case the ACR is set to MCR.
      
      For nailed-up connections, this attribute is determined by the 
      provisioned value of the rateDecreaseFactor attribute. For signalled 
      connections, it is indicated in the ABR Setup Parameters 
      Information Element."
::= { mscAtmIfVptTmAbrOperEntry 13 }

mscAtmIfVptTmAbrRateIncreaseFactor OBJECT-TYPE
   SYNTAX     Unsigned32 (0..15)
   ACCESS     read-only
   STATUS     mandatory
   DESCRIPTION
     "This attribute indicates the Rate Increase Factor (RIF) for this 
      connection. The RIF value is computed by using the operational 
      value of this attribute, n, as 2 to the inverse power n. For example, if 
      the value of this attribute is 6, RIF is 2E-6 = 1/64.
      
      RIF controls the amount by which the cell transmission rate may 
      increase upon receipt of a backward Resource Management (RM) 
      cell. For example, if a backward RM cell is received with the 
      Congestion Indication (CI) and the No Increase (NI) fields both set 
      to 0, the Allowed Cell Rate (ACR) value would be increased by the 
      amount (RIF*ACR). The ACR is not allowed to exceed the Peak 
      Cell Rate (PCR), in which case the ACR is set to PCR.
      
      For nailed-up connections, this attribute is determined by the 
      provisioned value of the rateIncreaseFactor attribute. For signalled 
      connections, it is indicated in the ABR Setup Parameters 
      Information Element."
::= { mscAtmIfVptTmAbrOperEntry 14 }

mscAtmIfVptTmAbrMaxCellPerRmCell OBJECT-TYPE
   SYNTAX     Unsigned32 (2 | 4 | 8 | 16 | 32 | 64 | 128 | 256)
   ACCESS     read-only
   STATUS     mandatory
   DESCRIPTION
     "This attribute indicates the maximum number of cells an ABR 
      source may transmit for each forward Resource Management (RM) 
      cell. The count of the cells transmitted includes data cells, OAM 
      cells, backward RM cells, and the forward RM cell.
      
      For nailed-up connections, this attribute is determined by the 
      provisioned value of the maxCellsPerRmCell attribute. For 
      signalled connections, it is indicated in the ABR Additional 
      Parameters Information Element."
::= { mscAtmIfVptTmAbrOperEntry 15 }

mscAtmIfVptTmAbrMaxTimeBetweenRmCell OBJECT-TYPE
   SYNTAX     Unsigned32 (781 | 1563 | 3125 | 6250 | 12500 | 25000 | 50000 | 100000)
   ACCESS     read-only
   STATUS     mandatory
   DESCRIPTION
     "This attribute indicates the TRM parameter for this connection.
      
      TRM provides an upper bound on the time interval between forward 
      Resource Management (RM) cells for an ABR source. Since the last 
      forward RM cell was sent, if at least TRM time has elapsed since 
      and at least 2 other cells have been sent, the next cell to be 
      transmitted would be a forward RM cell.
      
      For nailed-up connections, this attribute is determined by the 
      provisioned value of the maxTimeBetweenRmCell attribute. For 
      signalled connections, it is indicated in the ABR Additional 
      Parameters Information Element."
::= { mscAtmIfVptTmAbrOperEntry 16 }

mscAtmIfVptTmAbrCutoffDecreaseFactor OBJECT-TYPE
   SYNTAX     Unsigned32 (0 | 1 | 2 | 4 | 8 | 16 | 32 | 64)
   ACCESS     read-only
   STATUS     mandatory
   DESCRIPTION
     "This attribute indicates the Cutoff Decrease Factor (CDF) parameter 
      for this connection. When the value of this attribute is non-zero, 
      CDF is computed as the inverse of the value. For example, if the 
      value is 32, the value of CDF is 1/32. When the value of this 
      attribute is 0, CDF is also zero.
      
      CDF controls the decrease in the Allowed Cell Rate (ACR) 
      associated with the forwardRmCellLimit attribute, the limit of the 
      number of forward Resource Management (RM) cells which may 
      be sent in the absence of received backward RM cells. When this 
      limit is crossed, the ACR value would be decreased by the amount 
      (CDF*ACR). The ACR is not allowed to fall below the Minimum 
      Cell Rate (MCR), in which case the ACR is set to MCR.
      
      For nailed-up connections, this attribute is determined by the 
      provisioned value of the cutoffDecreaseFactor attribute. For 
      signalled connections, it is indicated in the ABR Additional 
      Parameters Information Element."
::= { mscAtmIfVptTmAbrOperEntry 17 }

mscAtmIfVptTmAbrAcrDecreaseTimeFactor OBJECT-TYPE
   SYNTAX     Unsigned32 (0..1023)
   ACCESS     read-only
   STATUS     mandatory
   DESCRIPTION
     "This attribute indicates the Allowed Cell Rate Decrease Time Factor 
      (ADTF) parameter for this connection.
      
      ADTF is the time interval permitted between sending forward 
      Resource Management (RM) cells before the Allowed Cell Rate 
      (ACR) is decreased to initialCellRate. In other words, if the source 
      does not transit a forward RM cell for the period specified by adtf, it 
      reduces its ACR to the value of its initialCellRate.
      
      For nailed-up connections, this attribute is determined by the 
      provisioned value of the acrDecreaseTimeFactor attribute. For 
      signalled connections, it is indicated in the ABR Additional 
      Parameters Information Element."
::= { mscAtmIfVptTmAbrOperEntry 18 }

mscAtmIfVptTmAbrForwardRmCellLimit OBJECT-TYPE
   SYNTAX     Unsigned32 (1 | 3 | 7 | 15 | 31 | 63 | 127 | 255 | 511 | 1023 | 2047 | 4095)
   ACCESS     read-only
   STATUS     mandatory
   DESCRIPTION
     "This attribute indicates the CRM parameter for this connection.
      
      CRM is the limit of the number of forward Resource Management 
      (RM) cells which may be sent in the absence of received backward 
      RM cells. When this limit is crossed, the Allowed Cell Rate (ACR) 
      value would be decreased by the amount (CDF*ACR), where CDF 
      is determined by the cutoffDecreaseFactor. The ACR is not allowed 
      to fall below the Minimum Cell Rate (MCR), in which case the 
      ACR is set to MCR.
      
      The value of CRM is obtained as transientBufferExposure divided 
      by maxCellsPerRmCell."
::= { mscAtmIfVptTmAbrOperEntry 19 }

mscAtmIfVptTmAbrTxRateChangeInfo OBJECT-TYPE
   SYNTAX     INTEGER  {
                 congestionIndicated(0),
                 noIncreaseIndicated(1),
                 explicitRateIndicated(2) }
   ACCESS     read-only
   STATUS     mandatory
   DESCRIPTION
     "This attribute indicates the rate change information put into the last 
      forward Resource Management (RM) cell turned around as a 
      backward-RM cell. For connections configured as an ABR Source 
      or Destination, the turned around backward-RM cell is sent over the 
      interface. For connections configured as an ABR Virtual Source or 
      Virtual Destination, the turned around backward-RM cell is sent 
      over the backplane."
::= { mscAtmIfVptTmAbrOperEntry 20 }

mscAtmIfVptTmAbrAcrRateChangeInfo OBJECT-TYPE
   SYNTAX     INTEGER  {
                 noChange(0),
                 decreasedByRdf(1),
                 increasedByRif(2),
                 setToExplicitRate(3),
                 notApplicable(15) }
   ACCESS     read-only
   STATUS     mandatory
   DESCRIPTION
     "This attribute indicates the type of change in the Allowed Cell Rate 
      (ACR) as a result of the information in the last backward Resource 
      Management (B-RM) cell received from the interface.
      
      This attribute value is only applicable when the Vcc Tm or Vpc Tm 
      abrConnectionType attribute is sourceDest or VirtualSourceDest. 
      In all other cases, this attribute value is notApplicable.
      
      A value of noChange indicates that the rate did not change as a 
      result of the last backward RM cell received.
      
      A value of decreasedByRdf or increasedByRif indicates that the 
      ACR was increased or decreased by the corresponding factor. This 
      change is as a result of the CI or NI bit setting in the last backward 
      RM cell, or an ADTF timeout.
      
      A value of setToExplicitRate indicates that the ACR was set to the 
      ER value in the last backward RM cell."
::= { mscAtmIfVptTmAbrOperEntry 21 }

mscAtmIfVptTmAbrTxFwdRmCells OBJECT-TYPE
   SYNTAX     Unsigned32 (0..4095)
   ACCESS     read-only
   STATUS     mandatory
   DESCRIPTION
     "This attribute counts the number of forward Resource Management 
      (RM) cells sent over the interface since the last backward RM-cell 
      was received from the interface. If the value of this attribute is 
      greater than or equal to the value of forwardRmCellLimit, the 
      Allowed Cell Rate (ACR) value would be decreased by the amount 
      (CDF*ACR), where CDF is determined by the 
      cutoffDecreaseFactor.
      
      This counter is reset to zero each time a backward-RM cell is 
      received.
      
      This counter does not wrap to zero if it reaches its maximum value 
      of 4095 in order to indicate that no backward RM cell has been 
      received."
::= { mscAtmIfVptTmAbrOperEntry 22 }

mscAtmIfVptTmAbrRxEfci OBJECT-TYPE
   SYNTAX     INTEGER  {
                 notIndicated(0),
                 indicated(1) }
   ACCESS     read-only
   STATUS     mandatory
   DESCRIPTION
     "This attribute indicates the value of the Explicit Forward 
      Congestion Indication (EFCI) bit of the last data cell received from 
      the interface.
      
      When a forward Resource Management (RM) cell is turned around 
      as a backward-RM cell, the Congestion Indication (CI) field of the 
      backward-RM cell is set to 1, if the value of this attribute is 
      indicated.
      
      This attribute is set to notIndicated each time a backward-RM cell 
      is transmitted."
::= { mscAtmIfVptTmAbrOperEntry 23 }


-- AtmIf/n Vpt/vpi VirtualChannelConnection/vci 
-- This component represents a virtual channel connection terminated 
-- by a Virtual Path Terminator (VPT).
-- 
-- For Vccs beneath Vpts, the instance value defines the VCI value for 
-- this connectionfor example, Vpt/16 Vcc/32 would define a 
-- connection with a VPI of 16, and a VCI of 32. The VPI value of the 
-- Vcc is inherited from the parent Vpt.
-- 
-- The VPI can be in the range of 0 to 4095 and the VCI can be in the 
-- range of 0 to 65535. Note that a Vcc instance of 0.0 is invalid as 
-- defined in the ATM Forum. Thus, the combination of Vpt/0 Vcc/0 is 
-- also invalid.

mscAtmIfVptVcc OBJECT IDENTIFIER ::= { mscAtmIfVpt 20 }



mscAtmIfVptVccRowStatusTable OBJECT-TYPE
   SYNTAX     SEQUENCE OF MscAtmIfVptVccRowStatusEntry
   ACCESS     not-accessible
   STATUS     mandatory
   DESCRIPTION
     "This entry controls the addition and deletion of 
      mscAtmIfVptVcc components."
::= { mscAtmIfVptVcc 1 }

mscAtmIfVptVccRowStatusEntry OBJECT-TYPE
   SYNTAX     MscAtmIfVptVccRowStatusEntry
   ACCESS     not-accessible
   STATUS     mandatory
   DESCRIPTION
     "A single entry in the table represents a single 
      mscAtmIfVptVcc component."
   INDEX {
      mscAtmIfIndex,
      mscAtmIfVptIndex,
      mscAtmIfVptVccIndex }
::= { mscAtmIfVptVccRowStatusTable 1 }

MscAtmIfVptVccRowStatusEntry ::= SEQUENCE {
   mscAtmIfVptVccRowStatus
      RowStatus,
   mscAtmIfVptVccComponentName
      DisplayString,
   mscAtmIfVptVccStorageType
      StorageType,
   mscAtmIfVptVccIndex
      Integer32 }

mscAtmIfVptVccRowStatus OBJECT-TYPE
   SYNTAX     RowStatus 
   ACCESS     read-write
   STATUS     mandatory
   DESCRIPTION
     "This variable is used as the basis for SNMP naming of
      mscAtmIfVptVcc components.
      These components can be added and deleted."
::= { mscAtmIfVptVccRowStatusEntry 1 }

mscAtmIfVptVccComponentName OBJECT-TYPE
   SYNTAX     DisplayString 
   ACCESS     read-only
   STATUS     mandatory
   DESCRIPTION
     "This variable provides the component's string name for
      use with the ASCII Console Interface"
::= { mscAtmIfVptVccRowStatusEntry 2 }

mscAtmIfVptVccStorageType OBJECT-TYPE
   SYNTAX     StorageType 
   ACCESS     read-only
   STATUS     mandatory
   DESCRIPTION
     "This variable represents the storage type value for the
      mscAtmIfVptVcc tables."
::= { mscAtmIfVptVccRowStatusEntry 4 }

mscAtmIfVptVccIndex OBJECT-TYPE
   SYNTAX     Integer32 (0..65535)
   ACCESS     not-accessible
   STATUS     mandatory
   DESCRIPTION
     "This variable represents the index for the mscAtmIfVptVcc tables."
::= { mscAtmIfVptVccRowStatusEntry 10 }

mscAtmIfVptVccStateTable OBJECT-TYPE
   SYNTAX     SEQUENCE OF MscAtmIfVptVccStateEntry
   ACCESS     not-accessible
   STATUS     mandatory
   DESCRIPTION
     "This group contains the three OSI State attributes. The descriptions 
      generically indicate what each state attribute implies about the 
      component. Note that not all the values and state combinations 
      described here are supported by every component which reuses this 
      group. For component-specific information and the valid state 
      combinations, refer to the appropriate NTP."
::= { mscAtmIfVptVcc 100 }

mscAtmIfVptVccStateEntry OBJECT-TYPE
   SYNTAX     MscAtmIfVptVccStateEntry
   ACCESS     not-accessible
   STATUS     mandatory
   DESCRIPTION
     "An entry in the mscAtmIfVptVccStateTable."
   INDEX {
      mscAtmIfIndex,
      mscAtmIfVptIndex,
      mscAtmIfVptVccIndex }
::= { mscAtmIfVptVccStateTable 1 }

MscAtmIfVptVccStateEntry ::= SEQUENCE {
   mscAtmIfVptVccAdminState
      INTEGER,
   mscAtmIfVptVccOperationalState
      INTEGER,
   mscAtmIfVptVccUsageState
      INTEGER }

mscAtmIfVptVccAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock -force or 
      Lock command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscAtmIfVptVccStateEntry 1 }

mscAtmIfVptVccOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscAtmIfVptVccStateEntry 2 }

mscAtmIfVptVccUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscAtmIfVptVccStateEntry 3 }

mscAtmIfVptVccOperTable OBJECT-TYPE
   SYNTAX     SEQUENCE OF MscAtmIfVptVccOperEntry
   ACCESS     not-accessible
   STATUS     mandatory
   DESCRIPTION
     "This group contains operational information for a Vcc, Vpc, or Vpt 
      component."
::= { mscAtmIfVptVcc 110 }

mscAtmIfVptVccOperEntry OBJECT-TYPE
   SYNTAX     MscAtmIfVptVccOperEntry
   ACCESS     not-accessible
   STATUS     mandatory
   DESCRIPTION
     "An entry in the mscAtmIfVptVccOperTable."
   INDEX {
      mscAtmIfIndex,
      mscAtmIfVptIndex,
      mscAtmIfVptVccIndex }
::= { mscAtmIfVptVccOperTable 1 }

MscAtmIfVptVccOperEntry ::= SEQUENCE {
   mscAtmIfVptVccConnectionPointType
      INTEGER }

mscAtmIfVptVccConnectionPointType OBJECT-TYPE
   SYNTAX     INTEGER  {
                 connectionEndPoint(0),
                 segmentEndPoint(1),
                 connectingPoint(2),
                 unknown(3) }
   ACCESS     read-only
   STATUS     mandatory
   DESCRIPTION
     "This attribute reflects the role of the connection component at this 
      interface.
      
      A value of connectionEndPoint indicates that user cells, end-to-end 
      OAM cells, and segment OAM cells are processed by the 
      connection component.
      
      A value of segmentEndPoint indicates that user cells and end-to-
      end OAM cells are relayed by the connection component, while 
      segment OAM cells are processed by the connection component.
      
      A value of connectingPoint indicates that user cells, end-to-end 
      OAM cells, and segment OAM cells are relayed by the connection 
      component.
      
      A value of unknown indicates that the connection component is 
      inactive."
::= { mscAtmIfVptVccOperEntry 10 }

mscAtmIfVptVccConnInfoTable OBJECT-TYPE
   SYNTAX     SEQUENCE OF MscAtmIfVptVccConnInfoEntry
   ACCESS     not-accessible
   STATUS     mandatory
   DESCRIPTION
     "This group contains operational connection characteristics 
      information for a Vcc component."
::= { mscAtmIfVptVcc 115 }

mscAtmIfVptVccConnInfoEntry OBJECT-TYPE
   SYNTAX     MscAtmIfVptVccConnInfoEntry
   ACCESS     not-accessible
   STATUS     mandatory
   DESCRIPTION
     "An entry in the mscAtmIfVptVccConnInfoTable."
   INDEX {
      mscAtmIfIndex,
      mscAtmIfVptIndex,
      mscAtmIfVptVccIndex }
::= { mscAtmIfVptVccConnInfoTable 1 }

MscAtmIfVptVccConnInfoEntry ::= SEQUENCE {
   mscAtmIfVptVccDistributionType
      INTEGER,
   mscAtmIfVptVccNumLeaves
      Gauge32,
   mscAtmIfVptVccCallDirection
      INTEGER }

mscAtmIfVptVccDistributionType OBJECT-TYPE
   SYNTAX     INTEGER  {
                 pointToPoint(0),
                 pointToMultipoint(1) }
   ACCESS     read-only
   STATUS     mandatory
   DESCRIPTION
     "This attribute indicates the way data is distributed in the connection.
      
      A value of pointToPoint indicates this connection point is part of a 
      point-to-point connection.
      
      A value of pointToMultipoint indicates this connection point is part 
      of a point-to-multipoint connection."
   DEFVAL     { pointToPoint }
::= { mscAtmIfVptVccConnInfoEntry 11 }

mscAtmIfVptVccNumLeaves OBJECT-TYPE
   SYNTAX     Gauge32 (0..2147483647)
   ACCESS     read-only
   STATUS     mandatory
   DESCRIPTION
     "This attribute indicates the number of destination leaves of the 
      connection. If the distributionType is pointToPoint the value of this 
      attribute is 0."
   DEFVAL     { 0 }
::= { mscAtmIfVptVccConnInfoEntry 12 }

mscAtmIfVptVccCallDirection OBJECT-TYPE
   SYNTAX     INTEGER  {
                 fromLink(0),
                 toLink(1),
                 notApplicable(2) }
   ACCESS     read-only
   STATUS     mandatory
   DESCRIPTION
     "This attribute indicates the direction of the call setup request for an 
      SVC.
      
      A value of fromLink means that the call setup originated from the 
      link.
      
      A value of toLink means that the call setup was directed to the link.
      
      For PVC connections, the value of this attribute is notApplicable.
      
      For SPVC connections, the value of this attribute is notApplicable 
      for Vccs with the SourcePVC and DestinationPVC subcomponents.
      
      For Signalling channels, the value of this attribute is notApplicable."
   DEFVAL     { notApplicable }
::= { mscAtmIfVptVccConnInfoEntry 13 }

mscAtmIfVptVccStatusTable OBJECT-TYPE
   SYNTAX     SEQUENCE OF MscAtmIfVptVccStatusEntry
   ACCESS     not-accessible
   STATUS     mandatory
   DESCRIPTION
     "This group contains operational status information for a Vcc, Vpc or 
      Vpt component."
::= { mscAtmIfVptVcc 120 }

mscAtmIfVptVccStatusEntry OBJECT-TYPE
   SYNTAX     MscAtmIfVptVccStatusEntry
   ACCESS     not-accessible
   STATUS     mandatory
   DESCRIPTION
     "An entry in the mscAtmIfVptVccStatusTable."
   INDEX {
      mscAtmIfIndex,
      mscAtmIfVptIndex,
      mscAtmIfVptVccIndex }
::= { mscAtmIfVptVccStatusTable 1 }

MscAtmIfVptVccStatusEntry ::= SEQUENCE {
   mscAtmIfVptVccOperStatus
      INTEGER,
   mscAtmIfVptVccLocalFailureCause
      INTEGER,
   mscAtmIfVptVccTroubled
      INTEGER,
   mscAtmIfVptVccSegLinkSideLoopbackState
      INTEGER,
   mscAtmIfVptVccSegSwitchSideLoopbackState
      INTEGER,
   mscAtmIfVptVccEndToEndLoopbackState
      INTEGER,
   mscAtmIfVptVccRxOamCellCongestionState
      INTEGER,
   mscAtmIfVptVccAisState
      INTEGER,
   mscAtmIfVptVccRdiState
      INTEGER }

mscAtmIfVptVccOperStatus OBJECT-TYPE
   SYNTAX     INTEGER  {
                 unknown(0),
                 end2endUp(1),
                 end2endDown(2),
                 localUpEnd2endUnknown(3),
                 localDown(4) }
   ACCESS     read-only
   STATUS     mandatory
   DESCRIPTION
     "This attribute indicates the present operational status of the Vcc, 
      Vpc or Vpt component. Its value is dependent upon the current state 
      of the segLinkSideLoopbackState and endToEndLoopbackState 
      attributes.
      
      The value is end2endUp when the endToEndLoopbackState is good 
      and the segLinkSideLoopbackState is either good or unknown.
      
      The value is end2endDown when the endToEndLoopbackState is 
      bad and the segLinkSideLoopbackState is either good or unknown.
      
      The value is localUpEnd2endUnknown when the 
      endToEndLoopbackState is unknown and the 
      segLinkSideLoopbackState is good.
      
      The value is localDown when segLinkSideLoopbackState is bad.
      
      The value is localUpEnd2endUnknown when the 
      endToEndLoopbackState is notApplicable and the 
      segLinkSideLoopbackState is good.
      
      The value is unknown when the endToEndLoopbackState is either 
      unknown or notApplicable and the segLinkSideLoopbackState is 
      unknown."
::= { mscAtmIfVptVccStatusEntry 20 }

mscAtmIfVptVccLocalFailureCause OBJECT-TYPE
   SYNTAX     INTEGER  {
                 noFailure(0),
                 localBwLoss(1),
                 portDown(2),
                 notAdmitted(3),
                 appNotRegistered(4),
                 disabledByApp(5),
                 bwReduced(6),
                 vpDown(7) }
   ACCESS     read-only
   STATUS     mandatory
   DESCRIPTION
     "This attribute indicates the failure cause of the Vcc, Vpc or Vpt 
      component. noFailure indicates that there is currently no 
      bandwidth related failure for this connection. 
      
      portDown indicates that the interface corresponding to the parent 
      AtmIf is down. 
      
      localBwLoss indicates that the Ima corresponding to this AtmIf has 
      lost some, but not all bandwidth, and as a result, this connection has 
      been released.
      
      notAdmitted indicates that this connection has failed to be admitted 
      by the Connection Admission Control (CAC) algorithm.
      
      appNotRegistered indicates that there is no application registered to 
      use this connection. This may be the case, for example when there 
      is a Vcc Test application, but the test has not been started. Check the 
      status of the application to determine why it is not functional.
      
      disabledByApp indicates that the application using this connection 
      has requested that the connection be disabled. An example is a 
      connection used by a trunk application where the trunk has timed 
      out on an attempt to stage. Check the application to determine why 
      it is not fully functional.
      
      bwReduced indicates that this connection is operating in a reduced 
      bandwidth state. It is a bandwidth elastic connection which 
      currently has been allocated less than the requested (equivalent) 
      bandwidth.
      
      vpDown indicates that this connection has been notified of a fault 
      detected at the associated VP-layer. vpDown is applicable for Vpt 
      Vccs only."
::= { mscAtmIfVptVccStatusEntry 25 }

mscAtmIfVptVccTroubled OBJECT-TYPE
   SYNTAX     INTEGER  {
                 no(0),
                 yes(1) }
   ACCESS     read-only
   STATUS     mandatory
   DESCRIPTION
     "This attribute indicates whether or not the connection is in a 
      troubled state. Connections become troubled because of OAM 
      failures; when one of the attributes segLinkSideLoopbackState, 
      segSwitchSideLoopbackState, endToEndLoopbackState, aisState 
      (when receiving AIS cells only) or rdiState go bad, this attribute is 
      set to yes; otherwise it is set to no."
   DEFVAL     { no }
::= { mscAtmIfVptVccStatusEntry 28 }

mscAtmIfVptVccSegLinkSideLoopbackState OBJECT-TYPE
   SYNTAX     INTEGER  {
                 good(0),
                 bad(1),
                 unknown(2),
                 notApplicable(3) }
   ACCESS     read-only
   STATUS     mandatory
   DESCRIPTION
     "This attribute contains the current state of the link-side segment 
      loopback for this connection. Link-side segment loopback cells are 
      transmitted (inserted) by a connection component in the direction of 
      the link (port). The value of this attribute is dependent upon the 
      current setting of the segLinkSideLoopback provisionable attribute, 
      the connection point type as specified by the connectionPointType 
      attribute, and the current loopback state (if applicable).
      
      The value is notApplicable when the connectionPointType is a 
      connectingPoint. 
      
      The value is notApplicable when the distributionType is 
      pointToMultipoint.
      
      The value is good when the segLinkSideLoopback is on, the 
      connectionPointType is a segmentEndPoint or a 
      connectionEndPoint, and the segment link side loopback is 
      working.
      
      The value is bad when the segLinkSideLoopback is on, the 
      connectionPointType is a segmentEndPoint or a 
      connectionEndPoint, and the link side segment loopback is not 
      working.
      
      The value is unknown when the segLinkSideLoopback is off.
      
      The value is unknown when the segLinkSideLoopback is on, the 
      connectionPointType is a segmentEndPoint and the segment switch 
      side loopback has not yet been determined.
      
      The state of this attribute determines, in part, the value of the 
      operStatus attribute."
::= { mscAtmIfVptVccStatusEntry 30 }

mscAtmIfVptVccSegSwitchSideLoopbackState OBJECT-TYPE
   SYNTAX     INTEGER  {
                 good(0),
                 bad(1),
                 unknown(2),
                 notApplicable(3) }
   ACCESS     read-only
   STATUS     mandatory
   DESCRIPTION
     "This attribute contains the current state of the switch-side segment 
      loopback for this connection. Switch-side segment loopback cells 
      are transmitted (inserted) by a connection component in the 
      direction of the bus. The value of this attribute is dependent upon 
      the current setting of the segSwitchSideLoopback provisionable 
      attribute, the connection point type as specified by the 
      connectionPointType attribute, and the current loopback state (if 
      applicable).
      
      The value is only applicable when the connectionPointType is a 
      segmentEndPoint. 
      
      The value is notApplicable when the connectionPointType is a 
      connectingPoint or connectionEndPoint. 
      
      The value is notApplicable when the distributionType is 
      pointToMultipoint.
      
      The value is good when the segSwitchSideLoopback is on, the 
      connectionPointType is a segmentEndPoint and the segment switch 
      side loopback is working.
      
      The value is bad when the segSwitchSideLoopback is on, the 
      connectionPointType is a segmentEndPoint and the switch side 
      segment loopback is not working.
      
      The value is unknown when the segSwitchSideLoopback is off.
      
      The value is unknown when the segSwitchSideLoopback is on, the 
      connectionPointType is a segmentEndPoint and the segment switch 
      side loopback has not been determined."
::= { mscAtmIfVptVccStatusEntry 40 }

mscAtmIfVptVccEndToEndLoopbackState OBJECT-TYPE
   SYNTAX     INTEGER  {
                 good(0),
                 bad(1),
                 unknown(2),
                 notApplicable(3) }
   ACCESS     read-only
   STATUS     mandatory
   DESCRIPTION
     "This attribute contains the current state of the end-to-end loopback 
      for this connection. Its value is dependent upon the current setting 
      of the endToEndLoopback provisionable attribute and the 
      connection point type as specified by the connectionPointType 
      attribute.
      
      The value is only applicable when the connectionPointType is a 
      connectionEndPoint. 
      
      The value is notApplicable when the connectionPointType is a 
      connectingPoint or segmentEndPoint. 
      
      The value is notApplicable when the distributionType is a 
      pointToMultipoint.
      
      The value is good when the endToEndLoopback is on, the 
      connectionPointType is a connectionEndPoint and the end-to-end 
      loopback is working.
      
      The value is bad when the endToEndLoopback is on, the 
      connectionPointType is a connectionEndPoint and the end-to-end 
      loopback is not working.
      
      The value is unknown when the endToEndLoopback is off.
      
      The value is unknown when the endToEndLoopback is on, the 
      connectionPointType is a connectionEndPoint and the end-to-end 
      loopback status has not been determined.
      
      The state of this attribute determines, in part, the value of the 
      operStatus attribute."
::= { mscAtmIfVptVccStatusEntry 50 }

mscAtmIfVptVccRxOamCellCongestionState OBJECT-TYPE
   SYNTAX     INTEGER  {
                 good(0),
                 bad(1),
                 unknown(2),
                 notApplicable(3) }
   ACCESS     read-only
   STATUS     mandatory
   DESCRIPTION
     "This attribute contains the current state of the receive side OAM cell 
      congestion for this connection. Its value reflects whether the rate of 
      received OAM cells for this connection is below a specified 
      threshold. The connection maintains a count of the number of OAM 
      cells which are terminated per second. Once that count exceeds the 
      specified threshold, extraction of all OAM cells for this connection 
      is disabled for a period of one minute. This is a congestion 
      management mechanism to prevent the processor from being 
      overloaded with handling OAM cells for a particular connection. 
      This mechanism ensures that tasks, such as trunks obtain enough 
      processor cycles to remain in service, and are not adversely affected 
      by excessive rate of OAM cells on a particular connection.
      
      The value is good when the rate of received OAM cells is less than 
      the allowed threshold.
      
      The value is bad when the arrival rate has exceeded the allowed 
      threshold. It remains bad for one minute, before returning to good 
      again. During this timeout, extraction of all OAM cells is disabled 
      for this connection. As a result, other loopback failure conditions 
      may occur.
      
      The value is unknown when the application has not yet begun to 
      use this connection. An example is the Test component before a test 
      has been started.
      
      Each type of OAM cell is counted separately. The threshold for AIS 
      cells is three cells per second. If more than three AIS cells are 
      received within a one second interval, this attribute is set to bad. 
      The threshold for RDI cells and each loopback type is also three, 
      but the threshold for trace cells is 250 per second.
      
      The state of this attribute has no direct effect on the value of the 
      operStatus attribute or on the number of troubled connections."
::= { mscAtmIfVptVccStatusEntry 55 }

mscAtmIfVptVccAisState OBJECT-TYPE
   SYNTAX     INTEGER  {
                 good(0),
                 bad(1),
                 unknown(2),
                 notApplicable(3) }
   ACCESS     read-only
   STATUS     mandatory
   DESCRIPTION
     "This attribute contains the current state of the Alarm Indication 
      Signal for this connection.
      
      A value of good indicates that the connection's application is active 
      and no alarm has occurred.
      
      A value of bad indicates that the connection's application is active 
      and an alarm has occurred.
      
      A value of unknown indicates that the connection's application is 
      inactive.
      
      A value of notApplicable occurs when the connectionPointType is 
      either a segmentEndPoint or a connectingPoint."
::= { mscAtmIfVptVccStatusEntry 60 }

mscAtmIfVptVccRdiState OBJECT-TYPE
   SYNTAX     INTEGER  {
                 good(0),
                 bad(1),
                 unknown(2),
                 notApplicable(3) }
   ACCESS     read-only
   STATUS     mandatory
   DESCRIPTION
     "This attribute indicates the current state of the Remote Defect 
      Indication for this connection.
      
      A value of good indicates that the connection's application is active 
      and no alarm has occurred.
      
      A value of bad indicates that the connection's application is active 
      and an alarm has occurred.
      
      A value of unknown indicates that the connection's application is 
      inactive.
      
      A value of notApplicable occurs when the connectionPointType is 
      either a segmentEndPoint or a connectingPoint."
::= { mscAtmIfVptVccStatusEntry 70 }

mscAtmIfVptVccTrafficTable OBJECT-TYPE
   SYNTAX     SEQUENCE OF MscAtmIfVptVccTrafficEntry
   ACCESS     not-accessible
   STATUS     mandatory
   DESCRIPTION
     "This group is HISTORICAL. Please refer to the group AtmTmOper;
      
      This attribute group contains attributes for the Vcc and Vpc 
      components to reflect operational traffic attributes."
::= { mscAtmIfVptVcc 130 }

mscAtmIfVptVccTrafficEntry OBJECT-TYPE
   SYNTAX     MscAtmIfVptVccTrafficEntry
   ACCESS     not-accessible
   STATUS     mandatory
   DESCRIPTION
     "An entry in the mscAtmIfVptVccTrafficTable."
   INDEX {
      mscAtmIfIndex,
      mscAtmIfVptIndex,
      mscAtmIfVptVccIndex }
::= { mscAtmIfVptVccTrafficTable 1 }

MscAtmIfVptVccTrafficEntry ::= SEQUENCE {
   mscAtmIfVptVccTxTrafficDescType
      INTEGER,
   mscAtmIfVptVccTxQosClass
      INTEGER,
   mscAtmIfVptVccFwdQosClass
      INTEGER,
   mscAtmIfVptVccTxQueueLength
      INTEGER,
   mscAtmIfVptVccTxQueueCongestionState
      INTEGER,
   mscAtmIfVptVccHoldingPriority
      INTEGER,
   mscAtmIfVptVccRxTrafficDescType
      INTEGER,
   mscAtmIfVptVccRxQosClass
      INTEGER,
   mscAtmIfVptVccBwdQosClass
      INTEGER,
   mscAtmIfVptVccAtmServiceCategory
      INTEGER,
   mscAtmIfVptVccTrafficShaping
      INTEGER,
   mscAtmIfVptVccBearerClassBbc
      INTEGER,
   mscAtmIfVptVccTransferCapabilityBbc
      INTEGER,
   mscAtmIfVptVccClippingBbc
      INTEGER,
   mscAtmIfVptVccUnshapedTransmitQueueing
      INTEGER,
   mscAtmIfVptVccBestEffort
      INTEGER,
   mscAtmIfVptVccUsageParameterControl
      INTEGER,
   mscAtmIfVptVccTxFrameDiscard
      OCTET STRING,
   mscAtmIfVptVccRxFrameDiscard
      OCTET STRING,
   mscAtmIfVptVccBandwidthElastic
      INTEGER,
   mscAtmIfVptVccBandwidthReduction
      INTEGER }

mscAtmIfVptVccTxTrafficDescType OBJECT-TYPE
   SYNTAX     INTEGER  {
                 n1(1),
                 n2(2),
                 n3(3),
                 n4(4),
                 n5(5),
                 n6(6),
                 n7(7),
                 n8(8) }
   ACCESS     read-only
   STATUS     obsolete
   DESCRIPTION
     "This attribute is HISTORICAL. Please refer to the attribute of the 
      same name in the group AtmTmOper.
      
      This attribute indicates the type of traffic management which is 
      applied to the transmit direction of this connection as defined in the 
      ATM Forum. The txTrafficDescType determines the number and 
      meaning of the parameters in the txTrafficDescParm attribute."
::= { mscAtmIfVptVccTrafficEntry 10 }

mscAtmIfVptVccTxQosClass OBJECT-TYPE
   SYNTAX     INTEGER  {
                 unspecified(0),
                 constantBitRate(1),
                 variableBitRate(2),
                 connectionOriented(3),
                 connectionless(4) }
   ACCESS     read-only
   STATUS     obsolete
   DESCRIPTION
     "This attribute indicates the quality of service for the transmit 
      direction for this connection.
      
      The constantBitRate class refers to traffic offered on services such 
      as a constant bit rate video service. This traffic is highest priority.
      
      The variableBitRate class refers to traffic offered on services such 
      as packetized audio and video.
      
      The connectionOriented class refers to connection-oriented traffic 
      such as Frame Relay or X.25 traffic. 
      
      The connectionless traffic refers to traffic offered through 
      connectionless trunks such as certain LAN protocols.
      
      The unspecified class supports a 'best effort' type of service, where 
      there is a minimum guarantee of bandwidth. This traffic is lowest 
      priority.
      
      This attribute is obsolete, replaced by the UNI 4.0 attribute 
      atmServiceCategory."
::= { mscAtmIfVptVccTrafficEntry 30 }

mscAtmIfVptVccFwdQosClass OBJECT-TYPE
   SYNTAX     INTEGER  {
                 n0(0),
                 n1(1),
                 n2(2),
                 n3(3),
                 n4(4),
                 notApplicable(14) }
   ACCESS     read-only
   STATUS     obsolete
   DESCRIPTION
     "This attribute is HISTORICAL. Please refer to the attribute of the 
      same name in the group AtmTmOper.
      
      This attribute indicates the quality of service for the calling to called 
      direction for this connection. This is only applicable to Soft PVC 
      and SVC connections. 
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified QOS class; no objective is specified for 
      the performance parameters.
      
      A value of notApplicable is displayed in the case of nailed-up PVCs 
      for which this attribute has no significance."
::= { mscAtmIfVptVccTrafficEntry 31 }

mscAtmIfVptVccTxQueueLength OBJECT-TYPE
   SYNTAX     INTEGER (0..30720)
   ACCESS     read-only
   STATUS     obsolete
   DESCRIPTION
     "This attribute is HISTORICAL. Please refer to the attribute of the 
      same name in the group AtmTmOper.
      
      This attribute indicates the current length of the transmit queue for 
      this connection. If this connection has traffic shaping disabled, then 
      this attribute displays the common queue length. If traffic shaping is 
      enabled, then this attribute displays the per-VC queue length."
::= { mscAtmIfVptVccTrafficEntry 32 }

mscAtmIfVptVccTxQueueCongestionState OBJECT-TYPE
   SYNTAX     INTEGER (0..3)
   ACCESS     read-only
   STATUS     obsolete
   DESCRIPTION
     "This attribute is HISTORICAL. Please refer to the attribute of the 
      same name in the group AtmTmOper.
      
      This attribute indicates the congestion state of the transmit queue 
      for this connection. If the connection has traffic shaping disabled, 
      then this attribute displays the common queue congestion state. If 
      traffic shaping is enabled, then this attribute displays the per-VC 
      queue congestion state.
      
      The congestion state of a queue is indicated by a numeric value 
      ranging from 0 to 3. When a queue is in a congested state x, only 
      traffic with discard priority (DP) 0 to x are enqueued. Traffic with 
      DP > x is discarded. 
      
      Therefore, if the congestion state is 3, there is no congestion and all 
      traffic is enqueued. Likewise, when the congestion state is 0, there 
      is maximum congestion and only traffic with DP=0 is enqueued on 
      that queue."
::= { mscAtmIfVptVccTrafficEntry 33 }

mscAtmIfVptVccHoldingPriority OBJECT-TYPE
   SYNTAX     INTEGER  {
                 n0(0),
                 n1(1),
                 n2(2),
                 n3(3),
                 n4(4),
                 notApplicable(6) }
   ACCESS     read-only
   STATUS     obsolete
   DESCRIPTION
     "This attribute is HISTORICAL. Please refer to the attribute of the 
      same name in the group AtmTmOper.
      
      This attribute indicates the actual holding priority in effect for this 
      connection. In a situation where the link bandwidth fluctuates, such 
      as over an IMA link, holding priority is used to determine which 
      connections are held and which are released. Holding priority 4 
      connections are the first to be released. Holding priority 0 
      connections are the last to be released. Some applications, for 
      example Vcc Test, may override the provisioned holding priority. 
      
      A value of notApplicable is displayed when this is an elastic 
      connection. Holding priority does not apply to bandwidth elastic 
      connections.
      
      Holding priority has no effect for ubr atmServiceCategory or 
      txTrafficDescriptorType 1 or 2 connections."
::= { mscAtmIfVptVccTrafficEntry 35 }

mscAtmIfVptVccRxTrafficDescType OBJECT-TYPE
   SYNTAX     INTEGER  {
                 n1(1),
                 n2(2),
                 n3(3),
                 n4(4),
                 n5(5),
                 n6(6),
                 n7(7),
                 n8(8) }
   ACCESS     read-only
   STATUS     obsolete
   DESCRIPTION
     "This attribute is HISTORICAL. Please refer to the attribute of the 
      same name in the group AtmTmOper.
      
      This attribute indicates the type of traffic management which is 
      applied to the receive direction of this connection as defined in the 
      ATM Forum. The rxTrafficDescType determines the number and 
      meaning of the parameters in the rxTrafficDescParm attribute."
::= { mscAtmIfVptVccTrafficEntry 40 }

mscAtmIfVptVccRxQosClass OBJECT-TYPE
   SYNTAX     INTEGER  {
                 unspecified(0),
                 constantBitRate(1),
                 variableBitRate(2),
                 connectionOriented(3),
                 connectionless(4) }
   ACCESS     read-only
   STATUS     obsolete
   DESCRIPTION
     "This attribute reflects the value of the provisioned attribute in the 
      Vcd or Vpd. Refer to that attribute for more detailed explanation. 
      
      This attribute is obsolete replaced by the UNI 4.0 attribute 
      atmServiceCategory."
::= { mscAtmIfVptVccTrafficEntry 60 }

mscAtmIfVptVccBwdQosClass OBJECT-TYPE
   SYNTAX     INTEGER  {
                 n0(0),
                 n1(1),
                 n2(2),
                 n3(3),
                 n4(4),
                 notApplicable(14) }
   ACCESS     read-only
   STATUS     obsolete
   DESCRIPTION
     "This attribute is HISTORICAL. Please refer to the attribute of the 
      same name in the group AtmTmOper.
      
      This attribute indicates the quality of service for the called to calling 
      direction for this connection. This is only applicable to Soft PVC 
      and SVC connections. 
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified QOS class; no objective is specified for 
      the performance parameters.
      
      A value of notApplicable is displayed in the case of nailed-up PVCs 
      for which this attribute has no significance."
::= { mscAtmIfVptVccTrafficEntry 61 }

mscAtmIfVptVccAtmServiceCategory OBJECT-TYPE
   SYNTAX     INTEGER  {
                 unspecifiedBitRate(0),
                 constantBitRate(1),
                 rtVariableBitRate(2),
                 nrtVariableBitRate(3) }
   ACCESS     read-only
   STATUS     obsolete
   DESCRIPTION
     "This attribute is HISTORICAL. Please refer to the attribute of the 
      same name in the group AtmTmOper.
      
      This attribute indicates the ATM service category used for traffic in 
      both directions of the connection. 
      
      The constantBitRate service category is intended for real time 
      applications, that is, those requiring tightly constrained delay and 
      delay variation, as would be appropriate for voice and video 
      applications. The consistent availability of a fixed quantity of 
      bandwidth is considered appropriate for CBR service. Cells which 
      are delayed beyond the value specified by Cell Transfer Delay are 
      assumed to have significantly reduced value of the application.
      
      The rtVariableBitRate service category is intended for real time 
      applications; that is those requiring tightly constrained delay and 
      delay variation, as would be appropriate for voice and video 
      applications. Sources are expected to transmit at a rate which varies 
      with time. Equivalently, the source can be described as 'bursty'. 
      Cells which are delayed beyond the value specified by Cell Transfer 
      Delay are assumed to be of significantly reduced value to the 
      application. Real time VBR service may support statistical 
      multiplexing of real time sources.
      
      The nrtVariableBitRate service category is intended for non-real 
      time applications which have bursty traffic characteristics and which 
      can be characterized in terms of a PCR, SCR, and MBS. For those 
      cells which are transferred within the traffic contract, the application 
      expects a low cell loss ratio. For all connections, it expects a bound 
      on the mean cell transfer delay. Non-real time VBR service may 
      support statistical multiplexing of connections.
      
      The unspecifiedBitRate service is intended for non-real time 
      applications, that is those not requiring tightly constrained delay 
      and delay variation. UBR sources are expected to be bursty. UBR 
      service supports a high degree of statistical multiplexing among 
      sources. UBR service does not specify traffic related service 
      guarantees. No numerical commitments are made with respect to 
      the cell loss ratio experienced by a UBR connection, or as to the 
      cell transfer delay experienced by cells on the connection."
::= { mscAtmIfVptVccTrafficEntry 62 }

mscAtmIfVptVccTrafficShaping OBJECT-TYPE
   SYNTAX     INTEGER  {
                 enabled(0),
                 disabled(1),
                 notApplicable(4) }
   ACCESS     read-only
   STATUS     obsolete
   DESCRIPTION
     "This attribute is HISTORICAL. Please refer to the attribute of the 
      same name in the group AtmTmOper.
      
      This attribute indicates the traffic shaping state of the connection.
      
      A value of notApplicable indicates that traffic shaping is not 
      applicable or not supported for this connection. This is the case 
      when the atmServiceCategory is constantBitRate, or when the 
      txTrafficDescType is 1 or 2. In these cases, the value of 
      notApplicable is set regardless of whether traffic shaping is enabled 
      or disabled in the provisioning data.
      
      A value of disabled indicates that traffic shaping is applicable and 
      supported for the type of connection but has been turned off in the 
      provisioning data.
      
      A value of enabled indicates that traffic shaping is applicable and 
      supported for the type of connection and has been turned on in the 
      provisioning data. This is the only case that indicates that traffic 
      shaping is performed on the connection. In this case, the actual 
      shaping rate is reflected in the txTrafficDescParm attribute, 
      parameter number 4."
::= { mscAtmIfVptVccTrafficEntry 70 }

mscAtmIfVptVccBearerClassBbc OBJECT-TYPE
   SYNTAX     INTEGER  {
                 a(1),
                 c(3),
                 x(16),
                 vp(24),
                 notApplicable(30) }
   ACCESS     read-only
   STATUS     obsolete
   DESCRIPTION
     "This attribute is HISTORICAL. Please refer to the attribute of the 
      same name in the group AtmTmOper.
      
      This attribute indicates the bearer capability for this connection.
      
      Class a service is a connection-oriented, constant bit rate ATM 
      transport service. Class a service has end to end timing 
      requirements and may require stringent cell loss, cell delay and cell 
      delay variation performance.When a is displayed, the user is 
      requesting more than an ATM only service. The network may look 
      at the AAL to provide interworking based upon its contents. 
      
      Class c service is a connection-oriented, variable bit rate ATM 
      transport service. Class c service has no end-to-end timing 
      requirements.When c is displayed, the user is requesting more than 
      an ATM only service. The network interworking function may look 
      at the AAL and provide service based on it.
      
      Class x service is a connection-oriented ATM transport service 
      where the AAL, trafficType (cbr or vbr) and timing requirements 
      are user defined (that is, transparent to the network). When the 
      value of this attribute is x, the user is requesting an ATM only 
      service from the network. In this case, the network shall not process 
      any higher layer protocol.
      
      Class vp service is used to indicate a transparent VP service when 
      the user is requesting an ATM only service from the network. In this 
      case, the network does not process any higher layer protocol. This 
      service differs from class x service in that with the class vp service 
      both the VCI field (except for VCI values 0, 3, 4, and 6 through 15) 
      and Payload Type field are transported transparently by the network. 
      This attribute value is only applicable to SPVP and SVP 
      connections.
      
      A value of notApplicable is displayed in the case of nailed-up PVCs 
      for which this attribute has no significance."
::= { mscAtmIfVptVccTrafficEntry 71 }

mscAtmIfVptVccTransferCapabilityBbc OBJECT-TYPE
   SYNTAX     INTEGER  {
                 n0(0),
                 n1(1),
                 n2(2),
                 n5(5),
                 n8(8),
                 n9(9),
                 n10(10),
                 notApplicable(30) }
   ACCESS     read-only
   STATUS     obsolete
   DESCRIPTION
     "This attribute is HISTORICAL. Please refer to the attribute of the 
      same name in the group AtmTmOper.
      
      This attribute indicates the transfer capability for this connection. 
      Uni 3.0/3.1 traffic type and end-to-end timing parameters are 
      mapped into this parameter as follows:
      <transferCapability: TrafficType, Timing>
      0: NoIndication, NoIndication
      1: NoIndication, yes
      2: NoIndication, no
      5: CBR, yes
      8: VBR, NoIndication
      9: VBR, yes
      10: VBR, no
      
      A value of notApplicable is displayed in the case of nailed-up PVCs 
      for which this attribute has no significance, or in the case that the 
      transfer capability in the call request was set to NoIndication.
      
      The CBR traffic type refers to traffic offered on services such as a 
      constant bit rate video service or a circuit emulation.
      
      The VBR traffic type refers to traffic offered on services such as 
      packetized audio and video, or data.
      
      The value NoIndication for traffic type is used if the user has not set 
      the traffic type; similarly for end-to-end timing.
      
      The value yes for end-to-end timing indicates that end-to-end 
      timing is required for the connection.
      
      The value no for end-to-end timing indicates that end-to-end timing 
      is not required for the connection."
::= { mscAtmIfVptVccTrafficEntry 72 }

mscAtmIfVptVccClippingBbc OBJECT-TYPE
   SYNTAX     INTEGER  {
                 no(0),
                 yes(1),
                 notApplicable(14) }
   ACCESS     read-only
   STATUS     obsolete
   DESCRIPTION
     "This attribute is HISTORICAL. Please refer to the attribute of the 
      same name in the group AtmTmOper.
      
      This attribute indicates the value of the clipping susceptibility 
      parameter in the BBC Information Element.
      
      Clipping is an impairment in which the first fraction of a second of 
      information to be transferred is lost. It occurs after a call is 
      answered and before an associated connection is switched through.
      
      A value of notApplicable is displayed in the case of nailed-up PVCs 
      for which this attribute has no significance."
::= { mscAtmIfVptVccTrafficEntry 74 }

mscAtmIfVptVccUnshapedTransmitQueueing OBJECT-TYPE
   SYNTAX     INTEGER  {
                 perVc(0),
                 common(1),
                 notApplicable(4) }
   ACCESS     read-only
   STATUS     obsolete
   DESCRIPTION
     "This attribute is HISTORICAL. Please refer to the attribute of the 
      same name in the group AtmTmOper.
      
      This attribute indicates the unshaped transmit queuing state of the 
      connection.
      
      A value of common indicates that transmit traffic is being enqueued 
      onto common transmit queues. 
      
      A value of perVc indicates that transmit traffic is being enqueued 
      onto a per-VC queue for this connection. This is the case when 
      trafficShaping is disabled, but per-VC queueing has been 
      configured for this connection. 
      
      A value of notApplicable indicates that transmit traffic is being 
      shaped for this connection. Transmit traffic for a shaped connection 
      is enqueued onto a per-VC queue, but this attribute is only 
      applicable for unshaped connections."
::= { mscAtmIfVptVccTrafficEntry 75 }

mscAtmIfVptVccBestEffort OBJECT-TYPE
   SYNTAX     INTEGER  {
                 indicated(0),
                 notIndicated(1),
                 notApplicable(14) }
   ACCESS     read-only
   STATUS     obsolete
   DESCRIPTION
     "This attribute is HISTORICAL. Please refer to the attribute of the 
      same name in the group AtmTmOper.
      
      This attribute indicates value of best effort parameter in the ATM 
      Traffic Descriptor Information Element.
      
      The value indicated implies that the quality of service for this 
      connection is not guaranteed.
      
      The value notIndicated implies that the quality of service for this 
      connection is guaranteed.
      
      A value of notApplicable is displayed in the case of nailed-up PVCs 
      for which this attribute has no significance."
::= { mscAtmIfVptVccTrafficEntry 76 }

mscAtmIfVptVccUsageParameterControl OBJECT-TYPE
   SYNTAX     INTEGER  {
                 enabled(0),
                 disabled(1),
                 notApplicable(3) }
   ACCESS     read-only
   STATUS     obsolete
   DESCRIPTION
     "This attribute is HISTORICAL. Please refer to the attribute of the 
      same name in the group AtmTmOper.
      
      This attribute indicates the UPC state of the connection.
      
      A value of notApplicable indicates that UPC is not applicable or not 
      supported for the connection. This is the case when the connection's 
      rxTrafficDescType is 1 or 2. A value of notApplicable is set 
      regardless of whether UPC is disabled or enabled in provisioning 
      data.
      
      A value of disabled indicates that UPC is applicable and supported 
      for the type of connection but has been turned off in the 
      provisioning data.
      
      A value of enabled indicates that UPC is applicable and supported 
      for the type of connection and has been turned on in the 
      provisioning data. This is the only case that indicates that UPC is 
      enforced on the connection. In this case the traffic descriptor 
      parameters used for UPC enforcement are reflected in the 
      rxTrafficDescParms of the connection."
::= { mscAtmIfVptVccTrafficEntry 80 }

mscAtmIfVptVccTxFrameDiscard OBJECT-TYPE
   SYNTAX     OCTET STRING (SIZE (1))
   ACCESS     read-only
   STATUS     obsolete
   DESCRIPTION
     "This attribute is HISTORICAL. Please refer to the attribute of the 
      same name in the group AtmTmOper.
      
      This attribute indicates the set of current frame discard functions in 
      effect in the transmit data direction at this connection point.
      
      A value of ppd indicates that the Partial Packet Discard (PPD) 
      function is in effect. PPD may be applied at an interim connecting 
      point for a connection which is transporting frame traffic (AAL5 at 
      the endpoint). PPD is controlled by provisioning for PVCs and 
      SPVCs, and by call setup parameters in the AAL and Traffic 
      Descriptor Information Elements.
      
      A value of epd indicates that the Early Packet Discard (EPD) 
      function is in effect at this connection endpoint. PPD and EPD are 
      enabled by default at a connection endpoint which is performing 
      AAL5 segmentation and assembly.
      
      Frame discard functions are not applicable for Virtual Path 
      Connections (VPCs).

      Description of bits:
      ppd(0)
      epd(1)"
::= { mscAtmIfVptVccTrafficEntry 85 }

mscAtmIfVptVccRxFrameDiscard OBJECT-TYPE
   SYNTAX     OCTET STRING (SIZE (1))
   ACCESS     read-only
   STATUS     obsolete
   DESCRIPTION
     "This attribute is HISTORICAL. Please refer to the attribute of the 
      same name in the group AtmTmOper.
      
      This attribute indicates the set of current frame discard functions in 
      effect in the receive data direction at this connection point.
      
      A value of ppd indicates that the Partial Packet Discard (PPD) 
      function is in effect. PPD may be applied at an interim connecting 
      point for a connection which is transporting frame traffic (AAL5 at 
      the endpoint). PPD is controlled by provisioning for PVCs and 
      SPVCs, and by call setup parameters in the AAL and Traffic 
      Descriptor Information Elements.
      
      A value of epd indicates that the Early Packet Discard (EPD) 
      function is in effect at this connection endpoint. PPD and EPD are 
      enabled by default at a connection endpoint which is performing 
      AAL5 segmentation and assembly.
      
      Frame discard functions are not applicable for Virtual Path 
      Connections (VPCs).

      Description of bits:
      ppd(0)
      epd(1)"
::= { mscAtmIfVptVccTrafficEntry 86 }

mscAtmIfVptVccBandwidthElastic OBJECT-TYPE
   SYNTAX     INTEGER  {
                 no(0),
                 yes(1) }
   ACCESS     read-only
   STATUS     obsolete
   DESCRIPTION
     "This attribute is HISTORICAL. Please refer to the attribute of the 
      same name in the group AtmTmOper.
      
      This attribute is only of importance for connections which are 
      carried on a link with a variable bandwidth. For example, the 
      bandwidth may be reduced in the event that one or more physical 
      links in the IMA group fail, such that the originally requested 
      bandwidth cannot be maintained. This attribute shows whether the 
      application (for example, Trunk) running on this connection can 
      continue to operate if the bandwidth is reduced. If the bandwidth is 
      reduced, the amount by which it is reduced is displayed in the 
      bandwidthReduction attribute. 
      
      A value of yes, indicates that this connection is elastic, and the 
      bandwidth may be reduced but the connection is not released. 
      
      A value of no indicates that the bandwidth for this connection is not 
      reduced in the event of link bandwidth reduction. However, this 
      connection may be released based on its holdingPriority.
      
      Bandwidth elasticity has no effect for ubr atmServiceCategory or 
      txTrafficDescriptorType 1 or 2 connections."
::= { mscAtmIfVptVccTrafficEntry 90 }

mscAtmIfVptVccBandwidthReduction OBJECT-TYPE
   SYNTAX     INTEGER (0..2147483647)
   ACCESS     read-only
   STATUS     obsolete
   DESCRIPTION
     "This attribute is HISTORICAL. Please refer to the attribute of the 
      same name in the group AtmTmOper.
      
      This attribute shows the amount by which the bandwidth has been 
      reduced for this connection. This value is non-zero only for 
      connections which have bandwidthElastic displayed as yes, and 
      which are also operating in a reduced bandwidth mode. This is 
      typically be the case for selected connections running over an IMA 
      link. This attribute takes a value from 0 (no reduction) up to the 
      ECR. All connections which are running at their full allocated 
      bandwidth, bwReduction have the value 0. Connections which have 
      been reduced in allocated bandwidth have a positive number for this 
      attribute. The bwReduction may be subtracted from the ECR (which 
      is displayed as txTrafficDescParm 5) to determine the actual 
      bandwidth allocated to this connection."
::= { mscAtmIfVptVccTrafficEntry 100 }

mscAtmIfVptVccStatsTable OBJECT-TYPE
   SYNTAX     SEQUENCE OF MscAtmIfVptVccStatsEntry
   ACCESS     not-accessible
   STATUS     mandatory
   DESCRIPTION
     "This group contains traffic statistics for a Vcc, Vpc, or Vpt 
      component."
::= { mscAtmIfVptVcc 140 }

mscAtmIfVptVccStatsEntry OBJECT-TYPE
   SYNTAX     MscAtmIfVptVccStatsEntry
   ACCESS     not-accessible
   STATUS     mandatory
   DESCRIPTION
     "An entry in the mscAtmIfVptVccStatsTable."
   INDEX {
      mscAtmIfIndex,
      mscAtmIfVptIndex,
      mscAtmIfVptVccIndex }
::= { mscAtmIfVptVccStatsTable 1 }

MscAtmIfVptVccStatsEntry ::= SEQUENCE {
   mscAtmIfVptVccStatsTxCell
      PassportCounter64,
   mscAtmIfVptVccStatsTxCellClp
      PassportCounter64,
   mscAtmIfVptVccTxDiscard
      PassportCounter64,
   mscAtmIfVptVccTxDiscardClp
      PassportCounter64,
   mscAtmIfVptVccStatsTxCellDiscard
      PassportCounter64,
   mscAtmIfVptVccStatsTxCellDiscardClp
      PassportCounter64,
   mscAtmIfVptVccStatsTxFrameDiscard
      PassportCounter64,
   mscAtmIfVptVccStatsTxFrameDiscardClp
      PassportCounter64,
   mscAtmIfVptVccStatsRxCell
      PassportCounter64,
   mscAtmIfVptVccStatsRxCellClp
      PassportCounter64,
   mscAtmIfVptVccRxDiscard
      PassportCounter64,
   mscAtmIfVptVccRxDiscardClp
      PassportCounter64,
   mscAtmIfVptVccStatsRxCellDiscard
      PassportCounter64,
   mscAtmIfVptVccStatsRxCellDiscardClp
      PassportCounter64,
   mscAtmIfVptVccStatsRxFrameDiscard
      PassportCounter64,
   mscAtmIfVptVccStatsRxFrameDiscardClp
      PassportCounter64,
   mscAtmIfVptVccStatsRxUpcViolationOnEnforcer1
      PassportCounter64,
   mscAtmIfVptVccStatsRxUpcViolationOnEnforcer2
      PassportCounter64,
   mscAtmIfVptVccStatsRxAal5FrameError
      PassportCounter64,
   mscAtmIfVptVccStatsRxAal5FrameAbort
      PassportCounter64 }

mscAtmIfVptVccStatsTxCell OBJECT-TYPE
   SYNTAX     PassportCounter64 
   ACCESS     read-only
   STATUS     mandatory
   DESCRIPTION
     "This attribute counts the number of cells that have been transmitted 
      from the interface on this connection. The counter wraps to zero if it 
      exceeds its maximum value of (2**64)-1."
::= { mscAtmIfVptVccStatsEntry 10 }

mscAtmIfVptVccStatsTxCellClp OBJECT-TYPE
   SYNTAX     PassportCounter64 
   ACCESS     read-only
   STATUS     mandatory
   DESCRIPTION
     "This attribute counts the number of cells that have been transmitted 
      from the interface on this connection with the CLP=1. The counter 
      wraps to zero if it exceeds its maximum value of (2**64)-1."
::= { mscAtmIfVptVccStatsEntry 20 }

mscAtmIfVptVccTxDiscard OBJECT-TYPE
   SYNTAX     PassportCounter64 
   ACCESS     read-only
   STATUS     obsolete
   DESCRIPTION
     "This attribute is replaced by new attributes txCellDiscard and 
      txFrameDiscard.
      
      This attribute counts the number of cells or frames received from 
      the bus on this connection that have been discarded.
      
      If the connection segments frames into cells, the counter indicates 
      the number of frames discarded. Connections which segment 
      frames into cells have a connectionPointType of 
      connectionEndPoint.
      
      If the connection relays cells without adaptation, the counter 
      indicates the number of cells discarded. Connections which relay 
      cells without adaptation have a connectionPointType of 
      segmentEndPoint or connectingPoint.
      
      AAL1 connections are an exception to this rule; although they have 
      a connectionPointType of connectionEndPoint, they do not do 
      adaptation at this point. Thus, in the AAL1 case, this attribute 
      counts discarded cells.
      
      Discards are done due to congestion or when the connection's 
      interface is disabled.
      
      The counter wraps to zero if it exceeds its maximum value of 
      (2**64)-1."
::= { mscAtmIfVptVccStatsEntry 30 }

mscAtmIfVptVccTxDiscardClp OBJECT-TYPE
   SYNTAX     PassportCounter64 
   ACCESS     read-only
   STATUS     obsolete
   DESCRIPTION
     "This attribute is replaced by new attributes txCellDiscardClp and 
      txFrameDiscardClp.
      
      This attribute counts the number of cells or frames received from 
      the bus on this connection with CLP=1 that have been discarded.
      
      If the connection segments frames into cells, the counter indicates 
      the number of frames discarded. Connections which segment 
      frames into cells have a connectionPointType of 
      connectionEndPoint.
      
      If the connection relays cells without adaptation, the counter 
      indicates the number of cells discarded. Connections which relay 
      cells without adaptation have a connectionPointType of 
      segmentEndPoint or connectingPoint.
      
      AAL1 connections are an exception to this rule; although they have 
      a connectionPointType of connectionEndPoint, they do not do 
      adaptation at this point. Thus, in the AAL1 case, this attribute 
      counts discarded cells.
      
      Discards are done due to congestion or when the connection's 
      interface is disabled.
      
      The counter wraps to zero if it exceeds its maximum value of 
      (2**64)-1."
::= { mscAtmIfVptVccStatsEntry 40 }

mscAtmIfVptVccStatsTxCellDiscard OBJECT-TYPE
   SYNTAX     PassportCounter64 
   ACCESS     read-only
   STATUS     mandatory
   DESCRIPTION
     "This attribute counts the number of cells received from the bus on 
      this connection that have been discarded.
      
      Discarded cells are not counted in the txCell attribute.
      
      Cells are discarded due to transmit congestion, Partial Packet 
      Discard (PPD), Early Packet Discard (EPD), and Weighted Random 
      Early Detection (W-RED) mechanisms, or when the connection's 
      interface is disabled.
      
      For CQC-based ATM cards, this attribute is applicable only to 
      connections that relay cells without adaptation. Such connections 
      usually have a connectionPointType of segmentEndPoint or 
      connectingPoint. AAL1 connections are an exception to this rule; 
      although they have a connectionPointType of connectionEndPoint, 
      they do not do adaptation at this point. For Vpts, this attribute 
      provides an aggregated total of all txCellDiscard values for all such 
      connections associated with the Vpt.
      
      For Vccs on CQC-based ATM cards, if the connection segments 
      frames into cells, this attribute is not applicable and is not 
      displayed.
      
      The counter wraps to zero if it exceeds its maximum value of 
      (2**64)-1."
::= { mscAtmIfVptVccStatsEntry 42 }

mscAtmIfVptVccStatsTxCellDiscardClp OBJECT-TYPE
   SYNTAX     PassportCounter64 
   ACCESS     read-only
   STATUS     mandatory
   DESCRIPTION
     "This attribute counts the number of cells received from the bus on 
      this connection with CLP=1 that have been discarded.
      
      This count is included in the txCellDiscard attribute. Discarded 
      cells are not counted in the txCellClp attribute.
      
      Cells are discarded due to transmit congestion, Partial Packet 
      Discard (PPD), Early Packet Discard (EPD), and Weighted Random 
      Early Detection (W-RED) mechanisms, or when the connection's 
      interface is disabled.
      
      For CQC-based ATM cards, this attribute is applicable only to 
      connections that relay cells without adaptation. Such connections 
      have a connectionPointType of segmentEndPoint or 
      connectingPoint. AAL1 connections are an exception to this rule; 
      although they have a connectionPointType of connectionEndPoint, 
      they do not do adaptation at this point. For Vpts, this attribute 
      provides an aggregated total of all txCellDiscardClp values for all 
      such connections associated with the Vpt.
      
      For Vccs on CQC-based ATM cards, if the connection segments 
      frames into cells, this attribute is not applicable and is not 
      displayed.
      
      The counter wraps to zero if it exceeds its maximum value of 
      (2**64)-1."
::= { mscAtmIfVptVccStatsEntry 43 }

mscAtmIfVptVccStatsTxFrameDiscard OBJECT-TYPE
   SYNTAX     PassportCounter64 
   ACCESS     read-only
   STATUS     mandatory
   DESCRIPTION
     "This attribute counts the number of frames received from the bus on 
      this connection that have been discarded.
      
      Frames are discarded due to congestion, Partial Packet Discard 
      (PPD), Early Packet Discard (EPD), and Weighted Random Early 
      Detection (W-RED) mechanisms, or when the connection interface 
      is disabled.
      
      This count is independent of the txCell or txCellDiscard attribute.
      
      For CQC-based ATM cards, this attribute is applicable only to 
      connections that segment frames into cells. Such connections have a 
      connectionPointType of connectionEndPoint. AAL1 connections 
      are an exception to this rule; although they have a 
      connectionPointType of connectionEndPoint, they do not do 
      adaptation at this point. For Vpts, this attribute provides an 
      aggregated total of all txFrameDiscard values for all such 
      connections associated with the Vpt.
      
      For CQC-based ATM cards, for Vpcs, and Vccs that relay cells 
      without adaptation, this attribute is not applicable and is not 
      displayed.
      
      Discards due to EPD, PPD, and W-RED for a standard Vpt Vcc are 
      not included in this attribute. These discards are counted in the 
      Vcc's parent Vpt txFrameDiscard attribute.
      
      The counter wraps to zero if it exceeds its maximum value of 
      (2**64)-1."
::= { mscAtmIfVptVccStatsEntry 46 }

mscAtmIfVptVccStatsTxFrameDiscardClp OBJECT-TYPE
   SYNTAX     PassportCounter64 
   ACCESS     read-only
   STATUS     mandatory
   DESCRIPTION
     "This attribute counts the number of discarded frames on this 
      connection that were received from the bus and composed of one or 
      more CLP=1 cells.
      
      Frames are discarded due to congestion, Partial Packet Discard 
      (PPD), Early Packet Discard (EPD), and Weighted Random Early 
      Detection (W-RED) mechanisms, or when the connection interface 
      is disabled.
      
      This count is included in the txFrameDiscard attribute.
      
      For CQC-based ATM cards, this attribute is applicable only to 
      connections that segment frames into cells. Such connections have a 
      connectionPointType of connectionEndPoint. AAL1 connections 
      are an exception to this rule; although they have a 
      connectionPointType of connectionEndPoint, they do not do 
      adaptation at this point. For Vpts, this attribute provides an 
      aggregated total of all txFrameDiscardClp values for all such 
      connections associated with the Vpt.
      
      For CQC-based ATM cards, for Vpcs and Vccs that relay cells 
      without adaptation, this attribute is not applicable and is not 
      displayed.
      
      
      Discards due to EPD, PPD, and W-RED for a standard Vpt Vcc are 
      not included in this attribute. These discards are counted in the 
      Vcc's parent Vpt txFrameDiscardClp attribute.
      
      The counter wraps to zero if it exceeds its maximum value of 
      (2**64)-1."
::= { mscAtmIfVptVccStatsEntry 47 }

mscAtmIfVptVccStatsRxCell OBJECT-TYPE
   SYNTAX     PassportCounter64 
   ACCESS     read-only
   STATUS     mandatory
   DESCRIPTION
     "This attribute counts the number of cells that have been received 
      from the interface on this connection. The counter wraps to zero if it 
      exceeds its maximum value of (2**64)-1."
::= { mscAtmIfVptVccStatsEntry 50 }

mscAtmIfVptVccStatsRxCellClp OBJECT-TYPE
   SYNTAX     PassportCounter64 
   ACCESS     read-only
   STATUS     mandatory
   DESCRIPTION
     "This attribute counts the number of cells that have been received 
      from the interface on this connection with the CLP=1. The counter 
      wraps to zero if it exceeds its maximum value of (2**64)-1."
::= { mscAtmIfVptVccStatsEntry 60 }

mscAtmIfVptVccRxDiscard OBJECT-TYPE
   SYNTAX     PassportCounter64 
   ACCESS     read-only
   STATUS     obsolete
   DESCRIPTION
     "This attribute is replaced by new attributes rxCellDiscard and 
      rxFrameDiscard.
      
      This attribute counts the number of cells or frames received from 
      the interface on this connection that have been discarded.
      
      If the connection segments frames into cells, the counter indicates 
      the number of frames discarded. Connections which segment 
      frames into cells have a connectionPointType of 
      connectionEndPoint.
      
      If the connection relays cells without adaptation, the counter 
      indicates the number of cells discarded. Connections which relay 
      cells without adaptation have a connectionPointType of 
      segmentEndPoint or connectingPoint.
      
      AAL1 connections are an exception to this rule; although they have 
      a connectionPointType of connectionEndPoint, they do not do 
      adaptation at this point. Thus, in the AAL1 case, this attribute 
      counts discarded cells.
      
      Discards are done due to congestion, non-conformance with UPC or 
      AAL reassembly problems.
      
      The counter wraps to zero if it exceeds its maximum value of 
      (2**64)-1."
::= { mscAtmIfVptVccStatsEntry 70 }

mscAtmIfVptVccRxDiscardClp OBJECT-TYPE
   SYNTAX     PassportCounter64 
   ACCESS     read-only
   STATUS     obsolete
   DESCRIPTION
     "This attribute is replaced by new attributes rxCellDiscardClp and 
      rxFrameDiscardClp.
      
      This attribute counts the number of cells or frames received from 
      the interface on this connection with CLP=1 that have been 
      discarded.
      
      If the connection segments frames into cells, the counter indicates 
      the number of frames discarded. Connections which segment 
      frames into cells have a connectionPointType of 
      connectionEndPoint.
      
      If the connection relays cells without adaptation, the counter 
      indicates the number of cells discarded. Connections which relay 
      cells without adaptation have a connectionPointType of 
      segmentEndPoint or connectingPoint.
      
      AAL1 connections are an exception to this rule; although they have 
      a connectionPointType of connectionEndPoint, they do not do 
      adaptation at this point. Thus, in the AAL1 case, this attribute 
      counts discarded cells.
      
      Discards are done due to congestion, non-conformance with UPC or 
      AAL reassembly problems.
      
      The counter wraps to zero if it exceeds its maximum value of 
      (2**64)-1."
::= { mscAtmIfVptVccStatsEntry 80 }

mscAtmIfVptVccStatsRxCellDiscard OBJECT-TYPE
   SYNTAX     PassportCounter64 
   ACCESS     read-only
   STATUS     mandatory
   DESCRIPTION
     "This attribute counts the number of cells received from the interface 
      on this connection that have been discarded. This count is included 
      in the rxCell attribute.
      
      This count includes cells discarded due to non-conformance with 
      UPC, cells which are part of a frame which has been discarded due 
      to an AAL5 frame reassembly error, cells which are discarded due 
      to congestion, or cells which are received while the next hop 
      connection to which the traffic is directed across the backplane is 
      down. The next hop connection is the Vcc or Vpc identified by the 
      nextHop attribute of the Nrp or Rp component. 
      
      For CQC-based ATM cards, this attribute is applicable only to 
      connections that relay cells without adaptation. Such connections 
      have a connectionPointType of connectionEndPoint or 
      connectingPoint. AAL1 connections are an exception to this rule; 
      although they have a connectionPointType of connectionEndPoint, 
      they do not do adaptation at this point. For Vpts, this attribute 
      provides an aggregated total of all rxCellDiscard values for all such 
      connections associated with the Vpt.
      
      For CQC-based ATM cards, for Vpcs, and Vccs that relay cells 
      without adaptation, this attribute is not applicable and is not 
      displayed.
      
      Discards due to non-conformance with UPC at the VP layer, for a 
      standard Vpt Vcc, are not included in this attribute. These discards 
      are counted in the Vcc's parent Vpt rxCellDiscard attribute. 
      
      The counter wraps to zero if it exceeds its maximum value of 
      (2**64)-1."
::= { mscAtmIfVptVccStatsEntry 82 }

mscAtmIfVptVccStatsRxCellDiscardClp OBJECT-TYPE
   SYNTAX     PassportCounter64 
   ACCESS     read-only
   STATUS     mandatory
   DESCRIPTION
     "This attribute counts the number of cells received from the interface 
      on this connection with CLP=1 that have been discarded. This count 
      is included in the rxCell and rxCellDiscard attributes.
      
      This count includes cells discarded due to non-conformance with 
      UPC, cells which are part of a frame which has been discarded due 
      to an AAL5 frame reassembly error, cells which are discarded due 
      to congestion, or cells which are received while the next hop 
      connection to which the traffic is directed across the backplane is 
      down. The next hop connection is the Vcc or Vpc identified by the 
      nextHop attribute of the Nrp or Rp component. 
      
      For CQC-based ATM cards, this attribute is applicable only to 
      connections that relay cells without adaptation. Such connections 
      have a connectionPointType of connectionEndPoint or 
      connectingPoint. AAL1 connections are an exception to this rule; 
      although they have a connectionPointType of connectionEndPoint, 
      they do not do adaptation at this point. For Vpts, this attribute 
      provides an aggregated total of all rxCellDiscard values for all such 
      connections associated with the Vpt.
      
      For CQC-based ATM cards, for Vpcs, and Vccs that relay cells 
      without adaptation, this attribute is not applicable and is not 
      displayed.
      
      Discards due to non-conformance with UPC at the VP layer, for a 
      standard Vpt Vcc, are not included in this attribute. These discards 
      are counted in the Vcc's parent Vpt rxCellDiscard attribute.
      
      The counter wraps to zero if it exceeds its maximum value of 
      (2**64)-1."
::= { mscAtmIfVptVccStatsEntry 83 }

mscAtmIfVptVccStatsRxFrameDiscard OBJECT-TYPE
   SYNTAX     PassportCounter64 
   ACCESS     read-only
   STATUS     mandatory
   DESCRIPTION
     "This attribute counts the number of frames received from the 
      interface on this connection that have been discarded. This count is 
      independent of the rxCellDiscard attribute.
      
      This count includes frames discarded due to an AAL5 frame 
      reassembly error, frames discarded due to early packet discard 
      (EPD), and frames discarded due to processor (CPU) congestion. 
      This attribute is applicable only to connections that reassemble 
      incoming cells into frames. Connections which reassemble cells 
      into frames have a connectionPointType of connectionEndPoint. 
      AAL1 connections are an exception to this rule; even though they 
      have a connectionPointType of connectionEndPoint, they do not 
      do adaptation at this point. For Vpts, this attribute provides an 
      aggregated total of all rxFrameDiscard values for all applicable 
      connections associated with the Vpt.
      
      For Vpcs and for Vccs that relay cells without adaptation, this 
      attribute is not applicable and is not displayed.
      
      The counter wraps to zero if it exceeds its maximum value of 
      (2**64)-1."
::= { mscAtmIfVptVccStatsEntry 86 }

mscAtmIfVptVccStatsRxFrameDiscardClp OBJECT-TYPE
   SYNTAX     PassportCounter64 
   ACCESS     read-only
   STATUS     mandatory
   DESCRIPTION
     "This attribute counts the number of discarded frames on this 
      connection that were received from the interface and composed of 
      one or more CLP1 cells. This count is included in the 
      rxFrameDiscard attribute. It is independent of the rxCellDiscard 
      attribute.
      
      This count includes frames discarded due to an AAL5 frame 
      reassembly error, frames discarded due to early packet discard 
      (EPD), and frames discarded due to processor (CPU) congestion. 
      This attribute is applicable only to connections that reassemble 
      incoming cells into frames. Such connections have a 
      connectionPointType of connectionEndPoint. AAL1 connections 
      are an exception to this rule; although they have a 
      connectionPointType of connectionEndPoint, they do not do 
      adaptation at this point. For Vpts, this attribute provides an 
      aggregated total of all rxFrameDiscardClp values for all applicable 
      connections associated with the Vpt.
      
      For Vpcs and for Vccs that relay cells without adaptation, this 
      attribute is not applicable and is not displayed.
      
      The counter wraps to zero if it exceeds its maximum value of 
      (2**64)-1."
::= { mscAtmIfVptVccStatsEntry 88 }

mscAtmIfVptVccStatsRxUpcViolationOnEnforcer1 OBJECT-TYPE
   SYNTAX     PassportCounter64 
   ACCESS     read-only
   STATUS     mandatory
   DESCRIPTION
     "This attribute counts the number of UPC violations observed by the 
      Generic Cell Rate Algorithm (GCRA) Enforcer 1. This attribute is 
      only applicable if UPC is enforced or monitored. This attribute is 
      not applicable for standard Vpt Vccs. This attribute is not applicable 
      and is not displayed on CQC-based ATM cards.
      
      When the value of rxTrafficDescType for this connection is 3, 4, 5, 
      6, 7 or 8, Enforcer 1 enforces conformance of traffic received from 
      the interface to PCR CLP0+1.
      
      When the value of rxTrafficDescType for this connection is 9, 
      Enforcer 1 performs the Dynamic Generic Cell Rate Algorithm 
      (DGCRA) used for the Available Bit Rate (ABR) service category.
      
      If UPC is enforced all non-conforming cells are discarded by this 
      enforcer. These discarded cells are included in rxCellDiscard. 
      
      For basic Vpts, this attribute provides an aggregated total of all 
      rxUpcViolationOnEnforcer1 values for the Vccs associated with the 
      Vpt.
      
      The counter wraps to zero if it exceeds its maximum value of 
      (2**64)-1."
::= { mscAtmIfVptVccStatsEntry 90 }

mscAtmIfVptVccStatsRxUpcViolationOnEnforcer2 OBJECT-TYPE
   SYNTAX     PassportCounter64 
   ACCESS     read-only
   STATUS     mandatory
   DESCRIPTION
     "This attribute counts the number of UPC violations observed by the 
      Generic Cell Rate Algorithm (GCRA) Enforcer 2. This attribute is 
      only applicable if UPC is enforced or monitored. This attribute is 
      not applicable for standard Vpt Vccs. This attribute is not applicable 
      and is not displayed on CQC-based ATM cards.
      
      Enforcer2 is applicable only if the rxTrafficDescType for this 
      connection is 4, 5, 6, 7 or 8.
      
      When the value of rxTrafficDescType 4 or 5, Enforcer 2 enforces 
      conformance of traffic received from the interface to PCR CLP0.
      
      When the value of rxTrafficDescType 6, Enforcer 2 enforces 
      conformance of traffic received from the interface to SCR CLP0+1.
      
      When the value of rxTrafficDescType 7 or 8, Enforcer 2 enforces 
      conformance of traffic received from the interface to SCR CLP0.
      
      If UPC is enforced, enforcer 2 discards non-conforming cells for 
      rxTrafficDescType values of 4, 6 and 7. It tags non-conforming cells 
      for rxTrafficDescType values of 5 and 8. Discarded cells are 
      counted in the rxCellDiscard attribute. 
      
      For basic Vpts, this attribute provides an aggregated total of all 
      rxUpcViolationOnEnforcer2 values for the Vccs associated with 
      the Vpt.
      
      The counter wraps to zero if it exceeds its maximum value of 
      (2**64)-1."
::= { mscAtmIfVptVccStatsEntry 92 }

mscAtmIfVptVccStatsRxAal5FrameError OBJECT-TYPE
   SYNTAX     PassportCounter64 
   ACCESS     read-only
   STATUS     mandatory
   DESCRIPTION
     "This attribute counts the number of frames received from the 
      interface on this connection that have AAL5 length errors or AAL5 
      CRC errors. 
      
      This attribute is not applicable and is not displayed on CQC-based 
      ATM cards.
      
      AAL5 length or CRC errors typically occur because of cell discards 
      due to congestion, UPC, or due to corruption of data between the 
      AAL5 segmentation and reassembly end points.
      
      This attribute is applicable only to connections that reassemble 
      incoming cells into frames. Such connections have a 
      connectionPointType of connectionEndPoint. AAL1 connections 
      are an exception to this rule; although they have a 
      connectionPointType of connectionEndPoint, they do not do 
      adaptation at this point. For Vpts, this attribute provides an 
      aggregated total of all rxAal5FrameError values for all applicable 
      connections associated with the Vpt.
      
      For Vpcs and for Vccs that relay cells without adaptation, this 
      attribute is not applicable and is not displayed.
      
      The counter wraps to zero if it exceeds its maximum value of 
      (2**64)-1."
::= { mscAtmIfVptVccStatsEntry 100 }

mscAtmIfVptVccStatsRxAal5FrameAbort OBJECT-TYPE
   SYNTAX     PassportCounter64 
   ACCESS     read-only
   STATUS     mandatory
   DESCRIPTION
     "This attribute counts the number of frames received from the 
      interface on this connection that have the AAL5 length field set to 
      zero. 
      
      This attribute is not applicable and is not displayed for CQC-based 
      ATM cards.
      
      An AAL5 length of zero is an indication by the far end 
      segmentation point to this reassembly point that the frame is to be 
      discarded without reassembly. This mechanism is typically used by 
      a segmentation point if it detects an error in a frame after some of 
      the cells belonging to that frame have already been transmitted.
      
      This attribute is applicable only to connections that reassemble 
      incoming cells into frames. Such connections have a 
      connectionPointType of connectionEndPoint. AAL1 connections 
      are an exception to this rule; although they have a 
      connectionPointType of connectionEndPoint, they do not do 
      adaptation at this point. For Vpts, this attribute provides an 
      aggregated total of all rxAal5FrameAbort values for all applicable 
      connections associated with the Vpt.
      
      For Vpcs and for Vccs that relay cells without adaptation, this 
      attribute is not applicable and is not displayed.
      
      The counter wraps to zero if it exceeds its maximum value of 
      (2**64)-1."
::= { mscAtmIfVptVccStatsEntry 102 }

mscAtmIfVptVccTxTdpTable OBJECT-TYPE
   SYNTAX     SEQUENCE OF MscAtmIfVptVccTxTdpEntry
   ACCESS     not-accessible
   STATUS     obsolete
   DESCRIPTION
     "This attribute is HISTORICAL. Please refer to the attribute of the 
      same name in the group AtmTmOper.
      
      This attribute is a vector of five transmit traffic parameters. The first 
      three elements reflect the settings of the first three elements of the 
      txTrafficDescParm attribute in the AtmTrafficProv group. 
      
      When txTrafficDescType is 1 or 2, parameters 1 through 5 are 
      unused.
      
      In this description, PCR is the greater of either the PCR or the 
      requested shaping rate (parameter 1 or parameter 5) specified in the 
      Traffic group under the Vcd or Vpd.
      
      When txTrafficDescType is 3, parameter 1 represents the PCR for 
      CLP equal to 0 or 1 traffic; parameters 2 and 3 are unused.
      
      When txTrafficDescType is 4, parameter 1 represents the PCR for 
      CLP equal to 0 and 1 traffic; parameter 2 represents the PCR for 
      CLP equal to 0 traffic with cell discard.
      
      When txTrafficDescType is 5, parameter 1 represents the PCR for 
      CLP equal to 0 and 1 traffic; parameter 2 represents the PCR for 
      CLP equal to 0 traffic with cell tagging.
      
      When txTrafficDescType is 6, parameter 1 represents the PCR for 
      CLP equal to 0 and 1 traffic; parameter 2 represents the SCR for 
      CLP equal to 0 and 1 traffic; parameter 3 represents the MBS for 
      CLP equal to 0 and 1 traffic.
      
      When txTrafficDescType is 7, parameter 1 represents the PCR for 
      CLP equal to 0 and 1 traffic; parameter 2 represents the SCR for 
      CLP equal to 0 traffic with cell discard; parameter 3 represents the 
      MBS for CLP equal to 0 traffic.
      
      When txTrafficDescType is 8, parameter 1 represents the PCR for 
      CLP equal to 0 and 1 traffic; parameter 2 represents the SCR for 
      CLP equal to 0 traffic with cell tagging; parameter 3 represents the 
      MBS for CLP equal to 0 traffic
      
      When txTrafficDescType is 3, 4, 5, 6, 7 or 8, parameter 4 reflects 
      the actual shaping rate in cell/s for this connection. This rate is one 
      of the set of available shaping rates for this type of ATM-FP, based 
      on the number of interfaces doing shaping (attribute 
      perVcQueueInterfaces), the provisioned cell rate, the 
      shapingScalingFactor attribute of the AtmResourceControl 
      component, and whether traffic shaping is enabled. A rate of zero 
      (0) indicates that shaping is not performed. 
      
      When txTrafficDescType is 3, 4, 5, 6, 7 or 8, parameter 5 reflects 
      the equivalent cell rate in cell/s for this connection as determined by 
      the Connection Admission Control (CAC) algorithm. The 
      equivalent cell rate is useful in determining the admission 
      characteristics of this connection."
::= { mscAtmIfVptVcc 294 }

mscAtmIfVptVccTxTdpEntry OBJECT-TYPE
   SYNTAX     MscAtmIfVptVccTxTdpEntry
   ACCESS     not-accessible
   STATUS     obsolete
   DESCRIPTION
     "An entry in the mscAtmIfVptVccTxTdpTable."
   INDEX {
      mscAtmIfIndex,
      mscAtmIfVptIndex,
      mscAtmIfVptVccIndex,
      mscAtmIfVptVccTxTdpIndex }
::= { mscAtmIfVptVccTxTdpTable 1 }

MscAtmIfVptVccTxTdpEntry ::= SEQUENCE {
   mscAtmIfVptVccTxTdpIndex
      Integer32,
   mscAtmIfVptVccTxTdpValue
      Unsigned32 }

mscAtmIfVptVccTxTdpIndex OBJECT-TYPE
   SYNTAX     Integer32 (1..5)
   ACCESS     not-accessible
   STATUS     obsolete
   DESCRIPTION
     "This variable represents the mscAtmIfVptVccTxTdpTable
      specific index for the mscAtmIfVptVccTxTdpTable."
::= { mscAtmIfVptVccTxTdpEntry 1 }

mscAtmIfVptVccTxTdpValue OBJECT-TYPE
   SYNTAX     Unsigned32 (0..2147483647)
   ACCESS     read-only
   STATUS     obsolete
   DESCRIPTION
     "This variable represents an individual value for the
      mscAtmIfVptVccTxTdpTable."
::= { mscAtmIfVptVccTxTdpEntry 2 }

mscAtmIfVptVccRxTdpTable OBJECT-TYPE
   SYNTAX     SEQUENCE OF MscAtmIfVptVccRxTdpEntry
   ACCESS     not-accessible
   STATUS     obsolete
   DESCRIPTION
     "This attribute is HISTORICAL. Please refer to the attribute of the 
      same name in the group AtmTmOper.
      
      This attribute is a vector of four traffic parameters whose meanings 
      are defined by the rxTrafficDescType attribute. The values of peak 
      cell rate (PCR), sustained cell rate (SCR) are expressed in cells/s. 
      Maximum burst size (MBS) is expressed in cells. Cell Delay 
      Variation Tolerance (CDVT) is expressed in microseconds.
      
      When rxTrafficDescType is 1 or 2, none of the parameters are used.
      
      When rxTrafficDescType is 3, parameter 1 represents the PCR for 
      CLP equal to 0 and 1 traffic; parameter 4 represents the CDVT.
      
      When rxTrafficDescType is 4, parameter 1 represents the PCR for 
      CLP equal to 0 and 1 traffic; parameter 2 represents the PCR for 
      CLP equal to 0 traffic with cell discard; parameter 4 represents the 
      CDVT.
      
      When rxTrafficDescType is 5, parameter 1 represents the PCR for 
      CLP equal to 0 and 1 traffic; parameter 2 represents the PCR for 
      CLP equal to 0 traffic with cell tagging; parameter 4 represents the 
      CDVT.
      
      When rxTrafficDescType is a 6, parameter 1 represents the PCR for 
      CLP equal to 0 and 1 traffic; parameter 2 represents the SCR for 
      CLP equal to 0 and 1 traffic; parameter 3 represents the MBS for 
      CLP equal to 0 and 1 traffic; parameter 4 represents the CDVT. 
      
      When rxTrafficDescType is 7, parameter 1 represents the PCR for 
      CLP equal to 0 and 1 traffic; parameter 2 represents the SCR for 
      CLP equal to 0 traffic with cell discard; parameter 3 represents the 
      MBS for CLP equal to 0 traffic; parameter 4 represents the CDVT.
      
      When rxTrafficDescType is 8, parameter 1 represents the PCR for 
      CLP equal to 0 and 1 traffic; parameter 2 represents the SCR for 
      CLP equal to 0 traffic with cell tagging; parameter 3 represents the 
      MBS for CLP equal to 0 traffic; parameter 4 represents the CDVT. 
      
      If Upc is disabled for this connection, the values of PCR, SCR, 
      MBS and CDVT is a combination of provisioned parameters. If Upc 
      is enabled, the values of PCR, SCR, MBS, and CDVT is exactly the 
      values used by the usage parameter control hardware in policing the 
      arriving traffic. These may vary slightly from the provisioned values 
      due to granularity of the hardware. In the case where the PCR is 
      equal to the SCR, the effective MBS is zero."
::= { mscAtmIfVptVcc 295 }

mscAtmIfVptVccRxTdpEntry OBJECT-TYPE
   SYNTAX     MscAtmIfVptVccRxTdpEntry
   ACCESS     not-accessible
   STATUS     obsolete
   DESCRIPTION
     "An entry in the mscAtmIfVptVccRxTdpTable."
   INDEX {
      mscAtmIfIndex,
      mscAtmIfVptIndex,
      mscAtmIfVptVccIndex,
      mscAtmIfVptVccRxTdpIndex }
::= { mscAtmIfVptVccRxTdpTable 1 }

MscAtmIfVptVccRxTdpEntry ::= SEQUENCE {
   mscAtmIfVptVccRxTdpIndex
      Integer32,
   mscAtmIfVptVccRxTdpValue
      Unsigned32 }

mscAtmIfVptVccRxTdpIndex OBJECT-TYPE
   SYNTAX     Integer32 (1..4)
   ACCESS     not-accessible
   STATUS     obsolete
   DESCRIPTION
     "This variable represents the mscAtmIfVptVccRxTdpTable
      specific index for the mscAtmIfVptVccRxTdpTable."
::= { mscAtmIfVptVccRxTdpEntry 1 }

mscAtmIfVptVccRxTdpValue OBJECT-TYPE
   SYNTAX     Unsigned32 (0..2147483647)
   ACCESS     read-only
   STATUS     obsolete
   DESCRIPTION
     "This variable represents an individual value for the
      mscAtmIfVptVccRxTdpTable."
::= { mscAtmIfVptVccRxTdpEntry 2 }

mscAtmIfVptVccTxQThreshTable OBJECT-TYPE
   SYNTAX     SEQUENCE OF MscAtmIfVptVccTxQThreshEntry
   ACCESS     not-accessible
   STATUS     obsolete
   DESCRIPTION
     "This attribute is HISTORICAL. Please refer to the attribute of the 
      same name in the group AtmTmOper.
      
      This attribute indicates the queue limit and the discard thresholds 
      for the transmit queue of this connection. 
      
      The first element indicates the queue limit. Depending upon the 
      atmServiceCategory of the connection, the provisioned value of the 
      transmit queue limit is derived from the txQueueLimit attribute 
      under one of the subcomponents of the AtmIf CA component. If the 
      connection has traffic shaping disabled, then this attribute relates to 
      the common queue. If traffic shaping is enabled, then this attribute 
      relates to the per-VC queue.
      
      The second element is the threshold that marks the transition from 
      congestion state 1 to congestion state 0. This is the threshold at 
      which traffic with discard priority (DP) = 1 is discarded. This 
      threshold is set approximately at 90 percent of the first parameter, 
      the operational queue limit.
      
      The third element is the threshold that marks the transition from 
      congestion state 2 to congestion state 1. This is the threshold at 
      which traffic with DP = 2 is discarded. This threshold is set 
      approximately at 75 percent of the first parameter, the operational 
      queue limit.
      
      The fourth element is the threshold that marks the transition from 
      congestion state 3 to congestion state 2. This is the threshold at 
      which traffic with DP = 3 is discarded. This threshold is set 
      approximately at 35 percent of the first parameter, the operational 
      queue limit."
::= { mscAtmIfVptVcc 352 }

mscAtmIfVptVccTxQThreshEntry OBJECT-TYPE
   SYNTAX     MscAtmIfVptVccTxQThreshEntry
   ACCESS     not-accessible
   STATUS     obsolete
   DESCRIPTION
     "An entry in the mscAtmIfVptVccTxQThreshTable."
   INDEX {
      mscAtmIfIndex,
      mscAtmIfVptIndex,
      mscAtmIfVptVccIndex,
      mscAtmIfVptVccTxQThreshIndex }
::= { mscAtmIfVptVccTxQThreshTable 1 }

MscAtmIfVptVccTxQThreshEntry ::= SEQUENCE {
   mscAtmIfVptVccTxQThreshIndex
      Integer32,
   mscAtmIfVptVccTxQThreshValue
      Unsigned32 }

mscAtmIfVptVccTxQThreshIndex OBJECT-TYPE
   SYNTAX     Integer32 (0..3)
   ACCESS     not-accessible
   STATUS     obsolete
   DESCRIPTION
     "This variable represents the mscAtmIfVptVccTxQThreshTable
      specific index for the mscAtmIfVptVccTxQThreshTable."
::= { mscAtmIfVptVccTxQThreshEntry 1 }

mscAtmIfVptVccTxQThreshValue OBJECT-TYPE
   SYNTAX     Unsigned32 (0..30720)
   ACCESS     read-only
   STATUS     obsolete
   DESCRIPTION
     "This variable represents an individual value for the
      mscAtmIfVptVccTxQThreshTable."
::= { mscAtmIfVptVccTxQThreshEntry 2 }

mscAtmIfVptVccFqpTable OBJECT-TYPE
   SYNTAX     SEQUENCE OF MscAtmIfVptVccFqpEntry
   ACCESS     not-accessible
   STATUS     obsolete
   DESCRIPTION
     "This attribute is HISTORICAL. Please refer to the attribute of the 
      same name in the group AtmTmOper.
      
      This attribute is a vector of three elements that indicate the quality 
      of service parameters for the forward direction for this connection. 
      This attribute is used for SPVC and SVC connections on a PNNI 
      interface.
      
      The cdv element indicates the acceptable peak-to-peak Cell Delay 
      Variation (CDV) of real-time connections (CBR, and rt-VBR). 
      
      The ctd element indicates the acceptable maximum Cell Transfer 
      Delay (maxCtd) of real-time connections (CBR, and rt-VBR). 
      
      The clr element indicates the acceptable Cell Loss Ratio (CLR) of 
      CBR, rt-VBR, and nrt-VBR connections."
::= { mscAtmIfVptVcc 357 }

mscAtmIfVptVccFqpEntry OBJECT-TYPE
   SYNTAX     MscAtmIfVptVccFqpEntry
   ACCESS     not-accessible
   STATUS     obsolete
   DESCRIPTION
     "An entry in the mscAtmIfVptVccFqpTable."
   INDEX {
      mscAtmIfIndex,
      mscAtmIfVptIndex,
      mscAtmIfVptVccIndex,
      mscAtmIfVptVccFqpIndex }
::= { mscAtmIfVptVccFqpTable 1 }

MscAtmIfVptVccFqpEntry ::= SEQUENCE {
   mscAtmIfVptVccFqpIndex
      INTEGER,
   mscAtmIfVptVccFqpValue
      Unsigned32 }

mscAtmIfVptVccFqpIndex OBJECT-TYPE
   SYNTAX     INTEGER  {
                 cdv(0),
                 ctd(1),
                 clr(2) }
   ACCESS     not-accessible
   STATUS     obsolete
   DESCRIPTION
     "This variable represents the mscAtmIfVptVccFqpTable
      specific index for the mscAtmIfVptVccFqpTable."
::= { mscAtmIfVptVccFqpEntry 1 }

mscAtmIfVptVccFqpValue OBJECT-TYPE
   SYNTAX     Unsigned32 (0..2147483647)
   ACCESS     read-only
   STATUS     obsolete
   DESCRIPTION
     "This variable represents an individual value for the
      mscAtmIfVptVccFqpTable."
::= { mscAtmIfVptVccFqpEntry 2 }

mscAtmIfVptVccBqpTable OBJECT-TYPE
   SYNTAX     SEQUENCE OF MscAtmIfVptVccBqpEntry
   ACCESS     not-accessible
   STATUS     obsolete
   DESCRIPTION
     "This attribute is HISTORICAL. Please refer to the attribute of the 
      same name in the group AtmTmOper.
      
      This attribute is a vector of three elements that indicate the quality 
      of service parameters for the backward direction for this 
      connection. This attribute is used for SPVC and SVC connections 
      on a PNNI interface.
      
      The cdv element indicates the acceptable peak-to-peak Cell Delay 
      Variation (CDV) of real-time connections (CBR, and rt-VBR). 
      
      The ctd element indicates the acceptable maximum Cell Transfer 
      Delay (maxCtd) of real-time connections (CBR, and rt-VBR). 
      
      The clr element indicates the acceptable Cell Loss Ratio (CLR) of 
      CBR, rt-VBR, and nrt-VBR connections."
::= { mscAtmIfVptVcc 358 }

mscAtmIfVptVccBqpEntry OBJECT-TYPE
   SYNTAX     MscAtmIfVptVccBqpEntry
   ACCESS     not-accessible
   STATUS     obsolete
   DESCRIPTION
     "An entry in the mscAtmIfVptVccBqpTable."
   INDEX {
      mscAtmIfIndex,
      mscAtmIfVptIndex,
      mscAtmIfVptVccIndex,
      mscAtmIfVptVccBqpIndex }
::= { mscAtmIfVptVccBqpTable 1 }

MscAtmIfVptVccBqpEntry ::= SEQUENCE {
   mscAtmIfVptVccBqpIndex
      INTEGER,
   mscAtmIfVptVccBqpValue
      Unsigned32 }

mscAtmIfVptVccBqpIndex OBJECT-TYPE
   SYNTAX     INTEGER  {
                 cdv(0),
                 ctd(1),
                 clr(2) }
   ACCESS     not-accessible
   STATUS     obsolete
   DESCRIPTION
     "This variable represents the mscAtmIfVptVccBqpTable
      specific index for the mscAtmIfVptVccBqpTable."
::= { mscAtmIfVptVccBqpEntry 1 }

mscAtmIfVptVccBqpValue OBJECT-TYPE
   SYNTAX     Unsigned32 (0..2147483647)
   ACCESS     read-only
   STATUS     obsolete
   DESCRIPTION
     "This variable represents an individual value for the
      mscAtmIfVptVccBqpTable."
::= { mscAtmIfVptVccBqpEntry 2 }


-- AtmIf/n Vcc/vpi.vci VirtualChannelDescriptor,
-- AtmIf/n Vpt/vpi Vcc/vci VirtualChannelDescriptor
-- The Vcd component contains provisioning information about its 
-- parent Vcc component.

mscAtmIfVptVccVcd OBJECT IDENTIFIER ::= { mscAtmIfVptVcc 2 }



mscAtmIfVptVccVcdRowStatusTable OBJECT-TYPE
   SYNTAX     SEQUENCE OF MscAtmIfVptVccVcdRowStatusEntry
   ACCESS     not-accessible
   STATUS     mandatory
   DESCRIPTION
     "This entry controls the addition and deletion of 
      mscAtmIfVptVccVcd components."
::= { mscAtmIfVptVccVcd 1 }

mscAtmIfVptVccVcdRowStatusEntry OBJECT-TYPE
   SYNTAX     MscAtmIfVptVccVcdRowStatusEntry
   ACCESS     not-accessible
   STATUS     mandatory
   DESCRIPTION
     "A single entry in the table represents a single 
      mscAtmIfVptVccVcd component."
   INDEX {
      mscAtmIfIndex,
      mscAtmIfVptIndex,
      mscAtmIfVptVccIndex,
      mscAtmIfVptVccVcdIndex }
::= { mscAtmIfVptVccVcdRowStatusTable 1 }

MscAtmIfVptVccVcdRowStatusEntry ::= SEQUENCE {
   mscAtmIfVptVccVcdRowStatus
      RowStatus,
   mscAtmIfVptVccVcdComponentName
      DisplayString,
   mscAtmIfVptVccVcdStorageType
      StorageType,
   mscAtmIfVptVccVcdIndex
      NonReplicated }

mscAtmIfVptVccVcdRowStatus OBJECT-TYPE
   SYNTAX     RowStatus 
   ACCESS     read-only
   STATUS     mandatory
   DESCRIPTION
     "This variable is used as the basis for SNMP naming of
      mscAtmIfVptVccVcd components.
      These components cannot be added nor deleted."
::= { mscAtmIfVptVccVcdRowStatusEntry 1 }

mscAtmIfVptVccVcdComponentName OBJECT-TYPE
   SYNTAX     DisplayString 
   ACCESS     read-only
   STATUS     mandatory
   DESCRIPTION
     "This variable provides the component's string name for
      use with the ASCII Console Interface"
::= { mscAtmIfVptVccVcdRowStatusEntry 2 }

mscAtmIfVptVccVcdStorageType OBJECT-TYPE
   SYNTAX     StorageType 
   ACCESS     read-only
   STATUS     mandatory
   DESCRIPTION
     "This variable represents the storage type value for the
      mscAtmIfVptVccVcd tables."
::= { mscAtmIfVptVccVcdRowStatusEntry 4 }

mscAtmIfVptVccVcdIndex OBJECT-TYPE
   SYNTAX     NonReplicated 
   ACCESS     not-accessible
   STATUS     mandatory
   DESCRIPTION
     "This variable represents the index for the mscAtmIfVptVccVcd tables."
::= { mscAtmIfVptVccVcdRowStatusEntry 10 }

mscAtmIfVptVccVcdLbkTable OBJECT-TYPE
   SYNTAX     SEQUENCE OF MscAtmIfVptVccVcdLbkEntry
   ACCESS     not-accessible
   STATUS     mandatory
   DESCRIPTION
     "This group contains the provisionable loopback attributes for a Vcc, 
      Vpc, or Vpt component.
      
      Note that certain loopback requests may not be possible on a given 
      connection. In such cases, the corresponding operational loopback 
      attribute in the Status group of the Vcc, Vpc, or Vpt component is 
      set to notApplicable and the requested loopback is not performed.
      
      If loopbacks are provisioned to be on, and for any reason the 
      segment or end-to-end OAM loopback cells are not relayed, the 
      connection component becomes troubled, and user cell traffic may 
      be discarded. If loopbacks are provisioned to be on, all of the nodes 
      in the segment, and external networks which are in the end-to-end 
      connection must relay the OAM loopback cells."
::= { mscAtmIfVptVccVcd 100 }

mscAtmIfVptVccVcdLbkEntry OBJECT-TYPE
   SYNTAX     MscAtmIfVptVccVcdLbkEntry
   ACCESS     not-accessible
   STATUS     mandatory
   DESCRIPTION
     "An entry in the mscAtmIfVptVccVcdLbkTable."
   INDEX {
      mscAtmIfIndex,
      mscAtmIfVptIndex,
      mscAtmIfVptVccIndex,
      mscAtmIfVptVccVcdIndex }
::= { mscAtmIfVptVccVcdLbkTable 1 }

MscAtmIfVptVccVcdLbkEntry ::= SEQUENCE {
   mscAtmIfVptVccVcdSegLinkSideLoopback
      INTEGER,
   mscAtmIfVptVccVcdSegSwitchSideLoopback
      INTEGER,
   mscAtmIfVptVccVcdEndToEndLoopback
      INTEGER,
   mscAtmIfVptVccVcdMCastConnectionType
      INTEGER }

mscAtmIfVptVccVcdSegLinkSideLoopback OBJECT-TYPE
   SYNTAX     INTEGER  {
                 on(0),
                 off(1),
                 sameAsInterface(2) }
   ACCESS     read-write
   STATUS     mandatory
   DESCRIPTION
     "This attribute specifies whether link-side segment loopback 
      insertion should be performed on this connection. 
      
      When sameAsInterface is selected, the link-side segment loopback 
      insertion for the connection is based on the segLinkSideLoopback 
      attribute of the connection's parent AtmIf componentif the ATM 
      interface has link-side segment loopback insertion turned on, then 
      link-side segment loopback insertion is also on for the connection. 
      
      When on or off is selected, link-side segment loopback insertion is 
      turned on or off respectively for the connection regardless of the 
      provisioning of the parent AtmIf component.
      
      Note that link-side segment loopback insertion is not possible if the 
      connectionPointType attribute of the Vcc or Vpc component is 
      connectingPoint. Link-side segment loopback insertion is also not 
      possible if the distributionType of the Vcc is pointToMultipoint. In 
      such cases, the associated segLinkSideLoopbackState attribute 
      indicates notApplicable and link-side segment loopback insertion is 
      not performed. Link-side segment loopback insertion is always 
      possible on a Vpt."
   DEFVAL     { sameAsInterface }
::= { mscAtmIfVptVccVcdLbkEntry 10 }

mscAtmIfVptVccVcdSegSwitchSideLoopback OBJECT-TYPE
   SYNTAX     INTEGER  {
                 on(0),
                 off(1),
                 sameAsInterface(2) }
   ACCESS     read-write
   STATUS     mandatory
   DESCRIPTION
     "This attribute specifies whether switch-side segment loopback 
      insertion should be performed on this connection.
      
      When sameAsInterface is selected, the switch-side segment 
      loopback for the connection is based on the segSwitchSideLoopback 
      attribute of the connection's parent AtmIf componentif the ATM 
      interface has switch-side segment loopback insertion turned on, 
      then switch-side segment loopback insertion is also on for the 
      connection. 
      
      When on or off is selected, switch-side segment loopback insertion 
      is turned on or off respectively for the connection regardless of the 
      provisioning of the parent AtmIf component.
      
      Note that switch-side segment loopback insertion is not possible if 
      the connectionPointType attribute of the Vcc or Vpc component is 
      connectingPoint or connectionEndPoint. Switch-side segment 
      loopback insertion is also not possible if the distributionType of the 
      Vcc is pointToMultipoint In such cases, the associated 
      segSwitchSideLoopbackState attribute indicates notApplicable and 
      switch-side segment loopback insertion is not performed. Switch-
      side segment loopback is never possible on a Vpt."
   DEFVAL     { sameAsInterface }
::= { mscAtmIfVptVccVcdLbkEntry 20 }

mscAtmIfVptVccVcdEndToEndLoopback OBJECT-TYPE
   SYNTAX     INTEGER  {
                 on(0),
                 off(1),
                 sameAsInterface(2) }
   ACCESS     read-write
   STATUS     mandatory
   DESCRIPTION
     "This attribute specifies whether end-to-end loopback insertion 
      should be performed on this connection.
      
      When sameAsInterface is selected, the end-to-end loopback for the 
      connection is based on the endToEndLoopback attribute of the 
      connection's parent AtmIf componentif the ATM interface has 
      end-to-end loopback insertion turned on, then end-to-end loopback 
      insertion is also on for the connection. 
      
      When on or off is selected, end-to-end loopback insertion is turned 
      on or off respectively for the connection regardless of the 
      provisioning of the parent AtmIf component.
      
      Note that end-to-end loopback insertion is not possible if the 
      connectionPointType attribute of the Vcc or Vpc component is 
      connectingPoint or segmentEndPoint. End-to-end loopback 
      insertion is also not possible if the distributionType of the Vcc is 
      pointToMultipoint. In such cases, the associated 
      endToEndLoopbackState attribute indicates notApplicable and end-
      to-end loopback insertion is not performed. End-to-end loopback 
      insertion is always possible on a Vpt."
   DEFVAL     { sameAsInterface }
::= { mscAtmIfVptVccVcdLbkEntry 30 }

mscAtmIfVptVccVcdMCastConnectionType OBJECT-TYPE
   SYNTAX     INTEGER  {
                 pointToPoint(0),
                 pointToMultipointRoot(1),
                 pointToMultipointLeaf(2) }
   ACCESS     read-write
   STATUS     mandatory
   DESCRIPTION
     "This attribute is introduced to exist temporarily to pass to AtmIf the 
      connection type defined under Vcc or Vpc. This attribute will be 
      obsoleted once a more elegant solution is available."
   DEFVAL     { pointToPoint }
::= { mscAtmIfVptVccVcdLbkEntry 50 }

mscAtmIfVptVccVcdTrafficTable OBJECT-TYPE
   SYNTAX     SEQUENCE OF MscAtmIfVptVccVcdTrafficEntry
   ACCESS     not-accessible
   STATUS     mandatory
   DESCRIPTION
     "This group contains traffic related provisionable attributes for the 
      Vcc and Vpc components. The attributes' operational values are 
      reflected in the Traffic group for these components. Changing any 
      of the attributes in this group causes a service interruption on the 
      Vcc or Vpc component."
::= { mscAtmIfVptVccVcd 110 }

mscAtmIfVptVccVcdTrafficEntry OBJECT-TYPE
   SYNTAX     MscAtmIfVptVccVcdTrafficEntry
   ACCESS     not-accessible
   STATUS     mandatory
   DESCRIPTION
     "An entry in the mscAtmIfVptVccVcdTrafficTable."
   INDEX {
      mscAtmIfIndex,
      mscAtmIfVptIndex,
      mscAtmIfVptVccIndex,
      mscAtmIfVptVccVcdIndex }
::= { mscAtmIfVptVccVcdTrafficTable 1 }

MscAtmIfVptVccVcdTrafficEntry ::= SEQUENCE {
   mscAtmIfVptVccVcdTxTrafficDescType
      INTEGER,
   mscAtmIfVptVccVcdTxQosClass
      INTEGER,
   mscAtmIfVptVccVcdFwdQosClass
      INTEGER,
   mscAtmIfVptVccVcdHoldingPriority
      INTEGER,
   mscAtmIfVptVccVcdRxTrafficDescType
      INTEGER,
   mscAtmIfVptVccVcdRxQosClass
      INTEGER,
   mscAtmIfVptVccVcdBwdQosClass
      INTEGER,
   mscAtmIfVptVccVcdAtmServiceCategory
      INTEGER,
   mscAtmIfVptVccVcdTrafficShaping
      INTEGER,
   mscAtmIfVptVccVcdUnshapedTransmitQueueing
      INTEGER,
   mscAtmIfVptVccVcdUsageParameterControl
      INTEGER,
   mscAtmIfVptVccVcdBearerClassBbc
      INTEGER,
   mscAtmIfVptVccVcdTransferCapabilityBbc
      INTEGER,
   mscAtmIfVptVccVcdClippingBbc
      INTEGER,
   mscAtmIfVptVccVcdBestEffort
      INTEGER,
   mscAtmIfVptVccVcdFwdFrameDiscard
      INTEGER,
   mscAtmIfVptVccVcdBwdFrameDiscard
      INTEGER }

mscAtmIfVptVccVcdTxTrafficDescType OBJECT-TYPE
   SYNTAX     INTEGER  {
                 n1(1),
                 n2(2),
                 n3(3),
                 n4(4),
                 n5(5),
                 n6(6),
                 n7(7),
                 n8(8),
                 n9(9) }
   ACCESS     read-write
   STATUS     obsolete
   DESCRIPTION
     "This attribute is migrated to the AtmTmProv group.
      
      This attribute specifies the type of traffic management which is 
      applied to the transmit direction of this connection as defined in the 
      ATM Forum. The txTrafficDescType determines the number and 
      meaning of the parameters in the txTrafficDescParm attribute."
   DEFVAL     { n1 }
::= { mscAtmIfVptVccVcdTrafficEntry 10 }

mscAtmIfVptVccVcdTxQosClass OBJECT-TYPE
   SYNTAX     INTEGER  {
                 unspecified(0),
                 constantBitRate(1),
                 variableBitRate(2),
                 connectionOriented(3),
                 connectionless(4) }
   ACCESS     read-write
   STATUS     obsolete
   DESCRIPTION
     "This attribute specifies the quality of service for the transmit 
      direction for this connection.
      
      The constantBitRate class refers to traffic offered on services such 
      as a constant bit rate video service. This traffic is highest priority.
      
      The variableBitRate class refers to traffic offered on services such 
      as packetized audio and video.
      
      The connectionOriented class refers to connection-oriented traffic 
      such as Frame Relay or X.25 traffic. 
      
      The connectionless traffic refers to traffic offered through 
      connectionless trunks such as certain LAN protocols.
      
      The unspecified class supports a 'best effort' type of service, where 
      there is a minimum guarantee of bandwidth. This traffic is lowest 
      priority.
      
      This attribute is obsolete. The value is migrated into 
      atmServiceCategory. The atmServiceCategory applies in both 
      transmit and receive directions.
      
      unspecified maps to unspecifiedBitRate;
      constantBitRate maps to constantBitRate;
      variableBitRate maps to variableBitRateRt;
      connectionOriented maps to variableBitRateNrt
      connectionless maps to variableBitRateNrt"
   DEFVAL     { connectionOriented }
::= { mscAtmIfVptVccVcdTrafficEntry 20 }

mscAtmIfVptVccVcdFwdQosClass OBJECT-TYPE
   SYNTAX     INTEGER  {
                 n0(0),
                 n1(1),
                 n2(2),
                 n3(3),
                 n4(4) }
   ACCESS     read-write
   STATUS     obsolete
   DESCRIPTION
     "This attribute is migrated to the AtmTmProv group.
      
      This attribute specifies the quality of service for the forward 
      direction for this connection. This attribute is only used for SPVC 
      connections.
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified bit rate QOS class; no objective is 
      specified for the performance parameters."
   DEFVAL     { n0 }
::= { mscAtmIfVptVccVcdTrafficEntry 21 }

mscAtmIfVptVccVcdHoldingPriority OBJECT-TYPE
   SYNTAX     INTEGER  {
                 n0(0),
                 n1(1),
                 n2(2),
                 n3(3),
                 n4(4) }
   ACCESS     read-write
   STATUS     obsolete
   DESCRIPTION
     "This attribute is migrated to the AtmTmProv group.
      
      This attribute specifies the holding priority of this connection. In a 
      situation where the link bandwidth fluctuates, such as over an IMA 
      link, holding priority is used to determine which connections are 
      held and which are released. Holding priority 4 connections are the 
      first to be released. Holding priority 0 connections are the last to be 
      released. This value provisioned in the Vcd or Vpd may be 
      overridden by certain applications, for example Vcc Test, which run 
      over this connection. The default holding priority for a provisioned 
      connection is higher then default holding priorities for dynamic 
      (SVC) connections."
   DEFVAL     { n2 }
::= { mscAtmIfVptVccVcdTrafficEntry 25 }

mscAtmIfVptVccVcdRxTrafficDescType OBJECT-TYPE
   SYNTAX     INTEGER  {
                 n1(1),
                 n2(2),
                 n3(3),
                 n4(4),
                 n5(5),
                 n6(6),
                 n7(7),
                 n8(8),
                 sameAsTx(15) }
   ACCESS     read-write
   STATUS     obsolete
   DESCRIPTION
     "This attribute is migrated to the AtmTmProv group.
      
      This attribute specifies the type of traffic management which is 
      applied to the receive direction of this connection as defined in the 
      ATM Forum. The rxTrafficDescType determines the number and 
      meaning of the parameters in the rxTrafficDescParm attribute
      
      When sameAsTx is selected, the rxTrafficDescType as well as the 
      rxTrafficDescParm are taken from the transmit values."
   DEFVAL     { sameAsTx }
::= { mscAtmIfVptVccVcdTrafficEntry 30 }

mscAtmIfVptVccVcdRxQosClass OBJECT-TYPE
   SYNTAX     INTEGER  {
                 unspecified(0),
                 constantBitRate(1),
                 variableBitRate(2),
                 connectionOriented(3),
                 connectionless(4),
                 sameAsTx(15) }
   ACCESS     read-write
   STATUS     obsolete
   DESCRIPTION
     "This attribute specifies the quality of service for the receive 
      direction for this connection.
      
      The constantBitRate class refers to traffic offered on services such 
      as a constant bit rate video service. 
      
      The variableBitRate class refers to traffic offered on services such 
      as packetized audio and video. 
      
      The connectionOriented class refers to connection-oriented traffic.
      
      The connectionless traffic refers to traffic offered through 
      connectionless trunks. 
      
      The unspecified class supports a 'best effort' type of service, where 
      there is a minimum guarantee of bandwidth. 
      
      The sameAsTx selection sets the receive quality of service to be the 
      same as the transmit quality of service.
      
      This attribute is obsolete. The value of txQosClass is migrated into 
      atmServiceCategory. The value of this attribute is ignored. 
      AtmServiceCategory applies in both transmit and receive directions."
   DEFVAL     { sameAsTx }
::= { mscAtmIfVptVccVcdTrafficEntry 40 }

mscAtmIfVptVccVcdBwdQosClass OBJECT-TYPE
   SYNTAX     INTEGER  {
                 n0(0),
                 n1(1),
                 n2(2),
                 n3(3),
                 n4(4),
                 sameAsFwd(15) }
   ACCESS     read-write
   STATUS     obsolete
   DESCRIPTION
     "This attribute is migrated to the AtmTmProv group.
      
      This attribute specifies the quality of service for the backward 
      direction for this connection. This attribute is only used for SPVC 
      connections.
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified bit rate QOS class; no objective is 
      specified for the performance parameters.
      
      The sameAsFwd selection sets the backward quality of service to 
      be the same as the forward quality of service."
   DEFVAL     { sameAsFwd }
::= { mscAtmIfVptVccVcdTrafficEntry 41 }

mscAtmIfVptVccVcdAtmServiceCategory OBJECT-TYPE
   SYNTAX     INTEGER  {
                 unspecifiedBitRate(0),
                 constantBitRate(1),
                 rtVariableBitRate(2),
                 nrtVariableBitRate(3),
                 derivedFromBBC(15) }
   ACCESS     read-write
   STATUS     obsolete
   DESCRIPTION
     "This attribute is migrated to the AtmTmProv group.
      
      This attribute specifies the ATM service category for both directions 
      of the connection. 
      
      The value derivedFromBBC may only be used if the SrcPvc 
      component is provisioned under this Vcc.Otherwise a specific ATM 
      service category must be specified. 
      
      If this attribute is set to derivedFromBBC, the Broadband Bearer 
      Capability (BBC) and bestEffort attributes are used to determine the 
      atmServiceCategory of this connection. 
      
      If this attribute is set to other than derivedFromBBC, the value of 
      this attribute is used to override the provisioned BBC Information 
      Element parameters. In those cases, the BBC attributes are not used. 
      
      The constantBitRate service category is intended for real time 
      applications, that is those requiring tightly constrained delay and 
      delay variation, as would be appropriate for voice and video 
      applications. The consistent availability of a fixed quantity of 
      bandwidth is considered appropriate for CBR service. Cells which 
      are delayed beyond the value specified by Cell Transfer Delay are 
      assumed to be of significantly reduce value to the application.
      
      The rtVariableBitRate service category is intended for real time 
      applications, that is those requiring tightly constrained delay and 
      delay variation, as would be appropriate for voice and video 
      applications. Sources are expected to transmit at a rate which varies 
      with time. Equivalently, the source can be described as 'bursty'. 
      Cells which are delayed beyond the value specified by CTD are 
      assumed to be of significantly reduced value to the application. Real 
      time VBR service may support statistical multiplexing of real time 
      sources.
      
      The nrtVariableBitRate service category is intended for non-real 
      time applications which have bursty traffic characteristics and which 
      can be characterized in terms of a PCR, SCR, and MBS. For those 
      cells which are transferred within the traffic contract, the application 
      expects a low cell loss ratio. For all connections, it expects a bound 
      on the mean cell transfer delay. Non-real time VBR service may 
      support statistical multiplexing of connections.
      
      The unspecifiedBitRate service is intended for non-real time 
      applications; that is, those not requiring tightly constrained delay 
      and delay variation. UBR sources are expected to be bursty. UBR 
      service supports a high degree of statistical multiplexing among 
      sources. UBR service does not specify traffic related service 
      guarantees. No numerical commitments are made with respect to 
      the cell loss ratio experienced by a UBR connection, or as to the 
      cell transfer delay experienced by cells on the connection."
   DEFVAL     { unspecifiedBitRate }
::= { mscAtmIfVptVccVcdTrafficEntry 42 }

mscAtmIfVptVccVcdTrafficShaping OBJECT-TYPE
   SYNTAX     INTEGER  {
                 disabled(1),
                 sameAsInterface(2) }
   ACCESS     read-write
   STATUS     obsolete
   DESCRIPTION
     "This attribute is migrated to the AtmTmProv group.
      
      This attribute specifies whether this connection uses traffic shaping 
      when transmitting traffic to the ATM interface.
      
      When sameAsInterface is selected, traffic shaping for the 
      connection is based on the trafficShaping attribute of the 
      connection's parent AtmIf componentif the ATM interface has 
      traffic shaping enabled, then traffic shaping is enabled for the 
      connection. Note that enabling traffic shaping may have no effect 
      under certain cases. These cases are listed in the description of the 
      trafficShaping operational attribute, which is under the Vcc and Vpc 
      components.
      
      When disabled is selected, traffic shaping for this connection is 
      disabled regardless of the provisioning of the parent AtmIf 
      component."
   DEFVAL     { sameAsInterface }
::= { mscAtmIfVptVccVcdTrafficEntry 50 }

mscAtmIfVptVccVcdUnshapedTransmitQueueing OBJECT-TYPE
   SYNTAX     INTEGER  {
                 common(1),
                 sameAsInterface(3) }
   ACCESS     read-write
   STATUS     obsolete
   DESCRIPTION
     "This attribute is migrated to the AtmTmProv group.
      
      This attribute only applies when this connection is unshaped. This 
      attribute defines the transmit queueing method for this connection if 
      it is unshaped. Refer to the unshapedTransmitQueueing attribute 
      under the AtmIf for more details on the meaning of this attribute. 
      
      When this attribute is set to sameAsInterface, the value from the 
      AtmIf is used. 
      
      When this attribute is set to common, transmit traffic on this 
      unshaped connection is destined for the common queue."
   DEFVAL     { sameAsInterface }
::= { mscAtmIfVptVccVcdTrafficEntry 60 }

mscAtmIfVptVccVcdUsageParameterControl OBJECT-TYPE
   SYNTAX     INTEGER  {
                 disabled(1),
                 sameAsInterface(2) }
   ACCESS     read-write
   STATUS     obsolete
   DESCRIPTION
     "This attribute is migrated to the AtmTmProv group.
      
      This attribute specifies whether this connection enforces usage 
      parameter control when receiving traffic from the ATM interface.
      
      When sameAsInterface is selected, UPC for the connection is 
      based on the usageParameterControl attribute of the connection's 
      parent AtmIf componentif the ATM interface has UPC enabled, 
      then UPC is enabled for the connection. Note that enabling UPC 
      may have no effect under certain cases. These cases are listed in the 
      description of the usageParameterControl operational attribute, 
      which is under the Vcc and Vpc components.
      
      When disabled is selected, UPC for this connection is disabled 
      regardless of the provisioning of the parent AtmIf component."
   DEFVAL     { sameAsInterface }
::= { mscAtmIfVptVccVcdTrafficEntry 70 }

mscAtmIfVptVccVcdBearerClassBbc OBJECT-TYPE
   SYNTAX     INTEGER  {
                 a(1),
                 c(3),
                 x(16),
                 vp(24),
                 derivedFromServiceCategory(31) }
   ACCESS     read-write
   STATUS     obsolete
   DESCRIPTION
     "This attribute is migrated to the AtmTmProv group.
      
      This attribute specifies the bearer capability. This attribute is only 
      used for SPVC and SPVP connections. It is one of the Broadband 
      Bearer Capability (BBC) attributes. The purpose of the BBC 
      information element is to indicate a requested broadband 
      connection-oriented bearer service to be provided by the network.
      
      The value derivedFromServiceCategory specifies that the actual 
      value which is used for this connection is derived from the value of 
      the atmServiceCategory. Either, this attribute must be set to 
      derivedFromServiceCategory, or the atmServiceCategory attribute 
      must be set to derivedFromBBC, but not both.
      
      Class a service is a connection-oriented, constant bit rate ATM 
      transport service. Class a service has end to end timing 
      requirements and may require stringent cell loss, cell delay and cell 
      delay variation performance.When a is set, the user is requesting 
      more than an ATM only service. The network may look at the AAL 
      to provide interworking based upon its contents. 
      
      Class c service is a connection-oriented, variable bit rate ATM 
      transport service. Class c service has no end-to-end timing 
      requirements. When c is set, the user is requesting more than an 
      ATM only service. The network interworking function may look at 
      the AAL and provide service based on it.
      
      Class x service is a connection-oriented ATM transport service 
      where the AAL, trafficType (vbr or cbr) and timing requirements 
      are user defined (that is, transparent to the network).When x is set 
      the user is requesting an ATM only service from the network.
      
      Class vp service is used to specify a transparent VP service. When 
      the value of this attribute is vp, the user is requesting an ATM only 
      service from the network. In this case, the network shall not process 
      any higher layer protocol. This service differs from class x service 
      in that with the class vp service both the VCI field (except or VCI 
      values 0, 3, 4, and 6 through 15) and Payload Type field are 
      transported transparently by the network. This attribute value is 
      only applicable to SPVP connections."
   DEFVAL     { derivedFromServiceCategory }
::= { mscAtmIfVptVccVcdTrafficEntry 71 }

mscAtmIfVptVccVcdTransferCapabilityBbc OBJECT-TYPE
   SYNTAX     INTEGER  {
                 n0(0),
                 n1(1),
                 n2(2),
                 n5(5),
                 n8(8),
                 n9(9),
                 n10(10),
                 notApplicable(30),
                 derivedFromServiceCategory(31) }
   ACCESS     read-write
   STATUS     obsolete
   DESCRIPTION
     "This attribute is migrated to the AtmTmProv group.
      
      This attribute specifies the transfer capability for this connection. 
      Uni 3.0/3.1 traffic type and end-to-end timing parameters are 
      mapped into this parameter as follows:
      <transferCapability: TrafficType, Timing>
      0: NoIndication, NoIndication
      1: NoIndication, yes
      2: NoIndication, no
      5: CBR, yes
      8: VBR, NoIndication
      9: VBR, yes
      10: VBR, no
      
      NotApplicable specifies that the user does not want to specify the 
      transfer capability.
      
      The CBR traffic type refers to traffic offered on services such as a 
      constant bit rate video service or a circuit emulation.
      
      The VBR traffic type refers to traffic offered on services such as 
      packetized audio and video, or data.
      
      The value no indication for traffic type is used if the user has not set 
      the traffic type; similarly for end-to-end timing.
      
      The value yes for end-to-end timing indicates that end-to-end 
      timing is required.
      
      The value no for end-to-end timing indicates that end-to-end timing 
      is not required.
      
      The value derivedFromServiceCategory specifies that the actual 
      value which is used for this connection is derived from the value of 
      the atmServiceCategory. Either, this attribute must be set to 
      derivedFromServiceCategory, or the atmServiceCategory attribute 
      must be set to derivedFromBBC, but not both."
   DEFVAL     { derivedFromServiceCategory }
::= { mscAtmIfVptVccVcdTrafficEntry 72 }

mscAtmIfVptVccVcdClippingBbc OBJECT-TYPE
   SYNTAX     INTEGER  {
                 no(0),
                 yes(1) }
   ACCESS     read-write
   STATUS     obsolete
   DESCRIPTION
     "This attribute is migrated to the AtmTmProv group.
      
      This attribute specifies the value for the clipping susceptibility 
      parameter in the BBC Information Element. This attribute is only 
      used for SPVC connections. It is one of the Broadband Bearer 
      Capability attributes.
      
      Clipping is an impairment in which the first fraction of a second of 
      information to be transferred is lost. It occurs after a call is 
      answered and before an associated connection is switched through."
   DEFVAL     { no }
::= { mscAtmIfVptVccVcdTrafficEntry 74 }

mscAtmIfVptVccVcdBestEffort OBJECT-TYPE
   SYNTAX     INTEGER  {
                 indicated(0),
                 notIndicated(1),
                 derivedFromServiceCategory(15) }
   ACCESS     read-write
   STATUS     obsolete
   DESCRIPTION
     "This attribute is migrated to the AtmTmProv group.
      
      This attribute specifies the value of the best effort parameter in the 
      ATM Traffic Descriptor Information Element. This attribute is only 
      used for Soft PVC connections. It is one of the Broadband Bearer 
      Capability attributes.
      
      The value indicated implies that the quality of service for this 
      connection is not guaranteed.
      
      The value notIndicated implies that the quality of service for this 
      connection is guaranteed.
      
      The value derivedFromServiceCategory specifies that the actual 
      value which is used for this connection is derived from the value of 
      the atmServiceCategory. Either, this attribute must be set to 
      derivedFromServiceCategory, or the atmServiceCategory attribute 
      must be set to derivedFromBBC, but not both."
   DEFVAL     { derivedFromServiceCategory }
::= { mscAtmIfVptVccVcdTrafficEntry 75 }

mscAtmIfVptVccVcdFwdFrameDiscard OBJECT-TYPE
   SYNTAX     INTEGER  {
                 notIndicated(0),
                 indicated(1) }
   ACCESS     read-write
   STATUS     obsolete
   DESCRIPTION
     "This attribute specifies the activation of frame discard functionality 
      in the forward data direction, at relay points, for this connection. It 
      applies to each hop of the connection. Frame discard functions 
      should not be requested if this connection is not transferring frame 
      (AAL5) traffic. Setting the value to indicated for any other traffic 
      type results in all traffic being discarded.
      
      If this connection point is a permanent (provisioned) VCC mid-
      point, this attribute specifies whether the Partial Packet 
      Discard (PPD) function is to be enabled or disabled in the transmit 
      direction at this connecting point. The PPD function allows the 
      connecting point to discard the remainder of a cell-forwarded AAL5 
      frame if one cell of this frame has been discarded. The PPD 
      function increases the 'goodput' of the link, since cells which are 
      only going to be discarded by the AAL5 reassembly are not 
      transmitted.
      
      At a permanent VCC connecting point which is not a connection 
      endpoint, when this attribute is set to indicated, the PPD function is 
      applied to transmit traffic at this connecting point. It should not be 
      indicated for connections whose end points are not performing 
      AAL5 segmentation and reassembly. When this attribute is set to 
      notIndicated, the PPD feature is not applied to transmit traffic at 
      this connecting point.
      
      At a SPVC origin on a PNNI interface, a value of indicated 
      specifies that frame discard is requested in the forward direction. 
      The frame discard function for SPVCs consists of PPD at the SPVC 
      origin and at all intermediate connecting points. When this attribute 
      is set to notIndicated, forward frame discard is not requested in the 
      SPVC call setup. Thus PPD is not enabled at the SPVC origin nor at 
      any intermediate connecting point.
      
      At all points along a VPC, this setting is ignored.
      
      At a permanent VCC connection endpoint, this value is ignored. If 
      AAL5 segmentation and reassembly has been requested, PPD and 
      Early Packet Discard (EPD) are automatically enabled.
      
      This attribute has been migrated to txFrameDiscard."
   DEFVAL     { notIndicated }
::= { mscAtmIfVptVccVcdTrafficEntry 76 }

mscAtmIfVptVccVcdBwdFrameDiscard OBJECT-TYPE
   SYNTAX     INTEGER  {
                 notIndicated(0),
                 indicated(1) }
   ACCESS     read-write
   STATUS     obsolete
   DESCRIPTION
     "This attribute specifies the activation of frame discard functionality 
      in the backward data direction, at relay points, for this connection. 
      It applies to each hop of the connection. Frame discard functions 
      should not be requested if this connection is not transferring frame 
      (AAL5) traffic. Setting the value to indicated for any other traffic 
      type results in all traffic being discarded.
      
      If this connection point is a permanent (provisioned) VCC mid-
      point, this attribute specifies whether the Partial Packet Discard 
      (PPD) function is to be enabled or disabled in the receive direction 
      at this connecting point. The PPD function allows the connecting 
      point to discard the remainder of a cell-forwarded AAL5 frame if 
      one cell of this frame has been discarded. The PPD function 
      increases the 'goodput' of the link, since cells which are only going 
      to be discarded by the AAL5 reassembly are not received.
      
      At a permanent VCC connecting point which is not a connection 
      endpoint, when this attribute is set to indicated, the PPD function is 
      applied to receive traffic at this connecting point. It should not be 
      indicated for connections whose end points are not performing 
      AAL5 segmentation and reassembly. When this attribute is set to 
      notIndicated, the PPD feature is not applied to receive traffic at this 
      connecting point.
      
      At a SPVC origin on a PNNI interface, a value of indicated 
      specifies that frame discard is requested in the backward direction. 
      The frame discard function for SPVCs consists of PPD at the SPVC 
      origin and at all intermediate connecting points. When this attribute 
      is set to notIndicated, backwards frame discard is not requested in 
      the SPVC call setup. Thus PPD is not enabled at the SPVC origin 
      nor at any intermediate connecting point.
      
      At all points along a VPC, this setting is ignored.
      
      At a permanent VCC connection endpoint, this value is ignored. If 
      AAL5 segmentation and reassembly has been requested, PPD and 
      Early Packet Discard (EPD) are automatically enabled.
      
      This attribute has been migrated to rxFrameDiscard."
   DEFVAL     { notIndicated }
::= { mscAtmIfVptVccVcdTrafficEntry 77 }

mscAtmIfVptVccVcdAcctTable OBJECT-TYPE
   SYNTAX     SEQUENCE OF MscAtmIfVptVccVcdAcctEntry
   ACCESS     not-accessible
   STATUS     mandatory
   DESCRIPTION
     "This group contains the provisionable ATM accounting attributes 
      for a Vcc, Vpc, or Vpt component."
::= { mscAtmIfVptVccVcd 111 }

mscAtmIfVptVccVcdAcctEntry OBJECT-TYPE
   SYNTAX     MscAtmIfVptVccVcdAcctEntry
   ACCESS     not-accessible
   STATUS     mandatory
   DESCRIPTION
     "An entry in the mscAtmIfVptVccVcdAcctTable."
   INDEX {
      mscAtmIfIndex,
      mscAtmIfVptIndex,
      mscAtmIfVptVccIndex,
      mscAtmIfVptVccVcdIndex }
::= { mscAtmIfVptVccVcdAcctTable 1 }

MscAtmIfVptVccVcdAcctEntry ::= SEQUENCE {
   mscAtmIfVptVccVcdCorrelationTag
      AsciiString }

mscAtmIfVptVccVcdCorrelationTag OBJECT-TYPE
   SYNTAX     AsciiString (SIZE (0..32))
   ACCESS     read-write
   STATUS     mandatory
   DESCRIPTION
     "This attribute specifies a unique indentifier for each end of a PVC. It 
      that may be used by downstream processing systems to correlate 
      accounting records issued at different nodes in the network. The 
      attribute can be up to 32 bytes long. If it is less than 32 bytes, it is 
      zero filled on the right to create a 32 byte value. The resulting value 
      is recorded in the attribute callConnId for this PVC's ATM 
      accounting records.
      If the attribute is a null string then this PVC does not have any 
      accounting records generated for it."
   DEFVAL     { ''H }  -- ""
::= { mscAtmIfVptVccVcdAcctEntry 10 }

mscAtmIfVptVccVcdTxTdpTable OBJECT-TYPE
   SYNTAX     SEQUENCE OF MscAtmIfVptVccVcdTxTdpEntry
   ACCESS     not-accessible
   STATUS     obsolete
   DESCRIPTION
     "This attribute is migrated to the AtmTmProv group.
      
      This attribute is a vector of five traffic parameters whose meanings 
      are defined by the txTrafficDescType attribute. The values of peak 
      cell rate (PCR), sustained cell rate (SCR) and requested shaping rate 
      are expressed in cell/s. Maximum burst size (MBS) is expressed in 
      cells. CDVT is expressed in microseconds. The values of PCR, 
      SCR, MBS and CDVT are used for connection admission control 
      (CAC). The value of CDVT is only used for connections where the 
      atmServiceCategory is constantBitRate. For all other values of 
      atmServiceCategory, CDVT is ignored. The values of PCR, SCR 
      and requested shaping rate are used to determine the actual shaping 
      rate where traffic shaping is enabled.
      
      When txTrafficDescType is 1 or 2, all of the parameters must be set 
      to zero.
      
      When txTrafficDescType is 3, parameter 1 represents the PCR for 
      CLP equal to 0 and 1 traffic; parameter 4 represents the CDVT; and 
      parameter 5 represents the requested shaping rate. A non-zero value 
      in parameter 5 overrides any value in parameter 1. This result is 
      used as the PCR. Parameter 1 must be non-zero. Parameters 2 and 3 
      must be zero.
      
      When txTrafficDescType is 4, parameter 1 represents the PCR for 
      CLP equal to 0 and 1 traffic with cell discard; parameter 2 
      represents the PCR for CLP equal to 0 traffic; parameter 4 
      represents the CDVT; and parameter 5 represents the requested 
      shaping rate. A non-zero value in parameter 5 overrides any value in 
      parameter 1. This result is used as the PCR. Parameter 1 must be 
      greater than or equal to parameter 2. Parameters 1 and 2 must be 
      non-zero. Parameter 3 must be zero.
      
      When txTrafficDescType is 5, parameter 1 represents the PCR for 
      CLP equal to 0 and 1 traffic with cell tagging; parameter 2 
      represents the PCR for CLP equal to 0 traffic; parameter 4 
      represents the CDVT; and parameter 5 represents the requested 
      shaping rate. A non-zero value in parameter 5 overrides any value in 
      parameter 1. This result is used as the PCR. Parameter 1 must be 
      greater than or equal to parameter 2. Parameters 1 and 2 must be 
      non-zero. Parameter 3 must be zero.
      
      When txTrafficDescType is 6, parameter 1 represents the PCR for 
      CLP equal to 0 and 1 traffic; parameter 2 represents the SCR for 
      CLP equal to 0 and 1 traffic; parameter 3 represents the MBS for 
      CLP equal to 0 and 1 traffic; parameter 4 represents the CDVT; and 
      parameter 5 represents the requested shaping rate. A non-zero value 
      in parameter 5 overrides any value in parameter 1. This result is 
      used as the PCR. Parameters 1, 2 and 3 must be non-zero. 
      Parameter 1 must be greater than or equal to parameter 2. Parameter 
      5, must either be zero (unused) or greater than or equal to parameter 
      2.
      
      When txTrafficDescType is 7, parameter 1 represents the PCR for 
      CLP equal to 0 and 1 traffic; parameter 2 represents the SCR for 
      CLP equal to 0 with cell discard; parameter 3 represents the MBS 
      for CLP equal to 0 traffic; parameter 4 represents the CDVT; and 
      parameter 5 represents the requested shaping rate. A non-zero value 
      in parameter 5 overrides any value in parameter 1. This result is 
      used as the PCR. Parameters 1, 2 and 3 must be non-zero. 
      Parameter 1 must be greater than or equal to parameter 2. Parameter 
      5, must either be zero (unused) or greater than or equal to parameter 
      2.
      
      When txTrafficDescType is 8, parameter 1 represents the PCR for 
      CLP equal to 0 and 1 traffic; parameter 2 represents the SCR for 
      CLP equal to 0 traffic with cell tagging; parameter 3 represents the 
      MBS for CLP equal to 0 traffic; parameter 4 represents the CDVT; 
      and parameter 5 represents the requested shaping rate. A non-zero 
      value in parameter 5 overrides any value in parameter 1. This result 
      is used as the PCR. Parameters 1, 2 and 3 must be non-zero. 
      Parameter 1 must be greater than or equal to parameter 2. Parameter 
      5, must either be zero (unused) or greater than or equal to parameter 
      2.
      
      Whenever it is valid for PCR to be specified, parameter 5 may also 
      be used to specify a requested shaping rate. A non-zero value in 
      parameter 5 overrides the value in parameter 1 and is used as the 
      peak cell rate in calculations of CAC and shaping rate.
      
      For txTrafficDescType 3, 4 and 5, the transmit traffic is shaped at 
      the next rate less than the PCR. 
      
      For txTrafficDescType 6, 7 and 8, the transmit traffic is shaped at 
      the highest available rate which is between PCR and SCR. 
      However, if there is no available shaping rate between PCR and 
      SCR, traffic is shaped at the next rate above the PCR."
::= { mscAtmIfVptVccVcd 297 }

mscAtmIfVptVccVcdTxTdpEntry OBJECT-TYPE
   SYNTAX     MscAtmIfVptVccVcdTxTdpEntry
   ACCESS     not-accessible
   STATUS     obsolete
   DESCRIPTION
     "An entry in the mscAtmIfVptVccVcdTxTdpTable."
   INDEX {
      mscAtmIfIndex,
      mscAtmIfVptIndex,
      mscAtmIfVptVccIndex,
      mscAtmIfVptVccVcdIndex,
      mscAtmIfVptVccVcdTxTdpIndex }
::= { mscAtmIfVptVccVcdTxTdpTable 1 }

MscAtmIfVptVccVcdTxTdpEntry ::= SEQUENCE {
   mscAtmIfVptVccVcdTxTdpIndex
      Integer32,
   mscAtmIfVptVccVcdTxTdpValue
      Unsigned32 }

mscAtmIfVptVccVcdTxTdpIndex OBJECT-TYPE
   SYNTAX     Integer32 (1..5)
   ACCESS     not-accessible
   STATUS     obsolete
   DESCRIPTION
     "This variable represents the mscAtmIfVptVccVcdTxTdpTable
      specific index for the mscAtmIfVptVccVcdTxTdpTable."
::= { mscAtmIfVptVccVcdTxTdpEntry 1 }

mscAtmIfVptVccVcdTxTdpValue OBJECT-TYPE
   SYNTAX     Unsigned32 (0..2147483647)
   ACCESS     read-write
   STATUS     obsolete
   DESCRIPTION
     "This variable represents an individual value for the
      mscAtmIfVptVccVcdTxTdpTable."
::= { mscAtmIfVptVccVcdTxTdpEntry 2 }

mscAtmIfVptVccVcdRxTdpTable OBJECT-TYPE
   SYNTAX     SEQUENCE OF MscAtmIfVptVccVcdRxTdpEntry
   ACCESS     not-accessible
   STATUS     obsolete
   DESCRIPTION
     "This attribute is migrated to the AtmTmProv group.
      
      This attribute is a vector of four traffic parameters whose meanings 
      are defined by the rxTrafficDescType attribute. The values of peak 
      cell rate (PCR) and sustained cell rate (SCR) are expressed in 
      cell/s. Maximum burst size (MBS) is expressed in cells. The value 
      of CDVT is expressed in microseconds. The values of PCR, SCR, 
      MBS and CDVT are used for usage parameter control (UPC).
      
      When rxTrafficDescType is 1 or 2, all of the parameters must be set 
      to zero (unused).
      
      When rxTrafficDescType is 3, parameter 1 represents the PCR for 
      CLP equal to 0 and 1 traffic. Parameter 1 must be non-zero. 
      Parameters 2 and 3 must be set to zero (unused).
      
      When rxTrafficDescType is 4, parameter 1 represents the PCR for 
      CLP equal to 0 and 1 traffic; parameter 2 represents the PCR for 
      CLP equal to 0 traffic with cell discard. Parameters 1 and 2 must be 
      non-zero. Parameter 3 must be set to zero (unused). Parameter 1 
      must be greater than or equal to parameter 2.
      
      When rxTrafficDescType is 5, parameter 1 represents the PCR for 
      CLP equal to 0 and 1 traffic; parameter 2 represents the PCR for 
      CLP equal to 0 traffic with cell tagging. Parameters 1 and 2 must be 
      non-zero. Parameter 3 must be set to zero (unused). Parameter 1 
      must be greater than or equal to parameter 2.
      
      When rxTrafficDescType is a 6, parameter 1 represents the PCR for 
      CLP equal to 0 and 1 traffic; parameter 2 represents the SCR for 
      CLP equal to 0 and 1 traffic; parameter 3 represents the MBS for 
      CLP equal to 0 and 1 traffic. Parameters 1, 2 and 3 must be non-
      zero. Parameter 1 must be greater than or equal to Parameter 2. 
      
      When rxTrafficDescType is 7, parameter 1 represents the PCR for 
      CLP equal to 0 and 1 traffic; parameter 2 represents the SCR for 
      CLP equal to 0 traffic with cell discard; parameter 3 represents the 
      MBS for CLP equal to 0 traffic. Parameters 1, 2 and 3 must be non-
      zero. Parameter 1 must be greater than or equal to parameter 2. 
      
      When rxTrafficDescType is 8, parameter 1 represents the PCR for 
      CLP equal to 0 and 1 traffic; parameter 2 represents the SCR for 
      CLP equal to 0 traffic with cell tagging; parameter 3 represents the 
      MBS for CLP equal to 0 traffic. Parameter 1, 2 and 3 must be non-
      zero. Parameter 1 must be greater than or equal to parameter 2.
      
      When rxTrafficDescType is any value from 3 through 8, parameter 
      4 represents the CDVT. If this value is zero, the CDVT is taken 
      from the ConnectionAdministrator defaults for the particular 
      atmServiceCategory of this connection.
      
      When rxTrafficDescriptorType is 3 through 8, there are certain 
      extreme combinations of rxTrafficDescParm which are outside the 
      capabilities of the UPC hardware. The check prov command detects 
      such cases and generates an error message. If this happens, adjust 
      the parameters until they fall within the supported limits. 
      
      To calculate the limits, use the following formulae:
      I1 = 1 000 000 000 / PCR
      L1 = CDVT * 1000
      I2 = 1 000 000 000 / SCR
      L2 = CDVT + (MBS - 1) * (I2 - I1)
      I1 and I2 must be less than or equal to 335 523 840. I1 + L1 must 
      be less than or equal to 1 342 156 800. I2 + L2 must be less than or 
      equal to 1 342 156 800. Note that I2 and L2 only apply when the 
      rxTrafficDescriptorType is 6 through 8.
      
      If the values of I1, L1, I2 or L2 are closer to the limits described 
      above, a further restriction applies. Specifically, if either:
      I1 > 41 940 480 or
      I2 > 41 940 480 or
      I1 + L1 > 167 769 600 or
      I2 + L2 > 167 769 600
      then both I1 and I2 must be greater than 20 480. 
      
      Parameter 5 of the rxTrafficDescParm is always unused. 
      
      If the rxTrafficDescType is sameAsTx, the values in this attribute 
      are taken from the txTrafficDescParm."
::= { mscAtmIfVptVccVcd 298 }

mscAtmIfVptVccVcdRxTdpEntry OBJECT-TYPE
   SYNTAX     MscAtmIfVptVccVcdRxTdpEntry
   ACCESS     not-accessible
   STATUS     obsolete
   DESCRIPTION
     "An entry in the mscAtmIfVptVccVcdRxTdpTable."
   INDEX {
      mscAtmIfIndex,
      mscAtmIfVptIndex,
      mscAtmIfVptVccIndex,
      mscAtmIfVptVccVcdIndex,
      mscAtmIfVptVccVcdRxTdpIndex }
::= { mscAtmIfVptVccVcdRxTdpTable 1 }

MscAtmIfVptVccVcdRxTdpEntry ::= SEQUENCE {
   mscAtmIfVptVccVcdRxTdpIndex
      Integer32,
   mscAtmIfVptVccVcdRxTdpValue
      Unsigned32 }

mscAtmIfVptVccVcdRxTdpIndex OBJECT-TYPE
   SYNTAX     Integer32 (1..5)
   ACCESS     not-accessible
   STATUS     obsolete
   DESCRIPTION
     "This variable represents the mscAtmIfVptVccVcdRxTdpTable
      specific index for the mscAtmIfVptVccVcdRxTdpTable."
::= { mscAtmIfVptVccVcdRxTdpEntry 1 }

mscAtmIfVptVccVcdRxTdpValue OBJECT-TYPE
   SYNTAX     Unsigned32 (0..2147483647)
   ACCESS     read-write
   STATUS     obsolete
   DESCRIPTION
     "This variable represents an individual value for the
      mscAtmIfVptVccVcdRxTdpTable."
::= { mscAtmIfVptVccVcdRxTdpEntry 2 }

mscAtmIfVptVccVcdFqpTable OBJECT-TYPE
   SYNTAX     SEQUENCE OF MscAtmIfVptVccVcdFqpEntry
   ACCESS     not-accessible
   STATUS     obsolete
   DESCRIPTION
     "This attribute is migrated to the AtmTmProv group.
      
      This attribute is a vector of three elements that specify the quality of 
      service parameters for the forward direction for this connection. 
      This attribute is used for SPVC connections.
      
      The cdv element specifies the acceptable peak-to-peak Cell Delay 
      Variation (CDV) of real-time connections (CBR, and rt-VBR). It is 
      signalled through the extended QoS information element.
      
      The ctd specifies the acceptable maximum Cell Transfer Delay 
      (maxCtd) of real-time connections (CBR, and rt-VBR). 
      It is signalled through the end to end transit delay information 
      element.
      
      The clr specifies the acceptable Cell Loss Ratio (CLR) of CBR, rt-
      VBR, and nrt-VBR connections. It is signalled through the extended 
      QoS information element."
::= { mscAtmIfVptVccVcd 359 }

mscAtmIfVptVccVcdFqpEntry OBJECT-TYPE
   SYNTAX     MscAtmIfVptVccVcdFqpEntry
   ACCESS     not-accessible
   STATUS     obsolete
   DESCRIPTION
     "An entry in the mscAtmIfVptVccVcdFqpTable."
   INDEX {
      mscAtmIfIndex,
      mscAtmIfVptIndex,
      mscAtmIfVptVccIndex,
      mscAtmIfVptVccVcdIndex,
      mscAtmIfVptVccVcdFqpIndex }
::= { mscAtmIfVptVccVcdFqpTable 1 }

MscAtmIfVptVccVcdFqpEntry ::= SEQUENCE {
   mscAtmIfVptVccVcdFqpIndex
      INTEGER,
   mscAtmIfVptVccVcdFqpValue
      Unsigned32 }

mscAtmIfVptVccVcdFqpIndex OBJECT-TYPE
   SYNTAX     INTEGER  {
                 cdv(0),
                 ctd(1),
                 clr(2) }
   ACCESS     not-accessible
   STATUS     obsolete
   DESCRIPTION
     "This variable represents the mscAtmIfVptVccVcdFqpTable
      specific index for the mscAtmIfVptVccVcdFqpTable."
::= { mscAtmIfVptVccVcdFqpEntry 1 }

mscAtmIfVptVccVcdFqpValue OBJECT-TYPE
   SYNTAX     Unsigned32 (0..2147483647)
   ACCESS     read-write
   STATUS     obsolete
   DESCRIPTION
     "This variable represents an individual value for the
      mscAtmIfVptVccVcdFqpTable."
::= { mscAtmIfVptVccVcdFqpEntry 2 }

mscAtmIfVptVccVcdBqpTable OBJECT-TYPE
   SYNTAX     SEQUENCE OF MscAtmIfVptVccVcdBqpEntry
   ACCESS     not-accessible
   STATUS     obsolete
   DESCRIPTION
     "This attribute is migrated to the AtmTmProv group.
      
      This attribute is a vector of three elements that specify the quality of 
      service parameters for the backward direction for this connection. 
      This attribute is used for SPVC connections.
      
      The cdv element specifies the acceptable peak-to-peak Cell Delay 
      Variation (CDV) of real-time connections (CBR, and rt-VBR). 
      
      It is signalled through the extended QoS information element.
      
      The ctd specifies the acceptable maximum Cell Transfer Delay 
      (maxCtd) of real-time connections (CBR, and rt-VBR). It is 
      signalled through the end to end transit delay information element.
      
      The clr specifies the acceptable Cell Loss Ratio (CLR) of CBR, rt-
      VBR, and nrt-VBR connections. It is signalled through the extended 
      QoS information element."
::= { mscAtmIfVptVccVcd 360 }

mscAtmIfVptVccVcdBqpEntry OBJECT-TYPE
   SYNTAX     MscAtmIfVptVccVcdBqpEntry
   ACCESS     not-accessible
   STATUS     obsolete
   DESCRIPTION
     "An entry in the mscAtmIfVptVccVcdBqpTable."
   INDEX {
      mscAtmIfIndex,
      mscAtmIfVptIndex,
      mscAtmIfVptVccIndex,
      mscAtmIfVptVccVcdIndex,
      mscAtmIfVptVccVcdBqpIndex }
::= { mscAtmIfVptVccVcdBqpTable 1 }

MscAtmIfVptVccVcdBqpEntry ::= SEQUENCE {
   mscAtmIfVptVccVcdBqpIndex
      INTEGER,
   mscAtmIfVptVccVcdBqpValue
      Unsigned32 }

mscAtmIfVptVccVcdBqpIndex OBJECT-TYPE
   SYNTAX     INTEGER  {
                 cdv(0),
                 ctd(1),
                 clr(2) }
   ACCESS     not-accessible
   STATUS     obsolete
   DESCRIPTION
     "This variable represents the mscAtmIfVptVccVcdBqpTable
      specific index for the mscAtmIfVptVccVcdBqpTable."
::= { mscAtmIfVptVccVcdBqpEntry 1 }

mscAtmIfVptVccVcdBqpValue OBJECT-TYPE
   SYNTAX     Unsigned32 (0..2147483647)
   ACCESS     read-write
   STATUS     obsolete
   DESCRIPTION
     "This variable represents an individual value for the
      mscAtmIfVptVccVcdBqpTable."
::= { mscAtmIfVptVccVcdBqpEntry 2 }


-- AtmIf/n Vcc/vpi.vci Vcd TrafficManagement, 
-- AtmIf/n Vpc/vci Vpd TrafficManagement,
-- AtmIf/n Vpt/vpi Vpd TrafficManagement,
-- AtmIf/n Vpt/vpi Vcc/vci Vcd TrafficManagement
-- This component contains provisioned traffic management attributes 
-- of a connection. It is added automatically when a Vcc, Vpc, or Vpt is 
-- added in provisioning mode. It is a mandatory subcomponent of the 
-- Vcd or Vpd component.

mscAtmIfVptVccVcdTm OBJECT IDENTIFIER ::= { mscAtmIfVptVccVcd 2 }



mscAtmIfVptVccVcdTmRowStatusTable OBJECT-TYPE
   SYNTAX     SEQUENCE OF MscAtmIfVptVccVcdTmRowStatusEntry
   ACCESS     not-accessible
   STATUS     mandatory
   DESCRIPTION
     "This entry controls the addition and deletion of 
      mscAtmIfVptVccVcdTm components."
::= { mscAtmIfVptVccVcdTm 1 }

mscAtmIfVptVccVcdTmRowStatusEntry OBJECT-TYPE
   SYNTAX     MscAtmIfVptVccVcdTmRowStatusEntry
   ACCESS     not-accessible
   STATUS     mandatory
   DESCRIPTION
     "A single entry in the table represents a single 
      mscAtmIfVptVccVcdTm component."
   INDEX {
      mscAtmIfIndex,
      mscAtmIfVptIndex,
      mscAtmIfVptVccIndex,
      mscAtmIfVptVccVcdIndex,
      mscAtmIfVptVccVcdTmIndex }
::= { mscAtmIfVptVccVcdTmRowStatusTable 1 }

MscAtmIfVptVccVcdTmRowStatusEntry ::= SEQUENCE {
   mscAtmIfVptVccVcdTmRowStatus
      RowStatus,
   mscAtmIfVptVccVcdTmComponentName
      DisplayString,
   mscAtmIfVptVccVcdTmStorageType
      StorageType,
   mscAtmIfVptVccVcdTmIndex
      NonReplicated }

mscAtmIfVptVccVcdTmRowStatus OBJECT-TYPE
   SYNTAX     RowStatus 
   ACCESS     read-only
   STATUS     mandatory
   DESCRIPTION
     "This variable is used as the basis for SNMP naming of
      mscAtmIfVptVccVcdTm components.
      These components cannot be added nor deleted."
::= { mscAtmIfVptVccVcdTmRowStatusEntry 1 }

mscAtmIfVptVccVcdTmComponentName OBJECT-TYPE
   SYNTAX     DisplayString 
   ACCESS     read-only
   STATUS     mandatory
   DESCRIPTION
     "This variable provides the component's string name for
      use with the ASCII Console Interface"
::= { mscAtmIfVptVccVcdTmRowStatusEntry 2 }

mscAtmIfVptVccVcdTmStorageType OBJECT-TYPE
   SYNTAX     StorageType 
   ACCESS     read-only
   STATUS     mandatory
   DESCRIPTION
     "This variable represents the storage type value for the
      mscAtmIfVptVccVcdTm tables."
::= { mscAtmIfVptVccVcdTmRowStatusEntry 4 }

mscAtmIfVptVccVcdTmIndex OBJECT-TYPE
   SYNTAX     NonReplicated 
   ACCESS     not-accessible
   STATUS     mandatory
   DESCRIPTION
     "This variable represents the index for the mscAtmIfVptVccVcdTm tables."
::= { mscAtmIfVptVccVcdTmRowStatusEntry 10 }

mscAtmIfVptVccVcdTmProvTable OBJECT-TYPE
   SYNTAX     SEQUENCE OF MscAtmIfVptVccVcdTmProvEntry
   ACCESS     not-accessible
   STATUS     mandatory
   DESCRIPTION
     "This group contains traffic related provisionable attributes for the 
      Vcc, Vpc, and Vpt components. Changing any of the attributes in 
      this group causes a service interruption on the Vcc, Vpc, or Vpt 
      component."
::= { mscAtmIfVptVccVcdTm 100 }

mscAtmIfVptVccVcdTmProvEntry OBJECT-TYPE
   SYNTAX     MscAtmIfVptVccVcdTmProvEntry
   ACCESS     not-accessible
   STATUS     mandatory
   DESCRIPTION
     "An entry in the mscAtmIfVptVccVcdTmProvTable."
   INDEX {
      mscAtmIfIndex,
      mscAtmIfVptIndex,
      mscAtmIfVptVccIndex,
      mscAtmIfVptVccVcdIndex,
      mscAtmIfVptVccVcdTmIndex }
::= { mscAtmIfVptVccVcdTmProvTable 1 }

MscAtmIfVptVccVcdTmProvEntry ::= SEQUENCE {
   mscAtmIfVptVccVcdTmTxTrafficDescType
      INTEGER,
   mscAtmIfVptVccVcdTmFwdQosClass
      INTEGER,
   mscAtmIfVptVccVcdTmTxQueueLimit
      Unsigned32,
   mscAtmIfVptVccVcdTmHoldingPriority
      INTEGER,
   mscAtmIfVptVccVcdTmRxTrafficDescType
      INTEGER,
   mscAtmIfVptVccVcdTmBwdQosClass
      INTEGER,
   mscAtmIfVptVccVcdTmAtmServiceCategory
      INTEGER,
   mscAtmIfVptVccVcdTmTrafficShaping
      INTEGER,
   mscAtmIfVptVccVcdTmUnshapedTransmitQueueing
      INTEGER,
   mscAtmIfVptVccVcdTmWeight
      Unsigned32,
   mscAtmIfVptVccVcdTmForceTagging
      INTEGER,
   mscAtmIfVptVccVcdTmUsageParameterControl
      INTEGER,
   mscAtmIfVptVccVcdTmBearerClassBbc
      INTEGER,
   mscAtmIfVptVccVcdTmTransferCapabilityBbc
      INTEGER,
   mscAtmIfVptVccVcdTmClippingBbc
      INTEGER,
   mscAtmIfVptVccVcdTmBestEffort
      INTEGER,
   mscAtmIfVptVccVcdTmTxPacketWiseDiscard
      INTEGER,
   mscAtmIfVptVccVcdTmRxPacketWiseDiscard
      INTEGER,
   mscAtmIfVptVccVcdTmAbrConnectionType
      INTEGER }

mscAtmIfVptVccVcdTmTxTrafficDescType OBJECT-TYPE
   SYNTAX     INTEGER  {
                 n1(1),
                 n2(2),
                 n3(3),
                 n4(4),
                 n5(5),
                 n6(6),
                 n7(7),
                 n8(8),
                 n9(9) }
   ACCESS     read-write
   STATUS     mandatory
   DESCRIPTION
     "This attribute specifies the type of traffic management which is 
      applied to the transmit direction of this connection as defined in the 
      ATM Forum. The txTrafficDescType determines the number and 
      meaning of the parameters in the txTrafficDescParm attribute.
      
      This attribute can have a value of 9 if and only if the 
      atmServiceCategory is availableBitRate."
   DEFVAL     { n1 }
::= { mscAtmIfVptVccVcdTmProvEntry 10 }

mscAtmIfVptVccVcdTmFwdQosClass OBJECT-TYPE
   SYNTAX     INTEGER  {
                 n0(0),
                 n1(1),
                 n2(2),
                 n3(3),
                 n4(4) }
   ACCESS     read-write
   STATUS     mandatory
   DESCRIPTION
     "This attribute specifies the quality of service for the forward 
      direction for this connection. This attribute is only used for SPVC 
      connections.
      
      Class 1 supports a QOS that meets Service Class A performance 
      requirements (circuit emulation, constant bit rate video).
      
      Class 2 supports a QOS that meets Service Class B performance 
      requirements (variable bit rate audio and video).
      
      Class 3 supports a QOS that meets Service Class C performance 
      requirements (Connection-Oriented Data Transfer).
      
      Class 4 supports a QOS that meets Service Class D performance 
      requirements (Connectionless Data Transfer).
      
      Class 0 is the unspecified bit rate QOS class; no objective is 
      specified for the performance parameters."
   DEFVAL     { n0 }
::= { mscAtmIfVptVccVcdTmProvEntry 21 }

mscAtmIfVptVccVcdTmTxQueueLimit OBJECT-TYPE
   SYNTAX     Unsigned32 (0 | 5..512000)
   ACCESS     read-write
   STATUS     mandatory
   DESCRIPTION
     "This attribute specifies an override to the default transmit queue 
      limit for this connection. An value other than sameAsCa may be 
      specified only for ATM IP and 1pOC48SmSrAtm cards. This 
      attribute is not applicable for basic Vpts.
      
      A value of sameAsCa means to use the default common or per-VC 
      transmit queue limit as defined by the CA service category for this 
      connection. 
      
      A value from 5 to 63,488 indicates that a specific transmit queue 
      limit is requested which differs from the default which is defined 
      under the CA component for this service category. A specific value 
      is ignored for connections where common queuing is specified for 
      the service category. 
      
      For the 1pOC48SmSrAtm card, this attribute is used to set the per 
      VC utilization limit.
      
      The actual transmit queue limit for a connection is visible in the Vcc 
      Tm, Vpc Tm or Vpt txQueueThresholds attribute.

      VALUES (

      0 = sameAsCa

      )"
   DEFVAL     { 0 }
::= { mscAtmIfVptVccVcdTmProvEntry 22 }

mscAtmIfVptVccVcdTmHoldingPriority OBJECT-TYPE
   SYNTAX     INTEGER  {
                 n0(0),
                 n1(1),
                 n2(2),
                 n3(3),
                 n4(4) }
   ACCESS     read-write
   STATUS     mandatory
   DESCRIPTION
     "This attribute specifies the holding priority of this connection. In a 
      situation where the link bandwidth fluctuates, such as over an IMA 
      link, holding priority is used to determine which connections are 
      held and which are released. Holding priority 4 connections are the 
      first to be released. Holding priority 0 connections are the last to be 
      released. This value provisioned in the Vcd or Vpd may be 
      overridden by certain applications, for example Vcc Test, which run 
      over this connection. The default holding priority for a provisioned 
      connection is higher then default holding priorities for dynamic 
      (SVC) connections. 
      
      This attribute is not applicable for Vpt Vccs."
   DEFVAL     { n2 }
::= { mscAtmIfVptVccVcdTmProvEntry 25 }

mscAtmIfVptVccVcdTmRxTrafficDescType OBJECT-TYPE
   SYNTAX     INTEGER  {
                 n1(1),
                 n2(2),
                 n3(3),
                 n4(4),
                 n5(5),
                 n6(6),
                 n7(7),
                 n8(8),
                 n9(9),
                 sameAsTx(15) }
   ACCESS     read-write
   STATUS     mandatory
   DESCRIPTION
     "This attribute specifies the type of traffic management which is 
      applied to the receive direction of this connection as defined in the 
      ATM Forum. The rxTrafficDescType determines the number and 
      meaning of the parameters in the rxTrafficDescParm attribute.
      
      When this attribute is set to sameAsTx, the rxTrafficDescType as 
      well as the rxTrafficDescParm are taken from the 
      txTrafficDescType and txTrafficDescParm values."
   DEFVAL     { sameAsTx }
::= { mscAtmIfVptVccVcdTmProvEntry 30 }

mscAtmIfVptVccVcdTmBwdQosClass OBJECT-TYPE
   SYNTAX     INTEGER  {
                 n0(0),
                 n1(1),
                 n2(2),
                 n3(3),
                 n4(4),
                 sameAsFwd(15) }
   ACCESS     read-write
   STATUS     mandatory
   DESCRIPTION
     "This attribute specifies the quality of service for the backward 
      direction for this connection. This attribute is only used for SPVC 
      connections.
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified bit rate QOS class; no objective is 
      specified for the performance parameters.
      
      The sameAsFwd selection sets the backward quality of service to 
      be the same as the forward quality of service."
   DEFVAL     { sameAsFwd }
::= { mscAtmIfVptVccVcdTmProvEntry 41 }

mscAtmIfVptVccVcdTmAtmServiceCategory OBJECT-TYPE
   SYNTAX     INTEGER  {
                 unspecifiedBitRate(0),
                 constantBitRate(1),
                 rtVariableBitRate(2),
                 nrtVariableBitRate(3),
                 availableBitRate(4),
                 derivedFromBBC(15) }
   ACCESS     read-write
   STATUS     mandatory
   DESCRIPTION
     "This attribute specifies the ATM service category for both directions 
      of the connection. 
      
      The value derivedFromBBC may only be used if the SrcPvc 
      component is provisioned under this Vcc. Otherwise a specific 
      ATM service category must be specified. 
      
      If this attribute is set to derivedFromBBC, the Broadband Bearer 
      Capability (BBC) and bestEffort attributes are used to determine the 
      atmServiceCategory of this connection. 
      
      If this attribute is set to other than derivedFromBBC, the value of 
      this attribute is used to override the provisioned BBC Information 
      Element parameters. In those cases, the BBC attributes are not used. 
      
      The constantBitRate service category is intended for real time 
      applications, that is those requiring tightly constrained delay and 
      delay variation, as would be appropriate for voice and video 
      applications. The consistent availability of a fixed quantity of 
      bandwidth is considered appropriate for CBR service. Cells which 
      are delayed beyond the value specified by Cell Transfer Delay are 
      assumed to be of significantly reduced value to the application.
      
      The rtVariableBitRate service category is intended for real time 
      applications, that is those requiring tightly constrained delay and 
      delay variation, as would be appropriate for voice and video 
      applications. Sources are expected to transmit at a rate which varies 
      with time. Equivalently, the source can be described as 'bursty'. 
      Cells which are delayed beyond the value specified by CTD are 
      assumed to be of significantly reduced value to the application. Real 
      time VBR service may support statistical multiplexing of real time 
      sources.
      
      The nrtVariableBitRate service category is intended for non-real 
      time applications which have bursty traffic characteristics and which 
      can be characterized in terms of a PCR, SCR, and MBS. For those 
      cells which are transferred within the traffic contract, the application 
      expects a low cell loss ratio. For all connections, it expects a bound 
      on the mean cell transfer delay. Non-real time VBR service may 
      support statistical multiplexing of connections. 
      
      The availableBitRate service is an ATM layer service category for 
      which the limiting ATM layer transfer characteristics provided by 
      the network may change subsequent to connection establishment. 
      ABR service has a flow control mechanism which supports several 
      types of feedback to control the source rate in response to changing 
      ATM layer transfer characteristics. ABR service is not intended to 
      support real-time applications. 
      
      The unspecifiedBitRate service is intended for non-real time 
      applications; that is, those not requiring tightly constrained delay 
      and delay variation. UBR sources are expected to be bursty. UBR 
      service supports a high degree of statistical multiplexing among 
      sources. UBR service does not specify traffic related service 
      guarantees. No numerical commitments are made with respect to 
      the cell loss ratio experienced by a UBR connection, or as to the 
      cell transfer delay experienced by cells on the connection."
   DEFVAL     { unspecifiedBitRate }
::= { mscAtmIfVptVccVcdTmProvEntry 42 }

mscAtmIfVptVccVcdTmTrafficShaping OBJECT-TYPE
   SYNTAX     INTEGER  {
                 disabled(1),
                 sameAsCa(2) }
   ACCESS     read-write
   STATUS     mandatory
   DESCRIPTION
     "This attribute specifies whether this connection uses traffic shaping 
      when transmitting traffic to the ATM interface.
      
      This attribute is ignored if the atmServiceCategory is 
      availableBitRate.
      
      Traffic shaping is not available on the 1pOC12SmLrAtm card, 
      therefore this attribute is ignored.
      
      When sameAsCa is selected, traffic shaping for the connection is 
      based on the trafficShaping attribute of the connection's service 
      category component under the CA. If the service category has 
      trafficShaping set to enabled or inverseUpc, then traffic shaping is 
      enabled for the connection. Note that enabling traffic shaping may 
      have no effect under certain cases. These cases are listed in the 
      description of the trafficShaping operational attribute, which is 
      under the Vcc Tm, Vpc Tm, or Vpt Tm components.
      
      When disabled is selected, traffic shaping for this connection is 
      disabled regardless of the provisioning of the connection's service 
      category component."
   DEFVAL     { sameAsCa }
::= { mscAtmIfVptVccVcdTmProvEntry 50 }

mscAtmIfVptVccVcdTmUnshapedTransmitQueueing OBJECT-TYPE
   SYNTAX     INTEGER  {
                 common(1),
                 sameAsCa(3) }
   ACCESS     read-write
   STATUS     mandatory
   DESCRIPTION
     "This attribute only applies when this connection is unshaped. This 
      attribute specifies the transmit queueing method for this connection 
      if it is unshaped. The two possible methods are per-VC queuing and 
      common queuing. 
      
      On ATM IP FPs, this attribute must be set to sameAsCa. 
      
      This attribute is ignored in the following situations:
      - if the connection has trafficShaping enabled or inverseUpc, or 
      - if the atmServiceCategory is availableBitRate, or
      - if the atmServiceCategory is constantBitRate and this is a CQC-
      based ATM FP.
      - for basic Vpts and standard Vpt Vccs
      
      When this attribute is set to sameAsCa, the transmit queueing 
      method for the connection is based on the 
      unshapedTransmitQueueing attribute of the connection's service 
      category component under the CA. 
      
      When this attribute is set to common, transmit traffic on this 
      unshaped connection is destined for the common queue."
   DEFVAL     { sameAsCa }
::= { mscAtmIfVptVccVcdTmProvEntry 60 }

mscAtmIfVptVccVcdTmWeight OBJECT-TYPE
   SYNTAX     Unsigned32 (0 | 1..4095 | 65535)
   ACCESS     read-write
   STATUS     mandatory
   DESCRIPTION
     "This attribute specifies an override for the weight of this unshaped 
      connection. This attribute is ignored for shaped connections, for 
      ABR connections, for connections on a CQC-based ATM FP and 
      basic Vpts.
      
      When the value is set to sameAsCa, the weight is determined by the 
      fairnessWeight attribute under the CA service category component 
      for all but standard Vpt Vccs. For standard Vpt Vccs, the weight is 
      determined by the Vcc's service category, when the value is set to 
      sameAsCa.
      
      When this attribute is set to a value from 1 to 4095, that value is 
      used for the fairness weight of this connection relative to other 
      connections. For all but standard Vpt Vccs, fairness weight 
      determines the proportion of transmit cell opportunities which are 
      allocated to this connection, compared to other connections in the 
      same service category. For standard Vpt Vccs, fairness weight 
      determines the proportion of transmit cell opportunities which are 
      allocated to this connection, compared to other connections 
      associated with the Vpt.
      
      When the value is set to upToQueueLimit, the fairness weight is 
      limited only by the txQueueLimit.

      VALUES (

      0 = upToQueueLimit

      65535 = sameAsCa

      )"
   DEFVAL     { 65535 }
::= { mscAtmIfVptVccVcdTmProvEntry 61 }

mscAtmIfVptVccVcdTmForceTagging OBJECT-TYPE
   SYNTAX     INTEGER  {
                 enabled(0),
                 disabled(1),
                 sameAsCa(2) }
   ACCESS     read-write
   STATUS     mandatory
   DESCRIPTION
     "This attribute specifies whether force tagging is enforced for this 
      connection for cells in the transmit direction. 
      
      On CQC-based ATM cards and for Vpts, this attribute is not 
      applicable and is ignored. 
      
      When the value is set to sameAsCa, the force tagging functionality 
      is determined by the forceTagging attribute under the CA service 
      category component. 
      
      When the value is set to enabled, force tagging is enabled for cells 
      in the transmit direction on this connection. When this option is 
      selected, the CLP bit is set to 1 for all cells in the transmit direction. 
      Cells which are tagged are counted in the txCellClp attribute. 
      
      When the value is set to disabled, force tagging is disabled for cells 
      in the transmit direction on this connection. When this option is 
      selected, the CLP bit is unchanged for cells in the transmit 
      direction."
   DEFVAL     { sameAsCa }
::= { mscAtmIfVptVccVcdTmProvEntry 62 }

mscAtmIfVptVccVcdTmUsageParameterControl OBJECT-TYPE
   SYNTAX     INTEGER  {
                 enforced(0),
                 disabled(1),
                 sameAsCa(2),
                 monitored(4) }
   ACCESS     read-write
   STATUS     mandatory
   DESCRIPTION
     "This attribute specifies whether this connection enforces usage 
      parameter control when receiving traffic from the ATM interface.
      
      When sameAsCa is selected, UPC for the connection is based on 
      the usageParameterControl attribute of the service category 
      component under the AtmIf CA. If the service category has UPC 
      enforced or monitored, then UPC is set to that value for the 
      connection. 
      
      When disabled is selected, UPC for this connection is disabled 
      regardless of the provisioning of the service category. 
      
      When enforced is selected, UPC for this connection is enforced 
      regardless of the provisioning of the service category. 
      
      Note that setting UPC to enforced or monitored may have no effect 
      under certain cases. These cases are listed in the description of the 
      usageParameterControl operational attribute, which is under the 
      Vcc, Vpc, and Vpt components."
   DEFVAL     { sameAsCa }
::= { mscAtmIfVptVccVcdTmProvEntry 70 }

mscAtmIfVptVccVcdTmBearerClassBbc OBJECT-TYPE
   SYNTAX     INTEGER  {
                 a(1),
                 c(3),
                 x(16),
                 vp(24),
                 derivedFromServiceCategory(31) }
   ACCESS     read-write
   STATUS     mandatory
   DESCRIPTION
     "This attribute specifies the bearer capability. This attribute is only 
      used for SPVC and SPVP connections. It is one of the Broadband 
      Bearer Capability (BBC) attributes. The purpose of the BBC 
      information element is to indicate a requested broadband 
      connection-oriented bearer service to be provided by the network.
      
      The value derivedFromServiceCategory specifies that the actual 
      value which is used for this connection is derived from the value of 
      the atmServiceCategory. Either, this attribute must be set to 
      derivedFromServiceCategory, or the atmServiceCategory attribute 
      must be set to derivedFromBBC, but not both.
      
      Class a service is a connection-oriented, constant bit rate ATM 
      transport service. Class a service has end to end timing 
      requirements and may require stringent cell loss, cell delay and cell 
      delay variation performance.When a is set, the user is requesting 
      more than an ATM only service. The network may look at the AAL 
      to provide interworking based upon its contents. 
      
      Class c service is a connection-oriented, variable bit rate ATM 
      transport service. Class c service has no end-to-end timing 
      requirements. When c is set, the user is requesting more than an 
      ATM only service. The network interworking function may look at 
      the AAL and provide service based on it.
      
      Class x service is a connection-oriented ATM transport service 
      where the AAL, trafficType (vbr or cbr) and timing requirements 
      are user defined (that is, transparent to the network).When x is set 
      the user is requesting an ATM only service from the network. In this 
      case, the network shall not process any higher layer protocol.
      
      Class vp service is used to specify a transparent VP service. When 
      the value of this attribute is vp, the user is requesting an ATM only 
      service from the network. In this case, the network shall not process 
      any higher layer protocol. This service differs from class x service 
      in that with the class vp service both the VCI field (except or VCI 
      values 0, 3, 4, and 6 through 15) and Payload Type field are 
      transported transparently by the network. This attribute value is 
      only applicable to SPVP connections."
   DEFVAL     { derivedFromServiceCategory }
::= { mscAtmIfVptVccVcdTmProvEntry 71 }

mscAtmIfVptVccVcdTmTransferCapabilityBbc OBJECT-TYPE
   SYNTAX     INTEGER  {
                 n0(0),
                 n1(1),
                 n2(2),
                 n5(5),
                 n8(8),
                 n9(9),
                 n10(10),
                 notApplicable(30),
                 derivedFromServiceCategory(31) }
   ACCESS     read-write
   STATUS     mandatory
   DESCRIPTION
     "This attribute specifies the transfer capability for this connection. 
      Uni 3.0/3.1 traffic type and end-to-end timing parameters are 
      mapped into this parameter as follows:
      <transferCapability: TrafficType, Timing>
      0: NoIndication, NoIndication
      1: NoIndication, yes
      2: NoIndication, no
      5: CBR, yes
      8: VBR, NoIndication
      9: VBR, yes
      10: VBR, no
      
      notApplicable specifies that the user does not want to specify the 
      transfer capability.
      
      The CBR traffic type refers to traffic offered on services such as a 
      constant bit rate video service or a circuit emulation.
      The VBR traffic type refers to traffic offered on services such as 
      packetized audio and video, or data.
      
      The value no indication for traffic type is used if the user has not set 
      the traffic type; similarly for end-to-end timing.
      
      The value yes for end-to-end timing indicates that end-to-end 
      timing is required.
      
      The value no for end-to-end timing indicates that end-to-end timing 
      is not required.
      
      The value derivedFromServiceCategory specifies that the actual 
      value which is used for this connection is derived from the value of 
      the atmServiceCategory. Either, this attribute must be set to 
      derivedFromServiceCategory, or the atmServiceCategory attribute 
      must be set to derivedFromBBC, but not both."
   DEFVAL     { derivedFromServiceCategory }
::= { mscAtmIfVptVccVcdTmProvEntry 72 }

mscAtmIfVptVccVcdTmClippingBbc OBJECT-TYPE
   SYNTAX     INTEGER  {
                 no(0),
                 yes(1) }
   ACCESS     read-write
   STATUS     mandatory
   DESCRIPTION
     "This attribute specifies the value for the clipping susceptibility 
      parameter in the BBC Information Element. This attribute is only 
      used for SPVC connections. It is one of the Broadband Bearer 
      Capability attributes.
      
      Clipping is an impairment in which the first fraction of a second of 
      information to be transferred is lost. It occurs after a call is 
      answered and before an associated connection is switched through."
   DEFVAL     { no }
::= { mscAtmIfVptVccVcdTmProvEntry 74 }

mscAtmIfVptVccVcdTmBestEffort OBJECT-TYPE
   SYNTAX     INTEGER  {
                 indicated(0),
                 notIndicated(1),
                 derivedFromServiceCategory(15) }
   ACCESS     read-write
   STATUS     mandatory
   DESCRIPTION
     "This attribute specifies the value of the best effort parameter in the 
      ATM Traffic Descriptor Information Element. This attribute is only 
      used for Soft PVC connections. It is one of the Broadband Bearer 
      Capability attributes.
      
      The value indicated implies that the quality of service for this 
      connection is not guaranteed.
      
      The value notIndicated implies that the quality of service for this 
      connection is guaranteed.
      
      The value derivedFromServiceCategory specifies that the actual 
      value which is used for this connection is derived from the value of 
      the atmServiceCategory. Either, this attribute must be set to 
      derivedFromServiceCategory, or the atmServiceCategory attribute 
      must be set to derivedFromBBC, but not both."
   DEFVAL     { derivedFromServiceCategory }
::= { mscAtmIfVptVccVcdTmProvEntry 75 }

mscAtmIfVptVccVcdTmTxPacketWiseDiscard OBJECT-TYPE
   SYNTAX     INTEGER  {
                 disabled(0),
                 enabled(1) }
   ACCESS     read-write
   STATUS     mandatory
   DESCRIPTION
     "This attribute specifies whether packet-wise discard functions are to 
      be enabled or disabled in the transmit data direction for this 
      connection. Packet-wise discard functions should only be requested 
      if this connection is transferring AAL5 frame traffic. This attribute 
      is not applicable for Vpts.
      
      Packet-wise functions increase the 'goodput' of the link. The 
      transmit packet-wise functions are Early Packet Discard (EPD) and 
      Partial Packet Discard (PPD). 
      
      EPD allows the connection to discard an entire frame once the 
      transmit queue has reached the EPD threshold. EPD increases the 
      'goodput' of a link, since discarding an entire frame means that 
      some queue capacity is guarded for some other frame which is 
      already partially transmitted. All cells of the frame are discarded 
      from the Beginning of Message (BOM) cell up to and including the 
      End of Message (EOM) cell. 
      
      PPD allows the connection to discard the remainder of a cell-
      forwarded AAL5 frame if one cell of this frame has been discarded. 
      All cells are discarded up to but not including the EOM cell. The 
      PPD function increases the 'goodput' of the link, since cells which 
      are only going to be discarded at the AAL5 reassembly point are 
      not transmitted.
      
      On CQC-based ATM cards, the packet-wise discard functions are 
      PPD and EPD. PPD is available at VCC cell-transfer points. PPD is 
      not applicable at frame-cell conversion points, and is not applicable 
      for Vpcs. PPD is configured by this attribute. Packet-wise discard 
      should only be enabled for connections carrying AAL5 
      segmentation traffic. Setting the value to enabled for any other 
      traffic type may result in all traffic being discarded. On CQC-based 
      ATM FPs, EPD is automatically enabled at frame-to-cell conversion 
      points, independent of the setting of this attribute. 
      
      On CQC-based ATM cards, at a permanent VCC connection 
      endpoint, this attribute is not applicable and is ignored. If AAL5 
      segmentation and reassembly has been requested, PPD and Early 
      Packet Discard (EPD) are automatically enabled.
      
      On ATM IP cards, packet-wise discard functions include EPD and 
      PPD. PPD and EPD apply to individual VCCs and VCCs within 
      VPCs at all connection points, including tandem VPC connections. 
      Both PPD and EPD are controlled by this attribute. This attribute 
      may safely be set to enabled for any connection (Vcc or Vpc) on 
      ATM IP FPs since they have the ability to automatically detect 
      AAL5-segmented traffic on a connection, and only enable packet-
      wise discards if AAL5-segmented traffic is detected.
      
      When this attribute is set to enabled, packet-wise discard functions 
      are applied to transmit traffic at this connection point. When this 
      attribute is set to disabled, packet-wise discard functions are not 
      applied to transmit traffic at this connection point.
      
      At a SPVC origin on a PNNI interface, a value of enabled specifies 
      that frame discard is requested in the backward direction. When this 
      attribute is set to disabled, backward frame discard is not requested 
      in the SPVC call setup. 
      
      The transmit packet-wise discard functions that are active are 
      visible in the Vcc/Vpc Tm txPacketWiseDiscard operational 
      attribute."
   DEFVAL     { disabled }
::= { mscAtmIfVptVccVcdTmProvEntry 76 }

mscAtmIfVptVccVcdTmRxPacketWiseDiscard OBJECT-TYPE
   SYNTAX     INTEGER  {
                 disabled(0),
                 enabled(1) }
   ACCESS     read-write
   STATUS     mandatory
   DESCRIPTION
     "This attribute specifies whether packet-wise discard functions are to 
      be enabled or disabled in the receive data direction for this 
      connection. Packet-wise discard functions should only be requested 
      if this connection is transferring AAL5 frame traffic. This attribute 
      is not applicable for Vpts.
      
      Packet-wise functions increase the 'goodput' of the link. The 
      receive packet-wise function is Partial Packet Discard (PPD). 
      
      PPD allows the connection to discard the remainder of a cell-
      forwarded AAL5 frame if one cell of this frame has been discarded, 
      for example due to UPC. All cells are discarded up to but not 
      including the EOM cell. The PPD function increases the 'goodput' 
      of the link, since cells which are only going to be discarded at the 
      AAL5 reassembly point are not transmitted.
      
      PPD is available at all VCC connection points where UPC may be 
      activated. PPD is not applicable for Vpcs. 
      
      On CQC-based ATM FPs, packet-wise discards should only be 
      enabled for connections carrying AAL5 segmentation traffic. 
      Setting the value to enabled for any other traffic type may result in 
      traffic being discarded. 
      
      On CQC-based ATM cards, at a permanent VCC connection 
      endpoint, this attribute is not applicable and is ignored. If AAL5 
      segmentation and reassembly has been requested, PPD and Early 
      Packet Discard (EPD) are automatically enabled.
      
      On ATM IP cards, this attribute may safely be set to enabled for any 
      connection (Vcc or Vpc) since they have the ability to automatically 
      detect AAL5-segmented traffic on a connection, and only enables 
      packet-wise discards if AAL5-segmented traffic is detected.
      
      When this attribute is set to enabled, packet-wise discard functions 
      are applied to receive traffic at this connection point. When this 
      attribute is set to disabled, packet-wise discard functions are not 
      applied to receive traffic at this connection point.
      
      At a SPVC origin on a PNNI interface, a value of enabled specifies 
      that frame discard is requested in the forward direction. When this 
      attribute is set to disabled, forward frame discard is not requested in 
      the SPVC call setup. 
      
      The receive packet-wise discard functions that are active are visible 
      in the Vcc/Vpc Tm rxPacketWiseDiscard operational attribute."
   DEFVAL     { disabled }
::= { mscAtmIfVptVccVcdTmProvEntry 78 }

mscAtmIfVptVccVcdTmAbrConnectionType OBJECT-TYPE
   SYNTAX     INTEGER  {
                 abrSwitch(0),
                 virtualSourceDest(3),
                 sourceDest(4),
                 nonAbrInterworking(5),
                 sameAsCa(14) }
   ACCESS     read-write
   STATUS     mandatory
   DESCRIPTION
     "This attribute specifies the type of ABR behavior which is to be 
      enforced at this connection. This attribute is only applicable if the 
      atmServiceCategory attribute is availableBitRate. If the 
      atmServicecategory attribute is not availableBitRate, this attribute 
      value is ignored.
      
      The actual ABR functionality which is in effect is visible in the 
      Vcc/Vpc/Vpt Tm abrConnectionType operational attribute.
      
      For CQC-based ATM cards, the only allowable values are 
      sameAsCa, nonAbrInterworking or abrSwitch. If abrSwitch is 
      selected, the CQC implements EFCI marking behavior.
      
      For the 1pOC12SmLrAtm card, the only allowable values are 
      sameAsCa or abrSwitch. If abrSwitch is selected, EFCI marking 
      behavior is implemented.
      
      sameAsCa is used to request the default behavior as specified in the 
      CA Abr component for this Vcc. Otherwise, this attribute overrides 
      the default behavior. 
      
      virtualSourceDest is used to request that this connection point 
      function as a virtual source/virtual destination. VS/VD functionality 
      is only supported on ATM IP FPs.
      
      sourceDest requires that this connection point function as a S/D for 
      RM cells. S/D mode is automatically invoked at this connection 
      point either if this is a connection end point, or if the next hop 
      connection point is configured as nonAbrInterworking.
      
      nonAbrInterworking is used to request that this connection point 
      function as an interworking between ABR and non-ABR service 
      categories. This means that there are no RM cells on the link side of 
      this connection, and that the next hop connection point is 
      performing as an ABR sourceDest.
      
      abrSwitch is used to request ABR switch behavior for this 
      connection point. The ABR switch behavior is first, to confirm to 
      virtualSourceDest or nonAbrInterworking setting on the next hop, 
      and otherwise to implement ABR ER switch behavior. For CQC-
      based FPs, ABR switch behavior is implemented as EFCI marking."
   DEFVAL     { sameAsCa }
::= { mscAtmIfVptVccVcdTmProvEntry 90 }

mscAtmIfVptVccVcdTmTxTdpTable OBJECT-TYPE
   SYNTAX     SEQUENCE OF MscAtmIfVptVccVcdTmTxTdpEntry
   ACCESS     not-accessible
   STATUS     mandatory
   DESCRIPTION
     "This attribute is a vector of five traffic parameters whose meanings 
      are defined by the txTrafficDescType attribute. 
      
      The values of peak cell rate (PCR), sustained cell rate (SCR), 
      Minimum Cell Rate (MCR) and requested shaping rate are 
      expressed in cell/s. Maximum burst size (MBS) is expressed in 
      cells. CDVT is expressed in microseconds. The values of PCR, 
      SCR, MCR, MBS and CDVT are used for connection admission 
      control (CAC). The value of CDVT is only used for connections 
      where the atmServiceCategory is constantBitRate. For all other 
      values of atmServiceCategory, CDVT is ignored. The values of 
      PCR, SCR, MCR and requested shaping rate are used to determine 
      the actual shaping rate where traffic shaping is enabled.
      
      When txTrafficDescType is 1 or 2, all of the parameters must be set 
      to zero.
      
      When txTrafficDescType is 3, parameter 1 represents the PCR for 
      CLP equal to 0 and 1 traffic; parameter 4 represents the CDVT; and 
      parameter 5 represents the requested shaping rate. A non-zero value 
      in parameter 5 overrides any value in parameter 1. This result is 
      used as the PCR. Parameter 1 must be non-zero. Parameters 2 and 3 
      must be zero.
      
      When txTrafficDescType is 4, parameter 1 represents the PCR for 
      CLP equal to 0 and 1 traffic with cell discard; parameter 2 
      represents the PCR for CLP equal to 0 traffic; parameter 4 
      represents the CDVT; and parameter 5 represents the requested 
      shaping rate. A non-zero value in parameter 5 overrides any value in 
      parameter 1. This result is used as the PCR. Parameter 1 must be 
      greater than or equal to parameter 2. Parameters 1 and 2 must be 
      non-zero. Parameter 3 must be zero.
      
      When txTrafficDescType is 5, parameter 1 represents the PCR for 
      CLP equal to 0 and 1 traffic with cell tagging; parameter 2 
      represents the PCR for CLP equal to 0 traffic; parameter 4 
      represents the CDVT; and parameter 5 represents the requested 
      shaping rate. A non-zero value in parameter 5 overrides any value in 
      parameter 1. This result is used as the PCR. Parameter 1 must be 
      greater than or equal to parameter 2. Parameters 1 and 2 must be 
      non-zero. Parameter 3 must be zero.
      
      When txTrafficDescType is 6, parameter 1 represents the PCR for 
      CLP equal to 0 and 1 traffic; parameter 2 represents the SCR for 
      CLP equal to 0 and 1 traffic; parameter 3 represents the MBS for 
      CLP equal to 0 and 1 traffic; parameter 4 represents the CDVT; and 
      parameter 5 represents the requested shaping rate. A non-zero value 
      in parameter 5 overrides any value in parameter 1. This result is 
      used as the PCR. Parameters 1, 2 and 3 must be non-zero. 
      Parameter 1 must be greater than or equal to parameter 2. Parameter 
      5, must either be zero (unused) or greater than or equal to parameter 
      2.
      
      When txTrafficDescType is 7, parameter 1 represents the PCR for 
      CLP equal to 0 and 1 traffic; parameter 2 represents the SCR for 
      CLP equal to 0 with cell discard; parameter 3 represents the MBS 
      for CLP equal to 0 traffic; parameter 4 represents the CDVT; and 
      parameter 5 represents the requested shaping rate. A non-zero value 
      in parameter 5 overrides any value in parameter 1. This result is 
      used as the PCR. Parameters 1, 2 and 3 must be non-zero. 
      Parameter 1 must be greater than or equal to parameter 2. Parameter 
      5, must either be zero (unused) or greater than or equal to parameter 
      2.
      
      When txTrafficDescType is 8, parameter 1 represents the PCR for 
      CLP equal to 0 and 1 traffic; parameter 2 represents the SCR for 
      CLP equal to 0 traffic with cell tagging; parameter 3 represents the 
      MBS for CLP equal to 0 traffic; parameter 4 represents the CDVT; 
      and parameter 5 represents the requested shaping rate. A non-zero 
      value in parameter 5 overrides any value in parameter 1. This result 
      is used as the PCR. Parameters 1, 2 and 3 must be non-zero. 
      Parameter 1 must be greater than or equal to parameter 2. Parameter 
      5, must either be zero (unused) or greater than or equal to parameter 
      2.
      
      When txTrafficDescType is 9, parameter 1 represents the PCR; 
      parameter 2 represents the CDVT; parameter 3 represents the MCR; 
      parameter 4 and parameter 5 represent are not used and must be 
      zero. Parameter 1 must be non-zero and must be greater than or 
      equal to parameter 3. Parameter 3 may be optionally zero.
      
      Whenever it is valid for PCR to be specified, parameter 5 may also 
      be used to specify a requested shaping rate. A non-zero value in 
      parameter 5 overrides the value in parameter 1 and is used as the 
      peak cell rate in calculations of CAC and shaping rate. When the 
      atmServiceCategory is availableBitRate (ABR), the shaping rate is 
      dynamically chosen, based on the ABR flow control mechanism, as 
      a value between the MCR and the PCR or the requested shaping 
      rate if applicable.
      
      For txTrafficDescType 3, 4 and 5, the transmit traffic is shaped at 
      the next available shaping rate less than the PCR. 
      
      For txTrafficDescType 6, 7 and 8 if linear traffic shaping is selected, 
      the transmit traffic is shaped at the highest available rate which is 
      between PCR and SCR. However, if there is no available shaping 
      rate between PCR and SCR, traffic is shaped at the next rate above 
      the PCR. 
      
      For txTrafficDescType 6, 7 and 8 if inverse-UPC traffic shaping is 
      selected, the transmit traffic is shaped at a variable rate which 
      conforms to the PCR, SCR and MBS of the connection traffic 
      descriptor. Inverse-UPC traffic shaping is available only on ATM IP 
      cards."
::= { mscAtmIfVptVccVcdTm 456 }

mscAtmIfVptVccVcdTmTxTdpEntry OBJECT-TYPE
   SYNTAX     MscAtmIfVptVccVcdTmTxTdpEntry
   ACCESS     not-accessible
   STATUS     mandatory
   DESCRIPTION
     "An entry in the mscAtmIfVptVccVcdTmTxTdpTable."
   INDEX {
      mscAtmIfIndex,
      mscAtmIfVptIndex,
      mscAtmIfVptVccIndex,
      mscAtmIfVptVccVcdIndex,
      mscAtmIfVptVccVcdTmIndex,
      mscAtmIfVptVccVcdTmTxTdpIndex }
::= { mscAtmIfVptVccVcdTmTxTdpTable 1 }

MscAtmIfVptVccVcdTmTxTdpEntry ::= SEQUENCE {
   mscAtmIfVptVccVcdTmTxTdpIndex
      Integer32,
   mscAtmIfVptVccVcdTmTxTdpValue
      Unsigned32 }

mscAtmIfVptVccVcdTmTxTdpIndex OBJECT-TYPE
   SYNTAX     Integer32 (1..5)
   ACCESS     not-accessible
   STATUS     mandatory
   DESCRIPTION
     "This variable represents the mscAtmIfVptVccVcdTmTxTdpTable
      specific index for the mscAtmIfVptVccVcdTmTxTdpTable."
::= { mscAtmIfVptVccVcdTmTxTdpEntry 1 }

mscAtmIfVptVccVcdTmTxTdpValue OBJECT-TYPE
   SYNTAX     Unsigned32 (0..2147483647)
   ACCESS     read-write
   STATUS     mandatory
   DESCRIPTION
     "This variable represents an individual value for the
      mscAtmIfVptVccVcdTmTxTdpTable."
::= { mscAtmIfVptVccVcdTmTxTdpEntry 2 }

mscAtmIfVptVccVcdTmRxTdpTable OBJECT-TYPE
   SYNTAX     SEQUENCE OF MscAtmIfVptVccVcdTmRxTdpEntry
   ACCESS     not-accessible
   STATUS     mandatory
   DESCRIPTION
     "This attribute is a vector of four traffic parameters whose meanings 
      are defined by the rxTrafficDescType attribute. The values of peak 
      cell rate (PCR), sustained cell rate (SCR) and Minimum Cell Rate 
      (MCR) are expressed in cell/s. Maximum burst size (MBS) is 
      expressed in cells. The value of CDVT is expressed in 
      microseconds. The values of PCR, SCR, MCR, MBS and CDVT 
      are used for usage parameter control (UPC).
      
      When rxTrafficDescType is 1 or 2, all of the parameters must be set 
      to zero (unused).
      
      When rxTrafficDescType is 3, parameter 1 represents the PCR for 
      CLP equal to 0 and 1 traffic. Parameter 1 must be non-zero. 
      Parameters 2 and 3 must be set to zero (unused).
      
      When rxTrafficDescType is 4, parameter 1 represents the PCR 
      for CLP equal to 0 and 1 traffic; parameter 2 represents the PCR for 
      CLP equal to 0 traffic with cell discard. Parameters 1 and 2 must be 
      non-zero. Parameter 3 must be set to zero (unused). Parameter 1 
      must be greater than or equal to parameter 2.
      
      When rxTrafficDescType is 5, parameter 1 represents the PCR for 
      CLP equal to 0 and 1 traffic; parameter 2 represents the PCR for 
      CLP equal to 0 traffic with cell tagging. Parameters 1 and 2 must be 
      non-zero. Parameter 3 must be set to zero (unused). Parameter 1 
      must be greater than or equal to parameter 2.
      
      When rxTrafficDescType is a 6, parameter 1 represents the PCR for 
      CLP equal to 0 and 1 traffic; parameter 2 represents the SCR for 
      CLP equal to 0 and 1 traffic; parameter 3 represents the MBS for 
      CLP equal to 0 and 1 traffic. Parameters 1, 2 and 3 must be non-
      zero. Parameter 1 must be greater than or equal to Parameter 2. 
      
      When rxTrafficDescType is 7, parameter 1 represents the PCR for 
      CLP equal to 0 and 1 traffic; parameter 2 represents the SCR for 
      CLP equal to 0 traffic with cell discard; parameter 3 represents the 
      MBS for CLP equal to 0 traffic. Parameters 1, 2 and 3 must be non-
      zero. Parameter 1 must be greater than or equal to parameter 2. 
      
      When rxTrafficDescType is 8, parameter 1 represents the PCR for 
      CLP equal to 0 and 1 traffic; parameter 2 represents the SCR for 
      CLP equal to 0 traffic with cell tagging; parameter 3 represents the 
      MBS for CLP equal to 0 traffic. Parameter 1, 2 and 3 must be non-
      zero. Parameter 1 must be greater than or equal to parameter 2.
      
      When rxTrafficDescType is 9, parameter 1 represents the PCR; 
      parameter 2 represents the CDVT; parameter 3 represents the MCR. 
      Parameter 4 is not used and must be zero. Parameter 1,must be non-
      zero and must be greater than or equal to parameter 3. Parameter 3 
      may optionally be zero.
      
      When rxTrafficDescType is any value from 3 through 8, parameter 
      4 represents the CDVT. 
      
      If the value of CDVT either in parameter 2 or in parameter 4 is zero, 
      the CDVT is taken from the CA defaults for the particular 
      atmServiceCategory of this connection.
      
      On a CQC-based ATM card, when rxTrafficDescriptorType is 3 
      through 8, there are certain extreme combinations of 
      rxTrafficDescParm which are outside the capabilities of the UPC 
      hardware. The check prov command detects such cases and 
      generates an error message. If this happens, adjust the parameters 
      until they fall within the supported limits. 
      
      To calculate the limits, use the following formulae:
      I1 = 1 000 000 000 / PCR
      L1 = CDVT * 1000
      I2 = 1,000,000,000 / SCR
      L2 = CDVT + (MBS - 1) * (I2 - I1)
      I1 and I2 must be less than or equal to 335,523,840. I1 + L1 must 
      be less than or equal to 1,342,156,800. I2 + L2 must be less than or 
      equal to 1,342,156,800. Note that I2 and L2 only apply when the 
      rxTrafficDescriptorType is 6 through 8.
      
      If the values of I1, L1, I2 or L2 are closer to the limits described 
      above, a further restriction applies. Specifically, if either:
      I1 > 41,940,480 or
      I2 > 41,940,480 or
      I1 + L1 > 167,769,600 or
      I2 + L2 > 167,769,600
      then both I1 and I2 must be greater than 20,480. 
      
      Parameter 5 of the rxTrafficDescParm is always unused. 
      
      If the rxTrafficDescType is sameAsTx, the values provisioned in 
      this attribute are ignored. The traffic parameters for the receive 
      direction are taken from the txTrafficDescParm."
::= { mscAtmIfVptVccVcdTm 457 }

mscAtmIfVptVccVcdTmRxTdpEntry OBJECT-TYPE
   SYNTAX     MscAtmIfVptVccVcdTmRxTdpEntry
   ACCESS     not-accessible
   STATUS     mandatory
   DESCRIPTION
     "An entry in the mscAtmIfVptVccVcdTmRxTdpTable."
   INDEX {
      mscAtmIfIndex,
      mscAtmIfVptIndex,
      mscAtmIfVptVccIndex,
      mscAtmIfVptVccVcdIndex,
      mscAtmIfVptVccVcdTmIndex,
      mscAtmIfVptVccVcdTmRxTdpIndex }
::= { mscAtmIfVptVccVcdTmRxTdpTable 1 }

MscAtmIfVptVccVcdTmRxTdpEntry ::= SEQUENCE {
   mscAtmIfVptVccVcdTmRxTdpIndex
      Integer32,
   mscAtmIfVptVccVcdTmRxTdpValue
      Unsigned32 }

mscAtmIfVptVccVcdTmRxTdpIndex OBJECT-TYPE
   SYNTAX     Integer32 (1..5)
   ACCESS     not-accessible
   STATUS     mandatory
   DESCRIPTION
     "This variable represents the mscAtmIfVptVccVcdTmRxTdpTable
      specific index for the mscAtmIfVptVccVcdTmRxTdpTable."
::= { mscAtmIfVptVccVcdTmRxTdpEntry 1 }

mscAtmIfVptVccVcdTmRxTdpValue OBJECT-TYPE
   SYNTAX     Unsigned32 (0..2147483647)
   ACCESS     read-write
   STATUS     mandatory
   DESCRIPTION
     "This variable represents an individual value for the
      mscAtmIfVptVccVcdTmRxTdpTable."
::= { mscAtmIfVptVccVcdTmRxTdpEntry 2 }

mscAtmIfVptVccVcdTmFqpTable OBJECT-TYPE
   SYNTAX     SEQUENCE OF MscAtmIfVptVccVcdTmFqpEntry
   ACCESS     not-accessible
   STATUS     mandatory
   DESCRIPTION
     "This attribute is a vector of three elements that specify the quality of 
      service parameters for the forward direction for this connection. 
      This attribute is used for SPVC connections.
      
      The cdv element specifies the acceptable peak-to-peak Cell Delay 
      Variation (CDV) of real-time connections (CBR and rt-VBR). It is 
      signalled through the extended QoS information element.
      
      The ctd specifies the acceptable maximum Cell Transfer Delay 
      (maxCtd) of real-time connections (CBR and rt-VBR). 
      It is signalled through the end to end transit delay information 
      element.
      
      The clr specifies the acceptable Cell Loss Ratio (CLR) of CBR, rt-
      VBR, and nrt-VBR connections. It is signalled through the extended 
      QoS information element."
::= { mscAtmIfVptVccVcdTm 458 }

mscAtmIfVptVccVcdTmFqpEntry OBJECT-TYPE
   SYNTAX     MscAtmIfVptVccVcdTmFqpEntry
   ACCESS     not-accessible
   STATUS     mandatory
   DESCRIPTION
     "An entry in the mscAtmIfVptVccVcdTmFqpTable."
   INDEX {
      mscAtmIfIndex,
      mscAtmIfVptIndex,
      mscAtmIfVptVccIndex,
      mscAtmIfVptVccVcdIndex,
      mscAtmIfVptVccVcdTmIndex,
      mscAtmIfVptVccVcdTmFqpIndex }
::= { mscAtmIfVptVccVcdTmFqpTable 1 }

MscAtmIfVptVccVcdTmFqpEntry ::= SEQUENCE {
   mscAtmIfVptVccVcdTmFqpIndex
      INTEGER,
   mscAtmIfVptVccVcdTmFqpValue
      Unsigned32 }

mscAtmIfVptVccVcdTmFqpIndex OBJECT-TYPE
   SYNTAX     INTEGER  {
                 cdv(0),
                 ctd(1),
                 clr(2) }
   ACCESS     not-accessible
   STATUS     mandatory
   DESCRIPTION
     "This variable represents the mscAtmIfVptVccVcdTmFqpTable
      specific index for the mscAtmIfVptVccVcdTmFqpTable."
::= { mscAtmIfVptVccVcdTmFqpEntry 1 }

mscAtmIfVptVccVcdTmFqpValue OBJECT-TYPE
   SYNTAX     Unsigned32 (0..2147483647)
   ACCESS     read-write
   STATUS     mandatory
   DESCRIPTION
     "This variable represents an individual value for the
      mscAtmIfVptVccVcdTmFqpTable."
::= { mscAtmIfVptVccVcdTmFqpEntry 2 }

mscAtmIfVptVccVcdTmBqpTable OBJECT-TYPE
   SYNTAX     SEQUENCE OF MscAtmIfVptVccVcdTmBqpEntry
   ACCESS     not-accessible
   STATUS     mandatory
   DESCRIPTION
     "This attribute is a vector of three elements that specify the quality of 
      service parameters for the backward direction for this connection. 
      This attribute is used for SPVC connections.
      
      The cdv element specifies the acceptable peak-to-peak Cell Delay 
      Variation (CDV) of real-time connections (CBR and rt-VBR).
      It is signalled through the extended QoS information element.
      
      The ctd specifies the acceptable maximum Cell Transfer Delay 
      (maxCtd) of real-time connections (CBR and rt-VBR). It is 
      signalled through the end to end transit delay information element.
      
      The clr specifies the acceptable Cell Loss Ratio (CLR) of CBR, rt-
      VBR, and nrt-VBR connections. It is signalled through the extended 
      QoS information element."
::= { mscAtmIfVptVccVcdTm 459 }

mscAtmIfVptVccVcdTmBqpEntry OBJECT-TYPE
   SYNTAX     MscAtmIfVptVccVcdTmBqpEntry
   ACCESS     not-accessible
   STATUS     mandatory
   DESCRIPTION
     "An entry in the mscAtmIfVptVccVcdTmBqpTable."
   INDEX {
      mscAtmIfIndex,
      mscAtmIfVptIndex,
      mscAtmIfVptVccIndex,
      mscAtmIfVptVccVcdIndex,
      mscAtmIfVptVccVcdTmIndex,
      mscAtmIfVptVccVcdTmBqpIndex }
::= { mscAtmIfVptVccVcdTmBqpTable 1 }

MscAtmIfVptVccVcdTmBqpEntry ::= SEQUENCE {
   mscAtmIfVptVccVcdTmBqpIndex
      INTEGER,
   mscAtmIfVptVccVcdTmBqpValue
      Unsigned32 }

mscAtmIfVptVccVcdTmBqpIndex OBJECT-TYPE
   SYNTAX     INTEGER  {
                 cdv(0),
                 ctd(1),
                 clr(2) }
   ACCESS     not-accessible
   STATUS     mandatory
   DESCRIPTION
     "This variable represents the mscAtmIfVptVccVcdTmBqpTable
      specific index for the mscAtmIfVptVccVcdTmBqpTable."
::= { mscAtmIfVptVccVcdTmBqpEntry 1 }

mscAtmIfVptVccVcdTmBqpValue OBJECT-TYPE
   SYNTAX     Unsigned32 (0..2147483647)
   ACCESS     read-write
   STATUS     mandatory
   DESCRIPTION
     "This variable represents an individual value for the
      mscAtmIfVptVccVcdTmBqpTable."
::= { mscAtmIfVptVccVcdTmBqpEntry 2 }


-- AtmIf/n Vcc/vpi.vci Vcd Tm AvailableBitRate, 
-- AtmIf/n Vpc/vci Vpd Tm AvailableBitRate,
-- AtmIf/n Vpt/vpi Vpd Tm AvailableBitRate,
-- AtmIf/n Vpt/vpi Vcc/vci Vcd Tm AvailableBitRate
-- This component contains provisioned ABR-related attributes of a 
-- connection. It is an optional subcomponent of the Vcd Tm and Vpd 
-- Tm component. It is used to override DGCRA-related defaults in 
-- the CA Abr component. It contains the specific configuration for the 
-- ABR connection at this connection point. If this is the source of an 
-- SPVC connection, this component also contains the ABR 
-- parameters required for the SPVC call request.

mscAtmIfVptVccVcdTmAbr OBJECT IDENTIFIER ::= { mscAtmIfVptVccVcdTm 2 }



mscAtmIfVptVccVcdTmAbrRowStatusTable OBJECT-TYPE
   SYNTAX     SEQUENCE OF MscAtmIfVptVccVcdTmAbrRowStatusEntry
   ACCESS     not-accessible
   STATUS     mandatory
   DESCRIPTION
     "This entry controls the addition and deletion of 
      mscAtmIfVptVccVcdTmAbr components."
::= { mscAtmIfVptVccVcdTmAbr 1 }

mscAtmIfVptVccVcdTmAbrRowStatusEntry OBJECT-TYPE
   SYNTAX     MscAtmIfVptVccVcdTmAbrRowStatusEntry
   ACCESS     not-accessible
   STATUS     mandatory
   DESCRIPTION
     "A single entry in the table represents a single 
      mscAtmIfVptVccVcdTmAbr component."
   INDEX {
      mscAtmIfIndex,
      mscAtmIfVptIndex,
      mscAtmIfVptVccIndex,
      mscAtmIfVptVccVcdIndex,
      mscAtmIfVptVccVcdTmIndex,
      mscAtmIfVptVccVcdTmAbrIndex }
::= { mscAtmIfVptVccVcdTmAbrRowStatusTable 1 }

MscAtmIfVptVccVcdTmAbrRowStatusEntry ::= SEQUENCE {
   mscAtmIfVptVccVcdTmAbrRowStatus
      RowStatus,
   mscAtmIfVptVccVcdTmAbrComponentName
      DisplayString,
   mscAtmIfVptVccVcdTmAbrStorageType
      StorageType,
   mscAtmIfVptVccVcdTmAbrIndex
      NonReplicated }

mscAtmIfVptVccVcdTmAbrRowStatus OBJECT-TYPE
   SYNTAX     RowStatus 
   ACCESS     read-write
   STATUS     mandatory
   DESCRIPTION
     "This variable is used as the basis for SNMP naming of
      mscAtmIfVptVccVcdTmAbr components.
      These components can be added and deleted."
::= { mscAtmIfVptVccVcdTmAbrRowStatusEntry 1 }

mscAtmIfVptVccVcdTmAbrComponentName OBJECT-TYPE
   SYNTAX     DisplayString 
   ACCESS     read-only
   STATUS     mandatory
   DESCRIPTION
     "This variable provides the component's string name for
      use with the ASCII Console Interface"
::= { mscAtmIfVptVccVcdTmAbrRowStatusEntry 2 }

mscAtmIfVptVccVcdTmAbrStorageType OBJECT-TYPE
   SYNTAX     StorageType 
   ACCESS     read-only
   STATUS     mandatory
   DESCRIPTION
     "This variable represents the storage type value for the
      mscAtmIfVptVccVcdTmAbr tables."
::= { mscAtmIfVptVccVcdTmAbrRowStatusEntry 4 }

mscAtmIfVptVccVcdTmAbrIndex OBJECT-TYPE
   SYNTAX     NonReplicated 
   ACCESS     not-accessible
   STATUS     mandatory
   DESCRIPTION
     "This variable represents the index for the mscAtmIfVptVccVcdTmAbr tables."
::= { mscAtmIfVptVccVcdTmAbrRowStatusEntry 10 }

mscAtmIfVptVccVcdTmAbrProvTable OBJECT-TYPE
   SYNTAX     SEQUENCE OF MscAtmIfVptVccVcdTmAbrProvEntry
   ACCESS     not-accessible
   STATUS     mandatory
   DESCRIPTION
     "This group contains provisioned attributes for the ABR ATM 
      connections configured on an ATM interface."
::= { mscAtmIfVptVccVcdTmAbr 110 }

mscAtmIfVptVccVcdTmAbrProvEntry OBJECT-TYPE
   SYNTAX     MscAtmIfVptVccVcdTmAbrProvEntry
   ACCESS     not-accessible
   STATUS     mandatory
   DESCRIPTION
     "An entry in the mscAtmIfVptVccVcdTmAbrProvTable."
   INDEX {
      mscAtmIfIndex,
      mscAtmIfVptIndex,
      mscAtmIfVptVccIndex,
      mscAtmIfVptVccVcdIndex,
      mscAtmIfVptVccVcdTmIndex,
      mscAtmIfVptVccVcdTmAbrIndex }
::= { mscAtmIfVptVccVcdTmAbrProvTable 1 }

MscAtmIfVptVccVcdTmAbrProvEntry ::= SEQUENCE {
   mscAtmIfVptVccVcdTmAbrInitialCellRate
      Unsigned32,
   mscAtmIfVptVccVcdTmAbrTransientBufferExposure
      Unsigned32,
   mscAtmIfVptVccVcdTmAbrFixedRoundTripTime
      Unsigned32,
   mscAtmIfVptVccVcdTmAbrRateDecreaseFactor
      Unsigned32,
   mscAtmIfVptVccVcdTmAbrRateIncreaseFactor
      Unsigned32,
   mscAtmIfVptVccVcdTmAbrMaxCellPerRmCell
      Unsigned32,
   mscAtmIfVptVccVcdTmAbrMaxTimeBetweenRmCells
      Unsigned32,
   mscAtmIfVptVccVcdTmAbrCutoffDecreaseFactor
      Unsigned32,
   mscAtmIfVptVccVcdTmAbrAcrDecreaseTimeFactor
      Unsigned32,
   mscAtmIfVptVccVcdTmAbrDgcraMaximumDelay
      Unsigned32,
   mscAtmIfVptVccVcdTmAbrDgcraMinimumDelay
      Unsigned32,
   mscAtmIfVptVccVcdTmAbrFarEndAcrDecreaseTimeFactor
      Unsigned32,
   mscAtmIfVptVccVcdTmAbrFarEndInitialCellRate
      Unsigned32 }

mscAtmIfVptVccVcdTmAbrInitialCellRate OBJECT-TYPE
   SYNTAX     Unsigned32 (0..16777215 | 16777216 | 16777217 | 16777218)
   ACCESS     read-write
   STATUS     mandatory
   DESCRIPTION
     "This attribute specifies the Initial Cell Rate (ICR) parameter for this 
      connection. ICR is the rate at which a source should send initially 
      and after an idle period.
      
      When this attribute is set to sameAsCa, the initial cell rate is 
      determined by the AtmIf CA Abr/0 icr attribute. When the value of 
      this attribute is set to useMcr, ICR is set to the same value as the 
      Minimum Cell Rate (MCR) for the connection.
      
      When the value of this attribute is set to usePcr, ICR is set to the 
      same value as the Peak Cell Rate (PCR) for the connection.
      
      If this attribute is specified less than the MCR of the connection, 
      then the MCR is used as the ICR. If this attribute is specified more 
      than PCR of the connection, then PCR is used as the ICR.
      
      This attribute is ignored under all conditions where the operational 
      attribute abrConnectionType indicates erSwitch or efciSwitch.

      VALUES (

      16777216 = sameAsCa

      16777217 = useMcr

      16777218 = usePcr

      )"
   DEFVAL     { 16777216 }
::= { mscAtmIfVptVccVcdTmAbrProvEntry 10 }

mscAtmIfVptVccVcdTmAbrTransientBufferExposure OBJECT-TYPE
   SYNTAX     Unsigned32 (0..16777215)
   ACCESS     read-write
   STATUS     mandatory
   DESCRIPTION
     "This attribute specifies the Transient Buffer Exposure (TBE) for this 
      connection. TBE is the negotiated number of cells that the network 
      would like to limit the source to send during start-up periods, before 
      the first Resource Management (RM) cell returns.
      
      TBE divided by fixedRoundTripTime determines an upper bound 
      for the operational value of initialCellRate, the rate at which a 
      source should send initially and after an idle period.
      
      TBE divided by maxCellsPerRmCell specifies the operational value 
      of forwardRmCellLimit, the limit of the number of forward 
      Resource Management (RM) cells which may be sent in the 
      absence of received backward RM cells.
      
      This attribute is ignored under all conditions where the operational 
      attribute abrConnectionType is set to erSwitch."
   DEFVAL     { 16777215 }
::= { mscAtmIfVptVccVcdTmAbrProvEntry 11 }

mscAtmIfVptVccVcdTmAbrFixedRoundTripTime OBJECT-TYPE
   SYNTAX     Unsigned32 (0..16700000)
   ACCESS     read-write
   STATUS     mandatory
   DESCRIPTION
     "This attribute specifies the Fixed Round-Trip Time (FRTT) 
      parameter for this connection. FRTT is the sum of the fixed and 
      propagation delays from the source to a destination and back.
      
      The value of transientBufferExposure divided by the value of FRTT 
      (in seconds) determines an upper bound for the operational value of 
      initialCellRate, the rate at which a source should send initially and 
      after an idle period.
      
      This attribute is ignored under all conditions where the operational 
      attribute abrConnectionType indicates erSwitch or efciSwitch."
   DEFVAL     { 5000000 }
::= { mscAtmIfVptVccVcdTmAbrProvEntry 12 }

mscAtmIfVptVccVcdTmAbrRateDecreaseFactor OBJECT-TYPE
   SYNTAX     Unsigned32 (0..15 | 16777216)
   ACCESS     read-write
   STATUS     mandatory
   DESCRIPTION
     "This attribute specifies the Rate Decrease Factor (RDF) for this 
      connection. The RDF value is computed by using the provisioned 
      value of this attribute, n, as 2 to the inverse power n. For example, if 
      the value of this attribute is 8, RDF is 2E-8 = 1/256.
      
      RDF controls the amount by which the cell transmission rate may 
      decrease upon receipt of a backward Resource Management (RM) 
      cell. For example, if a backward RM cell is received with the 
      Congestion Indication (CI) field set to 1, the Allowed Cell Rate 
      (ACR) value would be reduced by the amount (RDF*ACR). The 
      ACR is not allowed to fall below the Minimum Cell Rate (MCR), in 
      which case the ACR is set to MCR.
      
      This attribute is ignored under all conditions where the operational 
      attribute abrConnectionType has the value erSwitch.

      VALUES (

      16777216 = sameAsCa

      )"
   DEFVAL     { 16777216 }
::= { mscAtmIfVptVccVcdTmAbrProvEntry 13 }

mscAtmIfVptVccVcdTmAbrRateIncreaseFactor OBJECT-TYPE
   SYNTAX     Unsigned32 (0..15 | 16777216)
   ACCESS     read-write
   STATUS     mandatory
   DESCRIPTION
     "This attribute specifies the Rate Increase Factor (RIF) for this 
      connection. The RIF value is computed by using the provisioned 
      value of this attribute, n, as 2 to the inverse power n. For example, if 
      the value of this attribute is 6, RIF is 2E-6 = 1/64.
      
      RIF controls the amount by which the cell transmission rate may 
      increase upon receipt of a backward Resource Management (RM) 
      cell. For example, if a backward RM cell is received with the 
      Congestion Indication (CI) and the No Increase (NI) fields both set 
      to 0, the Allowed Cell Rate (ACR) value would be increased by the 
      amount (RIF*ACR). The ACR is not allowed to exceed the Peak 
      Cell Rate (PCR), in which case the ACR is set to PCR.
      
      This attribute is ignored under all conditions where the operational 
      attribute abrConnectionType has the value erSwitch.

      VALUES (

      16777216 = sameAsCa

      )"
   DEFVAL     { 16777216 }
::= { mscAtmIfVptVccVcdTmAbrProvEntry 14 }

mscAtmIfVptVccVcdTmAbrMaxCellPerRmCell OBJECT-TYPE
   SYNTAX     Unsigned32 (2 | 4 | 8 | 16 | 32 | 64 | 128 | 256 | 16777216)
   ACCESS     read-write
   STATUS     mandatory
   DESCRIPTION
     "This attribute specifies the maximum number of cells an ABR 
      source may transmit for each forward Resource Management (RM) 
      cell. The count of the cells transmitted includes data cells, OAM 
      cells, backward RM cells, and the forward RM cell.
      
      A value of 2 is not recommended although it is permitted according 
      to the ATM Forum standard. When this attribute is set to a value of 
      2, it is possible that only one forward and one backward RM cell 
      are repeatedly transmitted, and all data traffic is queued up 
      indefinitely.
      
      This attribute is ignored under all conditions where the operational 
      attribute abrConnectionType has the value erSwitch.

      VALUES (

      16777216 = sameAsCa

      )"
   DEFVAL     { 16777216 }
::= { mscAtmIfVptVccVcdTmAbrProvEntry 15 }

mscAtmIfVptVccVcdTmAbrMaxTimeBetweenRmCells OBJECT-TYPE
   SYNTAX     Unsigned32 (781 | 1563 | 3125 | 6250 | 12500 | 25000 | 50000 | 100000 | 16777216)
   ACCESS     read-write
   STATUS     mandatory
   DESCRIPTION
     "This attribute specifies the TRM parameter for this connection.
      
      TRM provides an lower bound on the time interval between forward 
      Resource Management (RM) cells for an ABR source. Since the last 
      forward RM cell was sent, if at least TRM time has elapsed since 
      and at least two other cells have been sent, then the next cell to be 
      transmitted would be a forward RM cell.
      
      This attribute is ignored under all conditions where the operational 
      attribute abrConnectionType has the value erSwitch.
      
      The provisioned value of 781 is signalled as TRM = 0, in the ABR 
      Additional Parameters Information Element. 
      1563 is signalled as TRM = 1. 
      3125 is signalled as TRM = 2. 
      6250 is signalled as TRM = 3. 
      12500 is signalled as TRM = 4 
      25000 is signalled as TRM = 5. 
      50000 is signalled as TRM = 6. 
      100000 is signalled as TRM = 7.

      VALUES (

      16777216 = sameAsCa

      )"
   DEFVAL     { 16777216 }
::= { mscAtmIfVptVccVcdTmAbrProvEntry 16 }

mscAtmIfVptVccVcdTmAbrCutoffDecreaseFactor OBJECT-TYPE
   SYNTAX     Unsigned32 (0 | 1 | 2 | 4 | 8 | 16 | 32 | 64 | 16777216)
   ACCESS     read-write
   STATUS     mandatory
   DESCRIPTION
     "This attribute specifies the Cutoff Decrease Factor (CDF) parameter 
      for this connection. When the value of this attribute is non-zero, 
      CDF is computed as the inverse of the value. For example, if the 
      value is 32, the value of CDF is 1/32. When the value of this 
      attribute is 0, CDF is also zero.
      
      CDF controls the decrease in the Allowed Cell Rate (ACR) 
      associated with the CRM parameter, the limit of the number of 
      forward Resource Management (RM) cells which may be sent in 
      the absence of received backward RM cells. When this limit is 
      crossed, the ACR value would be decreased by the amount 
      (CDF*ACR). The ACR is not allowed to fall below the Minimum 
      Cell Rate (MCR), in which case the ACR is set to MCR.
      
      The value of CRM is indicated by the forwardRmCellLimit 
      attribute.
      
      This attribute is ignored under all conditions where the operational 
      attribute abrConnectionType indicates erSwitch or efciSwitch.

      VALUES (

      16777216 = sameAsCa

      )"
   DEFVAL     { 16777216 }
::= { mscAtmIfVptVccVcdTmAbrProvEntry 17 }

mscAtmIfVptVccVcdTmAbrAcrDecreaseTimeFactor OBJECT-TYPE
   SYNTAX     Unsigned32 (0..1023 | 16777216)
   ACCESS     read-write
   STATUS     mandatory
   DESCRIPTION
     "This attribute specifies the Allowed Cell Rate Decrease Time Factor 
      (ADTF) parameter for this connection.
      
      ADTF is the maximum time interval permitted between sending 
      forward Resource Management (RM) cells before the Allowed Cell 
      Rate (ACR) is decreased to initialCellRate. In other words, if the 
      source does not transit a forward RM cell for the period specified by 
      adtf, it reduces its ACR to the value of its initialCellRate.
      
      This attribute is ignored under all conditions where the operational 
      attribute abrConnectionType indicates erSwitch or efciSwitch.

      VALUES (

      16777216 = sameAsCa

      )"
   DEFVAL     { 16777216 }
::= { mscAtmIfVptVccVcdTmAbrProvEntry 18 }

mscAtmIfVptVccVcdTmAbrDgcraMaximumDelay OBJECT-TYPE
   SYNTAX     Unsigned32 (1..16700000 | 16777216)
   ACCESS     read-write
   STATUS     mandatory
   DESCRIPTION
     "This attribute specifies an upper bound on the delay after which the 
      rate change induced by a backward Resource Management (RM) 
      cell departing from this connection point (in the backward 
      direction) is expected to be observed at this connection point (in the 
      forward direction).
      
      This upper bound may be approximated as the sum of the round trip 
      fixed and propagation delays and the maximum queuing delays 
      between the ABR source and this interface.
      
      The value of this attribute is used in policing an ABR connection 
      using the Dynamic General Cell Rate Algorithm (DGCRA). A 
      larger value for this attribute implies a more lenient policer. When 
      there is a reduction in the Allowed Cell Rate (ACR), the policer 
      waits for a correspondingly longer period of time before it enforces 
      at the new cell rate.
      
      The value of this attribute must not be less than the 
      dgcraMinimumDelay attribute.

      VALUES (

      16777216 = sameAsCa

      )"
   DEFVAL     { 16777216 }
::= { mscAtmIfVptVccVcdTmAbrProvEntry 19 }

mscAtmIfVptVccVcdTmAbrDgcraMinimumDelay OBJECT-TYPE
   SYNTAX     Unsigned32 (1..16700000 | 16777216)
   ACCESS     read-write
   STATUS     mandatory
   DESCRIPTION
     "This attribute specifies a lower bound on the delay after which the 
      rate change induced by a backward Resource Management (RM) 
      cell departing from this connection point (in the backward 
      direction) is expected to be observed at this connection point (in the 
      forward connection).
      
      This lower bound may be approximated as the sum of the round trip 
      fixed and propagation delays between the ABR source and this 
      interface.
      
      The value of this attribute is used in policing an ABR connection 
      using the Dynamic General Cell Rate Algorithm (DGCRA). A 
      smaller value for this attribute implies a more lenient policer. When 
      there is a increase in the Allowed Cell Rate (ACR), the policer waits 
      for a correspondingly shorter period of time before it enforces at the 
      new cell rate.

      VALUES (

      16777216 = sameAsCa

      )"
   DEFVAL     { 16777216 }
::= { mscAtmIfVptVccVcdTmAbrProvEntry 20 }

mscAtmIfVptVccVcdTmAbrFarEndAcrDecreaseTimeFactor OBJECT-TYPE
   SYNTAX     Unsigned32 (0..1023)
   ACCESS     read-write
   STATUS     mandatory
   DESCRIPTION
     "This attribute specifies the Allowed Cell Rate Decrease Time Factor 
      (ADTF) of the far end ABR source. The value specified should be 
      the same as the ADTF parameter at the far end of this ABR 
      connection. 
      
      The value of this attribute is used in policing an ABR connection 
      using the Dynamic Generic Cell Rate Algorithm (DGCRA). A 
      larger value for this attribute implies a more lenient policer. When 
      the delay between two consecutive forward Resource Management 
      (RM) cells received at this interface corresponds to a value greater 
      than the value of this attribute, the policer begins to limit enforce 
      the incoming traffic at the initial cell rate (ICR) of the far end, as 
      specified by the farEndInitialCellRate attribute."
   DEFVAL     { 50 }
::= { mscAtmIfVptVccVcdTmAbrProvEntry 21 }

mscAtmIfVptVccVcdTmAbrFarEndInitialCellRate OBJECT-TYPE
   SYNTAX     Unsigned32 (0..16777215)
   ACCESS     read-write
   STATUS     mandatory
   DESCRIPTION
     "This attribute specifies the Initial Cell Rate (ICR) of the far end 
      ABR source. The value specified should be the same as the ICR 
      parameter at the far end of this ABR connection. 
      
      The value of this attribute is used in policing an ABR connection 
      using the Dynamic Generic Cell Rate Algorithm (DGCRA). A 
      larger value for this attribute implies a more lenient policer. When 
      the delay between two consecutive forward Resource Management 
      (RM) cells received at this interface corresponds to a value greater 
      than the farEndAcrDecreaseTimeFactor attribute, the policer begins 
      to enforce the incoming traffic at the value of this attribute.
      
      If this attribute is specified less than the MCR of the connection, 
      then the MCR is used as the feIcr. If this attribute is more than the 
      PCR of the connection, then PCR is used as the feIcr."
   DEFVAL     { 0 }
::= { mscAtmIfVptVccVcdTmAbrProvEntry 22 }


-- AtmIf/n Vcc/x.y Vcd PerformanceMonitoring
-- AtmIf/n Vpc/x Vpd PerformanceMonitoring
-- This component represents the Performance Monitoring (Pm) 
-- function on a provisioned connection. No Performane Monitoring is 
-- done unless this component is present. The attribute values override 
-- corresponding values in the AtmIf Pm settings. There can be a 
-- maximum of 255 Pms on one LP.

mscAtmIfVptVccVcdPm OBJECT IDENTIFIER ::= { mscAtmIfVptVccVcd 3 }



mscAtmIfVptVccVcdPmRowStatusTable OBJECT-TYPE
   SYNTAX     SEQUENCE OF MscAtmIfVptVccVcdPmRowStatusEntry
   ACCESS     not-accessible
   STATUS     mandatory
   DESCRIPTION
     "This entry controls the addition and deletion of 
      mscAtmIfVptVccVcdPm components."
::= { mscAtmIfVptVccVcdPm 1 }

mscAtmIfVptVccVcdPmRowStatusEntry OBJECT-TYPE
   SYNTAX     MscAtmIfVptVccVcdPmRowStatusEntry
   ACCESS     not-accessible
   STATUS     mandatory
   DESCRIPTION
     "A single entry in the table represents a single 
      mscAtmIfVptVccVcdPm component."
   INDEX {
      mscAtmIfIndex,
      mscAtmIfVptIndex,
      mscAtmIfVptVccIndex,
      mscAtmIfVptVccVcdIndex,
      mscAtmIfVptVccVcdPmIndex }
::= { mscAtmIfVptVccVcdPmRowStatusTable 1 }

MscAtmIfVptVccVcdPmRowStatusEntry ::= SEQUENCE {
   mscAtmIfVptVccVcdPmRowStatus
      RowStatus,
   mscAtmIfVptVccVcdPmComponentName
      DisplayString,
   mscAtmIfVptVccVcdPmStorageType
      StorageType,
   mscAtmIfVptVccVcdPmIndex
      NonReplicated }

mscAtmIfVptVccVcdPmRowStatus OBJECT-TYPE
   SYNTAX     RowStatus 
   ACCESS     read-write
   STATUS     mandatory
   DESCRIPTION
     "This variable is used as the basis for SNMP naming of
      mscAtmIfVptVccVcdPm components.
      These components can be added and deleted."
::= { mscAtmIfVptVccVcdPmRowStatusEntry 1 }

mscAtmIfVptVccVcdPmComponentName OBJECT-TYPE
   SYNTAX     DisplayString 
   ACCESS     read-only
   STATUS     mandatory
   DESCRIPTION
     "This variable provides the component's string name for
      use with the ASCII Console Interface"
::= { mscAtmIfVptVccVcdPmRowStatusEntry 2 }

mscAtmIfVptVccVcdPmStorageType OBJECT-TYPE
   SYNTAX     StorageType 
   ACCESS     read-only
   STATUS     mandatory
   DESCRIPTION
     "This variable represents the storage type value for the
      mscAtmIfVptVccVcdPm tables."
::= { mscAtmIfVptVccVcdPmRowStatusEntry 4 }

mscAtmIfVptVccVcdPmIndex OBJECT-TYPE
   SYNTAX     NonReplicated 
   ACCESS     not-accessible
   STATUS     mandatory
   DESCRIPTION
     "This variable represents the index for the mscAtmIfVptVccVcdPm tables."
::= { mscAtmIfVptVccVcdPmRowStatusEntry 10 }

mscAtmIfVptVccVcdPmProvTable OBJECT-TYPE
   SYNTAX     SEQUENCE OF MscAtmIfVptVccVcdPmProvEntry
   ACCESS     not-accessible
   STATUS     mandatory
   DESCRIPTION
     "This group contains provisioned attributes which specify 
      Performance Monitoring (PM) measurements, namely, Availability 
      Ratio (AR) and Cell Loss Ratio (CLR), and control modes for the 
      connection. The values specified in this group override those 
      specified by AtmIf Pm settings."
::= { mscAtmIfVptVccVcdPm 100 }

mscAtmIfVptVccVcdPmProvEntry OBJECT-TYPE
   SYNTAX     MscAtmIfVptVccVcdPmProvEntry
   ACCESS     not-accessible
   STATUS     mandatory
   DESCRIPTION
     "An entry in the mscAtmIfVptVccVcdPmProvTable."
   INDEX {
      mscAtmIfIndex,
      mscAtmIfVptIndex,
      mscAtmIfVptVccIndex,
      mscAtmIfVptVccVcdIndex,
      mscAtmIfVptVccVcdPmIndex }
::= { mscAtmIfVptVccVcdPmProvTable 1 }

MscAtmIfVptVccVcdPmProvEntry ::= SEQUENCE {
   mscAtmIfVptVccVcdPmSegSwitchSideMeasurement
      OCTET STRING,
   mscAtmIfVptVccVcdPmSegLinkSideMeasurement
      OCTET STRING,
   mscAtmIfVptVccVcdPmControlMode
      INTEGER }

mscAtmIfVptVccVcdPmSegSwitchSideMeasurement OBJECT-TYPE
   SYNTAX     OCTET STRING (SIZE (1))
   ACCESS     read-write
   STATUS     mandatory
   DESCRIPTION
     "This attribute specifies the set of Performance Monitoring (PM) 
      measurements on the switch side configuration for the connection.
      
      sameAsInterface means that the measurements specified by the 
      segSwitchSideMeasurement attribute of the AtmIf Pm component 
      will be performed. No other values may be specified if 
      sameAsInterface is selected. If the value is empty, no switch side 
      PM measurements are done.

      Description of bits:
      availabilityRatio(0)
      cellLossRatio(1)
      sameAsInterface(2)"
   DEFVAL     { '20'H }
::= { mscAtmIfVptVccVcdPmProvEntry 1 }

mscAtmIfVptVccVcdPmSegLinkSideMeasurement OBJECT-TYPE
   SYNTAX     OCTET STRING (SIZE (1))
   ACCESS     read-write
   STATUS     mandatory
   DESCRIPTION
     "This attribute specifies the set of Performance Monitoring (PM) 
      measurements on the link side configuration for the connection.
      
      sameAsInterface means that the measurements specified by the 
      segLinkSideMeasurement attribute of the AtmIf Pm component will 
      be performed. No other values may be specified if sameAsInterface 
      is selected. If the value is empty, no link side PM measurements are 
      done.
      
      The following are valid sets:
      (~sameAsInterface ~availabilityRatio ~cellLossRatio)
      (~sameAsInterface ~availabilityRatio cellLossRatio)
      (~sameAsInterface availabilityRatio ~cellLossRatio)
      (~sameAsInterface availabilityRatio cellLossRatio)
      (sameAsInterface ~availabilityRatio ~cellLossRatio)

      Description of bits:
      availabilityRatio(0)
      cellLossRatio(1)
      sameAsInterface(2)"
   DEFVAL     { '20'H }
::= { mscAtmIfVptVccVcdPmProvEntry 2 }

mscAtmIfVptVccVcdPmControlMode OBJECT-TYPE
   SYNTAX     INTEGER  {
                 autoStart(0),
                 onDemand(1),
                 sameAsInterface(2) }
   ACCESS     read-write
   STATUS     mandatory
   DESCRIPTION
     "This attribute specifies the control mode of Performance Monitoring 
      (PM) measurements for the connection.
      
      autoStart means that PM activation procedures will start when the 
      provisioned data is activated.
      
      onDemand means that PM activation procedures will start when the 
      operator issues the START command. The PM measurements in this 
      mode will continue until the operator issues the STOP command.
      
      sameAsInterface means that the behavior will be as specified by the 
      controlMode attribute of the AtmIf Pm component."
   DEFVAL     { sameAsInterface }
::= { mscAtmIfVptVccVcdPmProvEntry 3 }


-- AtmIf/n Vcc/vpi.vci Loop
-- The Loop component configures an ATM connection so that cells 
-- received from the ATM interface are retransmitted back to the 
-- interface through that connection. The Loop component requires 
-- exclusive use of its parent Vcc or Vpc and cannot co-exist with other 
-- ATM service components (such as Nep, Nrp, and Test).

mscAtmIfVptVccLoop OBJECT IDENTIFIER ::= { mscAtmIfVptVcc 3 }



mscAtmIfVptVccLoopRowStatusTable OBJECT-TYPE
   SYNTAX     SEQUENCE OF MscAtmIfVptVccLoopRowStatusEntry
   ACCESS     not-accessible
   STATUS     mandatory
   DESCRIPTION
     "This entry controls the addition and deletion of 
      mscAtmIfVptVccLoop components."
::= { mscAtmIfVptVccLoop 1 }

mscAtmIfVptVccLoopRowStatusEntry OBJECT-TYPE
   SYNTAX     MscAtmIfVptVccLoopRowStatusEntry
   ACCESS     not-accessible
   STATUS     mandatory
   DESCRIPTION
     "A single entry in the table represents a single 
      mscAtmIfVptVccLoop component."
   INDEX {
      mscAtmIfIndex,
      mscAtmIfVptIndex,
      mscAtmIfVptVccIndex,
      mscAtmIfVptVccLoopIndex }
::= { mscAtmIfVptVccLoopRowStatusTable 1 }

MscAtmIfVptVccLoopRowStatusEntry ::= SEQUENCE {
   mscAtmIfVptVccLoopRowStatus
      RowStatus,
   mscAtmIfVptVccLoopComponentName
      DisplayString,
   mscAtmIfVptVccLoopStorageType
      StorageType,
   mscAtmIfVptVccLoopIndex
      NonReplicated }

mscAtmIfVptVccLoopRowStatus OBJECT-TYPE
   SYNTAX     RowStatus 
   ACCESS     read-write
   STATUS     mandatory
   DESCRIPTION
     "This variable is used as the basis for SNMP naming of
      mscAtmIfVptVccLoop components.
      These components can be added and deleted."
::= { mscAtmIfVptVccLoopRowStatusEntry 1 }

mscAtmIfVptVccLoopComponentName OBJECT-TYPE
   SYNTAX     DisplayString 
   ACCESS     read-only
   STATUS     mandatory
   DESCRIPTION
     "This variable provides the component's string name for
      use with the ASCII Console Interface"
::= { mscAtmIfVptVccLoopRowStatusEntry 2 }

mscAtmIfVptVccLoopStorageType OBJECT-TYPE
   SYNTAX     StorageType 
   ACCESS     read-only
   STATUS     mandatory
   DESCRIPTION
     "This variable represents the storage type value for the
      mscAtmIfVptVccLoop tables."
::= { mscAtmIfVptVccLoopRowStatusEntry 4 }

mscAtmIfVptVccLoopIndex OBJECT-TYPE
   SYNTAX     NonReplicated 
   ACCESS     not-accessible
   STATUS     mandatory
   DESCRIPTION
     "This variable represents the index for the mscAtmIfVptVccLoop tables."
::= { mscAtmIfVptVccLoopRowStatusEntry 10 }


-- AtmIf/n Vcc/vpi.vci Nep
-- The NailedUpEndPoint component is used to link a VCC to an 
-- application that sends and receives frames using the connection. 
-- The Nep component requires exclusive use of its parent Vcc and 
-- cannot co-exist with other ATM service components (such as Nrp, 
-- Test, and Loop).

mscAtmIfVptVccNep OBJECT IDENTIFIER ::= { mscAtmIfVptVcc 5 }



mscAtmIfVptVccNepRowStatusTable OBJECT-TYPE
   SYNTAX     SEQUENCE OF MscAtmIfVptVccNepRowStatusEntry
   ACCESS     not-accessible
   STATUS     mandatory
   DESCRIPTION
     "This entry controls the addition and deletion of 
      mscAtmIfVptVccNep components."
::= { mscAtmIfVptVccNep 1 }

mscAtmIfVptVccNepRowStatusEntry OBJECT-TYPE
   SYNTAX     MscAtmIfVptVccNepRowStatusEntry
   ACCESS     not-accessible
   STATUS     mandatory
   DESCRIPTION
     "A single entry in the table represents a single 
      mscAtmIfVptVccNep component."
   INDEX {
      mscAtmIfIndex,
      mscAtmIfVptIndex,
      mscAtmIfVptVccIndex,
      mscAtmIfVptVccNepIndex }
::= { mscAtmIfVptVccNepRowStatusTable 1 }

MscAtmIfVptVccNepRowStatusEntry ::= SEQUENCE {
   mscAtmIfVptVccNepRowStatus
      RowStatus,
   mscAtmIfVptVccNepComponentName
      DisplayString,
   mscAtmIfVptVccNepStorageType
      StorageType,
   mscAtmIfVptVccNepIndex
      NonReplicated }

mscAtmIfVptVccNepRowStatus OBJECT-TYPE
   SYNTAX     RowStatus 
   ACCESS     read-write
   STATUS     mandatory
   DESCRIPTION
     "This variable is used as the basis for SNMP naming of
      mscAtmIfVptVccNep components.
      These components can be added and deleted."
::= { mscAtmIfVptVccNepRowStatusEntry 1 }

mscAtmIfVptVccNepComponentName OBJECT-TYPE
   SYNTAX     DisplayString 
   ACCESS     read-only
   STATUS     mandatory
   DESCRIPTION
     "This variable provides the component's string name for
      use with the ASCII Console Interface"
::= { mscAtmIfVptVccNepRowStatusEntry 2 }

mscAtmIfVptVccNepStorageType OBJECT-TYPE
   SYNTAX     StorageType 
   ACCESS     read-only
   STATUS     mandatory
   DESCRIPTION
     "This variable represents the storage type value for the
      mscAtmIfVptVccNep tables."
::= { mscAtmIfVptVccNepRowStatusEntry 4 }

mscAtmIfVptVccNepIndex OBJECT-TYPE
   SYNTAX     NonReplicated 
   ACCESS     not-accessible
   STATUS     mandatory
   DESCRIPTION
     "This variable represents the index for the mscAtmIfVptVccNep tables."
::= { mscAtmIfVptVccNepRowStatusEntry 10 }

mscAtmIfVptVccNepProvTable OBJECT-TYPE
   SYNTAX     SEQUENCE OF MscAtmIfVptVccNepProvEntry
   ACCESS     not-accessible
   STATUS     mandatory
   DESCRIPTION
     "This group contains provisionable attributes for the Nep component."
::= { mscAtmIfVptVccNep 100 }

mscAtmIfVptVccNepProvEntry OBJECT-TYPE
   SYNTAX     MscAtmIfVptVccNepProvEntry
   ACCESS     not-accessible
   STATUS     mandatory
   DESCRIPTION
     "An entry in the mscAtmIfVptVccNepProvTable."
   INDEX {
      mscAtmIfIndex,
      mscAtmIfVptIndex,
      mscAtmIfVptVccIndex,
      mscAtmIfVptVccNepIndex }
::= { mscAtmIfVptVccNepProvTable 1 }

MscAtmIfVptVccNepProvEntry ::= SEQUENCE {
   mscAtmIfVptVccNepApplicationName
      Link }

mscAtmIfVptVccNepApplicationName OBJECT-TYPE
   SYNTAX     Link 
   ACCESS     read-only
   STATUS     mandatory
   DESCRIPTION
     "This attribute specifies the application that sends and receives 
      frames using the VCC. This attribute is set, for example, by 
      provisioning the Trunk AtmAccess AtmConnection attribute. If it is 
      properly configured, this attribute will show a value such as
      'Trk/22 AtmAccess'."
::= { mscAtmIfVptVccNepProvEntry 10 }


-- AtmIf/n Vcc/vpi.vci Test
-- The Test component allows test traffic to be sent over an ATM 
-- connection. It is used to verify the integrity of hardware carrying 
-- ATM traffic, and provides test capabilities similar to those provided 
-- by non-ATM port and line tests. The Test component requires 
-- exclusive use of its parent Vcc and cannot co-exist with other ATM 
-- service components (such as Nep, Nrp, and Loop).
-- 
-- An ATM connection test circulates traffic through a VCC having a 
-- Test component at one end and the other end configured to loop 
-- back ATM cells. The Test component generates test frames, 
-- transforms them into ATM cells using AAL5 segmentation, and 
-- transmits them through the VCC; the returned cells are received by 
-- the Test component, reassembled back into frames, and the frames 
-- are consumed.
-- 
-- The test frames generated by the test are grouped into two 
-- independent streams.
-- 1) The loading frame stream circulates a set of "loading frames" 
-- through the connection as rapidly as possible. The intent of this 
-- stream is to verify the operation of the connection under a 
-- controlled load.
-- 2) The verification stream transmits a series of "verification frames" 
-- through the connection; as each frame is returned, the Test 
-- component verifies its contents and the next verification frame in 
-- the series is transmitted. The intent of this stream is to verify that 
-- frames are not being corrupted.
-- The test can be configured to send frames from either or both 
-- streams. The size and content of the test frames can also be 
-- controlled.

mscAtmIfVptVccTest OBJECT IDENTIFIER ::= { mscAtmIfVptVcc 6 }



mscAtmIfVptVccTestRowStatusTable OBJECT-TYPE
   SYNTAX     SEQUENCE OF MscAtmIfVptVccTestRowStatusEntry
   ACCESS     not-accessible
   STATUS     mandatory
   DESCRIPTION
     "This entry controls the addition and deletion of 
      mscAtmIfVptVccTest components."
::= { mscAtmIfVptVccTest 1 }

mscAtmIfVptVccTestRowStatusEntry OBJECT-TYPE
   SYNTAX     MscAtmIfVptVccTestRowStatusEntry
   ACCESS     not-accessible
   STATUS     mandatory
   DESCRIPTION
     "A single entry in the table represents a single 
      mscAtmIfVptVccTest component."
   INDEX {
      mscAtmIfIndex,
      mscAtmIfVptIndex,
      mscAtmIfVptVccIndex,
      mscAtmIfVptVccTestIndex }
::= { mscAtmIfVptVccTestRowStatusTable 1 }

MscAtmIfVptVccTestRowStatusEntry ::= SEQUENCE {
   mscAtmIfVptVccTestRowStatus
      RowStatus,
   mscAtmIfVptVccTestComponentName
      DisplayString,
   mscAtmIfVptVccTestStorageType
      StorageType,
   mscAtmIfVptVccTestIndex
      NonReplicated }

mscAtmIfVptVccTestRowStatus OBJECT-TYPE
   SYNTAX     RowStatus 
   ACCESS     read-write
   STATUS     mandatory
   DESCRIPTION
     "This variable is used as the basis for SNMP naming of
      mscAtmIfVptVccTest components.
      These components can be added and deleted."
::= { mscAtmIfVptVccTestRowStatusEntry 1 }

mscAtmIfVptVccTestComponentName OBJECT-TYPE
   SYNTAX     DisplayString 
   ACCESS     read-only
   STATUS     mandatory
   DESCRIPTION
     "This variable provides the component's string name for
      use with the ASCII Console Interface"
::= { mscAtmIfVptVccTestRowStatusEntry 2 }

mscAtmIfVptVccTestStorageType OBJECT-TYPE
   SYNTAX     StorageType 
   ACCESS     read-only
   STATUS     mandatory
   DESCRIPTION
     "This variable represents the storage type value for the
      mscAtmIfVptVccTest tables."
::= { mscAtmIfVptVccTestRowStatusEntry 4 }

mscAtmIfVptVccTestIndex OBJECT-TYPE
   SYNTAX     NonReplicated 
   ACCESS     not-accessible
   STATUS     mandatory
   DESCRIPTION
     "This variable represents the index for the mscAtmIfVptVccTest tables."
::= { mscAtmIfVptVccTestRowStatusEntry 10 }

mscAtmIfVptVccTestStateTable OBJECT-TYPE
   SYNTAX     SEQUENCE OF MscAtmIfVptVccTestStateEntry
   ACCESS     not-accessible
   STATUS     mandatory
   DESCRIPTION
     "This group contains the three OSI State attributes. The descriptions 
      generically indicate what each state attribute implies about the 
      component. Note that not all the values and state combinations 
      described here are supported by every component which reuses this 
      group. For component-specific information and the valid state 
      combinations, refer to the appropriate NTP."
::= { mscAtmIfVptVccTest 100 }

mscAtmIfVptVccTestStateEntry OBJECT-TYPE
   SYNTAX     MscAtmIfVptVccTestStateEntry
   ACCESS     not-accessible
   STATUS     mandatory
   DESCRIPTION
     "An entry in the mscAtmIfVptVccTestStateTable."
   INDEX {
      mscAtmIfIndex,
      mscAtmIfVptIndex,
      mscAtmIfVptVccIndex,
      mscAtmIfVptVccTestIndex }
::= { mscAtmIfVptVccTestStateTable 1 }

MscAtmIfVptVccTestStateEntry ::= SEQUENCE {
   mscAtmIfVptVccTestAdminState
      INTEGER,
   mscAtmIfVptVccTestOperationalState
      INTEGER,
   mscAtmIfVptVccTestUsageState
      INTEGER }

mscAtmIfVptVccTestAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock -force or 
      Lock command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscAtmIfVptVccTestStateEntry 1 }

mscAtmIfVptVccTestOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscAtmIfVptVccTestStateEntry 2 }

mscAtmIfVptVccTestUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscAtmIfVptVccTestStateEntry 3 }

mscAtmIfVptVccTestSetupTable OBJECT-TYPE
   SYNTAX     SEQUENCE OF MscAtmIfVptVccTestSetupEntry
   ACCESS     not-accessible
   STATUS     mandatory
   DESCRIPTION
     "This group contains attributes that govern the operation of an ATM 
      connection test. These attributes cannot be changed while the test is 
      running."
::= { mscAtmIfVptVccTest 110 }

mscAtmIfVptVccTestSetupEntry OBJECT-TYPE
   SYNTAX     MscAtmIfVptVccTestSetupEntry
   ACCESS     not-accessible
   STATUS     mandatory
   DESCRIPTION
     "An entry in the mscAtmIfVptVccTestSetupTable."
   INDEX {
      mscAtmIfIndex,
      mscAtmIfVptIndex,
      mscAtmIfVptVccIndex,
      mscAtmIfVptVccTestIndex }
::= { mscAtmIfVptVccTestSetupTable 1 }

MscAtmIfVptVccTestSetupEntry ::= SEQUENCE {
   mscAtmIfVptVccTestFrmTypes
      OCTET STRING,
   mscAtmIfVptVccTestFrmSize
      Unsigned32,
   mscAtmIfVptVccTestFrmPatternType
      INTEGER,
   mscAtmIfVptVccTestCustomizedPattern
      Hex,
   mscAtmIfVptVccTestDuration
      Unsigned32,
   mscAtmIfVptVccTestBandwidthElastic
      INTEGER,
   mscAtmIfVptVccTestOverrideHoldingPriority
      INTEGER }

mscAtmIfVptVccTestFrmTypes OBJECT-TYPE
   SYNTAX     OCTET STRING (SIZE (1))
   ACCESS     read-write
   STATUS     mandatory
   DESCRIPTION
     "This attribute specifies the types of the test frames to be transmitted 
      during the ATM connection test. It must contain at least one of the 
      following:
      loading: A set of 'loading frames' is circulated over the link as 
      rapidly as possible. This frame type should be selected when the 
      test is intended to verify the operation of the connection under a 
      specified load. These frames are not checked for bit errors.
      verification: A single 'verification frame' is transmitted over the 
      link; when the frame is returned, its contents are verified and the 
      next verification frame in the series is transmitted. This frame type 
      should be selected when the test is intended to verify that frames are 
      not being corrupted as they pass over the connection.

      Description of bits:
      loading(0)
      verification(1)"
   DEFVAL     { 'c0'H }
::= { mscAtmIfVptVccTestSetupEntry 10 }

mscAtmIfVptVccTestFrmSize OBJECT-TYPE
   SYNTAX     Unsigned32 (4..4096)
   ACCESS     read-write
   STATUS     mandatory
   DESCRIPTION
     "This attribute defines the size of the test frames used in an ATM 
      connection test."
   DEFVAL     { 1024 }
::= { mscAtmIfVptVccTestSetupEntry 20 }

mscAtmIfVptVccTestFrmPatternType OBJECT-TYPE
   SYNTAX     INTEGER  {
                 ccitt32kBitPattern(0),
                 ccitt8MBitPattern(1),
                 customizedPattern(2) }
   ACCESS     read-write
   STATUS     mandatory
   DESCRIPTION
     "This attribute specifies the bit sequence used to fill the frames used 
      in the ATM connection test. It must contain one of the following 
      values:
      ccitt32kBitPattern: a pseudo-random sequence of 32 Kbit is used
      ccitt8MBitPattern: a pseudo-random sequence of 8Mbit is used
      customizedPattern: the pattern defined in the customizedPattern 
      attribute is used"
   DEFVAL     { ccitt32kBitPattern }
::= { mscAtmIfVptVccTestSetupEntry 30 }

mscAtmIfVptVccTestCustomizedPattern OBJECT-TYPE
   SYNTAX     Hex (0..4294967295)
   ACCESS     read-write
   STATUS     mandatory
   DESCRIPTION
     "This attribute specifies a 32 bit sequence to be used to fill frames 
      when the framePatternType attribute is set to customizedPattern. 
      The default value gives a pattern of alternating 0 and 1 bits."
   DEFVAL     { 1431655765 }
::= { mscAtmIfVptVccTestSetupEntry 40 }

mscAtmIfVptVccTestDuration OBJECT-TYPE
   SYNTAX     Unsigned32 (1..30240)
   ACCESS     read-write
   STATUS     mandatory
   DESCRIPTION
     "This attribute specifies the maximum number of minutes that the 
      ATM connection test is allowed to run. The maximum allowed 
      value permits the test to be run for up to 21 days."
   DEFVAL     { 1 }
::= { mscAtmIfVptVccTestSetupEntry 50 }

mscAtmIfVptVccTestBandwidthElastic OBJECT-TYPE
   SYNTAX     INTEGER  {
                 no(0),
                 yes(1) }
   ACCESS     read-write
   STATUS     mandatory
   DESCRIPTION
     "This attribute specifies whether the connection (VCC) should be 
      configured with elastic bandwidth or not. Elastic bandwidth is of 
      importance in conjuction with IMA links, where some links fail and 
      the resulting bandwidth is less than the requested bandwidth for all 
      connections. In that case, some connections may be reduced in 
      bandwidth based on the setting of the bwElastic attribute.
      
      If this attribute is set to yes, the Test application signals to the 
      connection that the bandwidth for this connection is elastic, and 
      may be reduced in the case of IMA link failures. If the bandwidth is 
      reduced, the rate of test cells which can be handled by the 
      connection will also be reduced. 
      
      If this attribute is set to no, the Test application signals to the 
      connection that the bandwidth for this connection must be 
      maintained at the requested level. If the connection cannot maintain 
      the full bandwidth, the connection may be released (cleared) based 
      on the holding priority of the connection."
   DEFVAL     { no }
::= { mscAtmIfVptVccTestSetupEntry 60 }

mscAtmIfVptVccTestOverrideHoldingPriority OBJECT-TYPE
   SYNTAX     INTEGER  {
                 n0(0),
                 n1(1),
                 n2(2),
                 n3(3),
                 n4(4),
                 noOverride(6) }
   ACCESS     read-write
   STATUS     mandatory
   DESCRIPTION
     "This attribute specifies the override holding priority which should 
      be signalled to the VCC connection at the start of the test. Holding 
      priority is of importance in conjuction with IMA links, where some 
      links fail and the resulting bandwidth is less than the requested 
      bandwidth for all connections. In that case, some connections may 
      be released based on the connection's holding priority.
      
      Zero (0) is thie highest holding priority, and four (4) is the lowest 
      priority. A setting of zero to four overrides whatever holding 
      priority that has been configured at the connection (VCC). A setting 
      of noOverride means that the connection should use its internally 
      configured holding priority."
   DEFVAL     { noOverride }
::= { mscAtmIfVptVccTestSetupEntry 70 }

mscAtmIfVptVccTestResultsTable OBJECT-TYPE
   SYNTAX     SEQUENCE OF MscAtmIfVptVccTestResultsEntry
   ACCESS     not-accessible
   STATUS     mandatory
   DESCRIPTION
     "This group contains attributes that show the result of an ATM 
      connection test; if no test is running, the attribute group contains the 
      results of the most recently completed test. The attributes of the 
      Results group are reset to their inital values whenever a test is 
      started or any attribute of the Setup group is set."
::= { mscAtmIfVptVccTest 120 }

mscAtmIfVptVccTestResultsEntry OBJECT-TYPE
   SYNTAX     MscAtmIfVptVccTestResultsEntry
   ACCESS     not-accessible
   STATUS     mandatory
   DESCRIPTION
     "An entry in the mscAtmIfVptVccTestResultsTable."
   INDEX {
      mscAtmIfIndex,
      mscAtmIfVptIndex,
      mscAtmIfVptVccIndex,
      mscAtmIfVptVccTestIndex }
::= { mscAtmIfVptVccTestResultsTable 1 }

MscAtmIfVptVccTestResultsEntry ::= SEQUENCE {
   mscAtmIfVptVccTestElapsedTime
      Unsigned32,
   mscAtmIfVptVccTestTimeRemaining
      Unsigned32,
   mscAtmIfVptVccTestCauseOfTermination
      INTEGER,
   mscAtmIfVptVccTestBytesTx
      PassportCounter64,
   mscAtmIfVptVccTestBytesRx
      PassportCounter64,
   mscAtmIfVptVccTestLoadingFrmTx
      PassportCounter64,
   mscAtmIfVptVccTestLoadingFrmRx
      PassportCounter64,
   mscAtmIfVptVccTestLoadingFrmLost
      PassportCounter64,
   mscAtmIfVptVccTestVerificationFrmTx
      PassportCounter64,
   mscAtmIfVptVccTestVerificationFrmRx
      PassportCounter64,
   mscAtmIfVptVccTestVerificationFrmBad
      PassportCounter64,
   mscAtmIfVptVccTestUnrecognizableFrmRx
      PassportCounter64 }

mscAtmIfVptVccTestElapsedTime OBJECT-TYPE
   SYNTAX     Unsigned32 (0..30240)
   ACCESS     read-only
   STATUS     mandatory
   DESCRIPTION
     "This attribute displays the number of minutes that the test has been 
      running."
   DEFVAL     { 0 }
::= { mscAtmIfVptVccTestResultsEntry 10 }

mscAtmIfVptVccTestTimeRemaining OBJECT-TYPE
   SYNTAX     Unsigned32 (0..30240)
   ACCESS     read-only
   STATUS     mandatory
   DESCRIPTION
     "This attribute displays the number of minutes that the test will 
      continue to run before stopping automatically."
   DEFVAL     { 0 }
::= { mscAtmIfVptVccTestResultsEntry 20 }

mscAtmIfVptVccTestCauseOfTermination OBJECT-TYPE
   SYNTAX     INTEGER  {
                 testTimeExpired(0),
                 stoppedByOperator(1),
                 neverStarted(2),
                 testRunning(3) }
   ACCESS     read-only
   STATUS     mandatory
   DESCRIPTION
     "This attribute displays the reason the test ended. It contains one fo 
      the following values.
      testTimeExpired: the test ran for the specified duration
      stoppedByOperator: a STOP command was issued
      neverStarted: the test has not been started
      testRunning: the test is currently running"
   DEFVAL     { neverStarted }
::= { mscAtmIfVptVccTestResultsEntry 30 }

mscAtmIfVptVccTestBytesTx OBJECT-TYPE
   SYNTAX     PassportCounter64 
   ACCESS     read-only
   STATUS     mandatory
   DESCRIPTION
     "This attribute displays the number of bytes sent during the test. The 
      counter wraps to zero if it exceeds its maximum value of (2**64)-1."
::= { mscAtmIfVptVccTestResultsEntry 40 }

mscAtmIfVptVccTestBytesRx OBJECT-TYPE
   SYNTAX     PassportCounter64 
   ACCESS     read-only
   STATUS     mandatory
   DESCRIPTION
     "This attribute displays the number of bytes received during the test. 
      The counter wraps to zero if it exceeds its maximum value of 
      (2**64)-1."
::= { mscAtmIfVptVccTestResultsEntry 50 }

mscAtmIfVptVccTestLoadingFrmTx OBJECT-TYPE
   SYNTAX     PassportCounter64 
   ACCESS     read-only
   STATUS     mandatory
   DESCRIPTION
     "This attribute displays the number of loading frames sent during the 
      test. The counter wraps to zero if it exceeds its maximum value of 
      (2**64)-1."
::= { mscAtmIfVptVccTestResultsEntry 60 }

mscAtmIfVptVccTestLoadingFrmRx OBJECT-TYPE
   SYNTAX     PassportCounter64 
   ACCESS     read-only
   STATUS     mandatory
   DESCRIPTION
     "This attribute displays the number of loading frames received 
      during the test. The counter wraps to zero if it exceeds its maximum 
      value of (2**64)-1."
::= { mscAtmIfVptVccTestResultsEntry 70 }

mscAtmIfVptVccTestLoadingFrmLost OBJECT-TYPE
   SYNTAX     PassportCounter64 
   ACCESS     read-only
   STATUS     mandatory
   DESCRIPTION
     "This attribute displays the number of loading frames that were lost 
      during the test. The counter wraps to zero if it exceeds its maximum 
      value of (2**64)-1."
::= { mscAtmIfVptVccTestResultsEntry 80 }

mscAtmIfVptVccTestVerificationFrmTx OBJECT-TYPE
   SYNTAX     PassportCounter64 
   ACCESS     read-only
   STATUS     mandatory
   DESCRIPTION
     "This attribute displays the number of verification frames sent during 
      the test. The counter wraps to zero if it exceeds its maximum value 
      of (2**64)-1."
::= { mscAtmIfVptVccTestResultsEntry 90 }

mscAtmIfVptVccTestVerificationFrmRx OBJECT-TYPE
   SYNTAX     PassportCounter64 
   ACCESS     read-only
   STATUS     mandatory
   DESCRIPTION
     "This attribute displays the number of verification frames received 
      during the test (including errored verification frames). The counter 
      wraps to zero if it exceeds its maximum value of (2**64)-1.
      
      Note that the number of verification frames lost during the test can 
      be computed by the expression verificationFrmTx - 
      verificationFrmRx."
::= { mscAtmIfVptVccTestResultsEntry 100 }

mscAtmIfVptVccTestVerificationFrmBad OBJECT-TYPE
   SYNTAX     PassportCounter64 
   ACCESS     read-only
   STATUS     mandatory
   DESCRIPTION
     "This attribute displays the number of errored verification frames 
      received during the test. A verification frame is considered to be 
      errored if it contains a recognizable verification frame header, but 
      does not match the transmitted frame bit for bit. (Thus, a 
      verification frame that returns after the succeeding verification 
      frame has been transmitted is considered to be errored.) The counter 
      wraps to zero if it exceeds its maximum value of (2**64)-1.
      
      Note that the number of correct verification frames received during 
      the test can be computed by the expression verificationFrmRx - 
      verificationFrmBad."
::= { mscAtmIfVptVccTestResultsEntry 110 }

mscAtmIfVptVccTestUnrecognizableFrmRx OBJECT-TYPE
   SYNTAX     PassportCounter64 
   ACCESS     read-only
   STATUS     mandatory
   DESCRIPTION
     "This attribute displays the number of frames received during the test 
      which do not contain a valid loading frame header or verification 
      frame header. The counter wraps to zero if it exceeds its maximum 
      value of (2**64)-1."
::= { mscAtmIfVptVccTestResultsEntry 120 }


-- AtmIf/n Vpc/vpi TrafficManagement, 
-- AtmIf/n Vcc/vpi.vci TrafficManagement,
-- AtmIf/n Vpt/vpi TrafficManagement,
-- AtmIf/n Vpt/vpi Vcc/vci TrafficManagement
-- The Tm subcomponent contains the operational traffic management 
-- attributes of a connection. It is created dynamically for each 
-- activated Vcc, Vpc, or Vpt component.

mscAtmIfVptVccTm OBJECT IDENTIFIER ::= { mscAtmIfVptVcc 7 }



mscAtmIfVptVccTmRowStatusTable OBJECT-TYPE
   SYNTAX     SEQUENCE OF MscAtmIfVptVccTmRowStatusEntry
   ACCESS     not-accessible
   STATUS     mandatory
   DESCRIPTION
     "This entry controls the addition and deletion of 
      mscAtmIfVptVccTm components."
::= { mscAtmIfVptVccTm 1 }

mscAtmIfVptVccTmRowStatusEntry OBJECT-TYPE
   SYNTAX     MscAtmIfVptVccTmRowStatusEntry
   ACCESS     not-accessible
   STATUS     mandatory
   DESCRIPTION
     "A single entry in the table represents a single 
      mscAtmIfVptVccTm component."
   INDEX {
      mscAtmIfIndex,
      mscAtmIfVptIndex,
      mscAtmIfVptVccIndex,
      mscAtmIfVptVccTmIndex }
::= { mscAtmIfVptVccTmRowStatusTable 1 }

MscAtmIfVptVccTmRowStatusEntry ::= SEQUENCE {
   mscAtmIfVptVccTmRowStatus
      RowStatus,
   mscAtmIfVptVccTmComponentName
      DisplayString,
   mscAtmIfVptVccTmStorageType
      StorageType,
   mscAtmIfVptVccTmIndex
      NonReplicated }

mscAtmIfVptVccTmRowStatus OBJECT-TYPE
   SYNTAX     RowStatus 
   ACCESS     read-only
   STATUS     mandatory
   DESCRIPTION
     "This variable is used as the basis for SNMP naming of
      mscAtmIfVptVccTm components.
      These components cannot be added nor deleted."
::= { mscAtmIfVptVccTmRowStatusEntry 1 }

mscAtmIfVptVccTmComponentName OBJECT-TYPE
   SYNTAX     DisplayString 
   ACCESS     read-only
   STATUS     mandatory
   DESCRIPTION
     "This variable provides the component's string name for
      use with the ASCII Console Interface"
::= { mscAtmIfVptVccTmRowStatusEntry 2 }

mscAtmIfVptVccTmStorageType OBJECT-TYPE
   SYNTAX     StorageType 
   ACCESS     read-only
   STATUS     mandatory
   DESCRIPTION
     "This variable represents the storage type value for the
      mscAtmIfVptVccTm tables."
::= { mscAtmIfVptVccTmRowStatusEntry 4 }

mscAtmIfVptVccTmIndex OBJECT-TYPE
   SYNTAX     NonReplicated 
   ACCESS     not-accessible
   STATUS     mandatory
   DESCRIPTION
     "This variable represents the index for the mscAtmIfVptVccTm tables."
::= { mscAtmIfVptVccTmRowStatusEntry 10 }

mscAtmIfVptVccTmOperTable OBJECT-TYPE
   SYNTAX     SEQUENCE OF MscAtmIfVptVccTmOperEntry
   ACCESS     not-accessible
   STATUS     mandatory
   DESCRIPTION
     "This group contains attributes for the Tm component to reflect 
      operational traffic attributes."
::= { mscAtmIfVptVccTm 100 }

mscAtmIfVptVccTmOperEntry OBJECT-TYPE
   SYNTAX     MscAtmIfVptVccTmOperEntry
   ACCESS     not-accessible
   STATUS     mandatory
   DESCRIPTION
     "An entry in the mscAtmIfVptVccTmOperTable."
   INDEX {
      mscAtmIfIndex,
      mscAtmIfVptIndex,
      mscAtmIfVptVccIndex,
      mscAtmIfVptVccTmIndex }
::= { mscAtmIfVptVccTmOperTable 1 }

MscAtmIfVptVccTmOperEntry ::= SEQUENCE {
   mscAtmIfVptVccTmTxTrafficDescType
      INTEGER,
   mscAtmIfVptVccTmTxQosClass
      INTEGER,
   mscAtmIfVptVccTmTxQueueLength
      Unsigned32,
   mscAtmIfVptVccTmTxQueueCongestionState
      Unsigned32,
   mscAtmIfVptVccTmHoldingPriority
      INTEGER,
   mscAtmIfVptVccTmRxTrafficDescType
      INTEGER,
   mscAtmIfVptVccTmRxQosClass
      INTEGER,
   mscAtmIfVptVccTmAtmServiceCategory
      INTEGER,
   mscAtmIfVptVccTmTrafficShaping
      INTEGER,
   mscAtmIfVptVccTmBearerClassBbc
      INTEGER,
   mscAtmIfVptVccTmTransferCapabilityBbc
      INTEGER,
   mscAtmIfVptVccTmClippingBbc
      INTEGER,
   mscAtmIfVptVccTmUnshapedTransmitQueueing
      INTEGER,
   mscAtmIfVptVccTmBestEffort
      INTEGER,
   mscAtmIfVptVccTmForceTagging
      INTEGER,
   mscAtmIfVptVccTmWeight
      Unsigned32,
   mscAtmIfVptVccTmUsageParameterControl
      INTEGER,
   mscAtmIfVptVccTmTxPacketWiseDiscard
      OCTET STRING,
   mscAtmIfVptVccTmRxPacketWiseDiscard
      OCTET STRING,
   mscAtmIfVptVccTmBandwidthElastic
      INTEGER,
   mscAtmIfVptVccTmBandwidthReduction
      Unsigned32,
   mscAtmIfVptVccTmAbrConnectionType
      INTEGER }

mscAtmIfVptVccTmTxTrafficDescType OBJECT-TYPE
   SYNTAX     INTEGER  {
                 n1(1),
                 n2(2),
                 n3(3),
                 n4(4),
                 n5(5),
                 n6(6),
                 n7(7),
                 n8(8),
                 n9(9) }
   ACCESS     read-only
   STATUS     mandatory
   DESCRIPTION
     "T his attribute indicates the type of traffic management which is 
      applied to the transmit direction of this connection as defined in the 
      ATM Forum. The txTrafficDescType determines the number and 
      meaning of the parameters in the txTrafficDescParm attribute."
::= { mscAtmIfVptVccTmOperEntry 10 }

mscAtmIfVptVccTmTxQosClass OBJECT-TYPE
   SYNTAX     INTEGER  {
                 n0(0),
                 n1(1),
                 n2(2),
                 n3(3),
                 n4(4),
                 notApplicable(14) }
   ACCESS     read-only
   STATUS     mandatory
   DESCRIPTION
     "This attribute indicates the quality of service for the calling to called 
      direction for this connection. This is only applicable to Soft PVC 
      and SVC connections. 
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified QOS class; no objective is specified for 
      the performance parameters.
      
      A value of notApplicable is displayed in the case of nailed-up PVCs 
      for which this attribute has no significance."
::= { mscAtmIfVptVccTmOperEntry 31 }

mscAtmIfVptVccTmTxQueueLength OBJECT-TYPE
   SYNTAX     Unsigned32 (0..30720)
   ACCESS     read-only
   STATUS     mandatory
   DESCRIPTION
     "This attribute indicates the current number of cells in the transmit 
      queue for this connection. 
      
      If this connection has unshapedTransmitQueueing attribute 
      displayed as common, this attribute displays the length of the 
      common queue which is used for this atm service category. 
      
      If this connection has unshapedTransmitQueueing attribute 
      displayed as fifo, this attribute indicates the number of cells for this 
      connection which are enqueued in a first-in-first-out queuing 
      method for this atm service category. This will only occur for 
      connections on ATM IP cards with atmServiceCategory of nrtVbr 
      or ubr. 
      
      If this connection has unshapedTransmitQueueing attribute 
      displayed as perVc or as notApplicable, this attribute displays the 
      length of the per-VC queue.
      
      For the 1pOC48SmSrAtm card, this attribute displays the current 
      number of cells in the link class queue used by this connection to 
      buffer its traffic.
      
      
      This attribute does not apply to basic Vpts."
::= { mscAtmIfVptVccTmOperEntry 32 }

mscAtmIfVptVccTmTxQueueCongestionState OBJECT-TYPE
   SYNTAX     Unsigned32 (0..3)
   ACCESS     read-only
   STATUS     mandatory
   DESCRIPTION
     "This attribute indicates the congestion state of the transmit queue 
      for this connection. 
      
      If this connection has unshapedTransmitQueueing attribute 
      displayed as common, this attribute displays the congestion state of 
      the common queue. If this connection has 
      unshapedTransmitQueueing attribute displayed as perVc or as 
      notApplicable, this attribute displays the congestion state of the per-
      VC queue.
      
      For the 1pOC48SmSrAtm card, this attribute displays the current 
      congestion state of the link class queue used by this connection to 
      buffer its traffic.
      
      The congestion state of a queue is indicated by a numeric value 
      ranging from 0 to 3. When a queue is in a congested state x, only 
      traffic with discard priority (DP) 0 to x are enqueued. Traffic with 
      DP > x is discarded. 
      
      For example, if the congestion state is 3, there is no congestion and 
      all traffic is enqueued. Likewise, when the congestion state is 0, 
      there is maximum congestion and only traffic with DP=0 is 
      enqueued on that queue.
      
      This attribute does not apply to basic Vpts."
::= { mscAtmIfVptVccTmOperEntry 33 }

mscAtmIfVptVccTmHoldingPriority OBJECT-TYPE
   SYNTAX     INTEGER  {
                 n0(0),
                 n1(1),
                 n2(2),
                 n3(3),
                 n4(4),
                 notApplicable(6) }
   ACCESS     read-only
   STATUS     mandatory
   DESCRIPTION
     "This attribute indicates the actual holding priority in effect for this 
      connection. In a situation where the link bandwidth fluctuates, such 
      as over an IMA link, holding priority is used to determine which 
      connections are held and which are released. Holding priority 4 
      connections are the first to be released. Holding priority 0 
      connections are the last to be released. Some applications, for 
      example Vcc Test, may override the provisioned holding priority. 
      
      A value of notApplicable is displayed when this is an elastic 
      connection. Holding priority does not apply to bandwidth elastic 
      connections.
      
      Holding priority has no effect if the equivalent cell rate (ECR) for a 
      connection is zero.
      
      This attribute does not apply to Vpt Vccs."
::= { mscAtmIfVptVccTmOperEntry 35 }

mscAtmIfVptVccTmRxTrafficDescType OBJECT-TYPE
   SYNTAX     INTEGER  {
                 n1(1),
                 n2(2),
                 n3(3),
                 n4(4),
                 n5(5),
                 n6(6),
                 n7(7),
                 n8(8),
                 n9(9) }
   ACCESS     read-only
   STATUS     mandatory
   DESCRIPTION
     "This attribute indicates the type of traffic management which is 
      applied to the receive direction of this connection as defined in the 
      ATM Forum. The rxTrafficDescType determines the number and 
      meaning of the parameters in the rxTrafficDescParm attribute."
::= { mscAtmIfVptVccTmOperEntry 40 }

mscAtmIfVptVccTmRxQosClass OBJECT-TYPE
   SYNTAX     INTEGER  {
                 n0(0),
                 n1(1),
                 n2(2),
                 n3(3),
                 n4(4),
                 notApplicable(14),
                 sameAsFwd(15) }
   ACCESS     read-only
   STATUS     mandatory
   DESCRIPTION
     "This attribute indicates the quality of service for the called to calling 
      direction for this connection. This is only applicable to Soft PVC 
      and SVC connections. 
      
      Class 1 supports a QOS that meets Service Class A performance 
      requirements (circuit emulation, constant bit rate video).
      
      Class 2 supports a QOS that meets Service Class B performance 
      requirements (variable bit rate audio and video).
      
      Class 3 supports a QOS that meets Service Class C performance 
      requirements (Connection-Oriented Data Transfer).
      
      Class 4 supports a QOS that meets Service Class D performance 
      requirements (Connectionless Data Transfer).
      
      Class 0 is the unspecified QOS class; no objective is specified for 
      the performance parameters.
      
      A value of notApplicable is displayed in the case of nailed-up PVCs 
      for which this attribute has no significance."
::= { mscAtmIfVptVccTmOperEntry 61 }

mscAtmIfVptVccTmAtmServiceCategory OBJECT-TYPE
   SYNTAX     INTEGER  {
                 unspecifiedBitRate(0),
                 constantBitRate(1),
                 rtVariableBitRate(2),
                 nrtVariableBitRate(3),
                 availableBitRate(4) }
   ACCESS     read-only
   STATUS     mandatory
   DESCRIPTION
     "This attribute indicates the ATM service category used for traffic in 
      both directions of the connection. 
      
      The constantBitRate service category is intended for real time 
      applications, that is, those requiring tightly constrained delay and 
      delay variation, as would be appropriate for voice and video 
      applications. The consistent availability of a fixed quantity of 
      bandwidth is considered appropriate for CBR service. Cells which 
      are delayed beyond the value specified by Cell Transfer Delay are 
      assumed to have significantly reduced value for the application.
      
      The rtVariableBitRate service category is intended for real time 
      applications; that is those requiring tightly constrained delay and 
      delay variation, as would be appropriate for voice and video 
      applications. Sources are expected to transmit at a rate which varies 
      with time. Equivalently, the source can be described as 'bursty'. 
      Cells which are delayed beyond the value specified by Cell Transfer 
      Delay are assumed to be of significantly reduced value to the 
      application. Real time VBR service may support statistical 
      multiplexing of real time sources.
      
      The nrtVariableBitRate service category is intended for non-real 
      time applications which have bursty traffic characteristics and which 
      can be characterized in terms of a PCR, SCR, and MBS. For those 
      cells which are transferred within the traffic contract, the application 
      expects a low cell loss ratio. For all connections, it expects a bound 
      on the mean cell transfer delay. Non-real time VBR service may 
      support statistical multiplexing of connections.
      
      The availableBitRate service is an ATM layer service category for 
      which the limiting ATM layer transfer characteristics provided by 
      the network may change subsequent to connection establishment. 
      ABR service has a flow control mechanism which supports several 
      types of feedback to control the source rate in response to changing 
      ATM layer transfer characteristics. ABR service is not intended to 
      support real-time applications.
      
      The unspecifiedBitRate service is intended for non-real time 
      applications, that is those not requiring tightly constrained delay 
      and delay variation. UBR sources are expected to be bursty. UBR 
      service supports a high degree of statistical multiplexing among 
      sources. UBR service does not specify traffic related service 
      guarantees. No numerical commitments are made with respect to 
      the cell loss ratio experienced by a UBR connection, or as to the 
      cell transfer delay experienced by cells on the connection."
::= { mscAtmIfVptVccTmOperEntry 62 }

mscAtmIfVptVccTmTrafficShaping OBJECT-TYPE
   SYNTAX     INTEGER  {
                 disabled(1),
                 notApplicable(4),
                 linear(5),
                 inverseUpc(6) }
   ACCESS     read-only
   STATUS     mandatory
   DESCRIPTION
     "This attribute indicates the traffic shaping state of the connection.
      
      A value of notApplicable indicates that traffic shaping is not 
      applicable or not supported for this connection. This is the case:
      - when the txTrafficDescType is 1 or 2.
      - for standard Vpt Vccs and basic Vpts.
      - for CQC-based ATM cards, when the atmServiceCategory is 
      constantBitRate.
      
      In these cases, the value of notApplicable is set regardless of 
      whether traffic shaping is enabled or disabled in the provisioning 
      data.
      
      For the 1pOC12SmLrAtm card, traffic shaping is not available, 
      therefore this attribute is always notApplicable.
      
      A value of disabled indicates that traffic shaping is applicable and 
      supported for the type of connection but has been turned off in the 
      provisioning data.
      
      A value of linear or inverseUpc indicates that traffic shaping is 
      applicable and supported for the type of connection and has been 
      turned on in the provisioning data. This is the only case that 
      indicates that traffic shaping is performed on the connection. In this 
      case, the actual shaping rate is reflected in the txTrafficDescParm 
      attribute, parameter number 4. A value of linear indicates that 
      traffic is being shaped at the constant rate indicated in 
      txTrafficDescParm 4.
      
      A value of inverseUpc is possible only on ATM IP cards. This value 
      indicates that the shaper strictly conforms to the requirements of a 
      dual leaky bucket UPC enforcer. This value is indicated if traffic 
      shaping is enabled, and the txTrafficDescType for this connection is 
      6, 7 or 8.
      
      Traffic shaping for connections with atmServiceCategory as 
      availableBitRate (txTrafficDescType 9) depends upon the 
      abrConnectionType attribute. If abrConnectionType is sourceDest 
      or virtualSourceDest, the value of this attribute is linear. If 
      abrConnectionType is erSwitch or efciSwitch, this attribute is 
      notApplicable."
::= { mscAtmIfVptVccTmOperEntry 70 }

mscAtmIfVptVccTmBearerClassBbc OBJECT-TYPE
   SYNTAX     INTEGER  {
                 a(1),
                 c(3),
                 x(16),
                 vp(24),
                 notApplicable(30) }
   ACCESS     read-only
   STATUS     mandatory
   DESCRIPTION
     "This attribute indicates the bearer capability for this connection.
      
      Class a service is a connection-oriented, constant bit rate ATM 
      transport service. Class a service has end to end timing 
      requirements and may require stringent cell loss, cell delay and cell 
      delay variation performance.When a is displayed, the user is 
      requesting more than an ATM only service. The network may look 
      at the AAL to provide interworking based upon its contents. 
      
      Class c service is a connection-oriented, variable bit rate ATM 
      transport service. Class c service has no end-to-end timing 
      requirements.When c is displayed, the user is requesting more than 
      an ATM only service. The network interworking function may look 
      at the AAL and provide service based on it.
      
      Class x service is a connection-oriented ATM transport service 
      where the AAL, trafficType (cbr or vbr), and timing requirements 
      are user defined (that is, transparent to the network). When the 
      value of this attribute is x, the user is requesting an ATM only 
      service from the network. In this case, the network shall not process 
      any higher layer protocol.
      
      Class vp service is used to indicate a transparent VP service when 
      the user is requesting an ATM only service from the network. In this 
      case, the network does not process any higher layer protocol. This 
      service differs from class x service in that with the class vp service 
      both the VCI field (except for VCI values 0, 3, 4, and 6 through 15) 
      and Payload Type field are transported transparently by the network. 
      This attribute value is only applicable to SPVP and SVP 
      connections.
      
      A value of notApplicable is displayed in the case of nailed-up PVCs 
      for which this attribute has no significance."
::= { mscAtmIfVptVccTmOperEntry 71 }

mscAtmIfVptVccTmTransferCapabilityBbc OBJECT-TYPE
   SYNTAX     INTEGER  {
                 n0(0),
                 n1(1),
                 n2(2),
                 n5(5),
                 n8(8),
                 n9(9),
                 n10(10),
                 notApplicable(30) }
   ACCESS     read-only
   STATUS     mandatory
   DESCRIPTION
     "This attribute indicates the transfer capability for this connection. 
      Uni 3.0/3.1 traffic type and end-to-end timing parameters are 
      mapped into this parameter as follows:
      <transferCapability: TrafficType, Timing>
      0: NoIndication, NoIndication
      1: NoIndication, yes
      2: NoIndication, no
      5: CBR, yes
      8: VBR, NoIndication
      9: VBR, yes
      10: VBR, no
      
      A value of notApplicable is displayed in the case of nailed-up PVCs 
      for which this attribute has no significance, or in the case that the 
      transfer capability in the call request was set to NoIndication.
      
      The CBR traffic type refers to traffic offered on services such as a 
      constant bit rate video service or a circuit emulation.
      
      The VBR traffic type refers to traffic offered on services such as 
      packetized audio and video, or data.
      
      The value NoIndication for traffic type is used if the user has not set 
      the traffic type; similarly for end-to-end timing.
      
      The value yes for end-to-end timing indicates that end-to-end 
      timing is required for the connection.
      
      The value no for end-to-end timing indicates that end-to-end timing 
      is not required for the connection."
::= { mscAtmIfVptVccTmOperEntry 72 }

mscAtmIfVptVccTmClippingBbc OBJECT-TYPE
   SYNTAX     INTEGER  {
                 no(0),
                 yes(1),
                 notApplicable(14) }
   ACCESS     read-only
   STATUS     mandatory
   DESCRIPTION
     "This attribute indicates the value of the clipping susceptibility 
      parameter in the broadband bearer capability (BBC) Information 
      Element.
      
      Clipping is an impairment in which the first fraction of a second of 
      information to be transferred is lost. It occurs after a call is 
      answered and before an associated connection is switched through.
      
      A value of notApplicable is displayed in the case of nailed-up PVCs 
      for which this attribute has no significance."
::= { mscAtmIfVptVccTmOperEntry 74 }

mscAtmIfVptVccTmUnshapedTransmitQueueing OBJECT-TYPE
   SYNTAX     INTEGER  {
                 perVc(0),
                 common(1),
                 notApplicable(4),
                 fifo(5) }
   ACCESS     read-only
   STATUS     mandatory
   DESCRIPTION
     "This attribute indicates the unshaped transmit queuing state of the 
      connection.
      
      A value of common indicates that transmit traffic is being enqueued 
      onto the common transmit queue for this service category. 
      The txQueueLength attribute indicates the current length of the 
      common transmit queue.
      
      A value of fifo indicates that transmit traffic is being queued in a 
      first-in-first-out basis for this service category. This is similar to 
      common queueing, but the txQueueLength attribute indicates the 
      number of cells in this connection queue. A value of fifo will only 
      be indicated for connections on ATM IP cards with 
      atmServiceCategory of nrtVbr or ubr. 
      
      A value of perVc indicates that transmit traffic is being enqueued 
      onto a per-VC queue for this connection. 
      
      A value of notApplicable indicates that transmit traffic is being 
      shaped for this connection, or that unshaped transmit queuing is not 
      applicable for this type of connection. Transmit traffic for a shaped 
      connection is enqueued onto a per-VC queue, but this attribute is 
      only applicable for unshaped connections. Unshaped transmit 
      queuing is not applicable for basic Vpts.
      
      For 1pOC12SmLrAtm cards, perVc queueing is not available thus 
      this attribute only indicates common or notApplicable."
::= { mscAtmIfVptVccTmOperEntry 75 }

mscAtmIfVptVccTmBestEffort OBJECT-TYPE
   SYNTAX     INTEGER  {
                 indicated(0),
                 notIndicated(1),
                 notApplicable(14) }
   ACCESS     read-only
   STATUS     mandatory
   DESCRIPTION
     "This attribute indicates value of best effort parameter in the ATM 
      Traffic Descriptor Information Element.
      
      The value indicated implies that the quality of service for this 
      connection is not guaranteed.
      
      The value notIndicated implies that the quality of service for this 
      connection is guaranteed.
      
      A value of notApplicable is displayed in the case of nailed-up PVCs 
      for which this attribute has no significance."
::= { mscAtmIfVptVccTmOperEntry 76 }

mscAtmIfVptVccTmForceTagging OBJECT-TYPE
   SYNTAX     INTEGER  {
                 enabled(0),
                 disabled(1) }
   ACCESS     read-only
   STATUS     mandatory
   DESCRIPTION
     "This attribute indicates the state of force tagging option for this 
      connection. Force tagging refers to setting the CLP bit for all cells 
      on a connection. 
      
      For CQC-based ATM cards, this attribute is not applicable and is 
      not displayed.
      
      A value of enabled indicates that the CLP bit is being set to 1 for all 
      cells in the transmit direction on this connection. 
      
      A value of disabled indicates that the CLP bit is unchanged for cells 
      in the transmit direction on this connection. disabled is always 
      displayed for Vpts since forced tagging is applied on a per Vpt Vcc 
      basis."
::= { mscAtmIfVptVccTmOperEntry 78 }

mscAtmIfVptVccTmWeight OBJECT-TYPE
   SYNTAX     Unsigned32 (0 | 1..4095 | 65534)
   ACCESS     read-only
   STATUS     mandatory
   DESCRIPTION
     "This attribute indicates the relative weight of this unshaped 
      connection. Connections with a larger weight get a larger proportion 
      of the link bandwidth or in the case of standard Vpt Vccs, the Vpt 
      bandwidth.
      
      For all but standard Vpt Vccs, the default connection weight is 
      determined by the weight policy for a service category and the 
      traffic descriptor for a connection. For standard Vpt Vccs, the 
      default connection weight is determined by the Vcc's service 
      category.
      
      For CQC-based ATM cards, this attribute is not applicable and is 
      not displayed.
      
      A value from 1 to 4095 indicates an actual weight. The value 
      upToQueueLimit indicates that the weight of a connection is up to 
      the transmit queue limit for this connection. upToQueueLimit is 
      used with common (first-in-first-out) queueing. 
      
      This attribute is displayed as notApplicable if:
      - this connection has trafficShaping displayed as linear or 
      inverseUpc.
      - this is a basic Vpt.

      VALUES (

      0 = upToQueueLimit

      65534 = notApplicable

      )"
::= { mscAtmIfVptVccTmOperEntry 79 }

mscAtmIfVptVccTmUsageParameterControl OBJECT-TYPE
   SYNTAX     INTEGER  {
                 enforced(0),
                 disabled(1),
                 notApplicable(3),
                 monitored(4) }
   ACCESS     read-only
   STATUS     mandatory
   DESCRIPTION
     "This attribute indicates the UPC state of the connection.
      
      A value of notApplicable indicates that UPC is not applicable or not 
      supported for the connection. This is the case:
      - when the connection's rxTrafficDescType is 1 or 2. 
      - for standard Vpt Vccs and basic Vpts.
      
      A value of notApplicable is set regardless of whether UPC is 
      disabled or enabled in provisioning data.
      
      A value of disabled indicates that UPC is applicable and supported 
      for the type of connection but has been turned off in the 
      provisioning data.
      
      A value of enforced indicates that UPC is actively checking 
      conformance for the connection and is discarding or tagging cells 
      which do not conform to the connection traffic contract. The traffic 
      descriptor parameters used for UPC conformance are reflected in 
      the rxTrafficDescParms of the connection. On ATM IP cards, the 
      counts of UPC violations are visible in the Vcc, Vpc or Vpt 
      rxUpcViolationsOnEnforcer1 or rxUpcViolationsOnEnforcer2 
      attributes. 
      
      ATM IP cards provide the ability to monitor UPC violations without 
      tagging or discarding. A value of monitored indicates that UPC is 
      actively checking conformance for the connection and counting the 
      violations, but is not discarding or tagging cells which do not 
      conform to the connection traffic contract. The traffic descriptor 
      parameters used for UPC conformance are reflected in the 
      rxTrafficDescParms of the connection. The counts of UPC 
      violations are visible in the Vcc, Vpc or Vpt. 
      rxUpcViolationsOnEnforcer1 or rxUpcViolationsOnEnforcer2 
      attributes. The value of monitored appears only on ATM IP cards. 
      
      If the atmServiceCategory for this connection is availableBitRate, a 
      value of enforced indicates that Dynamic Generic Cell Rate 
      Algorithm (DGCRA) is active for the connection. The traffic 
      descriptor parameters used for DGCRA enforcement are reflected in 
      the rxTrafficDescParm of the connection."
::= { mscAtmIfVptVccTmOperEntry 80 }

mscAtmIfVptVccTmTxPacketWiseDiscard OBJECT-TYPE
   SYNTAX     OCTET STRING (SIZE (1))
   ACCESS     read-only
   STATUS     mandatory
   DESCRIPTION
     "This attribute indicates the current set of packet-wise discard 
      functions in effect in the transmit data direction at this connection 
      point.
      
      A value of ppd indicates that the Partial Packet Discard (PPD) 
      function is in effect. PPD may be applied at an intermediate 
      connecting point for a connection which is transporting frame traffic 
      (AAL5 at the endpoint). PPD is controlled by provisioning for 
      PVCs and SPVCs, and by call setup parameters in the AAL and 
      Traffic Descriptor Information Elements.
      
      A value of epd indicates that the Early Packet Discard (EPD) 
      function is in effect at this connection endpoint. On CQC-based 
      ATM cards, PPD and EPD are enabled by default at a connection 
      endpoint which is performing AAL5 segmentation and assembly.
      
      A value of wred indicates that Weighted Random Early Detection is 
      in effect at this connection point. W-RED can be enabled by 
      provisioning for PVCs and SPVCs.
      
      On ATM IP cards, all packet-wise discard functions also apply to 
      provisioned virtual path connections (VPCs). On CQC-based ATM 
      cards, packet-wise functions are not applicable for VPCs.
      
      This attribute is not applicable for Vpts.

      Description of bits:
      ppd(0)
      epd(1)
      wred(2)"
::= { mscAtmIfVptVccTmOperEntry 85 }

mscAtmIfVptVccTmRxPacketWiseDiscard OBJECT-TYPE
   SYNTAX     OCTET STRING (SIZE (1))
   ACCESS     read-only
   STATUS     mandatory
   DESCRIPTION
     "This attribute indicates the current set of packet-wise discard 
      functions in effect in the receive data direction at this connection 
      point.
      
      A value of ppd indicates that the Partial Packet Discard (PPD) 
      function is in effect. PPD may be applied at an intermediate 
      connecting point for a connection which is transporting frame traffic 
      (AAL5 at the endpoint). PPD is controlled by provisioning for 
      PVCs and SPVCs, and by call setup parameters in the AAL and 
      Traffic Descriptor Information Elements.
      
      A value of epd indicates that the Early Packet Discard (EPD) 
      function is in effect at this connection endpoint. PPD and EPD are 
      enabled by default at a connection endpoint which is performing 
      AAL5 segmentation and assembly.
      
      On ATM IP cards, all packet-wise discard functions also apply to 
      provisioned virtual path connections (VPCs). On CQC-based ATM 
      cards, packet-wise functions are not applicable for VPCs.
      
      This attribute is not applicable for Vpts.

      Description of bits:
      ppd(0)
      epd(1)"
::= { mscAtmIfVptVccTmOperEntry 86 }

mscAtmIfVptVccTmBandwidthElastic OBJECT-TYPE
   SYNTAX     INTEGER  {
                 no(0),
                 yes(1) }
   ACCESS     read-only
   STATUS     mandatory
   DESCRIPTION
     "This attribute is only of importance for connections which are 
      carried on a link with a variable bandwidth. For example, the 
      bandwidth may be reduced in the event that one or more physical 
      links in the IMA group fail, such that the originally requested 
      bandwidth cannot be maintained. This attribute shows whether the 
      application (for example, Trunk) running on this connection can 
      continue to operate if the bandwidth is reduced. If the bandwidth is 
      reduced, the amount by which it is reduced is displayed in the 
      bandwidthReduction attribute. 
      
      A value of yes, indicates that this connection is elastic, and the 
      bandwidth may be reduced but the connection is not released. 
      
      A value of no indicates that the bandwidth for this connection is not 
      reduced in the event of link bandwidth reduction. However, this 
      connection may be released based on its holdingPriority.
      
      Bandwidth elasticity has no effect for connections which have an 
      equivalent cell rate (ECR) of zero. 
      
      This attribute is not applicable for Vpts and Vpt Vccs."
::= { mscAtmIfVptVccTmOperEntry 90 }

mscAtmIfVptVccTmBandwidthReduction OBJECT-TYPE
   SYNTAX     Unsigned32 (0..2147483647)
   ACCESS     read-only
   STATUS     mandatory
   DESCRIPTION
     "This attribute shows the amount by which the bandwidth has been 
      reduced for this connection. This value is non-zero only for 
      connections which have bandwidthElastic displayed as yes, and 
      which are also operating in a reduced bandwidth mode. This is 
      typically the case for selected connections running over an IMA 
      link. This attribute takes a value from 0 (no reduction) up to the 
      ECR. For all connections which are running at their full allocated 
      bandwidth, bwReduction has the value 0. Connections which have 
      been reduced in allocated bandwidth have a positive number for this 
      attribute. The bwReduction may be subtracted from the ECR (which 
      is displayed as txTrafficDescParm 5) to determine the actual 
      bandwidth allocated to this connection."
::= { mscAtmIfVptVccTmOperEntry 100 }

mscAtmIfVptVccTmAbrConnectionType OBJECT-TYPE
   SYNTAX     INTEGER  {
                 erSwitch(1),
                 efciSwitch(2),
                 virtualSourceDest(3),
                 sourceDest(4),
                 nonAbrInterworking(5),
                 notApplicable(15) }
   ACCESS     read-only
   STATUS     mandatory
   DESCRIPTION
     "This attribute indicates the type of ABR behavior which is in effect 
      at this connection. This attribute is only applicable if the 
      atmServiceCategory attribute is availableBitRate. If the 
      atmServiceCategory attribute is not availableBitRate, this attribute 
      value is set to notApplicable.
      
      For CQC-based ATM cards and the 1pOC12SmLrAtm card, the 
      notApplicable, efciSwitch or nonAbrInterworking. In EFCI 
      marking mode, the Explicit Forward Congestion Indication (EFCI) 
      field in the data cell headers is used to indicate transmit queue 
      congestion. 
      
      For ATM IP cards other than 1pOC12SmLrAtm, if the displayed as 
      connectionEndPoint, this attribute has the value sourceDest. In this 
      mode, the ABR Source and Destination behavior is in effect at this 
      connection. This attribute is also sourceDest in the case where the 
      next hop connection is specified as nonAbrInterworking. The next 
      hop connection is the Vcc or Vpc identified by the nextHop attribute 
      of the Nrp or Rp component. 
      
      If the connectionPointType is not connectionEndPoint, the value of 
      this attribute depends upon the abrConnectionType provisioning 
      and the card type to which the traffic is forwarded on the backplane. 
      The default abrConnectionType is provisioned at the CA Abr 
      abrConnectionType attribute, and may be overridden for a 
      provisioned connection in the Vcd Tm abrConnectionType or Vpd 
      Tm abrConnectionType attribute. If the CA Abr abrConnectionType 
      attribute is virtualSourceDest at either one of the two connection 
      points, and if both the connection points are defined on ATM IP 
      cards, virtual source and destination behavior is applied to the 
      connection. In this instance, the attribute displays the value 
      virtualSourceDest.
      
      This attribute has the value erSwitch if ABR explicit rate 
      functionality is in effect at this connection. In this mode, the switch 
      may modify the Explicit Rate (ER) field of backward Resource 
      Management (RM) cells to indicate the status of congestion at this 
      connection point.
      
      This attribute has the value nonAbrInterworking in the case where 
      this connection point is functioning as an SPVC origin for an ABR 
      connection where the link side of this connection is configured as a 
      non-ABR ATM service category. This means that there are no RM 
      cells on the link side of this connection, and that the next hop 
      connection point is performing as an ABR sourceDest."
::= { mscAtmIfVptVccTmOperEntry 110 }

mscAtmIfVptVccTmTxTdpTable OBJECT-TYPE
   SYNTAX     SEQUENCE OF MscAtmIfVptVccTmTxTdpEntry
   ACCESS     not-accessible
   STATUS     mandatory
   DESCRIPTION
     "This attribute is a vector of five transmit traffic parameters whose 
      mapping is defined by the txTrafficDescType attribute. 
      
      The values of peak cell rate (PCR), sustained cell rate (SCR), 
      Minimum Cell Rate (MCR), actual cell rate (ACR), explicit rate 
      (ER), equivalent cell rate (ECR), and actual shaping rate are 
      expressed in cell/s. Maximum burst size (MBS) is expressed in 
      cells. CDVT is expressed in microseconds. 
      
      When txTrafficDescType is 1 or 2, parameters 1 through 5 are 
      unused.
      
      In this description, PCR is the greater of either the PCR or the 
      requested shaping rate (parameter 1 or parameter 5) specified in the 
      txTrafficDescParm attribute under the Vcd Tm or Vpd Tm 
      component.
      
      When txTrafficDescType is 3, parameter 1 represents the PCR for 
      CLP equal to 0 or 1 traffic; parameters 2 and 3 are unused.
      
      When txTrafficDescType is 4, parameter 1 represents the PCR for 
      CLP equal to 0 and 1 traffic; parameter 2 represents the PCR for 
      CLP equal to 0 traffic with cell discard.
      
      When txTrafficDescType is 5, parameter 1 represents the PCR for 
      CLP equal to 0 and 1 traffic; parameter 2 represents the PCR for 
      CLP equal to 0 traffic with cell tagging.
      
      When txTrafficDescType is 6, parameter 1 represents the PCR for 
      CLP equal to 0 and 1 traffic; parameter 2 represents the SCR for 
      CLP equal to 0 and 1 traffic; parameter 3 represents the MBS for 
      CLP equal to 0 and 1 traffic.
      
      When txTrafficDescType is 7, parameter 1 represents the PCR for 
      CLP equal to 0 and 1 traffic; parameter 2 represents the SCR for 
      CLP equal to 0 traffic with cell discard; parameter 3 represents the 
      MBS for CLP equal to 0 traffic.
      
      When txTrafficDescType is 8, parameter 1 represents the PCR for 
      CLP equal to 0 and 1 traffic; parameter 2 represents the SCR for 
      CLP equal to 0 traffic with cell tagging; parameter 3 represents the 
      MBS for CLP equal to 0 traffic.
      
      When txTrafficDescType is 3, 4, 5, 6, 7, or 8, parameter 4 reflects 
      the actual shaping rate in cell/s for this connection. For CQC-based 
      ATM cards, the set of available shaping rates is based on the 
      number of interfaces doing shaping (attribute 
      perVcQueueInterfaces), and the shapingScalingFactor attribute of 
      the Arc Cqc Override component. A rate of zero (0) indicates that 
      shaping is not performed, or that the interface is down. 
      
      When txTrafficDescType is 9, parameter 1 represents the PCR; 
      parameter 2 represents the Cell Delay Variation Toleration (CDVT); 
      parameter 3 represents the Minimum Cell Rate (MCR); the meaning 
      of parameter 4 depends upon the value of the abrConnectionType 
      attribute. if abrConnectionType is sourceDest or 
      virtualSourceDest, parameter 4 represents the Allowed Cell Rate 
      (ACR); If abrConnectionType is erSwitch, parameter 4 represents 
      the Explicit Rate (ER); and if abrConnectionType is efciSwitch, 
      parameter 4 reflects the actual shaping rate in cell/s for this 
      connection.
      
      When txTrafficDescType is 3, 4, 5, 6, 7, 8, or 9, parameter 5 reflects 
      the equivalent cell rate in cell/s for this connection as determined by 
      the Connection Admission Control (CAC) algorithm. The 
      equivalent cell rate is useful in determining the admission 
      characteristics of this connection."
::= { mscAtmIfVptVccTm 451 }

mscAtmIfVptVccTmTxTdpEntry OBJECT-TYPE
   SYNTAX     MscAtmIfVptVccTmTxTdpEntry
   ACCESS     not-accessible
   STATUS     mandatory
   DESCRIPTION
     "An entry in the mscAtmIfVptVccTmTxTdpTable."
   INDEX {
      mscAtmIfIndex,
      mscAtmIfVptIndex,
      mscAtmIfVptVccIndex,
      mscAtmIfVptVccTmIndex,
      mscAtmIfVptVccTmTxTdpIndex }
::= { mscAtmIfVptVccTmTxTdpTable 1 }

MscAtmIfVptVccTmTxTdpEntry ::= SEQUENCE {
   mscAtmIfVptVccTmTxTdpIndex
      Integer32,
   mscAtmIfVptVccTmTxTdpValue
      Unsigned32 }

mscAtmIfVptVccTmTxTdpIndex OBJECT-TYPE
   SYNTAX     Integer32 (1..5)
   ACCESS     not-accessible
   STATUS     mandatory
   DESCRIPTION
     "This variable represents the mscAtmIfVptVccTmTxTdpTable
      specific index for the mscAtmIfVptVccTmTxTdpTable."
::= { mscAtmIfVptVccTmTxTdpEntry 1 }

mscAtmIfVptVccTmTxTdpValue OBJECT-TYPE
   SYNTAX     Unsigned32 (0..2147483647)
   ACCESS     read-only
   STATUS     mandatory
   DESCRIPTION
     "This variable represents an individual value for the
      mscAtmIfVptVccTmTxTdpTable."
::= { mscAtmIfVptVccTmTxTdpEntry 2 }

mscAtmIfVptVccTmTxQThreshTable OBJECT-TYPE
   SYNTAX     SEQUENCE OF MscAtmIfVptVccTmTxQThreshEntry
   ACCESS     not-accessible
   STATUS     mandatory
   DESCRIPTION
     "This attribute indicates the queue limit and the discard thresholds 
      for the transmit queue of this connection. 
      
      If this connection has unshapedTransmitQueueing attribute 
      displayed as common, this attribute displays the thresholds of the 
      common queue. If this connection has unshapedTransmitQueueing 
      attribute displayed as perVc or as notApplicable, this attribute 
      displays the thresholds of the per-VC queue.
      
      The first element indicates the queue limit. The provisioned value of 
      the transmit queue limit is derived from the txQueueLimit attribute 
      under the service category subcomponents of the CA component for 
      the service category of this connection. 
      
      The second element is the threshold that marks the transition from 
      congestion state 1 to congestion state 0. This is the threshold at 
      which traffic with discard priority (DP) = 1 is discarded. This 
      threshold is set at approximately 90 percent of the first parameter, 
      the operational queue limit.
      
      The third element is the threshold that marks the transition from 
      congestion state 2 to congestion state 1. This is the threshold at 
      which traffic with DP = 2 is discarded. This threshold is set at 
      approximately 75 percent of the first parameter, the operational 
      queue limit.
      
      The fourth element is the threshold that marks the transition from 
      congestion state 3 to congestion state 2. This is the threshold at 
      which traffic with DP = 3 is discarded. This threshold is set at 
      approximately 35 percent of the first parameter, the operational 
      queue limit.
      
      This attribute does not apply to basic Vpts."
::= { mscAtmIfVptVccTm 452 }

mscAtmIfVptVccTmTxQThreshEntry OBJECT-TYPE
   SYNTAX     MscAtmIfVptVccTmTxQThreshEntry
   ACCESS     not-accessible
   STATUS     mandatory
   DESCRIPTION
     "An entry in the mscAtmIfVptVccTmTxQThreshTable."
   INDEX {
      mscAtmIfIndex,
      mscAtmIfVptIndex,
      mscAtmIfVptVccIndex,
      mscAtmIfVptVccTmIndex,
      mscAtmIfVptVccTmTxQThreshIndex }
::= { mscAtmIfVptVccTmTxQThreshTable 1 }

MscAtmIfVptVccTmTxQThreshEntry ::= SEQUENCE {
   mscAtmIfVptVccTmTxQThreshIndex
      Integer32,
   mscAtmIfVptVccTmTxQThreshValue
      Unsigned32 }

mscAtmIfVptVccTmTxQThreshIndex OBJECT-TYPE
   SYNTAX     Integer32 (0..3)
   ACCESS     not-accessible
   STATUS     mandatory
   DESCRIPTION
     "This variable represents the mscAtmIfVptVccTmTxQThreshTable
      specific index for the mscAtmIfVptVccTmTxQThreshTable."
::= { mscAtmIfVptVccTmTxQThreshEntry 1 }

mscAtmIfVptVccTmTxQThreshValue OBJECT-TYPE
   SYNTAX     Unsigned32 (0..512000)
   ACCESS     read-only
   STATUS     mandatory
   DESCRIPTION
     "This variable represents an individual value for the
      mscAtmIfVptVccTmTxQThreshTable."
::= { mscAtmIfVptVccTmTxQThreshEntry 2 }

mscAtmIfVptVccTmRxTdpTable OBJECT-TYPE
   SYNTAX     SEQUENCE OF MscAtmIfVptVccTmRxTdpEntry
   ACCESS     not-accessible
   STATUS     mandatory
   DESCRIPTION
     "This attribute is a vector of four traffic parameters whose meanings 
      are defined by the rxTrafficDescType attribute. The values of peak 
      cell rate (PCR), sustained cell rate (SCR), minimum cell rate 
      (MCR) are expressed in cell/s. Maximum burst size (MBS) is 
      expressed in cells. Cell delay variation tolerance (CDVT) is 
      expressed in microseconds.
      
      When rxTrafficDescType is 1 or 2, none of the parameters are used.
      
      When rxTrafficDescType is 3, parameter 1 represents the PCR for 
      CLP equal to 0 and 1 traffic; parameter 4 represents the CDVT.
      
      When rxTrafficDescType is 4, parameter 1 represents the PCR for 
      CLP equal to 0 and 1 traffic; parameter 2 represents the PCR for 
      CLP equal to 0 traffic with cell discard; parameter 4 represents the 
      CDVT.
      
      When rxTrafficDescType is 5, parameter 1 represents the PCR for 
      CLP equal to 0 and 1 traffic; parameter 2 represents the PCR for 
      CLP equal to 0 traffic with cell tagging; parameter 4 represents the 
      CDVT.
      
      When rxTrafficDescType is 6, parameter 1 represents the PCR for 
      CLP equal to 0 and 1 traffic; parameter 2 represents the SCR for 
      CLP equal to 0 and 1 traffic; parameter 3 represents the MBS for 
      CLP equal to 0 and 1 traffic; parameter 4 represents the CDVT. 
      
      When rxTrafficDescType is 7, parameter 1 represents the PCR for 
      CLP equal to 0 and 1 traffic; parameter 2 represents the SCR for 
      CLP equal to 0 traffic with cell discard; parameter 3 represents the 
      MBS for CLP equal to 0 traffic; parameter 4 represents the CDVT.
      
      When rxTrafficDescType is 8, parameter 1 represents the PCR for 
      CLP equal to 0 and 1 traffic; parameter 2 represents the SCR for 
      CLP equal to 0 traffic with cell tagging; parameter 3 represents the 
      MBS for CLP equal to 0 traffic; parameter 4 represents the CDVT. 
      
      When rxTrafficDescType is 9, parameter 1 represents the PCR; 
      parameter 2 represents CDVT; parameter 3 represents the MCR; 
      parameter 4 is not used.
      
      If upc is disabled for this connection, the values of PCR, SCR, 
      MBS and CDVT are the provisioned parameters.
      
      If upc is enabled, the values of PCR, SCR, MBS, and CDVT are 
      exactly the values used by the usage parameter control hardware in 
      policing the arriving traffic. These may vary slightly from the 
      provisioned values due to granularity of the hardware. In the case 
      where the PCR is equal to the SCR, the effective MBS is zero."
::= { mscAtmIfVptVccTm 453 }

mscAtmIfVptVccTmRxTdpEntry OBJECT-TYPE
   SYNTAX     MscAtmIfVptVccTmRxTdpEntry
   ACCESS     not-accessible
   STATUS     mandatory
   DESCRIPTION
     "An entry in the mscAtmIfVptVccTmRxTdpTable."
   INDEX {
      mscAtmIfIndex,
      mscAtmIfVptIndex,
      mscAtmIfVptVccIndex,
      mscAtmIfVptVccTmIndex,
      mscAtmIfVptVccTmRxTdpIndex }
::= { mscAtmIfVptVccTmRxTdpTable 1 }

MscAtmIfVptVccTmRxTdpEntry ::= SEQUENCE {
   mscAtmIfVptVccTmRxTdpIndex
      Integer32,
   mscAtmIfVptVccTmRxTdpValue
      Unsigned32 }

mscAtmIfVptVccTmRxTdpIndex OBJECT-TYPE
   SYNTAX     Integer32 (1..4)
   ACCESS     not-accessible
   STATUS     mandatory
   DESCRIPTION
     "This variable represents the mscAtmIfVptVccTmRxTdpTable
      specific index for the mscAtmIfVptVccTmRxTdpTable."
::= { mscAtmIfVptVccTmRxTdpEntry 1 }

mscAtmIfVptVccTmRxTdpValue OBJECT-TYPE
   SYNTAX     Unsigned32 (0..2147483647)
   ACCESS     read-only
   STATUS     mandatory
   DESCRIPTION
     "This variable represents an individual value for the
      mscAtmIfVptVccTmRxTdpTable."
::= { mscAtmIfVptVccTmRxTdpEntry 2 }

mscAtmIfVptVccTmTqpTable OBJECT-TYPE
   SYNTAX     SEQUENCE OF MscAtmIfVptVccTmTqpEntry
   ACCESS     not-accessible
   STATUS     mandatory
   DESCRIPTION
     "This attribute is a vector of three elements that indicate the quality 
      of service parameters for the forward direction for this connection. 
      This attribute is used for SPVC and SVC connections on a PNNI 
      interface.
      
      The cdv element indicates the acceptable peak-to-peak Cell Delay 
      Variation (CDV) of real-time connections (CBR and rt-VBR). 
      
      The ctd element indicates the acceptable maximum Cell Transfer 
      Delay (maxCtd) of real-time connections (CBR and rt-VBR). 
      
      The clr element indicates the acceptable Cell Loss Ratio (CLR) of 
      CBR, rt-VBR, and nrt-VBR connections."
::= { mscAtmIfVptVccTm 454 }

mscAtmIfVptVccTmTqpEntry OBJECT-TYPE
   SYNTAX     MscAtmIfVptVccTmTqpEntry
   ACCESS     not-accessible
   STATUS     mandatory
   DESCRIPTION
     "An entry in the mscAtmIfVptVccTmTqpTable."
   INDEX {
      mscAtmIfIndex,
      mscAtmIfVptIndex,
      mscAtmIfVptVccIndex,
      mscAtmIfVptVccTmIndex,
      mscAtmIfVptVccTmTqpIndex }
::= { mscAtmIfVptVccTmTqpTable 1 }

MscAtmIfVptVccTmTqpEntry ::= SEQUENCE {
   mscAtmIfVptVccTmTqpIndex
      INTEGER,
   mscAtmIfVptVccTmTqpValue
      Unsigned32 }

mscAtmIfVptVccTmTqpIndex OBJECT-TYPE
   SYNTAX     INTEGER  {
                 cdv(0),
                 ctd(1),
                 clr(2) }
   ACCESS     not-accessible
   STATUS     mandatory
   DESCRIPTION
     "This variable represents the mscAtmIfVptVccTmTqpTable
      specific index for the mscAtmIfVptVccTmTqpTable."
::= { mscAtmIfVptVccTmTqpEntry 1 }

mscAtmIfVptVccTmTqpValue OBJECT-TYPE
   SYNTAX     Unsigned32 (0..2147483647)
   ACCESS     read-only
   STATUS     mandatory
   DESCRIPTION
     "This variable represents an individual value for the
      mscAtmIfVptVccTmTqpTable."
::= { mscAtmIfVptVccTmTqpEntry 2 }

mscAtmIfVptVccTmRqpTable OBJECT-TYPE
   SYNTAX     SEQUENCE OF MscAtmIfVptVccTmRqpEntry
   ACCESS     not-accessible
   STATUS     mandatory
   DESCRIPTION
     "This attribute is a vector of three elements that indicate the quality 
      of service parameters for the backward direction for this 
      connection. This attribute is used for SPVC and SVC connections 
      on a PNNI interface.
      
      The cdv element indicates the acceptable peak-to-peak Cell Delay 
      Variation (CDV) of real-time connections (CBR and rt-VBR). 
      
      The ctd element indicates the acceptable maximum Cell Transfer 
      Delay (maxCtd) of real-time connections (CBR and rt-VBR). 
      
      The clr element indicates the acceptable Cell Loss Ratio (CLR) of 
      CBR, rt-VBR, and nrt-VBR connections."
::= { mscAtmIfVptVccTm 455 }

mscAtmIfVptVccTmRqpEntry OBJECT-TYPE
   SYNTAX     MscAtmIfVptVccTmRqpEntry
   ACCESS     not-accessible
   STATUS     mandatory
   DESCRIPTION
     "An entry in the mscAtmIfVptVccTmRqpTable."
   INDEX {
      mscAtmIfIndex,
      mscAtmIfVptIndex,
      mscAtmIfVptVccIndex,
      mscAtmIfVptVccTmIndex,
      mscAtmIfVptVccTmRqpIndex }
::= { mscAtmIfVptVccTmRqpTable 1 }

MscAtmIfVptVccTmRqpEntry ::= SEQUENCE {
   mscAtmIfVptVccTmRqpIndex
      INTEGER,
   mscAtmIfVptVccTmRqpValue
      Unsigned32 }

mscAtmIfVptVccTmRqpIndex OBJECT-TYPE
   SYNTAX     INTEGER  {
                 cdv(0),
                 ctd(1),
                 clr(2) }
   ACCESS     not-accessible
   STATUS     mandatory
   DESCRIPTION
     "This variable represents the mscAtmIfVptVccTmRqpTable
      specific index for the mscAtmIfVptVccTmRqpTable."
::= { mscAtmIfVptVccTmRqpEntry 1 }

mscAtmIfVptVccTmRqpValue OBJECT-TYPE
   SYNTAX     Unsigned32 (0..2147483647)
   ACCESS     read-only
   STATUS     mandatory
   DESCRIPTION
     "This variable represents an individual value for the
      mscAtmIfVptVccTmRqpTable."
::= { mscAtmIfVptVccTmRqpEntry 2 }


-- AtmIf/n Vpc/vpi Tm AvailableBitRate, 
-- AtmIf/n Vcc/vpi.vci Tm AvailableBitRate,
-- AtmIf/n Vpt/vpi Tm AvailableBitRate,
-- AtmIf/n Vpt/vpi Vcc/vci Tm AvailableBitRate
-- This component contains ABR-related operational attributes of a 
-- connection. It is dynamically created for connections where the 
-- atmServiceCategory is availableBitRate, and where 
-- abrConnectionType is sourceDest or virtualSourceDest.

mscAtmIfVptVccTmAbr OBJECT IDENTIFIER ::= { mscAtmIfVptVccTm 2 }



mscAtmIfVptVccTmAbrRowStatusTable OBJECT-TYPE
   SYNTAX     SEQUENCE OF MscAtmIfVptVccTmAbrRowStatusEntry
   ACCESS     not-accessible
   STATUS     mandatory
   DESCRIPTION
     "This entry controls the addition and deletion of 
      mscAtmIfVptVccTmAbr components."
::= { mscAtmIfVptVccTmAbr 1 }

mscAtmIfVptVccTmAbrRowStatusEntry OBJECT-TYPE
   SYNTAX     MscAtmIfVptVccTmAbrRowStatusEntry
   ACCESS     not-accessible
   STATUS     mandatory
   DESCRIPTION
     "A single entry in the table represents a single 
      mscAtmIfVptVccTmAbr component."
   INDEX {
      mscAtmIfIndex,
      mscAtmIfVptIndex,
      mscAtmIfVptVccIndex,
      mscAtmIfVptVccTmIndex,
      mscAtmIfVptVccTmAbrIndex }
::= { mscAtmIfVptVccTmAbrRowStatusTable 1 }

MscAtmIfVptVccTmAbrRowStatusEntry ::= SEQUENCE {
   mscAtmIfVptVccTmAbrRowStatus
      RowStatus,
   mscAtmIfVptVccTmAbrComponentName
      DisplayString,
   mscAtmIfVptVccTmAbrStorageType
      StorageType,
   mscAtmIfVptVccTmAbrIndex
      NonReplicated }

mscAtmIfVptVccTmAbrRowStatus OBJECT-TYPE
   SYNTAX     RowStatus 
   ACCESS     read-only
   STATUS     mandatory
   DESCRIPTION
     "This variable is used as the basis for SNMP naming of
      mscAtmIfVptVccTmAbr components.
      These components cannot be added nor deleted."
::= { mscAtmIfVptVccTmAbrRowStatusEntry 1 }

mscAtmIfVptVccTmAbrComponentName OBJECT-TYPE
   SYNTAX     DisplayString 
   ACCESS     read-only
   STATUS     mandatory
   DESCRIPTION
     "This variable provides the component's string name for
      use with the ASCII Console Interface"
::= { mscAtmIfVptVccTmAbrRowStatusEntry 2 }

mscAtmIfVptVccTmAbrStorageType OBJECT-TYPE
   SYNTAX     StorageType 
   ACCESS     read-only
   STATUS     mandatory
   DESCRIPTION
     "This variable represents the storage type value for the
      mscAtmIfVptVccTmAbr tables."
::= { mscAtmIfVptVccTmAbrRowStatusEntry 4 }

mscAtmIfVptVccTmAbrIndex OBJECT-TYPE
   SYNTAX     NonReplicated 
   ACCESS     not-accessible
   STATUS     mandatory
   DESCRIPTION
     "This variable represents the index for the mscAtmIfVptVccTmAbr tables."
::= { mscAtmIfVptVccTmAbrRowStatusEntry 10 }

mscAtmIfVptVccTmAbrOperTable OBJECT-TYPE
   SYNTAX     SEQUENCE OF MscAtmIfVptVccTmAbrOperEntry
   ACCESS     not-accessible
   STATUS     mandatory
   DESCRIPTION
     "This group contains operational attributes for connections using 
      ABR service category."
::= { mscAtmIfVptVccTmAbr 110 }

mscAtmIfVptVccTmAbrOperEntry OBJECT-TYPE
   SYNTAX     MscAtmIfVptVccTmAbrOperEntry
   ACCESS     not-accessible
   STATUS     mandatory
   DESCRIPTION
     "An entry in the mscAtmIfVptVccTmAbrOperTable."
   INDEX {
      mscAtmIfIndex,
      mscAtmIfVptIndex,
      mscAtmIfVptVccIndex,
      mscAtmIfVptVccTmIndex,
      mscAtmIfVptVccTmAbrIndex }
::= { mscAtmIfVptVccTmAbrOperTable 1 }

MscAtmIfVptVccTmAbrOperEntry ::= SEQUENCE {
   mscAtmIfVptVccTmAbrInitialCellRate
      Unsigned32,
   mscAtmIfVptVccTmAbrTransientBufferExposure
      Unsigned32,
   mscAtmIfVptVccTmAbrFixedRoundTripTime
      Unsigned32,
   mscAtmIfVptVccTmAbrRateDecreaseFactor
      Unsigned32,
   mscAtmIfVptVccTmAbrRateIncreaseFactor
      Unsigned32,
   mscAtmIfVptVccTmAbrMaxCellPerRmCell
      Unsigned32,
   mscAtmIfVptVccTmAbrMaxTimeBetweenRmCell
      Unsigned32,
   mscAtmIfVptVccTmAbrCutoffDecreaseFactor
      Unsigned32,
   mscAtmIfVptVccTmAbrAcrDecreaseTimeFactor
      Unsigned32,
   mscAtmIfVptVccTmAbrForwardRmCellLimit
      Unsigned32,
   mscAtmIfVptVccTmAbrTxRateChangeInfo
      INTEGER,
   mscAtmIfVptVccTmAbrAcrRateChangeInfo
      INTEGER,
   mscAtmIfVptVccTmAbrTxFwdRmCells
      Unsigned32,
   mscAtmIfVptVccTmAbrRxEfci
      INTEGER }

mscAtmIfVptVccTmAbrInitialCellRate OBJECT-TYPE
   SYNTAX     Unsigned32 (0..16777215)
   ACCESS     read-only
   STATUS     mandatory
   DESCRIPTION
     "This attribute indicates the Initial Cell Rate (ICR) parameter for this 
      connection. ICR is the rate at which a source should send initially 
      and after an idle period.
      
      For nailed-up connections, this attribute is determined by the 
      provisioned value of the initialCellRate attribute. For signalled 
      connections, it is indicated in the ABR Setup Parameters 
      Information Element.
      
      The ICR for a connection is a value between the MCR and the PCR. 
      Furthermore, ICR has an upper bound determined by the 
      transientBufferExposure divided by fixedRoundTripTime."
::= { mscAtmIfVptVccTmAbrOperEntry 10 }

mscAtmIfVptVccTmAbrTransientBufferExposure OBJECT-TYPE
   SYNTAX     Unsigned32 (0..16777215)
   ACCESS     read-only
   STATUS     mandatory
   DESCRIPTION
     "This attribute indicates the Transient Buffer Exposure (TBE) for 
      this connection. TBE is the negotiated number of cells that the 
      network would like to limit the resource to send during start-up 
      periods, before the first Resource Management (RM) cell returns.
      
      For nailed-up connections, this attribute is determined by the 
      provisioned value of the transientBufferExposure attribute. For 
      signalled connections, it is indicated in the ABR Setup Parameters 
      Information Element."
::= { mscAtmIfVptVccTmAbrOperEntry 11 }

mscAtmIfVptVccTmAbrFixedRoundTripTime OBJECT-TYPE
   SYNTAX     Unsigned32 (0..16700000)
   ACCESS     read-only
   STATUS     mandatory
   DESCRIPTION
     "This attribute indicates the Fixed Round-Trip Time (FRTT) 
      parameter for this connection. FRTT is the sum of the fixed and 
      propagation delays from the source to a destination and back.
      
      For nailed-up connections, this attribute is determined by the 
      provisioned value of the fixedRoundTripTime attribute. For 
      signalled connections, it is indicated in the ABR Setup Parameters 
      Information Element."
::= { mscAtmIfVptVccTmAbrOperEntry 12 }

mscAtmIfVptVccTmAbrRateDecreaseFactor OBJECT-TYPE
   SYNTAX     Unsigned32 (0..15)
   ACCESS     read-only
   STATUS     mandatory
   DESCRIPTION
     "This attribute indicates the Rate Decrease Factor (RDF) for this 
      connection. The RDF value is computed by using the operational 
      value of this attribute, n, as 2 to the inverse power n. For example, if 
      the value of this attribute is 8, RDF is 2E-8 = 1/256.
      
      RDF controls the amount by which the cell transmission rate may 
      decrease upon receipt of a backward Resource Management (RM) 
      cell. For example, if a backward RM cell is received with the 
      Congestion Indication (CI) field set to 1, the Allowed Cell Rate 
      (ACR) value would be reduced by the amount (RDF*ACR). The 
      ACR is not allowed to fall below the Minimum Cell Rate (MCR), in 
      which case the ACR is set to MCR.
      
      For nailed-up connections, this attribute is determined by the 
      provisioned value of the rateDecreaseFactor attribute. For signalled 
      connections, it is indicated in the ABR Setup Parameters 
      Information Element."
::= { mscAtmIfVptVccTmAbrOperEntry 13 }

mscAtmIfVptVccTmAbrRateIncreaseFactor OBJECT-TYPE
   SYNTAX     Unsigned32 (0..15)
   ACCESS     read-only
   STATUS     mandatory
   DESCRIPTION
     "This attribute indicates the Rate Increase Factor (RIF) for this 
      connection. The RIF value is computed by using the operational 
      value of this attribute, n, as 2 to the inverse power n. For example, if 
      the value of this attribute is 6, RIF is 2E-6 = 1/64.
      
      RIF controls the amount by which the cell transmission rate may 
      increase upon receipt of a backward Resource Management (RM) 
      cell. For example, if a backward RM cell is received with the 
      Congestion Indication (CI) and the No Increase (NI) fields both set 
      to 0, the Allowed Cell Rate (ACR) value would be increased by the 
      amount (RIF*ACR). The ACR is not allowed to exceed the Peak 
      Cell Rate (PCR), in which case the ACR is set to PCR.
      
      For nailed-up connections, this attribute is determined by the 
      provisioned value of the rateIncreaseFactor attribute. For signalled 
      connections, it is indicated in the ABR Setup Parameters 
      Information Element."
::= { mscAtmIfVptVccTmAbrOperEntry 14 }

mscAtmIfVptVccTmAbrMaxCellPerRmCell OBJECT-TYPE
   SYNTAX     Unsigned32 (2 | 4 | 8 | 16 | 32 | 64 | 128 | 256)
   ACCESS     read-only
   STATUS     mandatory
   DESCRIPTION
     "This attribute indicates the maximum number of cells an ABR 
      source may transmit for each forward Resource Management (RM) 
      cell. The count of the cells transmitted includes data cells, OAM 
      cells, backward RM cells, and the forward RM cell.
      
      For nailed-up connections, this attribute is determined by the 
      provisioned value of the maxCellsPerRmCell attribute. For 
      signalled connections, it is indicated in the ABR Additional 
      Parameters Information Element."
::= { mscAtmIfVptVccTmAbrOperEntry 15 }

mscAtmIfVptVccTmAbrMaxTimeBetweenRmCell OBJECT-TYPE
   SYNTAX     Unsigned32 (781 | 1563 | 3125 | 6250 | 12500 | 25000 | 50000 | 100000)
   ACCESS     read-only
   STATUS     mandatory
   DESCRIPTION
     "This attribute indicates the TRM parameter for this connection.
      
      TRM provides an upper bound on the time interval between forward 
      Resource Management (RM) cells for an ABR source. Since the last 
      forward RM cell was sent, if at least TRM time has elapsed since 
      and at least 2 other cells have been sent, the next cell to be 
      transmitted would be a forward RM cell.
      
      For nailed-up connections, this attribute is determined by the 
      provisioned value of the maxTimeBetweenRmCell attribute. For 
      signalled connections, it is indicated in the ABR Additional 
      Parameters Information Element."
::= { mscAtmIfVptVccTmAbrOperEntry 16 }

mscAtmIfVptVccTmAbrCutoffDecreaseFactor OBJECT-TYPE
   SYNTAX     Unsigned32 (0 | 1 | 2 | 4 | 8 | 16 | 32 | 64)
   ACCESS     read-only
   STATUS     mandatory
   DESCRIPTION
     "This attribute indicates the Cutoff Decrease Factor (CDF) parameter 
      for this connection. When the value of this attribute is non-zero, 
      CDF is computed as the inverse of the value. For example, if the 
      value is 32, the value of CDF is 1/32. When the value of this 
      attribute is 0, CDF is also zero.
      
      CDF controls the decrease in the Allowed Cell Rate (ACR) 
      associated with the forwardRmCellLimit attribute, the limit of the 
      number of forward Resource Management (RM) cells which may 
      be sent in the absence of received backward RM cells. When this 
      limit is crossed, the ACR value would be decreased by the amount 
      (CDF*ACR). The ACR is not allowed to fall below the Minimum 
      Cell Rate (MCR), in which case the ACR is set to MCR.
      
      For nailed-up connections, this attribute is determined by the 
      provisioned value of the cutoffDecreaseFactor attribute. For 
      signalled connections, it is indicated in the ABR Additional 
      Parameters Information Element."
::= { mscAtmIfVptVccTmAbrOperEntry 17 }

mscAtmIfVptVccTmAbrAcrDecreaseTimeFactor OBJECT-TYPE
   SYNTAX     Unsigned32 (0..1023)
   ACCESS     read-only
   STATUS     mandatory
   DESCRIPTION
     "This attribute indicates the Allowed Cell Rate Decrease Time Factor 
      (ADTF) parameter for this connection.
      
      ADTF is the time interval permitted between sending forward 
      Resource Management (RM) cells before the Allowed Cell Rate 
      (ACR) is decreased to initialCellRate. In other words, if the source 
      does not transit a forward RM cell for the period specified by adtf, it 
      reduces its ACR to the value of its initialCellRate.
      
      For nailed-up connections, this attribute is determined by the 
      provisioned value of the acrDecreaseTimeFactor attribute. For 
      signalled connections, it is indicated in the ABR Additional 
      Parameters Information Element."
::= { mscAtmIfVptVccTmAbrOperEntry 18 }

mscAtmIfVptVccTmAbrForwardRmCellLimit OBJECT-TYPE
   SYNTAX     Unsigned32 (1 | 3 | 7 | 15 | 31 | 63 | 127 | 255 | 511 | 1023 | 2047 | 4095)
   ACCESS     read-only
   STATUS     mandatory
   DESCRIPTION
     "This attribute indicates the CRM parameter for this connection.
      
      CRM is the limit of the number of forward Resource Management 
      (RM) cells which may be sent in the absence of received backward 
      RM cells. When this limit is crossed, the Allowed Cell Rate (ACR) 
      value would be decreased by the amount (CDF*ACR), where CDF 
      is determined by the cutoffDecreaseFactor. The ACR is not allowed 
      to fall below the Minimum Cell Rate (MCR), in which case the 
      ACR is set to MCR.
      
      The value of CRM is obtained as transientBufferExposure divided 
      by maxCellsPerRmCell."
::= { mscAtmIfVptVccTmAbrOperEntry 19 }

mscAtmIfVptVccTmAbrTxRateChangeInfo OBJECT-TYPE
   SYNTAX     INTEGER  {
                 congestionIndicated(0),
                 noIncreaseIndicated(1),
                 explicitRateIndicated(2) }
   ACCESS     read-only
   STATUS     mandatory
   DESCRIPTION
     "This attribute indicates the rate change information put into the last 
      forward Resource Management (RM) cell turned around as a 
      backward-RM cell. For connections configured as an ABR Source 
      or Destination, the turned around backward-RM cell is sent over the 
      interface. For connections configured as an ABR Virtual Source or 
      Virtual Destination, the turned around backward-RM cell is sent 
      over the backplane."
::= { mscAtmIfVptVccTmAbrOperEntry 20 }

mscAtmIfVptVccTmAbrAcrRateChangeInfo OBJECT-TYPE
   SYNTAX     INTEGER  {
                 noChange(0),
                 decreasedByRdf(1),
                 increasedByRif(2),
                 setToExplicitRate(3),
                 notApplicable(15) }
   ACCESS     read-only
   STATUS     mandatory
   DESCRIPTION
     "This attribute indicates the type of change in the Allowed Cell Rate 
      (ACR) as a result of the information in the last backward Resource 
      Management (B-RM) cell received from the interface.
      
      This attribute value is only applicable when the Vcc Tm or Vpc Tm 
      abrConnectionType attribute is sourceDest or VirtualSourceDest. 
      In all other cases, this attribute value is notApplicable.
      
      A value of noChange indicates that the rate did not change as a 
      result of the last backward RM cell received.
      
      A value of decreasedByRdf or increasedByRif indicates that the 
      ACR was increased or decreased by the corresponding factor. This 
      change is as a result of the CI or NI bit setting in the last backward 
      RM cell, or an ADTF timeout.
      
      A value of setToExplicitRate indicates that the ACR was set to the 
      ER value in the last backward RM cell."
::= { mscAtmIfVptVccTmAbrOperEntry 21 }

mscAtmIfVptVccTmAbrTxFwdRmCells OBJECT-TYPE
   SYNTAX     Unsigned32 (0..4095)
   ACCESS     read-only
   STATUS     mandatory
   DESCRIPTION
     "This attribute counts the number of forward Resource Management 
      (RM) cells sent over the interface since the last backward RM-cell 
      was received from the interface. If the value of this attribute is 
      greater than or equal to the value of forwardRmCellLimit, the 
      Allowed Cell Rate (ACR) value would be decreased by the amount 
      (CDF*ACR), where CDF is determined by the 
      cutoffDecreaseFactor.
      
      This counter is reset to zero each time a backward-RM cell is 
      received.
      
      This counter does not wrap to zero if it reaches its maximum value 
      of 4095 in order to indicate that no backward RM cell has been 
      received."
::= { mscAtmIfVptVccTmAbrOperEntry 22 }

mscAtmIfVptVccTmAbrRxEfci OBJECT-TYPE
   SYNTAX     INTEGER  {
                 notIndicated(0),
                 indicated(1) }
   ACCESS     read-only
   STATUS     mandatory
   DESCRIPTION
     "This attribute indicates the value of the Explicit Forward 
      Congestion Indication (EFCI) bit of the last data cell received from 
      the interface.
      
      When a forward Resource Management (RM) cell is turned around 
      as a backward-RM cell, the Congestion Indication (CI) field of the 
      backward-RM cell is set to 1, if the value of this attribute is 
      indicated.
      
      This attribute is set to notIndicated each time a backward-RM cell 
      is transmitted."
::= { mscAtmIfVptVccTmAbrOperEntry 23 }


-- AtmIf/n EmissionPriority/n 
-- This component controls the characteristics of an emission priority 
-- for an AtmIf. This component is optional on ATM IP FPs. It is not 
-- permitted on CQC-based ATM FPs.
-- 
-- On ATM IP FPs, there are eight emission priorities (EP). EP 0 is the 
-- highest priority and EP 7 is the lowest priority. Normally, link 
-- bandwidth is allocated in strict precedence of emission priority. All 
-- traffic at EP 0 is transmitted on the link first. Then, when there is an 
-- unused cell opportunity, a cell from EP 1 is transmitted. When EP 0 
-- and 1 have nothing to send, then EP 2 gets the transmit cell 
-- opportunities. Each emission priority 2 through 7 has a 
-- corresponding Ep component with instance number 2 through 7. 
-- Emission priorities 0 and 1 do not have corresponding Ep 
-- components since there is no configuration which is relevant for 
-- those EPs. 
-- 
-- Traffic is associated with an EP in the following way. Each Vcc or 
-- Vpc has an associated atmServiceCategory. Under the AtmIf 
-- component there is a service category component which provides 
-- default characteristics for that service category. For example, AtmIf/
-- n CA Cbr/0 defines the default characteristics for connections of the 
-- CBR service category. Each service category has an 
-- emissionPriority (ep) attribute, for example AtmIf/n CA Cbr/0 ep. 
-- The value provisioned in that ep attribute maps to the corresponding 
-- EP component. If AtmIf/n CA Cbr/0 ep is specified as 2, CBR is 
-- associated with AtmIf/n Ep/2. 
-- 
-- EP 0 and EP 1 are in the absolute priority range. Traffic in the 
-- absolute priority range always gets first choice for a transmit cell 
-- opportunity. EP 2 through EP 7 are in the guaranteed bandwidth 
-- range. Traffic at EP 3 through EP 7 in the guaranteed bandwidth 
-- range may achieve a priority which is different from the strict 
-- hierarchical priority, if a minimum bandwidth guarantee is 
-- provisioned for an Ep. 

mscAtmIfEp OBJECT IDENTIFIER ::= { mscAtmIf 10 }



mscAtmIfEpRowStatusTable OBJECT-TYPE
   SYNTAX     SEQUENCE OF MscAtmIfEpRowStatusEntry
   ACCESS     not-accessible
   STATUS     mandatory
   DESCRIPTION
     "This entry controls the addition and deletion of 
      mscAtmIfEp components."
::= { mscAtmIfEp 1 }

mscAtmIfEpRowStatusEntry OBJECT-TYPE
   SYNTAX     MscAtmIfEpRowStatusEntry
   ACCESS     not-accessible
   STATUS     mandatory
   DESCRIPTION
     "A single entry in the table represents a single 
      mscAtmIfEp component."
   INDEX {
      mscAtmIfIndex,
      mscAtmIfEpIndex }
::= { mscAtmIfEpRowStatusTable 1 }

MscAtmIfEpRowStatusEntry ::= SEQUENCE {
   mscAtmIfEpRowStatus
      RowStatus,
   mscAtmIfEpComponentName
      DisplayString,
   mscAtmIfEpStorageType
      StorageType,
   mscAtmIfEpIndex
      Integer32 }

mscAtmIfEpRowStatus OBJECT-TYPE
   SYNTAX     RowStatus 
   ACCESS     read-write
   STATUS     mandatory
   DESCRIPTION
     "This variable is used as the basis for SNMP naming of
      mscAtmIfEp components.
      These components can be added and deleted."
::= { mscAtmIfEpRowStatusEntry 1 }

mscAtmIfEpComponentName OBJECT-TYPE
   SYNTAX     DisplayString 
   ACCESS     read-only
   STATUS     mandatory
   DESCRIPTION
     "This variable provides the component's string name for
      use with the ASCII Console Interface"
::= { mscAtmIfEpRowStatusEntry 2 }

mscAtmIfEpStorageType OBJECT-TYPE
   SYNTAX     StorageType 
   ACCESS     read-only
   STATUS     mandatory
   DESCRIPTION
     "This variable represents the storage type value for the
      mscAtmIfEp tables."
::= { mscAtmIfEpRowStatusEntry 4 }

mscAtmIfEpIndex OBJECT-TYPE
   SYNTAX     Integer32 (2..7)
   ACCESS     not-accessible
   STATUS     mandatory
   DESCRIPTION
     "This variable represents the index for the mscAtmIfEp tables."
::= { mscAtmIfEpRowStatusEntry 10 }

mscAtmIfEpProvTable OBJECT-TYPE
   SYNTAX     SEQUENCE OF MscAtmIfEpProvEntry
   ACCESS     not-accessible
   STATUS     mandatory
   DESCRIPTION
     "This group contains provisioned attributes which specify the 
      behavior of an emission priority for the ATM interface."
::= { mscAtmIfEp 100 }

mscAtmIfEpProvEntry OBJECT-TYPE
   SYNTAX     MscAtmIfEpProvEntry
   ACCESS     not-accessible
   STATUS     mandatory
   DESCRIPTION
     "An entry in the mscAtmIfEpProvTable."
   INDEX {
      mscAtmIfIndex,
      mscAtmIfEpIndex }
::= { mscAtmIfEpProvTable 1 }

MscAtmIfEpProvEntry ::= SEQUENCE {
   mscAtmIfEpMinimumBandwidthGuarantee
      Unsigned32 }

mscAtmIfEpMinimumBandwidthGuarantee OBJECT-TYPE
   SYNTAX     Unsigned32 (0 | 1..100)
   ACCESS     read-write
   STATUS     mandatory
   DESCRIPTION
     "This attribute specifies the minimum bandwidth guarantee 
      associated with this EmissionPriority. A minimum bandwidth 
      guarantee is designed to prevent starvation of traffic at this EP by 
      traffic at higher EPs. Minimum bandwidth guarantees only operate 
      for EPs within the guaranteed bandwidth range 2 through 7. Note, 
      that for APC-based cards, EPs 5 and 6 are not supported.
      
      The minimum bandwidth guarantee specified is a percentage of the 
      bandwidth which remains after all traffic at EP 0 and EP 1 is served. 
      For example, if EP 0 and EP 1 traffic consumes 20% of link 
      bandwidth, the minimum bandwidth guarantee applies to the 
      remaining 80% of the link bandwidth. A minimum bandwidth 
      guarantee of 2% would actually result in this EP getting 2% of 80% 
      (total 1.6%) of the link bandwidth.
      
      The sum of minimumBandwidthGuarantee values for all Eps under 
      an AtmIf must not exceed 100%. 
      
      The value priority specifies that this Ep gets the bandwidth 
      guarantee which is applicable based on the hierarchy of emission 
      priorities. In this case, there is no minimum bandwidth guarantee. 
      
      For all non Apc-based cards the allowed value of the attribute is 
      between 0 and 48. Such a value specifies that from 1% to 48% of 
      the remaining link bandwidth is reserved for traffic at this EP. Given 
      a value n of minimumBandwidthGuarantee, then for n% of transmit 
      cell opportunities in the guaranteed bandwidth range, this EP get 
      first opportunity to send a cell. If this EP uses less than n% of the 
      link bandwidth, the extra opportunities are allocated in priority. Due 
      to scheduling and cell arrival times, traffic at this EP may not 
      necessarily achieve full utilization of its minimum bandwidth 
      guarantee. 
      
      When specifying a value for minimumBandwidthGuarantee, 
      consider the effect on cell delay variation (CDV) of traffic which 
      would normally be of higher priority. For example, if RtVbr service 
      category traffic is assigned to Ep/2 and Ubr traffic is assigned on 
      Ep/7 where Ep/7 has a minimumBandwidthGuarantee of 25%, there 
      can be a large impact on CDV of the RtVbr traffic. Traffic of the 
      Cbr or RtVbr service category which is sensitive to CDV and is of 
      known volume, can be assigned on EP 0 or EP 1 which are 
      independent of the effects of minimum bandwidth guarantee.

      VALUES (

      0 = priority

      )"
   DEFVAL     { 0 }
::= { mscAtmIfEpProvEntry 1 }


-- AtmIf/n PerformanceMonitoring
-- This component provides the default Performance Monitoring (PM) 
-- measurements and control modes for all AtmIf Vcc and AtmIf Vpc 
-- connections on the ATM interface. For provisioned connections, 
-- PM is done only if a PM component is provisioned under the Vcc 
-- Vcd or Vpc Vpd component. For all switched connections, PM will 
-- be done as specified by this component subject to resource limits.

mscAtmIfPm OBJECT IDENTIFIER ::= { mscAtmIf 11 }



mscAtmIfPmRowStatusTable OBJECT-TYPE
   SYNTAX     SEQUENCE OF MscAtmIfPmRowStatusEntry
   ACCESS     not-accessible
   STATUS     mandatory
   DESCRIPTION
     "This entry controls the addition and deletion of 
      mscAtmIfPm components."
::= { mscAtmIfPm 1 }

mscAtmIfPmRowStatusEntry OBJECT-TYPE
   SYNTAX     MscAtmIfPmRowStatusEntry
   ACCESS     not-accessible
   STATUS     mandatory
   DESCRIPTION
     "A single entry in the table represents a single 
      mscAtmIfPm component."
   INDEX {
      mscAtmIfIndex,
      mscAtmIfPmIndex }
::= { mscAtmIfPmRowStatusTable 1 }

MscAtmIfPmRowStatusEntry ::= SEQUENCE {
   mscAtmIfPmRowStatus
      RowStatus,
   mscAtmIfPmComponentName
      DisplayString,
   mscAtmIfPmStorageType
      StorageType,
   mscAtmIfPmIndex
      NonReplicated }

mscAtmIfPmRowStatus OBJECT-TYPE
   SYNTAX     RowStatus 
   ACCESS     read-only
   STATUS     mandatory
   DESCRIPTION
     "This variable is used as the basis for SNMP naming of
      mscAtmIfPm components.
      These components cannot be added nor deleted."
::= { mscAtmIfPmRowStatusEntry 1 }

mscAtmIfPmComponentName OBJECT-TYPE
   SYNTAX     DisplayString 
   ACCESS     read-only
   STATUS     mandatory
   DESCRIPTION
     "This variable provides the component's string name for
      use with the ASCII Console Interface"
::= { mscAtmIfPmRowStatusEntry 2 }

mscAtmIfPmStorageType OBJECT-TYPE
   SYNTAX     StorageType 
   ACCESS     read-only
   STATUS     mandatory
   DESCRIPTION
     "This variable represents the storage type value for the
      mscAtmIfPm tables."
::= { mscAtmIfPmRowStatusEntry 4 }

mscAtmIfPmIndex OBJECT-TYPE
   SYNTAX     NonReplicated 
   ACCESS     not-accessible
   STATUS     mandatory
   DESCRIPTION
     "This variable represents the index for the mscAtmIfPm tables."
::= { mscAtmIfPmRowStatusEntry 10 }

mscAtmIfPmProvTable OBJECT-TYPE
   SYNTAX     SEQUENCE OF MscAtmIfPmProvEntry
   ACCESS     not-accessible
   STATUS     mandatory
   DESCRIPTION
     "This group contains provisioned attributes which specify the default 
      Performance Monitoring (PM) measurements, namely, Cell Loss 
      Ratio (CLR) and Availability Ratio (AR), and control modes for all 
      AtmIf Vcc and AtmIf Vpc connections on the ATM interface."
::= { mscAtmIfPm 100 }

mscAtmIfPmProvEntry OBJECT-TYPE
   SYNTAX     MscAtmIfPmProvEntry
   ACCESS     not-accessible
   STATUS     mandatory
   DESCRIPTION
     "An entry in the mscAtmIfPmProvTable."
   INDEX {
      mscAtmIfIndex,
      mscAtmIfPmIndex }
::= { mscAtmIfPmProvTable 1 }

MscAtmIfPmProvEntry ::= SEQUENCE {
   mscAtmIfPmSegSwitchSideMeasurement
      OCTET STRING,
   mscAtmIfPmSegLinkSideMeasurement
      OCTET STRING,
   mscAtmIfPmControlMode
      INTEGER }

mscAtmIfPmSegSwitchSideMeasurement OBJECT-TYPE
   SYNTAX     OCTET STRING (SIZE (1))
   ACCESS     read-write
   STATUS     mandatory
   DESCRIPTION
     "This attribute specifies the default Performance Monitoring (PM) 
      measurements on the switch side configuration for all AtmIf Vcc and 
      AtmIf Vpc connections on the ATM interface.

      Description of bits:
      availabilityRatio(0)
      cellLossRatio(1)"
::= { mscAtmIfPmProvEntry 1 }

mscAtmIfPmSegLinkSideMeasurement OBJECT-TYPE
   SYNTAX     OCTET STRING (SIZE (1))
   ACCESS     read-write
   STATUS     mandatory
   DESCRIPTION
     "This attribute specifies the default Performance Monitoring (PM) 
      measurements on the link side configuration for all AtmIf Vcc and 
      AtmIf Vpc connections, on the ATM interface.

      Description of bits:
      availabilityRatio(0)
      cellLossRatio(1)"
::= { mscAtmIfPmProvEntry 2 }

mscAtmIfPmControlMode OBJECT-TYPE
   SYNTAX     INTEGER  {
                 autoStart(0),
                 onDemand(1) }
   ACCESS     read-write
   STATUS     mandatory
   DESCRIPTION
     "This attribute specifies the default control mode of Performance 
      Monitoring (PM) measurements for all AtmIf Vcc and AtmIf Vpc 
      connections on the ATM interface.
      
      autoStart means Performance Monitoring (PM) measurements start 
      when the provisioned data is activated.
      
      onDemand means PM measurements start when the operator issues 
      the START conmmand. The PM measurements in this mode will 
      continue until the operator issues the STOP command."
   DEFVAL     { autoStart }
::= { mscAtmIfPmProvEntry 3 }




-- 
-- Version and Compliance statements
-- 



-- Object-Group Statement:
-- A list of all current accessible leaf objects.

-- OBJECTS { mscAtmIfCARtVbrWeightPolicy,
--           mscAtmIfVccStatsTxFrameDiscardClp,
--           mscAtmIfVptVccVcdCorrelationTag,
--           mscAtmIfVpcVpdTmBqpValue,
--           mscAtmIfRxLinkUtilization,
--           mscAtmIfVccTestBytesRx,
--           mscAtmIfVptVccVcdSegLinkSideLoopback,
--           mscAtmIfVptTmAbrCutoffDecreaseFactor,
--           mscAtmIfVccTmBandwidthElastic,
--           mscAtmIfVpcTmTqpValue,
--           mscAtmIfVccTmUnshapedTransmitQueueing,
--           mscAtmIfVccTestLoadingFrmTx,
--           mscAtmIfVptVccVcdTmAbrFixedRoundTripTime,
--           mscAtmIfVptVccVcdPmControlMode,
--           mscAtmIfVptCARtVbrCellLossRatio,
--           mscAtmIfVptVccVcdTmAbrStorageType,
--           mscAtmIfVpcPmBwdTotalUserCellsTx01,
--           mscAtmIfCACbrEpdOffset,
--           mscAtmIfCARtVbrOpUnshapedTransmitQueueing,
--           mscAtmIfVpcVpdTmAtmServiceCategory,
--           mscAtmIfVptCAAbrStorageType,
--           mscAtmIfCAUbrMaxVpcs,
--           mscAtmIfCAAbrAcrDecreaseTimeFactor,
--           mscAtmIfCANrtVbrRowStatus,
--           mscAtmIfVpcPmCurrentAvailabilityStatus,
--           mscAtmIfVccStatsRxAal5FrameError,
--           mscAtmIfVptSegSwitchSideLoopbackState,
--           mscAtmIfVpcTmRowStatus,
--           mscAtmIfVccVcdTmRowStatus,
--           mscAtmIfVccTmAbrMaxTimeBetweenRmCell,
--           mscAtmIfVptCAPoolProvBwValue,
--           mscAtmIfVpcTmRqpValue,
--           mscAtmIfVptCACbrStorageType,
--           mscAtmIfVptVccOperationalState,
--           mscAtmIfVpcStatsRxCell,
--           mscAtmIfNAcctComponentName,
--           mscAtmIfVptTmAtmServiceCategory,
--           mscAtmIfCAAbrRateDecreaseFactor,
--           mscAtmIfVccTmTxQueueLength,
--           mscAtmIfVccNepApplicationName,
--           mscAtmIfCAAbrEpdOffset,
--           mscAtmIfVptTmAbrForwardRmCellLimit,
--           mscAtmIfVpcOperationalState,
--           mscAtmIfVptCAAbrPool,
--           mscAtmIfVccVcdPmSegSwitchSideMeasurement,
--           mscAtmIfVccPmBwdTotalUserCellsRx01,
--           mscAtmIfVptVccTmBandwidthReduction,
--           mscAtmIfVpcVpdTmRxTdpValue,
--           mscAtmIfVptVccTmAbrTxFwdRmCells,
--           mscAtmIfVccPmStorageType,
--           mscAtmIfNAcctStorageType,
--           mscAtmIfCAUbrUnshapedTransmitQueueing,
--           mscAtmIfVptVccComponentName,
--           mscAtmIfVpcVpdTmAbrRateIncreaseFactor,
--           mscAtmIfVpcVpdComponentName,
--           mscAtmIfVccNumLeaves,
--           mscAtmIfVptVccTmAbrConnectionType,
--           mscAtmIfVpcTmAbrRowStatus,
--           mscAtmIfVptVccTestComponentName,
--           mscAtmIfVptCARtVbrMaxCtd,
--           mscAtmIfCANrtVbrUsageParameterControl,
--           mscAtmIfShapeUsageValue,
--           mscAtmIfCANrtVbrTxQueueLimit,
--           mscAtmIfVptStatsRxCellClp,
--           mscAtmIfVpcTmUsageParameterControl,
--           mscAtmIfVpcPmBwdTotalUserCellsTx0,
--           mscAtmIfOperationalState,
--           mscAtmIfCANrtVbrHoldingPriority,
--           mscAtmIfVptComponentName,
--           mscAtmIfVccTestLoadingFrmRx,
--           mscAtmIfVpcVpdTmTrafficShaping,
--           mscAtmIfVpcPmRowStatus,
--           mscAtmIfVptVpdTmAbrTransientBufferExposure,
--           mscAtmIfVpcTmHoldingPriority,
--           mscAtmIfVccOperStatus,
--           mscAtmIfVpcVpdMCastConnectionType,
--           mscAtmIfOpShapingRatesValue,
--           mscAtmIfVccTestOverrideHoldingPriority,
--           mscAtmIfVpcStatsRxAal5FrameAbort,
--           mscAtmIfCAUbrShapeRecoupPolicy,
--           mscAtmIfVpcTmTxQThreshValue,
--           mscAtmIfCAPoolWaitAdmConnsValue,
--           mscAtmIfComponentName,
--           mscAtmIfVccVcdTmFwdQosClass,
--           mscAtmIfVpcPmBwdTotalUserCellsRx0,
--           mscAtmIfVpcPmArTotalTime,
--           mscAtmIfCAActualMaxVpcs,
--           mscAtmIfCAPermanentMulticastBranches,
--           mscAtmIfVptTmAbrTxFwdRmCells,
--           mscAtmIfPmStorageType,
--           mscAtmIfCARtVbrUsageParameterControl,
--           mscAtmIfCACbrMaxCtd,
--           mscAtmIfCACbrForceTagging,
--           mscAtmIfVccVcdTmAbrFixedRoundTripTime,
--           mscAtmIfVccStatsRxFrameDiscard,
--           mscAtmIfCACbrProvCdvt,
--           mscAtmIfVptCAPoolWaitAdmConnsValue,
--           mscAtmIfVptVpdTmClippingBbc,
--           mscAtmIfVccTmAbrStorageType,
--           mscAtmIfVptVccVcdTmBwdQosClass,
--           mscAtmIfTxLinkUtilization,
--           mscAtmIfVptVccStatsRxUpcViolationOnEnforcer2,
--           mscAtmIfVccPmArAvailabilityRatio,
--           mscAtmIfVccTmTxQueueCongestionState,
--           mscAtmIfVptCACbrCdvt,
--           mscAtmIfVpcVpdSegLinkSideLoopback,
--           mscAtmIfVptVccVcdTmHoldingPriority,
--           mscAtmIfVptVccTmAbrTransientBufferExposure,
--           mscAtmIfVptVccLoopComponentName,
--           mscAtmIfVptVccStatsRxUpcViolationOnEnforcer1,
--           mscAtmIfVptVpdTmTransferCapabilityBbc,
--           mscAtmIfCAPermanentVccs,
--           mscAtmIfVptVccTestVerificationFrmTx,
--           mscAtmIfVptVccTestUsageState,
--           mscAtmIfVptVccStatsTxCell,
--           mscAtmIfVccVcdTmBwdQosClass,
--           mscAtmIfVpcLastMaximumCtd,
--           mscAtmIfVptVccVcdEndToEndLoopback,
--           mscAtmIfVptStatsTxCellClp,
--           mscAtmIfVccVcdTmAbrRowStatus,
--           mscAtmIfVptUsageState,
--           mscAtmIfVccVcdTmTxTdpValue,
--           mscAtmIfCAAbrHoldingPriority,
--           mscAtmIfConnMapOvFirstNonZeroVpiForVccs,
--           mscAtmIfCAPoolAvailableBwValue,
--           mscAtmIfVptCARtVbrComponentName,
--           mscAtmIfVccVcdTmUsageParameterControl,
--           mscAtmIfCAAbrRateIncreaseFactor,
--           mscAtmIfVccVcdTmTxQueueLimit,
--           mscAtmIfVccTmTqpValue,
--           mscAtmIfVptVccStatsRxCell,
--           mscAtmIfCACbrProvClr,
--           mscAtmIfVccVcdPmRowStatus,
--           mscAtmIfVccTmAbrRateDecreaseFactor,
--           mscAtmIfVccVcdTmHoldingPriority,
--           mscAtmIfTxCellClp,
--           mscAtmIfVptCAPermanentVccs,
--           mscAtmIfVptCARowStatus,
--           mscAtmIfCARtVbrSvcMpHoldingPriority,
--           mscAtmIfVptStatsRxUpcViolationOnEnforcer2,
--           mscAtmIfVccTmAbrFixedRoundTripTime,
--           mscAtmIfCAUbrMaxVccs,
--           mscAtmIfVccVcdTmAbrConnectionType,
--           mscAtmIfVccPmFwdTotalUserCellsTx0,
--           mscAtmIfVptCACbrRowStatus,
--           mscAtmIfVptVccVcdTmAbrTransientBufferExposure,
--           mscAtmIfVccPmCurrentAvailabilityStatus,
--           mscAtmIfVptVccTestVerificationFrmRx,
--           mscAtmIfVptVpdTmAbrRateIncreaseFactor,
--           mscAtmIfCACbrComponentName,
--           mscAtmIfVccTmRowStatus,
--           mscAtmIfVptTmTrafficShaping,
--           mscAtmIfConnMapOvStorageType,
--           mscAtmIfVccTmRqpValue,
--           mscAtmIfVptStatsRxUpcViolationOnEnforcer1,
--           mscAtmIfVptVpdTmTrafficShaping,
--           mscAtmIfVccVcdPmControlMode,
--           mscAtmIfCANrtVbrEmissionPriority,
--           mscAtmIfVptVccTestTimeRemaining,
--           mscAtmIfCAAbrFrttPortion,
--           mscAtmIfRxCellClp,
--           mscAtmIfVptVpdTmBearerClassBbc,
--           mscAtmIfCAComponentName,
--           mscAtmIfEpStorageType,
--           mscAtmIfVptVccStatsRxCellDiscardClp,
--           mscAtmIfVccOperationalState,
--           mscAtmIfVccPmFwdTotalUserCellsRx0,
--           mscAtmIfVptCAAbrRowStatus,
--           mscAtmIfVpcTmAbrCutoffDecreaseFactor,
--           mscAtmIfVptVccNepComponentName,
--           mscAtmIfVptCARtVbrCdv,
--           mscAtmIfVccTmAbrRowStatus,
--           mscAtmIfVpcLastAverageCtd,
--           mscAtmIfVptTmBandwidthReduction,
--           mscAtmIfCAUbrPool,
--           mscAtmIfVptVccVcdTmClippingBbc,
--           mscAtmIfVptVccTmAbrAcrRateChangeInfo,
--           mscAtmIfCAAbrMaxCellPerRmCell,
--           mscAtmIfUnknownStatus,
--           mscAtmIfCAMaxAutoSelectedVciForNonZeroVpi,
--           mscAtmIfVccTmUsageParameterControl,
--           mscAtmIfVccPmBwdTotalUserCellsTx0,
--           mscAtmIfCAAbrComponentName,
--           mscAtmIfVptVccStorageType,
--           mscAtmIfVptVpdVptType,
--           mscAtmIfVpcSegSwitchSideLoopbackState,
--           mscAtmIfVccPmRowStatus,
--           mscAtmIfTxCellMemoryCongestionState,
--           mscAtmIfVccTmHoldingPriority,
--           mscAtmIfCANrtVbrCdvt,
--           mscAtmIfConnMapNumVccsPerNonZeroVpiOper,
--           mscAtmIfVccPmFailureCause,
--           mscAtmIfVptVccTmBestEffort,
--           mscAtmIfVpcTmAtmServiceCategory,
--           mscAtmIfVptVpdRowStatus,
--           mscAtmIfVpcVpdEndToEndLoopback,
--           mscAtmIfVptAisState,
--           mscAtmIfVptVccTestLoadingFrmLost,
--           mscAtmIfVptVccTestBandwidthElastic,
--           mscAtmIfCAMinAutoSelectedVciForNonZeroVpi,
--           mscAtmIfVpcTmAbrForwardRmCellLimit,
--           mscAtmIfVccPmBwdTotalUserCellsRx0,
--           mscAtmIfVccPmArTotalTime,
--           mscAtmIfVptStatsRxCell,
--           mscAtmIfCACbrCdv,
--           mscAtmIfVccVcdTmAbrDgcraMaximumDelay,
--           mscAtmIfVptVpdCorrelationTag,
--           mscAtmIfVpcCurrentCtd,
--           mscAtmIfTxCell,
--           mscAtmIfVptVpdTmTxTdpValue,
--           mscAtmIfVptVccVcdSegSwitchSideLoopback,
--           mscAtmIfVptVpdTmAbrFarEndInitialCellRate,
--           mscAtmIfVpcVpdStorageType,
--           mscAtmIfVccVcdTmFqpValue,
--           mscAtmIfCACbrUnshapedTransmitQueueing,
--           mscAtmIfVptVccTestStorageType,
--           mscAtmIfVccVcdSegLinkSideLoopback,
--           mscAtmIfVptVpdTmAbrInitialCellRate,
--           mscAtmIfVptVccNepRowStatus,
--           mscAtmIfVptTmAbrAcrRateChangeInfo,
--           mscAtmIfVpcComponentName,
--           mscAtmIfVptStorageType,
--           mscAtmIfVpcVpdTmAbrTransientBufferExposure,
--           mscAtmIfVccVcdTmAbrDgcraMinimumDelay,
--           mscAtmIfVptVccTestAdminState,
--           mscAtmIfTxFrameDiscardClp,
--           mscAtmIfRxCell,
--           mscAtmIfVptVpdTmRxTdpValue,
--           mscAtmIfPmRowStatus,
--           mscAtmIfVptVccVcdTmAbrRateIncreaseFactor,
--           mscAtmIfVpcPmArMeasurementStatus,
--           mscAtmIfCANrtVbrPerVcQueueLimitReferenceRate,
--           mscAtmIfCANrtVbrTrafficShaping,
--           mscAtmIfCAOamCcConnections,
--           mscAtmIfVptAdminState,
--           mscAtmIfVccNepComponentName,
--           mscAtmIfVptTmAbrTransientBufferExposure,
--           mscAtmIfVpcStatsTxFrameDiscard,
--           mscAtmIfVptVccVcdPmSegSwitchSideMeasurement,
--           mscAtmIfVccVcdTmAbrCutoffDecreaseFactor,
--           mscAtmIfVptTmAbrComponentName,
--           mscAtmIfVptVccTmTransferCapabilityBbc,
--           mscAtmIfCACbrShapeRecoupPolicy,
--           mscAtmIfVccTestBytesTx,
--           mscAtmIfVptVpdTmRxPacketWiseDiscard,
--           mscAtmIfVpcTmAbrTxFwdRmCells,
--           mscAtmIfVpcPmFwdAverageClr01,
--           mscAtmIfVptVccVcdPmSegLinkSideMeasurement,
--           mscAtmIfVpcPmFwdLastSampleClr0,
--           mscAtmIfCACbrStorageType,
--           mscAtmIfVccTestCustomizedPattern,
--           mscAtmIfCAUbrMinPerVcQueueLimit,
--           mscAtmIfVccVcdTmBqpValue,
--           mscAtmIfVptVpdTmBwdQosClass,
--           mscAtmIfVccStatsRxUpcViolationOnEnforcer2,
--           mscAtmIfVpcVpdTmClippingBbc,
--           mscAtmIfVptCACbrPool,
--           mscAtmIfVptVpdTmAbrFarEndAcrDecreaseTimeFactor,
--           mscAtmIfVptVccStatsRxAal5FrameError,
--           mscAtmIfCAUbrCdvt,
--           mscAtmIfVptVpdTmWeight,
--           mscAtmIfVccPmBwdMinimumClr0,
--           mscAtmIfVptVccVcdTmAbrComponentName,
--           mscAtmIfVccVcdTmAtmServiceCategory,
--           mscAtmIfVptVccTestFrmTypes,
--           mscAtmIfVptVpdTmAbrAcrDecreaseTimeFactor,
--           mscAtmIfVptCAUbrVccUsage,
--           mscAtmIfVpcVpdTmTransferCapabilityBbc,
--           mscAtmIfVptVccLoopStorageType,
--           mscAtmIfVpcStatsRxFrameDiscard,
--           mscAtmIfPmComponentName,
--           mscAtmIfCAAbrStorageType,
--           mscAtmIfVpcStatsTxCellClp,
--           mscAtmIfVptVpdTmAbrRateDecreaseFactor,
--           mscAtmIfCAMaxMulticastBranches,
--           mscAtmIfCANrtVbrWeightPolicy,
--           mscAtmIfVpcUsageState,
--           mscAtmIfVptTmTransferCapabilityBbc,
--           mscAtmIfVptTmTxQueueLength,
--           mscAtmIfMaxVpiBits,
--           mscAtmIfVptStatsRxAal5FrameError,
--           mscAtmIfVptCARtVbrStorageType,
--           mscAtmIfVptVccVcdTmAbrFarEndInitialCellRate,
--           mscAtmIfVccTmAbrCutoffDecreaseFactor,
--           mscAtmIfNAcctAccountConnectionType,
--           mscAtmIfConnMapOvRowStatus,
--           mscAtmIfVptCANrtVbrCellLossRatio,
--           mscAtmIfVpcStatsRxCellClp,
--           mscAtmIfVccComponentName,
--           mscAtmIfVptVccVcdTmAbrInitialCellRate,
--           mscAtmIfCAMinMulticastBranches,
--           mscAtmIfCAUbrRowStatus,
--           mscAtmIfCANrtVbrOpUnshapedTransmitQueueing,
--           mscAtmIfVpcStatsRxUpcViolationOnEnforcer2,
--           mscAtmIfVpcPmFwdPmCellDiscardCount,
--           mscAtmIfVptVccTmTxQosClass,
--           mscAtmIfEpRowStatus,
--           mscAtmIfLastAal5RxErrorConnection,
--           mscAtmIfVptVccVcdTmTxPacketWiseDiscard,
--           mscAtmIfVptCAUbrMinimumCellRate,
--           mscAtmIfCARtVbrEpdOffset,
--           mscAtmIfCAMaxVccs,
--           mscAtmIfVccSegSwitchSideLoopbackState,
--           mscAtmIfVccVcdTmTrafficShaping,
--           mscAtmIfVptCARtVbrPool,
--           mscAtmIfVptVccTroubled,
--           mscAtmIfVpcLoopComponentName,
--           mscAtmIfCAUbrVptUsage,
--           mscAtmIfVpcStatsRxUpcViolationOnEnforcer1,
--           mscAtmIfVpcPmFwdTotalClrInterval,
--           mscAtmIfVpcPmBwdAverageClr01,
--           mscAtmIfCAOamBrPmConnections,
--           mscAtmIfVccTmAtmServiceCategory,
--           mscAtmIfVptVccTmTxQThreshValue,
--           mscAtmIfVpcVpdTmBearerClassBbc,
--           mscAtmIfVccAdminState,
--           mscAtmIfCAStorageType,
--           mscAtmIfVccTmAbrForwardRmCellLimit,
--           mscAtmIfVptVccTmRxQosClass,
--           mscAtmIfVpcVpdPmSegLinkSideMeasurement,
--           mscAtmIfVptVccRowStatus,
--           mscAtmIfVptStatsRxAal5FrameAbort,
--           mscAtmIfVccTestFrmPatternType,
--           mscAtmIfVpcLastCtdSampleSize,
--           mscAtmIfVccCurrentCtd,
--           mscAtmIfCAUbrUsageParameterControl,
--           mscAtmIfVptTmBearerClassBbc,
--           mscAtmIfCAUbrTxQueueLimit,
--           mscAtmIfVpcTmBandwidthReduction,
--           mscAtmIfCAAbrAbrConnectionType,
--           mscAtmIfNAcctRowStatus,
--           mscAtmIfCAUbrHoldingPriority,
--           mscAtmIfVptVccVcdTmAbrFarEndAcrDecreaseTimeFactor,
--           mscAtmIfVpcPmBwdPmCellDiscardCount,
--           mscAtmIfVptVccTmTxTdpValue,
--           mscAtmIfVptVccStatsRxCellClp,
--           mscAtmIfCAAbrMaxTimeBetweenRmCell,
--           mscAtmIfVptVccVcdTmWeight,
--           mscAtmIfVptTmTxQosClass,
--           mscAtmIfVccPmBwdTotalUserCellsTx01,
--           mscAtmIfVpcStatsTxCell,
--           mscAtmIfVccTestVerificationFrmTx,
--           mscAtmIfVptVccTmTqpValue,
--           mscAtmIfVptVccTmAbrInitialCellRate,
--           mscAtmIfCAOamFPmConnections,
--           mscAtmIfVccVcdTmBearerClassBbc,
--           mscAtmIfVccPmArMeasurementStatus,
--           mscAtmIfCAPoolProvBwValue,
--           mscAtmIfVpcVpdRowStatus,
--           mscAtmIfVptVccTmRowStatus,
--           mscAtmIfCAUbrEpdOffset,
--           mscAtmIfVptVccVcdTmUsageParameterControl,
--           mscAtmIfVptVccTestRowStatus,
--           mscAtmIfVccTmTrafficShaping,
--           mscAtmIfVptVccVcdTmAbrRateDecreaseFactor,
--           mscAtmIfCAMaxAutoSelectedVciForVpiZero,
--           mscAtmIfVptTmRxQosClass,
--           mscAtmIfCAAbrPool,
--           mscAtmIfVccPmBwdLastSampleUserCellsTx01,
--           mscAtmIfVccTmAbrTxFwdRmCells,
--           mscAtmIfVptRowStatus,
--           mscAtmIfVpcVpdTmTxTdpValue,
--           mscAtmIfAal5RxErrors,
--           mscAtmIfVpcVpdTmAbrFarEndInitialCellRate,
--           mscAtmIfVccPmBwdMaximumClr01,
--           mscAtmIfVptRxOamCellCongestionState,
--           mscAtmIfFaultHoldOffTime,
--           mscAtmIfConnMapNumVccsForVpiZeroOper,
--           mscAtmIfVptVccTmTxPacketWiseDiscard,
--           mscAtmIfVptVccTmRxPacketWiseDiscard,
--           mscAtmIfVccTestComponentName,
--           mscAtmIfCARtVbrMaxCtd,
--           mscAtmIfVpcVpdTmAbrInitialCellRate,
--           mscAtmIfCARtVbrForceTagging,
--           mscAtmIfVpcTmAbrAcrRateChangeInfo,
--           mscAtmIfCAMinAutoSelectedVciForVpiZero,
--           mscAtmIfVptTmTxTdpValue,
--           mscAtmIfVpcPmBwdLastSampleClr01,
--           mscAtmIfVpcStorageType,
--           mscAtmIfVpcVpdTmTxPacketWiseDiscard,
--           mscAtmIfCABwPoolValue,
--           mscAtmIfVpcPmBwdMaximumClr01,
--           mscAtmIfVptTmAbrRateIncreaseFactor,
--           mscAtmIfVccStatsTxCell,
--           mscAtmIfVptTmAbrInitialCellRate,
--           mscAtmIfVptCAPoolRequBwValue,
--           mscAtmIfVptVccTmWeight,
--           mscAtmIfVptVpdEndToEndLoopback,
--           mscAtmIfVpcAdminState,
--           mscAtmIfVpcTmAbrTransientBufferExposure,
--           mscAtmIfVptTmTxPacketWiseDiscard,
--           mscAtmIfVccStatsTxCellClp,
--           mscAtmIfVccPmBwdLastSampleUserCellsRx01,
--           mscAtmIfVptTmRxTdpValue,
--           mscAtmIfVptVpdTmComponentName,
--           mscAtmIfVccTmStorageType,
--           mscAtmIfVpcVpdTmRxPacketWiseDiscard,
--           mscAtmIfVccUsageState,
--           mscAtmIfVpcPmBwdMinimumClr01,
--           mscAtmIfVptCANrtVbrComponentName,
--           mscAtmIfVptVccVcdTmForceTagging,
--           mscAtmIfTxCellMemoryThresholdValue,
--           mscAtmIfVptVccTmAbrRateDecreaseFactor,
--           mscAtmIfVccTestVerificationFrmRx,
--           mscAtmIfVptVccLoopRowStatus,
--           mscAtmIfVptVccVcdTmRxPacketWiseDiscard,
--           mscAtmIfVptTmRxPacketWiseDiscard,
--           mscAtmIfVccStatsRxCellClp,
--           mscAtmIfVpcVpdTmAbrFarEndAcrDecreaseTimeFactor,
--           mscAtmIfCACbrMinPerVcQueueLimit,
--           mscAtmIfVpcVpdPmComponentName,
--           mscAtmIfCANrtVbrSvcMpHoldingPriority,
--           mscAtmIfVptVccTmBearerClassBbc,
--           mscAtmIfVccTestFrmSize,
--           mscAtmIfVptStatsTxCellDiscardClp,
--           mscAtmIfVptVpdTmAbrMaxCellPerRmCell,
--           mscAtmIfVptVccVcdTmAbrAcrDecreaseTimeFactor,
--           mscAtmIfVccStatsRxCell,
--           mscAtmIfConnMapNumNonZeroVpisForVccsOper,
--           mscAtmIfVccPmFwdPmCellDiscardCount,
--           mscAtmIfVpcVpdTmAbrAcrDecreaseTimeFactor,
--           mscAtmIfVptVpdTmAbrComponentName,
--           mscAtmIfVptVccTmClippingBbc,
--           mscAtmIfVpcTmClippingBbc,
--           mscAtmIfCAUbrEmissionPriority,
--           mscAtmIfVpcStatsTxFrameDiscardClp,
--           mscAtmIfVptVpdSegSwitchSideLoopback,
--           mscAtmIfVptCARtVbrRowStatus,
--           mscAtmIfVccStatsRxUpcViolationOnEnforcer1,
--           mscAtmIfVptTmWeight,
--           mscAtmIfVpcPmBwdTotalClrInterval,
--           mscAtmIfVccTestUsageState,
--           mscAtmIfVpcPmFwdLastSampleUserCellsTx01,
--           mscAtmIfCAAbrMinPerVcQueueLimit,
--           mscAtmIfVpcCallDirection,
--           mscAtmIfVptTmAbrAcrDecreaseTimeFactor,
--           mscAtmIfVccVcdEndToEndLoopback,
--           mscAtmIfVpcTmTransferCapabilityBbc,
--           mscAtmIfVpcTmTxQueueLength,
--           mscAtmIfVpcTmTrafficShaping,
--           mscAtmIfVptStatsRxCellDiscardClp,
--           mscAtmIfCAPoolRequBwValue,
--           mscAtmIfUsageState,
--           mscAtmIfTxCellDiscardClp,
--           mscAtmIfCAAbrCdvt,
--           mscAtmIfStandbyStatus,
--           mscAtmIfVccLastCtdSampleSize,
--           mscAtmIfVptVpdTmUnshapedTransmitQueueing,
--           mscAtmIfVptTmAbrRateDecreaseFactor,
--           mscAtmIfVptVccTestDuration,
--           mscAtmIfCAAbrEmissionPriority,
--           mscAtmIfVccVcdStorageType,
--           mscAtmIfVpcPmFwdLastSampleUserCellsRx01,
--           mscAtmIfVccTmBandwidthReduction,
--           mscAtmIfVptVccTmForceTagging,
--           mscAtmIfVccPmBwdPmCellDiscardCount,
--           mscAtmIfCARowStatus,
--           mscAtmIfVccStatsTxFrameDiscard,
--           mscAtmIfVccVcdTmTxTrafficDescType,
--           mscAtmIfRxCellDiscardClp,
--           mscAtmIfVccVcdTmAbrMaxCellPerRmCell,
--           mscAtmIfVccPmFwdLastSampleClr01,
--           mscAtmIfCACbrRowStatus,
--           mscAtmIfVccVcdTmAbrTransientBufferExposure,
--           mscAtmIfVccPmFwdAverageClr01,
--           mscAtmIfCAUbrVpcUsage,
--           mscAtmIfVptVccVcdTmRxTdpValue,
--           mscAtmIfVccPmFwdLastSampleClr0,
--           mscAtmIfVptConnectionPointType,
--           mscAtmIfLastAal5RxAbortConnection,
--           mscAtmIfVptCATroubledVccs,
--           mscAtmIfVpcPmBwdLastSampleUserCellsTx01,
--           mscAtmIfVptVccRdiState,
--           mscAtmIfVccTestTimeRemaining,
--           mscAtmIfVpcTmAbrRateIncreaseFactor,
--           mscAtmIfVptVpdTmBestEffort,
--           mscAtmIfVccLoopComponentName,
--           mscAtmIfVccStatsRxAal5FrameAbort,
--           mscAtmIfVccSegLinkSideLoopbackState,
--           mscAtmIfCAAbrRowStatus,
--           mscAtmIfVpcVpdTmStorageType,
--           mscAtmIfVpcVpdTmForceTagging,
--           mscAtmIfVccPmFwdMinimumClr01,
--           mscAtmIfVptVccTestBytesTx,
--           mscAtmIfCARtVbrCdv,
--           mscAtmIfVpcPmBwdLastSampleUserCellsRx01,
--           mscAtmIfVptStatsTxCellDiscard,
--           mscAtmIfVptVccAisState,
--           mscAtmIfVptTmTxQThreshValue,
--           mscAtmIfCACbrUsageParameterControl,
--           mscAtmIfVpcPmBwdTotalUserCellsRx01,
--           mscAtmIfCARtVbrUnshapedTransmitQueueing,
--           mscAtmIfVccTmAbrAcrRateChangeInfo,
--           mscAtmIfCACbrTxQueueLimit,
--           mscAtmIfVptVccVcdTmAbrMaxCellPerRmCell,
--           mscAtmIfVptVccLocalFailureCause,
--           mscAtmIfVpcTmTxQosClass,
--           mscAtmIfVccPmBwdLastSampleClr01,
--           mscAtmIfVccStorageType,
--           mscAtmIfVccRxOamCellCongestionState,
--           mscAtmIfCACbrHoldingPriority,
--           mscAtmIfCAUbrPerVcQueueLimitReferenceRate,
--           mscAtmIfVpcPmClrMeasurementStatus,
--           mscAtmIfCAUbrTrafficShaping,
--           mscAtmIfVptTroubled,
--           mscAtmIfVccPmFwdLastSampleUserCellsRx0,
--           mscAtmIfVptVccSegLinkSideLoopbackState,
--           mscAtmIfVptVccVcdRowStatus,
--           mscAtmIfVccVcdTmTransferCapabilityBbc,
--           mscAtmIfVptStatsRxCellDiscard,
--           mscAtmIfCATroubledVpts,
--           mscAtmIfLastDroppedRxCellConnection,
--           mscAtmIfTxCellDiscard,
--           mscAtmIfCAAbrUsageParameterControl,
--           mscAtmIfVptVpdTmTxPacketWiseDiscard,
--           mscAtmIfVptRdiState,
--           mscAtmIfVccTmAbrTransientBufferExposure,
--           mscAtmIfVccPmFwdTotalClrInterval,
--           mscAtmIfCAAbrTxQueueLimit,
--           mscAtmIfVptVccDistributionType,
--           mscAtmIfVpcTmRxQosClass,
--           mscAtmIfVpcStatsTxCellDiscard,
--           mscAtmIfVptTmAbrRxEfci,
--           mscAtmIfCARtVbrCdvt,
--           mscAtmIfVptVccVcdTmComponentName,
--           mscAtmIfConnMapComponentName,
--           mscAtmIfVpcRowStatus,
--           mscAtmIfVptVpdTmRxTrafficDescType,
--           mscAtmIfVpcPmFwdMinimumClr0,
--           mscAtmIfCARtVbrShapeRecoupPolicy,
--           mscAtmIfVptCASwitchedVccs,
--           mscAtmIfCAPoolAdmConnsValue,
--           mscAtmIfVptVccStatsTxCellDiscard,
--           mscAtmIfEndToEndLoopback,
--           mscAtmIfVptVccVcdTmUnshapedTransmitQueueing,
--           mscAtmIfVptVccTestCauseOfTermination,
--           mscAtmIfVptVccTmComponentName,
--           mscAtmIfLastLrcFrameErrorConnection,
--           mscAtmIfRxCellDiscard,
--           mscAtmIfVptVpdMCastConnectionType,
--           mscAtmIfVccTestStorageType,
--           mscAtmIfAal5RxAborts,
--           mscAtmIfVpcPmFwdAverageClr0,
--           mscAtmIfVccLastMinimumCtd,
--           mscAtmIfConnMapOvNumVccsPerNonZeroVpi,
--           mscAtmIfVccTestBandwidthElastic,
--           mscAtmIfVpcTmTxTdpValue,
--           mscAtmIfVpcPmBwdLastSampleClr0,
--           mscAtmIfVptVccStatsRxCellDiscard,
--           mscAtmIfCAPermittedAtmServiceCategories,
--           mscAtmIfVptLocalFailureCause,
--           mscAtmIfVpcPmBwdMaximumClr0,
--           mscAtmIfStorageType,
--           mscAtmIfVccVcdComponentName,
--           mscAtmIfVccTestAdminState,
--           mscAtmIfVpcTmAbrInitialCellRate,
--           mscAtmIfVccTmClippingBbc,
--           mscAtmIfVccVcdTmAbrRateIncreaseFactor,
--           mscAtmIfVptTmAbrFixedRoundTripTime,
--           mscAtmIfVptSegLinkSideLoopbackState,
--           mscAtmIfCAUbrForceTagging,
--           mscAtmIfVptVpdTmAbrConnectionType,
--           mscAtmIfVptTmAbrStorageType,
--           mscAtmIfVpcTmTxPacketWiseDiscard,
--           mscAtmIfCAUbrWeightPolicy,
--           mscAtmIfAdminState,
--           mscAtmIfVccPmFwdLastSampleUserCellsTx01,
--           mscAtmIfVpcTmRxTdpValue,
--           mscAtmIfVpcVpdTmComponentName,
--           mscAtmIfVptVpdTmStorageType,
--           mscAtmIfVccTmTransferCapabilityBbc,
--           mscAtmIfVpcPmBwdMinimumClr0,
--           mscAtmIfVccVcdPmSegLinkSideMeasurement,
--           mscAtmIfVptCANrtVbrStorageType,
--           mscAtmIfVptVccTestOperationalState,
--           mscAtmIfCAAbrDgcraMaximumDelay,
--           mscAtmIfVptVccTmAbrTxRateChangeInfo,
--           mscAtmIfCAMaxAutoSelectedVpi,
--           mscAtmIfVptTmComponentName,
--           mscAtmIfVptCAPoolAvailBwValue,
--           mscAtmIfCAUbrOpUnshapedTransmitQueueing,
--           mscAtmIfVpcTmRxPacketWiseDiscard,
--           mscAtmIfVccPmFwdLastSampleUserCellsRx01,
--           mscAtmIfVpcVpdTmFwdQosClass,
--           mscAtmIfDroppedRxCells,
--           mscAtmIfVpcVpdTmAbrMaxCellPerRmCell,
--           mscAtmIfVptVccTmUnshapedTransmitQueueing,
--           mscAtmIfVpcStatsTxCellDiscardClp,
--           mscAtmIfCANrtVbrEpdOffset,
--           mscAtmIfVptVccTestFrmPatternType,
--           mscAtmIfVptVpdTmAbrStorageType,
--           mscAtmIfVccTestFrmTypes,
--           mscAtmIfVptVccVcdTmTxTrafficDescType,
--           mscAtmIfCAAbrDgcraMinimumDelay,
--           mscAtmIfVpcVpdSegSwitchSideLoopback,
--           mscAtmIfCAMinAutoSelectedVpi,
--           mscAtmIfCAUbrVccUsage,
--           mscAtmIfVptVpdTmAbrRowStatus,
--           mscAtmIfVccLoopStorageType,
--           mscAtmIfVpcTmWeight,
--           mscAtmIfVptVccVcdPmComponentName,
--           mscAtmIfVptTmAbrMaxCellPerRmCell,
--           mscAtmIfVpcPmFwdLastSampleUserCellsTx0,
--           mscAtmIfVccVcdRowStatus,
--           mscAtmIfVpcTmAbrAcrDecreaseTimeFactor,
--           mscAtmIfCACbrEmissionPriority,
--           mscAtmIfLrcFrameErrors,
--           mscAtmIfVptVccEndToEndLoopbackState,
--           mscAtmIfVccTmAbrRateIncreaseFactor,
--           mscAtmIfAlarmStatus,
--           mscAtmIfVpcStatsRxCellDiscardClp,
--           mscAtmIfVptVccVcdTmRxTrafficDescType,
--           mscAtmIfVptVccTestElapsedTime,
--           mscAtmIfVccVcdCorrelationTag,
--           mscAtmIfVpcVpdTmUnshapedTransmitQueueing,
--           mscAtmIfVpcTmAbrRateDecreaseFactor,
--           mscAtmIfCARtVbrStorageType,
--           mscAtmIfVccVcdTmAbrFarEndInitialCellRate,
--           mscAtmIfVptTmAbrTxRateChangeInfo,
--           mscAtmIfVpcPmFailureCause,
--           mscAtmIfVptVccTmHoldingPriority,
--           mscAtmIfVpcPmFwdLastSampleUserCellsRx0,
--           mscAtmIfVptVccRxOamCellCongestionState,
--           mscAtmIfVptVccVcdMCastConnectionType,
--           mscAtmIfCANrtVbrCellLossRatio,
--           mscAtmIfVptTmBandwidthElastic,
--           mscAtmIfVptVccVcdTmTrafficShaping,
--           mscAtmIfVccVcdTmAbrInitialCellRate,
--           mscAtmIfTxCellEfci,
--           mscAtmIfVptTmUnshapedTransmitQueueing,
--           mscAtmIfVccTmTxQosClass,
--           mscAtmIfVccTestLoadingFrmLost,
--           mscAtmIfVccVcdTmTxPacketWiseDiscard,
--           mscAtmIfCAUbrMinimumCellRate,
--           mscAtmIfVccPmClrMeasurementStatus,
--           mscAtmIfVccPmFwdMaximumClr0,
--           mscAtmIfCARtVbrPool,
--           mscAtmIfVpcPmBwdLastSampleUserCellsTx0,
--           mscAtmIfVptVccVcdTmAbrConnectionType,
--           mscAtmIfVptVpdTmAbrDgcraMinimumDelay,
--           mscAtmIfVpcVpdTmBestEffort,
--           mscAtmIfVptEndToEndLoopbackState,
--           mscAtmIfVptCAActualMaxVccs,
--           mscAtmIfRxCellEfci,
--           mscAtmIfVptVccVcdTmStorageType,
--           mscAtmIfVccTmRxQosClass,
--           mscAtmIfVccTmBearerClassBbc,
--           mscAtmIfVccVcdTmRxPacketWiseDiscard,
--           mscAtmIfVccRowStatus,
--           mscAtmIfVptVpdTmForceTagging,
--           mscAtmIfVccPmFwdMinimumClr0,
--           mscAtmIfVptVccCallDirection,
--           mscAtmIfVpcPmFwdMaximumClr01,
--           mscAtmIfVpcPmBwdLastSampleUserCellsRx0,
--           mscAtmIfVptTmBestEffort,
--           mscAtmIfVccPmFwdTotalUserCellsRx01,
--           mscAtmIfCANrtVbrForceTagging,
--           mscAtmIfVccLoopRowStatus,
--           mscAtmIfVptVccTmRxTrafficDescType,
--           mscAtmIfVpcVpdPmRowStatus,
--           mscAtmIfPmSegLinkSideMeasurement,
--           mscAtmIfVpcTmForceTagging,
--           mscAtmIfVccVcdTmAbrFarEndAcrDecreaseTimeFactor,
--           mscAtmIfVccTmTxTdpValue,
--           mscAtmIfVccPmBwdTotalClrInterval,
--           mscAtmIfVptCAPoolAdmitBwValue,
--           mscAtmIfVccVcdTmWeight,
--           mscAtmIfVpcRxOamCellCongestionState,
--           mscAtmIfVpcVpdTmTxTrafficDescType,
--           mscAtmIfVccPmBwdMaximumClr0,
--           mscAtmIfVpcTroubled,
--           mscAtmIfVccVcdTmAbrAcrDecreaseTimeFactor,
--           mscAtmIfVccTmAbrInitialCellRate,
--           mscAtmIfVpcLoopStorageType,
--           mscAtmIfVpcStatsRxCellDiscard,
--           mscAtmIfCATroubledVpcs,
--           mscAtmIfCACbrPerVcQueueLimitReferenceRate,
--           mscAtmIfCACbrTrafficShaping,
--           mscAtmIfVpcRdiState,
--           mscAtmIfVptCACbrCellLossRatio,
--           mscAtmIfVpcPmArAvailabilityRatio,
--           mscAtmIfVccTestRowStatus,
--           mscAtmIfVptTmTxTrafficDescType,
--           mscAtmIfVccTmRxTdpValue,
--           mscAtmIfVccVcdTmAbrRateDecreaseFactor,
--           mscAtmIfVptCAUbrComponentName,
--           mscAtmIfVccNepRowStatus,
--           mscAtmIfVptCAPermittedAtmServiceCategories,
--           mscAtmIfVptVpdTmFwdQosClass,
--           mscAtmIfVpcPmFwdMinimumClr01,
--           mscAtmIfVpcVpdTmRxTrafficDescType,
--           mscAtmIfConnMapStorageType,
--           mscAtmIfVptVccVcdStorageType,
--           mscAtmIfRowStatus,
--           mscAtmIfVptVccStatsTxFrameDiscardClp,
--           mscAtmIfProceduralStatus,
--           mscAtmIfVptVccTmStorageType,
--           mscAtmIfCAAbrPerVcQueueLimitReferenceRate,
--           mscAtmIfCAUbrSvcMpHoldingPriority,
--           mscAtmIfVpcAisState,
--           mscAtmIfVccTmRxPacketWiseDiscard,
--           mscAtmIfVptVpdTmAbrFixedRoundTripTime,
--           mscAtmIfVpcConnectionPointType,
--           mscAtmIfCAAbrFairnessPolicy,
--           mscAtmIfVpcLocalFailureCause,
--           mscAtmIfInterfaceName,
--           mscAtmIfCARtVbrMinPerVcQueueLimit,
--           mscAtmIfVptVpdTmRowStatus,
--           mscAtmIfVccStatsTxCellDiscardClp,
--           mscAtmIfVptVccOperStatus,
--           mscAtmIfVccTestUnrecognizableFrmRx,
--           mscAtmIfVptVccStatsRxFrameDiscardClp,
--           mscAtmIfVptCANrtVbrRowStatus,
--           mscAtmIfVptCAUbrStorageType,
--           mscAtmIfVpcSegLinkSideLoopbackState,
--           mscAtmIfVpcVpdTmAbrConnectionType,
--           mscAtmIfVptCAConnectionPoolUsage,
--           mscAtmIfVccTmWeight,
--           mscAtmIfVptVccTmAbrMaxTimeBetweenRmCell,
--           mscAtmIfVccPmFwdLastSampleUserCellsTx0,
--           mscAtmIfVptVccTestLoadingFrmRx,
--           mscAtmIfVccTmAbrAcrDecreaseTimeFactor,
--           mscAtmIfConnMapOvNumVccsForVpiZero,
--           mscAtmIfVpcDistributionType,
--           mscAtmIfVpcPmFwdTotalUserCellsRx0,
--           mscAtmIfAvailabilityStatus,
--           mscAtmIfVccStatsRxCellDiscardClp,
--           mscAtmIfCACbrWeightPolicy,
--           mscAtmIfVptVccTestUnrecognizableFrmRx,
--           mscAtmIfVptTmAbrConnectionType,
--           mscAtmIfVptVccVcdTmBestEffort,
--           mscAtmIfCANrtVbrComponentName,
--           mscAtmIfCASwitchedVpcs,
--           mscAtmIfVptVccVcdPmStorageType,
--           mscAtmIfVccVcdTmForceTagging,
--           mscAtmIfVptVpdTmTxTrafficDescType,
--           mscAtmIfVptStatsTxFrameDiscardClp,
--           mscAtmIfVpcTmComponentName,
--           mscAtmIfVptTmStorageType,
--           mscAtmIfVptVpdTmUsageParameterControl,
--           mscAtmIfVptVccNumLeaves,
--           mscAtmIfVptVpdTmTxQueueLimit,
--           mscAtmIfVpcPmArAvailableTime,
--           mscAtmIfVptVpdTmHoldingPriority,
--           mscAtmIfVptVccTestBytesRx,
--           mscAtmIfVpcVpdTmAbrStorageType,
--           mscAtmIfCAAbrCutoffDecreaseFactor,
--           mscAtmIfVptVccTmTrafficShaping,
--           mscAtmIfVptStatsRxFrameDiscardClp,
--           mscAtmIfVpcTmAbrMaxCellPerRmCell,
--           mscAtmIfCARtVbrRowStatus,
--           mscAtmIfVccPmBwdLastSampleUserCellsTx0,
--           mscAtmIfRemoteAtmInterfaceLabel,
--           mscAtmIfVptTmAbrMaxTimeBetweenRmCell,
--           mscAtmIfVpcTmAbrComponentName,
--           mscAtmIfVptVccTestOverrideHoldingPriority,
--           mscAtmIfEpMinimumBandwidthGuarantee,
--           mscAtmIfVpcVpdPmStorageType,
--           mscAtmIfVptVccStatsTxFrameDiscard,
--           mscAtmIfVccNepStorageType,
--           mscAtmIfVccVcdTmRxTdpValue,
--           mscAtmIfVptTmRxTrafficDescType,
--           mscAtmIfVptVccStatsTxCellClp,
--           mscAtmIfVptVccTmAbrComponentName,
--           mscAtmIfVptCANrtVbrPool,
--           mscAtmIfVptTmForceTagging,
--           mscAtmIfVpcPmComponentName,
--           mscAtmIfConnMapOvNumNonZeroVpisForVccs,
--           mscAtmIfVpcTmAbrTxRateChangeInfo,
--           mscAtmIfRxFrameDiscardClp,
--           mscAtmIfVptVccTmTxQueueLength,
--           mscAtmIfVccPmBwdLastSampleUserCellsRx0,
--           mscAtmIfVccTestDuration,
--           mscAtmIfVccStatsTxCellDiscard,
--           mscAtmIfVptCACbrMaxCtd,
--           mscAtmIfVccTmTxQThreshValue,
--           mscAtmIfCANrtVbrUnshapedTransmitQueueing,
--           mscAtmIfVptVccStatsRxFrameDiscard,
--           mscAtmIfVccTmForceTagging,
--           mscAtmIfVpcTmUnshapedTransmitQueueing,
--           mscAtmIfVpcTmAbrRxEfci,
--           mscAtmIfVptVccVcdTmRowStatus,
--           mscAtmIfConnMapFirstNonZeroVpiForVccsOper,
--           mscAtmIfCARtVbrTxQueueLimit,
--           mscAtmIfVptVccVcdTmTransferCapabilityBbc,
--           mscAtmIfCARtVbrCellLossRatio,
--           mscAtmIfVccTroubled,
--           mscAtmIfVptVccTmTxQueueCongestionState,
--           mscAtmIfNAcctAccountClass,
--           mscAtmIfCARtVbrHoldingPriority,
--           mscAtmIfVccStatsRxCellDiscard,
--           mscAtmIfVptOperStatus,
--           mscAtmIfCANrtVbrStorageType,
--           mscAtmIfVccVcdTmComponentName,
--           mscAtmIfVccRdiState,
--           mscAtmIfVpcEndToEndLoopbackState,
--           mscAtmIfVptStatsTxFrameDiscard,
--           mscAtmIfVccLastMaximumCtd,
--           mscAtmIfVccTmAbrRxEfci,
--           mscAtmIfVpcVpdPmSegSwitchSideMeasurement,
--           mscAtmIfCANrtVbrShapeRecoupPolicy,
--           mscAtmIfCAMaxCaVpts,
--           mscAtmIfVptVccVcdTmAbrRowStatus,
--           mscAtmIfVpcTmBestEffort,
--           mscAtmIfVptCABwPoolValue,
--           mscAtmIfVptVpdTmAbrDgcraMaximumDelay,
--           mscAtmIfCAPoolAdmitBwValue,
--           mscAtmIfVptVccVcdTmFqpValue,
--           mscAtmIfVptVpdTmAbrMaxTimeBetweenRmCells,
--           mscAtmIfCustomerIdentifier,
--           mscAtmIfVccAisState,
--           mscAtmIfVptVccVcdTmTxQueueLimit,
--           mscAtmIfVptVpdTmFqpValue,
--           mscAtmIfVptStatsRxFrameDiscard,
--           mscAtmIfVccVcdTmAbrMaxTimeBetweenRmCells,
--           mscAtmIfSegLinkSideLoopback,
--           mscAtmIfTxFrameDiscard,
--           mscAtmIfCASwitchedMulticastBranches,
--           mscAtmIfVccLocalFailureCause,
--           mscAtmIfTxCellMemory,
--           mscAtmIfOamSegmentBoundary,
--           mscAtmIfPmControlMode,
--           mscAtmIfVccVcdTmAbrComponentName,
--           mscAtmIfConnMapRowStatus,
--           mscAtmIfVptVccTmAbrFixedRoundTripTime,
--           mscAtmIfVptVccTestLoadingFrmTx,
--           mscAtmIfVptCAUbrMaxVccs,
--           mscAtmIfVptTmTxQueueCongestionState,
--           mscAtmIfVptVccVcdPmRowStatus,
--           mscAtmIfVccVcdSegSwitchSideLoopback,
--           mscAtmIfVccPmBwdAverageClr01,
--           mscAtmIfVptVccTmRqpValue,
--           mscAtmIfVpcTmTxTrafficDescType,
--           mscAtmIfCAPermanentVpts,
--           mscAtmIfVpcVpdCorrelationTag,
--           mscAtmIfVptVccTestVerificationFrmBad,
--           mscAtmIfVccVcdPmComponentName,
--           mscAtmIfRxFrameDiscard,
--           mscAtmIfVccTestOperationalState,
--           mscAtmIfVccDistributionType,
--           mscAtmIfVpcVpdTmAbrComponentName,
--           mscAtmIfVpcTmAbrFixedRoundTripTime,
--           mscAtmIfVptCAComponentName,
--           mscAtmIfVptVpdTmAbrCutoffDecreaseFactor,
--           mscAtmIfVptVccUsageState,
--           mscAtmIfVccLastAverageCtd,
--           mscAtmIfVpcTmAbrStorageType,
--           mscAtmIfVptCACbrComponentName,
--           mscAtmIfCASwitchedVccs,
--           mscAtmIfNAcctServiceExchange,
--           mscAtmIfVccVcdTmUnshapedTransmitQueueing,
--           mscAtmIfVccTestCauseOfTermination,
--           mscAtmIfVccTmComponentName,
--           mscAtmIfVptVpdTmBqpValue,
--           mscAtmIfVpcVpdTmAbrFixedRoundTripTime,
--           mscAtmIfVpcTmRxTrafficDescType,
--           mscAtmIfVptVccVcdTmTxTdpValue,
--           mscAtmIfVptVccTmAbrRowStatus,
--           mscAtmIfVptTmTqpValue,
--           mscAtmIfVccPmArAvailableTime,
--           mscAtmIfVptCAUbrPool,
--           mscAtmIfCACbrSvcMpHoldingPriority,
--           mscAtmIfVpcVpdTmRowStatus,
--           mscAtmIfVptVccTmUsageParameterControl,
--           mscAtmIfVptCAAbrComponentName,
--           mscAtmIfVptVpdTmAtmServiceCategory,
--           mscAtmIfCAActualMaxVpts,
--           mscAtmIfCAUbrMaxVpts,
--           mscAtmIfVpcPmFwdTotalUserCellsTx01,
--           mscAtmIfVpcPmBwdAverageClr0,
--           mscAtmIfVccPmFwdMaximumClr01,
--           mscAtmIfVccTmAbrMaxCellPerRmCell,
--           mscAtmIfVccCallDirection,
--           mscAtmIfVptVccVcdComponentName,
--           mscAtmIfVptTmRowStatus,
--           mscAtmIfVccTmAbrComponentName,
--           mscAtmIfVptTmRqpValue,
--           mscAtmIfVptStatsTxCell,
--           mscAtmIfVptVccStatsRxAal5FrameAbort,
--           mscAtmIfVpcVpdTmBwdQosClass,
--           mscAtmIfVccVcdTmBestEffort,
--           mscAtmIfCARtVbrEmissionPriority,
--           mscAtmIfVptVccVcdTmFwdQosClass,
--           mscAtmIfVpcTmAbrConnectionType,
--           mscAtmIfVccTmTxPacketWiseDiscard,
--           mscAtmIfVpcVpdTmAbrRowStatus,
--           mscAtmIfCtdCalculation,
--           mscAtmIfVptOperationalState,
--           mscAtmIfVpcPmFwdTotalUserCellsRx01,
--           mscAtmIfVccPmComponentName,
--           mscAtmIfVptCACbrCdv,
--           mscAtmIfVptVccVcdTmAbrDgcraMaximumDelay,
--           mscAtmIfVccTmAbrTxRateChangeInfo,
--           mscAtmIfVpcTmStorageType,
--           mscAtmIfVpcVpdTmUsageParameterControl,
--           mscAtmIfVptVccVcdTmAbrMaxTimeBetweenRmCells,
--           mscAtmIfVpcVpdTmTxQueueLimit,
--           mscAtmIfVptVpdComponentName,
--           mscAtmIfVptTmAbrRowStatus,
--           mscAtmIfVpcVpdTmHoldingPriority,
--           mscAtmIfVptVccAdminState,
--           mscAtmIfCAConnectionPoolUsage,
--           mscAtmIfVptTmUsageParameterControl,
--           mscAtmIfVpcTmBearerClassBbc,
--           mscAtmIfCANrtVbrPool,
--           mscAtmIfVpcStatsRxFrameDiscardClp,
--           mscAtmIfNAcctAccountCollection,
--           mscAtmIfVptVccVcdTmAbrDgcraMinimumDelay,
--           mscAtmIfVpcStatsRxAal5FrameError,
--           mscAtmIfCAActualMaxVccs,
--           mscAtmIfVpcTmAbrMaxTimeBetweenRmCell,
--           mscAtmIfVptTmHoldingPriority,
--           mscAtmIfVpcVpdPmControlMode,
--           mscAtmIfVptVccTmBandwidthElastic,
--           mscAtmIfVccEndToEndLoopbackState,
--           mscAtmIfVptVccVcdTmBearerClassBbc,
--           mscAtmIfVpcVpdTmAbrRateDecreaseFactor,
--           mscAtmIfSegSwitchSideLoopback,
--           mscAtmIfVccVcdTmClippingBbc,
--           mscAtmIfVptVccVcdTmAbrCutoffDecreaseFactor,
--           mscAtmIfVptVccTmAbrAcrDecreaseTimeFactor,
--           mscAtmIfVccVcdTmRxTrafficDescType,
--           mscAtmIfVccTestElapsedTime,
--           mscAtmIfVccTestVerificationFrmBad,
--           mscAtmIfVccPmBwdLastSampleClr0,
--           mscAtmIfVptVccConnectionPointType,
--           mscAtmIfVpcPmStorageType,
--           mscAtmIfVpcTmTxQueueCongestionState,
--           mscAtmIfVptTmClippingBbc,
--           mscAtmIfVccTmBestEffort,
--           mscAtmIfVptVccTestCustomizedPattern,
--           mscAtmIfControlStatus,
--           mscAtmIfTxCellMemoryAvailable,
--           mscAtmIfVptVccVcdTmBqpValue,
--           mscAtmIfVpcNumLeaves,
--           mscAtmIfVccVcdMCastConnectionType,
--           mscAtmIfVpcPmFwdMaximumClr0,
--           mscAtmIfVptVccStatsTxCellDiscardClp,
--           mscAtmIfCACbrProvPool,
--           mscAtmIfVptVpdStorageType,
--           mscAtmIfVptVccVcdTmAtmServiceCategory,
--           mscAtmIfVpcOperStatus,
--           mscAtmIfVpcVpdTmWeight,
--           mscAtmIfVptVccTmRxTdpValue,
--           mscAtmIfVptVpdSegLinkSideLoopback,
--           mscAtmIfVccPmFwdAverageClr0,
--           mscAtmIfPmSegSwitchSideMeasurement,
--           mscAtmIfVccTmTxTrafficDescType,
--           mscAtmIfVptVccTmAbrStorageType,
--           mscAtmIfCARtVbrPerVcQueueLimitReferenceRate,
--           mscAtmIfVpcPmFwdLastSampleClr01,
--           mscAtmIfCARtVbrTrafficShaping,
--           mscAtmIfVccVcdTmStorageType,
--           mscAtmIfVptVccTestFrmSize,
--           mscAtmIfCAMaxCaVpcs,
--           mscAtmIfVptCAPoolAdmConnsValue,
--           mscAtmIfVpcTmBandwidthElastic,
--           mscAtmIfVpcVpdTmAbrDgcraMaximumDelay,
--           mscAtmIfVptVccNepApplicationName,
--           mscAtmIfVptVccTmTxTrafficDescType,
--           mscAtmIfVptVccTmAbrMaxCellPerRmCell,
--           mscAtmIfVpcVpdTmAbrMaxTimeBetweenRmCells,
--           mscAtmIfVpcLoopRowStatus,
--           mscAtmIfVptVccTmAbrCutoffDecreaseFactor,
--           mscAtmIfVccPmBwdMinimumClr01,
--           mscAtmIfVpcVpdTmFqpValue,
--           mscAtmIfVccTmRxTrafficDescType,
--           mscAtmIfVptVccTmAbrRateIncreaseFactor,
--           mscAtmIfCANrtVbrMinPerVcQueueLimit,
--           mscAtmIfCAAbrInitialCellRate,
--           mscAtmIfCAUbrStorageType,
--           mscAtmIfVptCAUbrRowStatus,
--           mscAtmIfVptVccTmAbrRxEfci,
--           mscAtmIfVccConnectionPointType,
--           mscAtmIfVccVcdTmAbrStorageType,
--           mscAtmIfVccStatsRxFrameDiscardClp,
--           mscAtmIfVpcVpdTmAbrDgcraMinimumDelay,
--           mscAtmIfCATroubledVccs,
--           mscAtmIfVptCAMaxVccs,
--           mscAtmIfVptVccSegSwitchSideLoopbackState,
--           mscAtmIfVccPmFwdTotalUserCellsTx01,
--           mscAtmIfVccPmBwdAverageClr0,
--           mscAtmIfCARtVbrComponentName,
--           mscAtmIfVptVccNepStorageType,
--           mscAtmIfConnMapOvComponentName,
--           mscAtmIfCAPermanentVpcs,
--           mscAtmIfVptVccTmAtmServiceCategory,
--           mscAtmIfVccVcdPmStorageType,
--           mscAtmIfCAUbrComponentName,
--           mscAtmIfVpcVpdTmAbrCutoffDecreaseFactor,
--           mscAtmIfVptCAStorageType,
--           mscAtmIfVptVccTmAbrForwardRmCellLimit,
--           mscAtmIfVccTmAbrConnectionType,
--           mscAtmIfEpComponentName,
--           mscAtmIfVpcLastMinimumCtd,
--           mscAtmIfVpcPmFwdTotalUserCellsTx0 }
-- STATUS  mandatory
-- DESCRIPTION
--   "A list of all current accessible leaf objects."

atmCoreGroup OBJECT IDENTIFIER ::= { atmCoreMIB 1 }
atmCoreGroupCB OBJECT IDENTIFIER ::= { atmCoreGroup 2 }
atmCoreGroupCB02 OBJECT IDENTIFIER ::= { atmCoreGroupCB 3 }
atmCoreGroupCB02A OBJECT IDENTIFIER ::= { atmCoreGroupCB02 2 }



-- Agent-Capabilities Statement:

-- PRODUCT-RELEASE "MscPassport Release 2.2 AtmCore."
-- STATUS          mandatory
-- DESCRIPTION     "Carrier Passport AtmCore MIB: MIB Version CB02A,
--                  Software Version CB02S1B."
-- SUPPORTS        Nortel-MsCarrier-MscPassport-AtmCoreMIB
--    INCLUDES     { atmCoreGroupCB02A }

atmCoreCapabilities OBJECT IDENTIFIER ::= { atmCoreMIB 3 }
atmCoreCapabilitiesCB OBJECT IDENTIFIER ::= { atmCoreCapabilities 2 }
atmCoreCapabilitiesCB02 OBJECT IDENTIFIER ::= { atmCoreCapabilitiesCB 3 }
atmCoreCapabilitiesCB02A OBJECT IDENTIFIER ::= { atmCoreCapabilitiesCB02 2 }





END
