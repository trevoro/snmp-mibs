-- *****************************************************************
-- tiaranet-snmp.mib:  Tiara Networks SNMP management MIB file
--
-- April,1st 1998, Shyla
--
-- Copyright (c) 1999-2000 by Tiara Networks, Inc.
-- All rights reserved.
--
-- *****************************************************************
--
TIARA-NETWORKS-SNMP-MIB DEFINITIONS ::= BEGIN

IMPORTS
        OBJECT-TYPE,
        IpAddress,
        MODULE-IDENTITY
                	FROM SNMPv2-SMI
        DisplayString
                	FROM SNMPv2-TC
	tiaraMgmt
	    	        FROM TIARA-NETWORKS-SMI ;

tiaraSnmpMib MODULE-IDENTITY
  	LAST-UPDATED "9904230000Z"
  	ORGANIZATION "Tiara Networks, Inc."
  	CONTACT-INFO
                " Tiara Networks
                  Customer Support

                  525 Race Street, Suite 100,
                  San Jose, CA 9512
                  USA

                  Tel: +1 408-216-4700
                  Fax: +1 408-216-4701

       	   	  E-mail: support@tiaranetworks.com"

  	DESCRIPTION
  		"SNMP Management group for Tiara Networks products."
  	REVISION      "9904230000Z"
  	DESCRIPTION
  		"Initial version of this MIB module."
         ::= { tiaraMgmt 5}


snmpObjects 		OBJECT IDENTIFIER ::= { tiaraSnmpMib 1 }

--
-- snmpObjects group
--
snmpAgentType OBJECT-TYPE
        SYNTAX  INTEGER {
            other(1),    -- none of the following
            snmpV1(2),   -- Simple Network Management Protocol
            snmpV2V1(3), -- Bi-lingual SNMP, Ver 2 and 1
            snmpV2cV1(4) -- Bi-lingual SNMP, V2c and V1
        }
        MAX-ACCESS    read-only
        STATUS        current
        DESCRIPTION   " Type of SNMP agent running on this entity. "
        ::= { snmpObjects 1 }

snmpRmonSupported OBJECT-TYPE
        SYNTAX        INTEGER 	{
			supported(1),
			not-supported(2)
	              }
        MAX-ACCESS    read-only
        STATUS        current
        DESCRIPTION   "	Indicates whether the SNMP agent supports the
			RMON MIB."
        ::= { snmpObjects 2 }

--
-- The snmpTrapRcvrTable contains all the information needed about 
-- which network management stations the agent wants to send the
-- trap. Using the table, a new network management station can be 
-- added or deleted.
--
snmpTrapRcvrTable OBJECT-TYPE
        SYNTAX        	SEQUENCE OF SnmpTrapRcvrEntry
        MAX-ACCESS    	not-accessible
        STATUS        	current
        DESCRIPTION   	" The trap receiver table lists the addresses
	  	          of the network management stations that
			  should receive trap messages from the agent.
			  This list is used by the agent to send the
			  traps. The snmpTrapRcvrEntryStatus parameter 
			  is used to add or delete an entry from
			  the table. Only the entries with valid
			  snmpTrapEntryStatus are used. A maximum of
			  10 entries can exist in this table at any
  			  point in time. A new entry can be created 
			  only if the values for all the columnar 
			  objects in the table are sent in the same 
			  SNMP SET request."
        ::= { snmpObjects 4 }

snmpTrapRcvrEntry OBJECT-TYPE
        SYNTAX        	SnmpTrapRcvrEntry
        MAX-ACCESS    	not-accessible
        STATUS        	current
        DESCRIPTION   	" A SNMP trap-receive table entry contains the
			  information of the network management
			  station to where the trap can be sent by the
			  agent. "
        INDEX         	{ snmpTrapRcvrAddress }
        ::= { snmpTrapRcvrTable 1 }

SnmpTrapRcvrEntry ::=
        SEQUENCE {
		snmpTrapRcvrEntryStatus	INTEGER,
                snmpTrapRcvrAddress	IpAddress,
                snmpTrapRcvrCommunity	DisplayString
        }

snmpTrapRcvrEntryStatus OBJECT-TYPE
        SYNTAX  	INTEGER {
                	    valid(1),
                	    invalid(2)
        		}
	MAX-ACCESS	read-write
	STATUS		current
	DESCRIPTION 	" The status of the SNMP trap-receive table
	                  entry. By default, the value is set to valid
			  when a new entry is created. When a network
			  management station is deleted from the table
			  the value of the parameter is set to
			  invalid. "
        DEFVAL          { valid }
	  ::= { snmpTrapRcvrEntry 1 }

snmpTrapRcvrAddress OBJECT-TYPE
        SYNTAX        	IpAddress
        MAX-ACCESS    	read-write
        STATUS        	current
        DESCRIPTION   	"IP address of the network management station
			 which can receive the trap from the agent. It
			 is unique for every entry and used as the
			 index for the SNMP trap-receive table. "
        ::= { snmpTrapRcvrEntry 2 }

snmpTrapRcvrCommunity OBJECT-TYPE
        SYNTAX        	DisplayString (SIZE (1..64))
        MAX-ACCESS    	read-write
        STATUS        	current
        DESCRIPTION   	" Community string associated with the network
	  		  management station receiving the trap
                          messages. The community string is used in
			  the trap messages. "
        ::= { snmpTrapRcvrEntry 3 }

END
