--
-- This SMIv2 module has been generated by smidump 0.2-cvs. Do not edit.
--

SONUS-SIP-SIGNALLING-MIB DEFINITIONS ::= BEGIN

IMPORTS
    Counter64, Integer32, IpAddress, MODULE-IDENTITY, NOTIFICATION-TYPE, 
    OBJECT-TYPE
        FROM SNMPv2-SMI
    RowStatus
        FROM SNMPv2-TC
    sonusEventClass, sonusEventDescription, sonusEventLevel
        FROM SONUS-COMMON-MIB
    sonusSignallingMIBs
        FROM SONUS-SMI
    SonusAdminState, SonusName, SonusServiceState
        FROM SONUS-TC;

sonusSipSignallingMIB MODULE-IDENTITY
    LAST-UPDATED    "200107310000Z"
    ORGANIZATION    
            "Sonus Networks, Inc."
    CONTACT-INFO    
            "   Customer Support
             Sonus Networks, Inc,
             5 carlisle Road
             Westford, MA 01886
             USA
             
             Tel: 978-692-8999
             Fax: 978-392-9118
             E-mail: cs.snmp@sonusnet.com"
    DESCRIPTION     
            "The MIB Module for SIP IP Call Signal Port Management."
    ::= { sonusSignallingMIBs 7 }


sonusSipSignallingMIBObjects OBJECT IDENTIFIER
    ::= { sonusSipSignallingMIB 1 }

sonusSipSigTimerObjects OBJECT IDENTIFIER
    ::= { sonusSipSignallingMIBObjects 1 }

sonusSipSigTimerT1 OBJECT-TYPE
    SYNTAX          Integer32 (1..10000)
    MAX-ACCESS      read-write
    STATUS          current
    DESCRIPTION     
            "This is the SIP protocol retransmission timer T1 (in milliseconds). This value applies to all future SIP calls."
    DEFVAL          { 500 }
    ::= { sonusSipSigTimerObjects 1 }

sonusSipSigTimerT2 OBJECT-TYPE
    SYNTAX          Integer32 (1..65535)
    MAX-ACCESS      read-write
    STATUS          current
    DESCRIPTION     
            "This is the SIP protocol retransmission timer T2 (in milliseconds). This value applies to all future SIP calls."
    DEFVAL          { 4000 }
    ::= { sonusSipSigTimerObjects 2 }

sonusSipSigTimerSessionKeepalive OBJECT-TYPE
    SYNTAX          Integer32 (0..1000)
    MAX-ACCESS      read-write
    STATUS          current
    DESCRIPTION     
            "This is the SIP protocol session keep-alive timer (in seconds). This value applies to all future SIP calls. when it is set to 0 keepalive is turned off"
    DEFVAL          { 120 }
    ::= { sonusSipSigTimerObjects 3 }

sonusSipSigRetryObjects OBJECT IDENTIFIER
    ::= { sonusSipSignallingMIBObjects 2 }

sonusSipSigNumOfRetry OBJECT-TYPE
    SYNTAX          Integer32 (4..12)
    MAX-ACCESS      read-write
    STATUS          current
    DESCRIPTION     
            "This is the number of retransmission for SIP message. This value applies to all future SIP calls."
    DEFVAL          { 7 }
    ::= { sonusSipSigRetryObjects 1 }

sonusSipSigInviteRetry OBJECT-TYPE
    SYNTAX          Integer32 (0..12)
    MAX-ACCESS      read-write
    STATUS          current
    DESCRIPTION     
            "This is the number of retransmission for INVITE. This value applies to all future SIP calls."
    DEFVAL          { 3 }
    ::= { sonusSipSigRetryObjects 2 }

sonusSipSigPortTable OBJECT-TYPE
    SYNTAX          SEQUENCE OF SonusSipSigPortEntry
    MAX-ACCESS      not-accessible
    STATUS          current
    DESCRIPTION     
            "Table of SIP Signalling Port configurations.  Limit of two ports."
    ::= { sonusSipSignallingMIBObjects 3 }

sonusSipSigPortEntry OBJECT-TYPE
    SYNTAX          SonusSipSigPortEntry
    MAX-ACCESS      not-accessible
    STATUS          current
    DESCRIPTION     
            "SIP Signalling Port configuration."
    INDEX           { sonusSipSigPortIndex }
    ::= { sonusSipSigPortTable 1 }

SonusSipSigPortEntry ::=
    SEQUENCE {
        sonusSipSigPortIndex            Integer32,
        sonusSipSigPortIpAddress        IpAddress,
        sonusSipSigPortNum              Integer32,
        sonusSipSigPortInterface        INTEGER,
        sonusSipSigPortRole             INTEGER,
        sonusSipSigPortMode             SonusServiceState,
        sonusSipSigPortState            SonusAdminState,
        sonusSipSigPortRowStatus        RowStatus,
        sonusSipSigPortAclState         SonusAdminState
    }

sonusSipSigPortIndex OBJECT-TYPE
    SYNTAX          Integer32
    MAX-ACCESS      read-only
    STATUS          current
    DESCRIPTION     
            "Identifies the Signal Listen Port entry."
    ::= { sonusSipSigPortEntry 1 }

sonusSipSigPortIpAddress OBJECT-TYPE
    SYNTAX          IpAddress
    MAX-ACCESS      read-write
    STATUS          current
    DESCRIPTION     
            "IP Address of the Sip Signalling Port - mandatory parameter"
    ::= { sonusSipSigPortEntry 2 }

sonusSipSigPortNum OBJECT-TYPE
    SYNTAX          Integer32 (1..65535)
    MAX-ACCESS      read-write
    STATUS          current
    DESCRIPTION     
            "UDP port number of SIP Signalling Port (default is 5060)."
    DEFVAL          { 5060 }
    ::= { sonusSipSigPortEntry 3 }

sonusSipSigPortInterface OBJECT-TYPE
    SYNTAX          INTEGER { mgtNif(1), nif(2) }
    MAX-ACCESS      read-write
    STATUS          current
    DESCRIPTION     
            "The interface type of SIP Call Signal Port. 'mgtnif' routes traffic over the gateway Managment ports.  'nif' routes traffic over one of the gateway PNS ports."
    DEFVAL          { mgtNif }
    ::= { sonusSipSigPortEntry 4 }

sonusSipSigPortRole OBJECT-TYPE
    SYNTAX          INTEGER { primary(1), secondary(2) }
    MAX-ACCESS      read-write
    STATUS          current
    DESCRIPTION     
            "Role of the Sip Call Siganlling Port."
    DEFVAL          { primary }
    ::= { sonusSipSigPortEntry 5 }

sonusSipSigPortMode OBJECT-TYPE
    SYNTAX          SonusServiceState
    MAX-ACCESS      read-write
    STATUS          current
    DESCRIPTION     
            "Mode of the SIP Signalling Port."
    DEFVAL          { inService }
    ::= { sonusSipSigPortEntry 6 }

sonusSipSigPortState OBJECT-TYPE
    SYNTAX          SonusAdminState
    MAX-ACCESS      read-write
    STATUS          current
    DESCRIPTION     
            "State of the SIP Signalling Port."
    DEFVAL          { disabled }
    ::= { sonusSipSigPortEntry 7 }

sonusSipSigPortRowStatus OBJECT-TYPE
    SYNTAX          RowStatus
    MAX-ACCESS      read-write
    STATUS          current
    DESCRIPTION     
            "This is for SNMP use."
    ::= { sonusSipSigPortEntry 8 }

sonusSipSigPortAclState OBJECT-TYPE
    SYNTAX          SonusAdminState
    MAX-ACCESS      read-write
    STATUS          current
    DESCRIPTION     
            "ACL checking state of the SIP Signalling port"
    DEFVAL          { disabled }
    ::= { sonusSipSigPortEntry 9 }

sonusSipSigPortStatusTable OBJECT-TYPE
    SYNTAX          SEQUENCE OF SonusSipSigPortStatusEntry
    MAX-ACCESS      not-accessible
    STATUS          current
    DESCRIPTION     
            "Table of SIP Signalling Port status."
    ::= { sonusSipSignallingMIBObjects 4 }

sonusSipSigPortStatusEntry OBJECT-TYPE
    SYNTAX          SonusSipSigPortStatusEntry
    MAX-ACCESS      not-accessible
    STATUS          current
    DESCRIPTION     
            "SIP Signalling Port Status."
    INDEX           { sonusSipSigPortStatusIndex }
    ::= { sonusSipSigPortStatusTable 1 }

SonusSipSigPortStatusEntry ::=
    SEQUENCE {
        sonusSipSigPortStatusIndex      Integer32,
        sonusSipSigPortStatusIpAddress  IpAddress,
        sonusSipSigPortStatusNum        Integer32,
        sonusSipSigPortStatusInterface  INTEGER,
        sonusSipSigPortStatusRole       INTEGER,
        sonusSipSigPortStatusNif        Integer32,
        sonusSipSigPortStatusState      SonusServiceState
    }

sonusSipSigPortStatusIndex OBJECT-TYPE
    SYNTAX          Integer32
    MAX-ACCESS      read-only
    STATUS          current
    DESCRIPTION     
            "Identifies the Signal Listen Port entry."
    ::= { sonusSipSigPortStatusEntry 1 }

sonusSipSigPortStatusIpAddress OBJECT-TYPE
    SYNTAX          IpAddress
    MAX-ACCESS      read-only
    STATUS          current
    DESCRIPTION     
            "IP Address of the Sip Signalling Port"
    ::= { sonusSipSigPortStatusEntry 2 }

sonusSipSigPortStatusNum OBJECT-TYPE
    SYNTAX          Integer32 (1..65535)
    MAX-ACCESS      read-only
    STATUS          current
    DESCRIPTION     
            "UDP port number of SIP Signalling Port."
    ::= { sonusSipSigPortStatusEntry 3 }

sonusSipSigPortStatusInterface OBJECT-TYPE
    SYNTAX          INTEGER { mgtNif(1), nif(2) }
    MAX-ACCESS      read-only
    STATUS          current
    DESCRIPTION     
            "The interface type of SIP Call Signal Port. 'mgtnif' routes traffic over the gateway Managment ports.  'nif' routes traffic over one of the gateway PNS ports."
    ::= { sonusSipSigPortStatusEntry 4 }

sonusSipSigPortStatusRole OBJECT-TYPE
    SYNTAX          INTEGER { primary(1), secondary(2) }
    MAX-ACCESS      read-only
    STATUS          current
    DESCRIPTION     
            "Role of the Sip Call Siganlling Port."
    ::= { sonusSipSigPortStatusEntry 5 }

sonusSipSigPortStatusNif OBJECT-TYPE
    SYNTAX          Integer32
    MAX-ACCESS      read-only
    STATUS          current
    DESCRIPTION     
            "The network interface index of the port."
    ::= { sonusSipSigPortStatusEntry 6 }

sonusSipSigPortStatusState OBJECT-TYPE
    SYNTAX          SonusServiceState
    MAX-ACCESS      read-only
    STATUS          current
    DESCRIPTION     
            "State of the SIP Signalling Port."
    ::= { sonusSipSigPortStatusEntry 7 }

sonusSipSigPortStatTable OBJECT-TYPE
    SYNTAX          SEQUENCE OF SonusSipSigPortStatEntry
    MAX-ACCESS      not-accessible
    STATUS          current
    DESCRIPTION     
            "Table of SIP Signalling Port statistics data."
    ::= { sonusSipSignallingMIBObjects 5 }

sonusSipSigPortStatEntry OBJECT-TYPE
    SYNTAX          SonusSipSigPortStatEntry
    MAX-ACCESS      not-accessible
    STATUS          current
    DESCRIPTION     
            "SIP Signalling Port Statistics."
    INDEX           { sonusSipSigPortStatIndex }
    ::= { sonusSipSigPortStatTable 1 }

SonusSipSigPortStatEntry ::=
    SEQUENCE {
        sonusSipSigPortStatIndex        Integer32,
        sonusSipSigPortStatIpAddress    IpAddress,
        sonusSipSigPortStatPortNum      Integer32,
        sonusSipSigPortStatCountReset   INTEGER,
        sonusSipSigPortStatCallRate     Integer32,
        sonusSipSigPortStatNumOrigCalls Integer32,
        sonusSipSigPortStatNumTermCalls Integer32,
        sonusSipSigPortStatNumTxPdus    Counter64,
        sonusSipSigPortStatNumRxPdus    Counter64,
        sonusSipSigPortStatNumTxBytes   Counter64,
        sonusSipSigPortStatNumRxBytes   Counter64
    }

sonusSipSigPortStatIndex OBJECT-TYPE
    SYNTAX          Integer32
    MAX-ACCESS      read-only
    STATUS          current
    DESCRIPTION     
            "Identifies the Signal Listen Port entry."
    ::= { sonusSipSigPortStatEntry 1 }

sonusSipSigPortStatIpAddress OBJECT-TYPE
    SYNTAX          IpAddress
    MAX-ACCESS      read-only
    STATUS          current
    DESCRIPTION     
            "IP Address of the Sip Signalling Port"
    ::= { sonusSipSigPortStatEntry 2 }

sonusSipSigPortStatPortNum OBJECT-TYPE
    SYNTAX          Integer32 (1..65535)
    MAX-ACCESS      read-only
    STATUS          current
    DESCRIPTION     
            "UDP port number of SIP Signalling Port."
    ::= { sonusSipSigPortStatEntry 3 }

sonusSipSigPortStatCountReset OBJECT-TYPE
    SYNTAX          INTEGER { unknown(1), reset(2) }
    MAX-ACCESS      read-write
    STATUS          current
    DESCRIPTION     
            "set opertion on this object resets all the statistics counts to zero"
    ::= { sonusSipSigPortStatEntry 4 }

sonusSipSigPortStatCallRate OBJECT-TYPE
    SYNTAX          Integer32
    MAX-ACCESS      read-only
    STATUS          current
    DESCRIPTION     
            "number of SIP calls per second during the last minute"
    ::= { sonusSipSigPortStatEntry 5 }

sonusSipSigPortStatNumOrigCalls OBJECT-TYPE
    SYNTAX          Integer32
    MAX-ACCESS      read-only
    STATUS          current
    DESCRIPTION     
            "Total number of outgoing calls sent out from this signaling port"
    ::= { sonusSipSigPortStatEntry 6 }

sonusSipSigPortStatNumTermCalls OBJECT-TYPE
    SYNTAX          Integer32
    MAX-ACCESS      read-only
    STATUS          current
    DESCRIPTION     
            "Total number of incoming calls received on this signaling port"
    ::= { sonusSipSigPortStatEntry 7 }

sonusSipSigPortStatNumTxPdus OBJECT-TYPE
    SYNTAX          Counter64
    MAX-ACCESS      read-only
    STATUS          current
    DESCRIPTION     
            "The total number of signalling PDUS sent out on this port"
    ::= { sonusSipSigPortStatEntry 8 }

sonusSipSigPortStatNumRxPdus OBJECT-TYPE
    SYNTAX          Counter64
    MAX-ACCESS      read-only
    STATUS          current
    DESCRIPTION     
            "The total number of signalling PDUS received on this port"
    ::= { sonusSipSigPortStatEntry 9 }

sonusSipSigPortStatNumTxBytes OBJECT-TYPE
    SYNTAX          Counter64
    MAX-ACCESS      read-only
    STATUS          current
    DESCRIPTION     
            "The total number of signalling BYTES sent out from this port"
    ::= { sonusSipSigPortStatEntry 10 }

sonusSipSigPortStatNumRxBytes OBJECT-TYPE
    SYNTAX          Counter64
    MAX-ACCESS      read-only
    STATUS          current
    DESCRIPTION     
            "The total number of signalling BYTES received by this port"
    ::= { sonusSipSigPortStatEntry 11 }

sonusSipAcl OBJECT IDENTIFIER
    ::= { sonusSipSignallingMIBObjects 6 }

sonusSipAclNextIndex OBJECT-TYPE
    SYNTAX          Integer32
    MAX-ACCESS      read-only
    STATUS          current
    DESCRIPTION     
            "the next valid index to use when creating a new sonusSipAclEntry"
    ::= { sonusSipAcl 1 }

sonusSipAclTable OBJECT-TYPE
    SYNTAX          SEQUENCE OF SonusSipAclEntry
    MAX-ACCESS      not-accessible
    STATUS          current
    DESCRIPTION     
            "This is the Application Server List"
    ::= { sonusSipAcl 2 }

sonusSipAclEntry OBJECT-TYPE
    SYNTAX          SonusSipAclEntry
    MAX-ACCESS      not-accessible
    STATUS          current
    DESCRIPTION     
            "An Application Server"
    INDEX           { sonusSipRemoteAppSvrIndex }
    ::= { sonusSipAclTable 1 }

SonusSipAclEntry ::=
    SEQUENCE {
        sonusSipRemoteAppSvrIndex       Integer32,
        sonusSipRemoteAppSvrName        SonusName,
        sonusSipRemoteAppSvrIpAddress   IpAddress,
        sonusSipRemoteAppSvrRowStatus   RowStatus
    }

sonusSipRemoteAppSvrIndex OBJECT-TYPE
    SYNTAX          Integer32
    MAX-ACCESS      read-only
    STATUS          current
    DESCRIPTION     
            "Identifies a remote application server entry."
    ::= { sonusSipAclEntry 1 }

sonusSipRemoteAppSvrName OBJECT-TYPE
    SYNTAX          SonusName
    MAX-ACCESS      read-write
    STATUS          current
    DESCRIPTION     
            "Name of the application server."
    ::= { sonusSipAclEntry 2 }

sonusSipRemoteAppSvrIpAddress OBJECT-TYPE
    SYNTAX          IpAddress
    MAX-ACCESS      read-write
    STATUS          current
    DESCRIPTION     
            "IP Address of the application server."
    ::= { sonusSipAclEntry 3 }

sonusSipRemoteAppSvrRowStatus OBJECT-TYPE
    SYNTAX          RowStatus
    MAX-ACCESS      read-write
    STATUS          current
    DESCRIPTION     
            "row status of the application server."
    ::= { sonusSipAclEntry 4 }

sonusSipSignallingMIBNotifications OBJECT IDENTIFIER
    ::= { sonusSipSignallingMIB 2 }

sonusSipSignallingMIBNotificationsPrefix OBJECT IDENTIFIER
    ::= { sonusSipSignallingMIBNotifications 0 }

sonusSipSignallingMIBNotificationsObjects OBJECT IDENTIFIER
    ::= { sonusSipSignallingMIBNotifications 1 }

sonusSipCallSigPortOpenNotification NOTIFICATION-TYPE
    OBJECTS         { sonusSipSigPortIpAddress, sonusSipSigPortNum, 
                      sonusEventDescription, sonusEventClass, 
                      sonusEventLevel }
    STATUS          current
    DESCRIPTION     
            "This trap indicates that a call signaling port is opened."
    ::= { sonusSipSignallingMIBNotificationsPrefix 1 }

sonusSipCallSigPortCloseNotification NOTIFICATION-TYPE
    OBJECTS         { sonusSipSigPortIpAddress, sonusSipSigPortNum, 
                      sonusEventDescription, sonusEventClass, 
                      sonusEventLevel }
    STATUS          current
    DESCRIPTION     
            "This trap indicates that a call signaling port is closed."
    ::= { sonusSipSignallingMIBNotificationsPrefix 2 }

END -- end of module SONUS-SIP-SIGNALLING-MIB.
