--			Ascend mibdebug MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBDEBUG-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibdebugProfile  OBJECT IDENTIFIER ::= { configuration 72}

	-- The mibdebugProfile table
	--
	-- This table contains parameters for the mibdebugProfile profile
	--

    mibdebugProfileTable	OBJECT-TYPE
	SYNTAX		SEQUENCE OF MibdebugProfileEntry
	ACCESS		not-accessible
	STATUS		mandatory
	DESCRIPTION	"A list of mibdebugProfile profile entries."
	::= { mibdebugProfile 1 }

    mibdebugProfileEntry	OBJECT-TYPE
	SYNTAX		MibdebugProfileEntry
	ACCESS		not-accessible
	STATUS		mandatory
	DESCRIPTION	"A mibdebugProfile entry containing objects that
			 maps to the parameters of mibdebugProfile profile."
	INDEX		{ debugProfile-Shelf-o, debugProfile-Slot-o, debugProfile-Item-o }
	::= { mibdebugProfileTable 1 }

    MibdebugProfileEntry ::=
	SEQUENCE {
	    debugProfile-Shelf-o
		INTEGER,
	    debugProfile-Slot-o
		INTEGER,
	    debugProfile-Item-o
		INTEGER,
	    debugProfile-PhysicalAddress-Shelf
		INTEGER,
	    debugProfile-PhysicalAddress-Slot
		INTEGER,
	    debugProfile-PhysicalAddress-ItemNumber
		INTEGER,
	    debugProfile-Active
		INTEGER,
	    debugProfile-EnableCoreDump
		INTEGER,
	    debugProfile-CoreDumpServer
		DisplayString,
	    debugProfile-EnableGdb
		INTEGER,
	    debugProfile-GdbHost
		DisplayString,
	    debugProfile-CsTracking
		INTEGER,
	    debugProfile-GenericField
		INTEGER,
	    debugProfile-MinWarningCoreDump
		INTEGER,
	    debugProfile-MaxWarningCoreDump
		INTEGER,
	    debugProfile-CoreDumpLocation
		INTEGER,
	    debugProfile-FlashCoreOverwrite
		INTEGER,
	    debugProfile-CoreDumpRipUpdate
		INTEGER,
	    debugProfile-CoredumpSourceAddress
		IpAddress,
	    debugProfile-Action-o
		INTEGER
	}

    debugProfile-Shelf-o	OBJECT-TYPE
	SYNTAX	INTEGER
	ACCESS	read-only
	STATUS	mandatory
	DESCRIPTION	""
	::= { mibdebugProfileEntry 1 }

    debugProfile-Slot-o	OBJECT-TYPE
	SYNTAX	INTEGER
	ACCESS	read-only
	STATUS	mandatory
	DESCRIPTION	""
	::= { mibdebugProfileEntry 2 }

    debugProfile-Item-o	OBJECT-TYPE
	SYNTAX	INTEGER
	ACCESS	read-only
	STATUS	mandatory
	DESCRIPTION	""
	::= { mibdebugProfileEntry 3 }

    debugProfile-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibdebugProfileEntry 4 }

    debugProfile-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibdebugProfileEntry 5 }

    debugProfile-PhysicalAddress-ItemNumber	OBJECT-TYPE
	SYNTAX	INTEGER
	ACCESS	read-write
	STATUS	mandatory
	DESCRIPTION	"A number that specifies an addressable entity within the context of shelf and slot."
	::= { mibdebugProfileEntry 6 }

    debugProfile-Active	OBJECT-TYPE
	SYNTAX	INTEGER {
		    no (1),
		    yes (2)
		}
	ACCESS	read-write
	STATUS	mandatory
	DESCRIPTION	"Setting this field to Yes enables this profile. Setting this field to No disables this entire profile."
	::= { mibdebugProfileEntry 7 }

    debugProfile-EnableCoreDump	OBJECT-TYPE
	SYNTAX	INTEGER {
		    no (1),
		    yes (2)
		}
	ACCESS	read-write
	STATUS	mandatory
	DESCRIPTION	"Core dump on system failure can be enabled by setting this field to Yes. Core dumps are disabled if this field is No."
	::= { mibdebugProfileEntry 8 }

    debugProfile-CoreDumpServer	OBJECT-TYPE
	SYNTAX	DisplayString
	ACCESS	read-write
	STATUS	mandatory
	DESCRIPTION	"The name (or IP address) of the host setup to receive our core dumps."
	::= { mibdebugProfileEntry 9 }

    debugProfile-EnableGdb	OBJECT-TYPE
	SYNTAX	INTEGER {
		    no (1),
		    yes (2)
		}
	ACCESS	read-write
	STATUS	mandatory
	DESCRIPTION	"GDB can be enabled by setting this field to Yes. GDB is disabled if this field is No."
	::= { mibdebugProfileEntry 10 }

    debugProfile-GdbHost	OBJECT-TYPE
	SYNTAX	DisplayString
	ACCESS	read-write
	STATUS	mandatory
	DESCRIPTION	"The name (or IP address) of the host running GDB."
	::= { mibdebugProfileEntry 11 }

    debugProfile-CsTracking	OBJECT-TYPE
	SYNTAX	INTEGER {
		    no (1),
		    yes (2)
		}
	ACCESS	read-write
	STATUS	mandatory
	DESCRIPTION	"csTracking can be enabled by setting this field to Yes. csTracking is disabled if this field is No."
	::= { mibdebugProfileEntry 12 }

    debugProfile-GenericField	OBJECT-TYPE
	SYNTAX	INTEGER
	ACCESS	read-write
	STATUS	mandatory
	DESCRIPTION	"This field can be used as a generic bitmask stored in nonvolatile memory and thus preserved over resets and powerdowns"
	::= { mibdebugProfileEntry 13 }

    debugProfile-MinWarningCoreDump	OBJECT-TYPE
	SYNTAX	INTEGER
	ACCESS	read-write
	STATUS	mandatory
	DESCRIPTION	"Minimum value for a range of warning numbers that will generate a core dump (a core dump is taken for warnings between the minimum and maximum warning numbers inclusive) if coredumps are enabled. The default value of 0 in the minimum and maximum fields mean that only warnings from 101 to 121 will cause a core dump."
	::= { mibdebugProfileEntry 14 }

    debugProfile-MaxWarningCoreDump	OBJECT-TYPE
	SYNTAX	INTEGER
	ACCESS	read-write
	STATUS	mandatory
	DESCRIPTION	"Maximum value for a range of warning numbers that will generate a core dump (a core dump is taken for warnings between the minimum and maximum warning numbers inclusive) if coredumps are enabled. The default value of 0 in the minimum and maximum fields mean that only warnings from 101 to 121 will cause a core dump."
	::= { mibdebugProfileEntry 15 }

    debugProfile-CoreDumpLocation	OBJECT-TYPE
	SYNTAX	INTEGER {
		    networkOnly (2),
		    flashOnly (3),
		    firstFlashThenNetwork (4)
		}
	ACCESS	read-write
	STATUS	mandatory
	DESCRIPTION	"Core dumps will go to the specified location if enabled."
	::= { mibdebugProfileEntry 16 }

    debugProfile-FlashCoreOverwrite	OBJECT-TYPE
	SYNTAX	INTEGER {
		    no (1),
		    yes (2)
		}
	ACCESS	read-write
	STATUS	mandatory
	DESCRIPTION	"A previous flash dump will be overwritten by a new dump if this field to Yes, but will be preserved if this field is No."
	::= { mibdebugProfileEntry 17 }

    debugProfile-CoreDumpRipUpdate	OBJECT-TYPE
	SYNTAX	INTEGER {
		    updateHigherFreq (1),
		    updateHighFreq (2),
		    updateMedFreq (3),
		    updateLowFreq (4),
		    updateLowerFreq (5),
		    updateOff (6)
		}
	ACCESS	read-write
	STATUS	mandatory
	DESCRIPTION	"RIP updates will be sent accordingly based on the setting here during coredump."
	::= { mibdebugProfileEntry 19 }

    debugProfile-CoredumpSourceAddress	OBJECT-TYPE
	SYNTAX	IpAddress
	ACCESS	read-write
	STATUS	mandatory
	DESCRIPTION	"The coredump source ip address for the shelf card. It is usually set only if the system-ip-address and the coredump server ip address belong to different networks."
	::= { mibdebugProfileEntry 20 }

    debugProfile-Action-o	OBJECT-TYPE
	SYNTAX	INTEGER {
		    noAction (1),
		    createProfile (2),
		    deleteProfile (3)
		}
	ACCESS	read-write
	STATUS	mandatory
	DESCRIPTION	""
	::= { mibdebugProfileEntry 18 }

END
