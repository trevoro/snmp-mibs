ACC-OSPF DEFINITIONS ::= BEGIN

    IMPORTS
	 OBJECT-TYPE, IpAddress, TimeTicks, Gauge, Counter FROM RFC1155-SMI
	 ospfLsdbAreaId FROM OSPF-MIB
	 TRAP-TYPE FROM RFC-1215
        accTrapLogSeqNum FROM ACC-SYSTEM
	accBRG, DisplayString, RowStatus, IfIndex, SmdsAddress
            FROM ACC-MIB

        ospfIfIpAddress,
		  --ospfAddresLessIf,
		  ospfIfType,
		  ospfVirtNbrArea,
        ospfAreaId,
		  ospfVirtIfAreaId,
		  ospfRouterId,
		  ospfVirtIfNeighbor,
        ospfASBdrRtrStatus,
		  ospfTOSSupport,
		  ospfMulticastExtensions, 
        ospfAdminStat,
		  ospfAreaAggregateAreaID,
		  ospfAreaAggregateNet,
        ospfAreaAggregateMask,
		  ospfNbrIpAddr,
		  ospfLsdbType,
        AreaID,
		  RouterID,
		  Status,
		  TruthValue,
		  InterfaceIndex
             FROM ACC-FAKE;

    -- Index objects from rfc1850
    OspfNbrIpAddr             ::= IpAddress
    OspfNbrAddressLessIndex   ::= INTEGER
    OspfIfIpAddress	      ::= IpAddress
--    OspfAddressLessIf 	      ::= INTEGER
    OspfAreaId		      ::= IpAddress
    -- ACC OSPF branch
    accOspf 		OBJECT IDENTIFIER ::= { accBRG 52 }
    accOspfGeneral	OBJECT IDENTIFIER ::= { accOspf 1 }
    --
    --  ACC general OSPF objects
    --
    accOspfMessageLevel OBJECT-TYPE
        SYNTAX  INTEGER (1..7)
        ACCESS  read-write
        STATUS  mandatory
        DESCRIPTION
             "The diagnostic and message level setting. A higher value
	      generates more detailed diagnostic feedback."
	DEFVAL { 1 }
        ::= { accOspfGeneral 1 }
    --
    --		Obsoleted OSPF Export Table
    --
    --		{ accOspf 2 }
    --
    --		The OSPF Area Table
    --
    accOspfAreaTable OBJECT-TYPE
        SYNTAX  SEQUENCE OF AccOspfAreaEntry 
        ACCESS  not-accessible
        STATUS  mandatory
	DESCRIPTION
	     "Proprietary extensions to the ospfAreaTable defined in
	      rfc1850."
    ::= { accOspf 3 }
    accOspfAreaEntry OBJECT-TYPE
        SYNTAX 	AccOspfAreaEntry
        ACCESS 	not-accessible
        STATUS  mandatory
	DESCRIPTION
		" "
        INDEX   { ospfAreaId }
        ::= { accOspfAreaTable 1 }
    AccOspfAreaEntry ::=
        SEQUENCE {
    	    accOspfAreaMessageLevel	INTEGER
        }
    	accOspfAreaMessageLevel OBJECT-TYPE
    	SYNTAX 	INTEGER (1..7)
    	ACCESS 	read-write
    	STATUS  mandatory
	DESCRIPTION
             "The configured diagnostic level for this OSPF area. 
              Increasing the value increases the diagnostic information.
              Level 7 is mostly informational."
        DEFVAL { 1 }
    	::= { accOspfAreaEntry 1 }
    --
    --          The OSPF Interface Table
    --
    accOspfIfTable OBJECT-TYPE
        SYNTAX  SEQUENCE OF AccOspfIfEntry
        ACCESS  not-accessible
        STATUS  mandatory
        DESCRIPTION
             "Proprietary extensions to the ospfIfTable defined in
              rfc1850."
    ::= { accOspf 4 }
    accOspfIfEntry OBJECT-TYPE
        SYNTAX  AccOspfIfEntry
        ACCESS  not-accessible
        STATUS  mandatory
	DESCRIPTION
		" "
        INDEX   { ospfIfIpAddress, ospfAddressLessIf }
        ::= { accOspfIfTable 1 }
    AccOspfIfEntry ::=
        SEQUENCE {
            accOspfIfMessageLevel     INTEGER
        }
        accOspfIfMessageLevel OBJECT-TYPE
        SYNTAX  INTEGER (1..7)
        ACCESS  read-write
        STATUS  mandatory
        DESCRIPTION
             "The configured diagnostic level for this OSPF interface.
              Increasing the value increases the diagnostic information.
              Level 7 is mostly informational."
        DEFVAL { 1 }
        ::= { accOspfIfEntry 1 }
    --
    --          The OSPF Neighbor Table
    --
    accOspfNbrTable OBJECT-TYPE
        SYNTAX  SEQUENCE OF AccOspfNbrEntry
        ACCESS  not-accessible
        STATUS  mandatory
        DESCRIPTION
             "Proprietary extensions to the ospfNbrTable defined in
              rfc1850."
    ::= { accOspf 5 }
    accOspfNbrEntry OBJECT-TYPE
        SYNTAX  AccOspfNbrEntry
        ACCESS  not-accessible
        STATUS  mandatory
	DESCRIPTION
		" "
        INDEX   { ospfNbrIpAddr, ospfNbrAddressLessIndex }
        ::= { accOspfNbrTable 1 }
    AccOspfNbrEntry ::=
        SEQUENCE {
            accOspfNbrMessageLevel     INTEGER
        }
        accOspfNbrMessageLevel OBJECT-TYPE
        SYNTAX  INTEGER (1..7)
        ACCESS  read-write
        STATUS  mandatory
        DESCRIPTION
             "The configured diagnostic level for this OSPF neighbor.
              Increasing the value increases the diagnostic information.
              Level 7 is mostly informational."
        DEFVAL { 1 }
        ::= { accOspfNbrEntry 1 }
    --
    --          The OSPF Export Table
    --
    accOspfExportTable OBJECT-TYPE
        SYNTAX  SEQUENCE OF AccOspfExportEntry
        ACCESS  not-accessible
        STATUS  mandatory
        DESCRIPTION
             "This table lists the export policies used by the local
              OSPF routing application. Export policies determine what
              foriegn routes OSPF will included in the OSPF routing domain."
    ::= { accOspf 6 }
    accOspfExportEntry OBJECT-TYPE
        SYNTAX  AccOspfExportEntry
        ACCESS  not-accessible
        STATUS  mandatory
        DESCRIPTION
                " "
        INDEX   { accOspfExportProtocol, accOspfExportSpecific2,
		  accOspfExportSpecific1, accOspfExportNetwork,
		  accOspfExportMask
                }
        ::= { accOspfExportTable 1 }
    AccOspfExportEntry ::=
        SEQUENCE {
        	accOspfExportProtocol           INTEGER,
        	accOspfExportSpecific2          INTEGER,
        	accOspfExportSpecific1          INTEGER,
        	accOspfExportNetwork            IpAddress,
        	accOspfExportMask               IpAddress,
        	accOspfExportAction             INTEGER,
        	accOspfExportMetric             INTEGER,
        	accOspfExportTag                INTEGER,
        	accOspfExportStatus             RowStatus
        }
        accOspfExportProtocol OBJECT-TYPE
        SYNTAX  INTEGER {
                    any(1),
                    local(2),
                    static(3),
                    iospf(4),
                    eospf(5),
                    rip(6),
                    ebgp(7),
                    ibgp(8)
                }
        ACCESS  read-only
        STATUS  mandatory
        DESCRIPTION
             "The protocol owner of the route."
        ::= { accOspfExportEntry  1 }
        accOspfExportSpecific2 OBJECT-TYPE
        SYNTAX  INTEGER
        ACCESS  read-only
        STATUS  mandatory
        DESCRIPTION
             "The secondary protocol specific value for this export
              policy."
        ::= { accOspfExportEntry  2 }
        accOspfExportSpecific1 OBJECT-TYPE
        SYNTAX  INTEGER
        ACCESS  read-only
        STATUS  mandatory
        DESCRIPTION
             "The protocol specific value for this export policy."
        ::= { accOspfExportEntry  3 }
        accOspfExportNetwork OBJECT-TYPE
        SYNTAX  IpAddress
        ACCESS  read-only
        STATUS  mandatory
        DESCRIPTION
             "The export policies NLRI prefix."
        ::= { accOspfExportEntry  4 }
        accOspfExportMask OBJECT-TYPE
        SYNTAX  IpAddress
        ACCESS  read-only
        STATUS  mandatory
        DESCRIPTION
             "The mask to be used against NLRI when performing a policy
              lookup. A match is considered met if the result is subsumable
              by the network object value."
        ::= { accOspfExportEntry  5 }
        accOspfExportAction OBJECT-TYPE
        SYNTAX  INTEGER {
                    export(1),
                    block(2)
                }
        ACCESS  read-write
        STATUS  mandatory
        DESCRIPTION
             "The action to be taken when a policy match is met."
        DEFVAL { export }
        ::= { accOspfExportEntry  6 }
        accOspfExportMetric OBJECT-TYPE
        SYNTAX  INTEGER (0..4294967295)
        ACCESS  read-write
        STATUS  mandatory
        DESCRIPTION
             "The metric to be included when importing into the OSPF
              domain."
        DEFVAL { 0 }
        ::= { accOspfExportEntry  7 }
        accOspfExportTag OBJECT-TYPE
        SYNTAX  INTEGER (0..4294967295)
        ACCESS  read-write
        STATUS  mandatory
        DESCRIPTION
             "The OSPF tag to be assigned to routes that match this
              export policy. A value of zero tells OSPF to automatically
              generate a tag."
        DEFVAL { 0 }
        ::= { accOspfExportEntry  8 }
        accOspfExportStatus OBJECT-TYPE
        SYNTAX  RowStatus
        ACCESS  read-write
        STATUS  mandatory
        DESCRIPTION
             "The current status of this entry."
        ::= { accOspfExportEntry  9 }
-- START CFG_TRAP_ENHANCEMENTS
-- ospf traps branch
	accOspfTraps OBJECT IDENTIFIER ::= { accOspf 7 } 
	accOspfTrapMsg	OBJECT-TYPE
	SYNTAX		DisplayString
	ACCESS		read-only
	STATUS		mandatory
	DESCRIPTION	
		"OSPF Trap Message."
	::= { accOspfTraps 1 }
-- END MANILA

        accOspfIntfNotNBMATrap TRAP-TYPE
        ENTERPRISE        accOspfTraps 
        VARIABLES       { accOspfTrapMsg,
                          ospfIfIpAddress ,
accTrapLogSeqNum}
        DESCRIPTION
                "Indicates, that a NON NBMA interface is being set to 
		 NBMA neighbor. As only X25 and FR are NBMA network types.
SEVERITY-DEFAULT: Warning 
EVENTTYPE-DEFAULT: 10 
ADDITIONAL-TEXT-VARIABLES: { accTrapLogSeqNum,accOspfTrapMsg }
PCAUSE-DEFAULT: 7 " 
 
        ::= 1 
        accOspfAllocPolNodeTrap TRAP-TYPE
        ENTERPRISE        accOspfTraps 
        VARIABLES       { accOspfTrapMsg,
                          accOspfExportNetwork,
                          accOspfExportMask ,
                           accTrapLogSeqNum}
        DESCRIPTION
                "The command to add export policy can fail because 
		 of a memory alloc failure.
SEVERITY-DEFAULT: Major 
EVENTTYPE-DEFAULT: 10 
ADDITIONAL-TEXT-VARIABLES: { accTrapLogSeqNum,accOspfTrapMsg }
PCAUSE-DEFAULT: 32 " 
 
        ::= 2
        accOspfNotificationIdTrap TRAP-TYPE
        ENTERPRISE        accOspfTraps 
        VARIABLES       { accOspfTrapMsg  ,
                           accTrapLogSeqNum}
        DESCRIPTION
                "Failure because of memory shortage most probably 
		 because of a memory alloc failure.
SEVERITY-DEFAULT: Major 
EVENTTYPE-DEFAULT: 10 
ADDITIONAL-TEXT-VARIABLES: { accTrapLogSeqNum,accOspfTrapMsg }
PCAUSE-DEFAULT: 32 " 
 
        ::= 3
        accOspfAreaTrap TRAP-TYPE
        ENTERPRISE        accOspfTraps 
        VARIABLES       { accOspfTrapMsg,
                          ospfAreaId ,
accTrapLogSeqNum}
        DESCRIPTION
                "While adding a summary entry for NSSA type, the 
		 area type has to be NSSA.
SEVERITY-DEFAULT: Major 
EVENTTYPE-DEFAULT: 10 
ADDITIONAL-TEXT-VARIABLES: { accTrapLogSeqNum,accOspfTrapMsg }
PCAUSE-DEFAULT: 32 " 
 
        ::= 4
        accOspfPrioTrap TRAP-TYPE
        ENTERPRISE        accOspfTraps 
        VARIABLES       { accOspfTrapMsg,
                          ospfIfIpAddress,
                          ospfIfType ,
accTrapLogSeqNum}
        DESCRIPTION
                "P2P interfaces cannot have settings for priorities. 
		 Hence they should be no such setting on them.
SEVERITY-DEFAULT: Warning 
EVENTTYPE-DEFAULT: 10 
ADDITIONAL-TEXT-VARIABLES: { accTrapLogSeqNum,accOspfTrapMsg }
PCAUSE-DEFAULT: 7 " 
 
        ::= 5
        accOspfPollIntTrap TRAP-TYPE
        ENTERPRISE        accOspfTraps 
        VARIABLES       { accOspfTrapMsg,
                          ospfIfIpAddress,
                          ospfIfType ,
accTrapLogSeqNum}
        DESCRIPTION
                "This Poll interval is valid only for NBMA interface. 
		 The trap indicates user tried to set poll interval 
		 on an interface other than NBMA.
SEVERITY-DEFAULT: Warning 
EVENTTYPE-DEFAULT: 10 
ADDITIONAL-TEXT-VARIABLES: { accTrapLogSeqNum,accOspfTrapMsg }
PCAUSE-DEFAULT: 7 " 
 
        ::= 6 
        accOspfBckboneAreaTrap TRAP-TYPE
        ENTERPRISE        accOspfTraps 
        VARIABLES       { accOspfTrapMsg,
                          ospfVirtIfAreaId ,
accTrapLogSeqNum}
        DESCRIPTION
                "Indicates OSPF backbone is entered as transit area 
		 for the virtual link.
SEVERITY-DEFAULT: Warning 
EVENTTYPE-DEFAULT: 10 
ADDITIONAL-TEXT-VARIABLES: { accTrapLogSeqNum,accOspfTrapMsg }
PCAUSE-DEFAULT: 7 " 
 
        ::= 7
        accOspfTransitAreaTrap TRAP-TYPE
        ENTERPRISE        accOspfTraps 
        VARIABLES       { accOspfTrapMsg,
                          ospfVirtIfAreaId ,
accTrapLogSeqNum}
        DESCRIPTION
                "Indicates that the entered area_id doesnt exist 
		 in the transit area.
SEVERITY-DEFAULT: Minor 
EVENTTYPE-DEFAULT: 10 
ADDITIONAL-TEXT-VARIABLES: { accTrapLogSeqNum,accOspfTrapMsg }
PCAUSE-DEFAULT: 152 " 
 
        ::= 8
        accOspfVirtLnkTrap TRAP-TYPE
        ENTERPRISE        accOspfTraps 
        VARIABLES       { accOspfTrapMsg,
                          ospfRouterId ,
accTrapLogSeqNum}
        DESCRIPTION
                "Virtual interfaces are associated with the backbone. 
		 Without the backbone, user cant configure Virtual 
		 interface.
SEVERITY-DEFAULT: Warning 
EVENTTYPE-DEFAULT: 10 
ADDITIONAL-TEXT-VARIABLES: { accTrapLogSeqNum,accOspfTrapMsg }
PCAUSE-DEFAULT: 7 " 
 
        ::= 9
        accOspfConfigBackboneTrap TRAP-TYPE
        ENTERPRISE        accOspfTraps 
        VARIABLES       { accOspfTrapMsg,
                          ospfAreaId ,
accTrapLogSeqNum}
        DESCRIPTION
                "The backbone area is always a transit area. 
		 Attempting to set the backbone area to anything 
		 other than transit area will be rejected.
SEVERITY-DEFAULT: Warning 
EVENTTYPE-DEFAULT: 10 
ADDITIONAL-TEXT-VARIABLES: { accTrapLogSeqNum,accOspfTrapMsg }
PCAUSE-DEFAULT: 7 " 
 
        ::= 10
        accOspfEnableAreaTrap TRAP-TYPE
        ENTERPRISE        accOspfTraps 
        VARIABLES       { accOspfTrapMsg,
                          ospfAreaId ,
accTrapLogSeqNum}
        DESCRIPTION
                "Either due to parent OSPF not found or due to 
		 memory shortage in allocating memory for dbh and 
		 dbt or while allocating memory for timer to reference 
		 correct routing instance, or due to shortage of 
		 memory while creating LSA, or when failed to enable 
		 the interface.
SEVERITY-DEFAULT: Major 
EVENTTYPE-DEFAULT: 10 
ADDITIONAL-TEXT-VARIABLES: { accTrapLogSeqNum,accOspfTrapMsg }
PCAUSE-DEFAULT: 32 " 
 
	::= 11
        accOspfAreaTransitTrap TRAP-TYPE
        ENTERPRISE        accOspfTraps 
        VARIABLES       { accOspfTrapMsg,
                          ospfAreaId ,
accTrapLogSeqNum}
        DESCRIPTION
                "The area_id user has entered is not of the type 
		 stub. It is of transit type.
SEVERITY-DEFAULT: Warning 
EVENTTYPE-DEFAULT: 10 
ADDITIONAL-TEXT-VARIABLES: { accTrapLogSeqNum,accOspfTrapMsg }
PCAUSE-DEFAULT: 7 " 
 
        ::= 12
        accOspfDisableTrap TRAP-TYPE
        ENTERPRISE        accOspfTraps 
        VARIABLES       { accOspfTrapMsg ,
                           accTrapLogSeqNum}
        DESCRIPTION
                "Indicates that the ospf_mgr_disable_gen has returned 
		 FALSE.
SEVERITY-DEFAULT: Warning 
EVENTTYPE-DEFAULT: 10 
ADDITIONAL-TEXT-VARIABLES: { accTrapLogSeqNum,accOspfTrapMsg }
PCAUSE-DEFAULT: 7 " 
 
        ::= 13
        accOspfInvASBRTrap TRAP-TYPE
        ENTERPRISE        accOspfTraps 
        VARIABLES       { accOspfTrapMsg,
                          ospfASBdrRtrStatus ,
accTrapLogSeqNum}
        DESCRIPTION
                "OSPF stub areas cannot contain ASBR.
SEVERITY-DEFAULT: Major 
EVENTTYPE-DEFAULT: 10 
ADDITIONAL-TEXT-VARIABLES: { accTrapLogSeqNum,accOspfTrapMsg }
PCAUSE-DEFAULT: 253 " 
 
        ::= 14
        accOspfNotifIdTrap TRAP-TYPE
        ENTERPRISE        accOspfTraps 
        VARIABLES       { accOspfTrapMsg ,
                           accTrapLogSeqNum}
        DESCRIPTION
                "Each instance of a routing protocol or the IP 
		 instance itself has a bit in the RTH for a change 
		 list entry. The trap indicates that it is due to 
		 the inability of getting bit offset in this field 
		 which is reserved for it in each rt_head in the 
		 routing table.
SEVERITY-DEFAULT: Major 
EVENTTYPE-DEFAULT: 10 
ADDITIONAL-TEXT-VARIABLES: { accTrapLogSeqNum,accOspfTrapMsg }
PCAUSE-DEFAULT: 253 " 
 
        ::= 15
        accOspfInvTOSTrap TRAP-TYPE
        ENTERPRISE        accOspfTraps 
        VARIABLES       { accOspfTrapMsg,
                          ospfTOSSupport ,
accTrapLogSeqNum}
        DESCRIPTION
                "TOS is preset to OFF, because TOS is not supported.
SEVERITY-DEFAULT: Warning 
EVENTTYPE-DEFAULT: 10 
ADDITIONAL-TEXT-VARIABLES: { accTrapLogSeqNum,accOspfTrapMsg }
PCAUSE-DEFAULT: 7 " 
 
        ::= 16
        accOspfInvMcastTrap TRAP-TYPE
        ENTERPRISE        accOspfTraps 
        VARIABLES       { accOspfTrapMsg,
                          ospfMulticastExtensions ,
accTrapLogSeqNum}
        DESCRIPTION
                "Indicates that the user has entered an Invalid 
		 Mcast option for the OSPF neighbor.
SEVERITY-DEFAULT: Warning 
EVENTTYPE-DEFAULT: 10 
ADDITIONAL-TEXT-VARIABLES: { accTrapLogSeqNum,accOspfTrapMsg }
PCAUSE-DEFAULT: 7 " 
 
        ::= 17
       accOspfEnableTrap TRAP-TYPE
        ENTERPRISE        accOspfTraps 
        VARIABLES       { accOspfTrapMsg,
                          ospfAdminStat,
                          ospfRouterId ,
accTrapLogSeqNum}
        DESCRIPTION
                "Indicates that either ospf_mgr_init_import_policy 
		 or ospf_mgr_init_export_policy has returned FALSE.
SEVERITY-DEFAULT: Minor 
EVENTTYPE-DEFAULT: 10 
ADDITIONAL-TEXT-VARIABLES: { accTrapLogSeqNum,accOspfTrapMsg }
PCAUSE-DEFAULT: 46 " 
 
        ::= 18
        accOspfCreateAreaTrap TRAP-TYPE
        ENTERPRISE        accOspfTraps 
        VARIABLES       { accOspfTrapMsg,
                          ospfAreaId ,
accTrapLogSeqNum}
        DESCRIPTION
                "Either parent ospf not found; or due to memory shortage.
SEVERITY-DEFAULT: Major 
EVENTTYPE-DEFAULT: 10 
ADDITIONAL-TEXT-VARIABLES: { accTrapLogSeqNum,accOspfTrapMsg }
PCAUSE-DEFAULT: 32 " 
 
        ::= 19
        accOspfCreateBckboneAreaTrap TRAP-TYPE
        ENTERPRISE        accOspfTraps 
        VARIABLES       { accOspfTrapMsg,
                          ospfAreaId ,
accTrapLogSeqNum}
        DESCRIPTION
                "Cannot create OSPF backbone area.
SEVERITY-DEFAULT: Major 
EVENTTYPE-DEFAULT: 10 
ADDITIONAL-TEXT-VARIABLES: { accTrapLogSeqNum,accOspfTrapMsg }
PCAUSE-DEFAULT: 32 " 
 
        ::= 20 
        accOspfAddImpPolTrap TRAP-TYPE
        ENTERPRISE        accOspfTraps 
        VARIABLES       { accOspfTrapMsg,
                          accOspfExportNetwork,
                          accOspfExportMask ,
                           accTrapLogSeqNum}
        DESCRIPTION
                "The command to add import policy can fail because of 
		 memory shortage.
SEVERITY-DEFAULT: Major 
EVENTTYPE-DEFAULT: 10 
ADDITIONAL-TEXT-VARIABLES: { accTrapLogSeqNum,accOspfTrapMsg }
PCAUSE-DEFAULT: 32 " 
 
        ::= 21   
        accOspfTrap22 TRAP-TYPE
        ENTERPRISE        accOspfTraps 
        VARIABLES       { accOspfTrapMsg,
                          ospfAreaId ,
accTrapLogSeqNum}
        DESCRIPTION
        	"Command to create a area ID can fail because of 
		 memory shortage.
SEVERITY-DEFAULT: Major 
EVENTTYPE-DEFAULT: 10 
ADDITIONAL-TEXT-VARIABLES: { accTrapLogSeqNum,accOspfTrapMsg }
PCAUSE-DEFAULT: 32 " 
 
        ::= 22
        accOspfCantEnableAreaTrap TRAP-TYPE
        ENTERPRISE        accOspfTraps 
        VARIABLES       { accOspfTrapMsg,
                          ospfAreaId ,
accTrapLogSeqNum}
        DESCRIPTION
                "Cannot locate area NVM_AREA_ID, deleting summary 
		 NVM_IP_ADDRESS /IP_MASK_LEN.
SEVERITY-DEFAULT: Major 
EVENTTYPE-DEFAULT: 10 
ADDITIONAL-TEXT-VARIABLES: { accTrapLogSeqNum,accOspfTrapMsg }
PCAUSE-DEFAULT: 32 " 
 
        ::= 23
        accOspfDelSummaryTrap TRAP-TYPE
        ENTERPRISE        accOspfTraps 
        VARIABLES       { accOspfTrapMsg,
                          ospfAreaAggregateAreaID,
                          ospfAreaAggregateNet,
                          ospfAreaAggregateMask ,
accTrapLogSeqNum}
        DESCRIPTION
                "The input  NVM_AREA_ID could not be located and 
		 hence deletes the summary entry.
SEVERITY-DEFAULT: Minor 
EVENTTYPE-DEFAULT: 10 
ADDITIONAL-TEXT-VARIABLES: { accTrapLogSeqNum,accOspfTrapMsg }
PCAUSE-DEFAULT: 152 " 
 
        ::= 24
        accOspfAddRangeTrap TRAP-TYPE
        ENTERPRISE        accOspfTraps 
        VARIABLES       { accOspfTrapMsg,
                          ospfAreaAggregateAreaID,
                          ospfAreaAggregateNet,
                          ospfAreaAggregateMask ,
accTrapLogSeqNum}
        DESCRIPTION
                "Failed to locate area, the area is not of type NSSA, 
		 address and mask dont match.
SEVERITY-DEFAULT: Warning 
EVENTTYPE-DEFAULT: 10 
ADDITIONAL-TEXT-VARIABLES: { accTrapLogSeqNum,accOspfTrapMsg }
PCAUSE-DEFAULT: 7 " 
 
        ::= 25
        accOspfCreateIntfTrap TRAP-TYPE
        ENTERPRISE        accOspfTraps 
        VARIABLES       { accOspfTrapMsg,
                          ospfIfIpAddress ,
accTrapLogSeqNum}
        DESCRIPTION
                "Cause for this could be that there is no corresponding 
		 IFB or due to the lack of memory.
SEVERITY-DEFAULT: Major 
EVENTTYPE-DEFAULT: 10 
ADDITIONAL-TEXT-VARIABLES: { accTrapLogSeqNum,accOspfTrapMsg }
PCAUSE-DEFAULT: 32 " 
 
        ::= 26
        accOspfEnableIntfTrap TRAP-TYPE
        ENTERPRISE        accOspfTraps 
        VARIABLES       { accOspfTrapMsg,
                          ospfIfIpAddress ,
accTrapLogSeqNum}
        DESCRIPTION
                "Area must be bound to an OSPF even though it is 
		 disabled. Or the interface type is not Virtual link 
		 and it has not IFB, failed to set an alarm per 
		 interface for retransimissions (due to memory shortage).
SEVERITY-DEFAULT: Major 
EVENTTYPE-DEFAULT: 10 
ADDITIONAL-TEXT-VARIABLES: { accTrapLogSeqNum,accOspfTrapMsg }
PCAUSE-DEFAULT: 32 " 
 
        ::= 27
        accOspfLocateIntfTrap TRAP-TYPE
        ENTERPRISE        accOspfTraps 
        VARIABLES       { accOspfTrapMsg,
                          ospfIfIpAddress ,
accTrapLogSeqNum}
        DESCRIPTION
                "Unable to locate an IFB by using the IpAddress or 
		 IfIndex (user might have entered wrong values for 
		 IfIpAddress??).
SEVERITY-DEFAULT: Major 
EVENTTYPE-DEFAULT: 10 
ADDITIONAL-TEXT-VARIABLES: { accTrapLogSeqNum,accOspfTrapMsg }
PCAUSE-DEFAULT: 32 " 
 
        ::= 28  
        accOspfLocateTransitAreaTrap TRAP-TYPE
        ENTERPRISE        accOspfTraps 
        VARIABLES       { accOspfTrapMsg,
                          ospfVirtNbrArea ,
accTrapLogSeqNum}
        DESCRIPTION
                "Indicates that it is unable to locate the area id 
		 in the virtual transit area.
SEVERITY-DEFAULT: Minor 
EVENTTYPE-DEFAULT: 10 
ADDITIONAL-TEXT-VARIABLES: { accTrapLogSeqNum,accOspfTrapMsg }
PCAUSE-DEFAULT: 152 " 
 
        ::= 29
        accOspfEnableVirtIntfTrap TRAP-TYPE
        ENTERPRISE        accOspfTraps 
        VARIABLES       { accOspfTrapMsg,
			  ospfVirtNbrArea ,
accTrapLogSeqNum}
        DESCRIPTION
                "area must be bound to an OSPF even though it is 
		 disabled. Or the interface type is not Virtual link 
		 and it has no IFB. Or failed to have set an alarm per 
		 interface for retransimissions (due to memory shortage).
SEVERITY-DEFAULT: Major 
EVENTTYPE-DEFAULT: 10 
ADDITIONAL-TEXT-VARIABLES: { accTrapLogSeqNum,accOspfTrapMsg }
PCAUSE-DEFAULT: 32 " 
 
        ::= 30
        accOspfCreateNbmaNbrTrap TRAP-TYPE
        ENTERPRISE        accOspfTraps 
        VARIABLES       { accOspfTrapMsg,
                          ospfNbrIpAddr ,
accTrapLogSeqNum}
        DESCRIPTION
                "the priority of Neighbor is greater than maximum allowed 
		 priority; due to memory shortage.
SEVERITY-DEFAULT: Major 
EVENTTYPE-DEFAULT: 10 
ADDITIONAL-TEXT-VARIABLES: { accTrapLogSeqNum,accOspfTrapMsg }
PCAUSE-DEFAULT: 32 " 
 
        ::= 31
        accOspfAckTqTmrAllocTrap TRAP-TYPE
        ENTERPRISE        accOspfTraps 
        VARIABLES       { accOspfTrapMsg,
                          ospfRouterId ,
accTrapLogSeqNum}
        DESCRIPTION
                "Ack_tq timer alloc failed due to memory shortage.
SEVERITY-DEFAULT: Major 
EVENTTYPE-DEFAULT: 10 
ADDITIONAL-TEXT-VARIABLES: { accTrapLogSeqNum,accOspfTrapMsg }
PCAUSE-DEFAULT: 32 " 
 
        ::= 32
        accOspfSumTqTmrAllocTrap TRAP-TYPE
        ENTERPRISE        accOspfTraps 
        VARIABLES       { accOspfTrapMsg,
                          ospfRouterId ,
accTrapLogSeqNum}
        DESCRIPTION
                "Sum_tq timer alloc failed due to memory shortage.
SEVERITY-DEFAULT: Major 
EVENTTYPE-DEFAULT: 10 
ADDITIONAL-TEXT-VARIABLES: { accTrapLogSeqNum,accOspfTrapMsg }
PCAUSE-DEFAULT: 32 " 
 
        ::= 33 
        accOspfDbageTqTmrAllocTrap TRAP-TYPE
        ENTERPRISE        accOspfTraps 
        VARIABLES       { accOspfTrapMsg,
                          ospfRouterId ,
accTrapLogSeqNum}
        DESCRIPTION
                "Dbage_tq timer timer alloc failed due to memory 
		 shortage.
SEVERITY-DEFAULT: Major 
EVENTTYPE-DEFAULT: 10 
ADDITIONAL-TEXT-VARIABLES: { accTrapLogSeqNum,accOspfTrapMsg }
PCAUSE-DEFAULT: 32 " 
 
        ::= 34
        accOspfAseTqTmrAllocTrap TRAP-TYPE
        ENTERPRISE        accOspfTraps 
        VARIABLES       { accOspfTrapMsg,
                          ospfRouterId ,
accTrapLogSeqNum}
        DESCRIPTION
                "Ase_tq timer alloc failed due to memory shortage.
SEVERITY-DEFAULT: Major 
EVENTTYPE-DEFAULT: 10 
ADDITIONAL-TEXT-VARIABLES: { accTrapLogSeqNum,accOspfTrapMsg }
PCAUSE-DEFAULT: 32 " 
 
        ::= 35
        accOspfDbhAllocTrap TRAP-TYPE
        ENTERPRISE        accOspfTraps 
        VARIABLES       { accOspfTrapMsg,
                          ospfLsdbType ,
accTrapLogSeqNum}
        DESCRIPTION
                "Alloc DBH failed due to memory shortage.
SEVERITY-DEFAULT: Major 
EVENTTYPE-DEFAULT: 10 
ADDITIONAL-TEXT-VARIABLES: { accTrapLogSeqNum,accOspfTrapMsg }
PCAUSE-DEFAULT: 32 " 
 
        ::= 36 
        accOspfTrap37 TRAP-TYPE
        ENTERPRISE        accOspfTraps 
        VARIABLES       { accOspfTrapMsg,
                          ospfVirtIfAreaId,
                          ospfVirtIfNeighbor ,
accTrapLogSeqNum}
        DESCRIPTION
        	"Indicates that Init Filter policy failed due to memory 
		 shortage.
SEVERITY-DEFAULT: Major 
EVENTTYPE-DEFAULT: 10 
ADDITIONAL-TEXT-VARIABLES: { accTrapLogSeqNum,accOspfTrapMsg }
PCAUSE-DEFAULT: 32 " 
 
        ::= 37 
        accOspfInitSbTrap TRAP-TYPE
        ENTERPRISE        accOspfTraps 
        VARIABLES       { accOspfTrapMsg,
                          ospfLsdbType,
                          ospfLsdbAreaId ,
accTrapLogSeqNum}
        DESCRIPTION
                "Init SB failed due to memory shortage.
SEVERITY-DEFAULT: Major 
EVENTTYPE-DEFAULT: 10 
ADDITIONAL-TEXT-VARIABLES: { accTrapLogSeqNum,accOspfTrapMsg }
PCAUSE-DEFAULT: 32 " 
 
        ::= 38 
        accOspfFreingNotifiIdTrap TRAP-TYPE
        ENTERPRISE        accOspfTraps 
        VARIABLES       { accOspfTrapMsg ,
                           accTrapLogSeqNum}
        DESCRIPTION  
		" 
SEVERITY-DEFAULT: Major 
EVENTTYPE-DEFAULT: 10 
ADDITIONAL-TEXT-VARIABLES: { accTrapLogSeqNum,accOspfTrapMsg }
PCAUSE-DEFAULT: 32 " 
 
        ::= 39
        accOspfNoBackboneTrap TRAP-TYPE
        ENTERPRISE        accOspfTraps 
        VARIABLES       { accOspfTrapMsg,
                          ospfVirtNbrArea ,
accTrapLogSeqNum}
        DESCRIPTION
		" 
SEVERITY-DEFAULT: Major 
EVENTTYPE-DEFAULT: 10 
ADDITIONAL-TEXT-VARIABLES: { accTrapLogSeqNum,accOspfTrapMsg }
PCAUSE-DEFAULT: 32 " 
 
        ::= 40 
END
