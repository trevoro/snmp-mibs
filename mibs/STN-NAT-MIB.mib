-- *****************************************************************
--
-- STN-NAT.mib:  
--      Spring Tide Networks Network Address Translation (NAT) MIB file.
--
--
--      Copyright (c) 2000 by Spring Tide Networks, Inc.
--                      ALL RIGHTS RESERVED       
--
-- *****************************************************************

-- MIB Object definitions for Spring Tide Network Address Translation


STN-NAT-MIB DEFINITIONS ::= BEGIN

    IMPORTS
	TEXTUAL-CONVENTION FROM SNMPv2-TC
        MODULE-IDENTITY,
        OBJECT-TYPE, 
        IpAddress,
        Integer32
                FROM SNMPv2-SMI

        MODULE-COMPLIANCE
                FROM SNMPv2-CONF

        InterfaceIndex
                FROM IF-MIB

        stnRouterNAT
                FROM STN-ROUTER-MIB

        stnNotification
                FROM SPRING-TIDE-NETWORKS-SMI;


    stnNat MODULE-IDENTITY
        LAST-UPDATED    "0002160000Z"
        ORGANIZATION    "Spring Tide Networks, Inc."
        CONTACT-INFO
                "
                Spring Tide Networks, Inc.
                Customer Service
                Postal: 3 Clock Tower Place
                        Maynard, MA 01754
                Tel:    1 888-786-4357
                Email:  stncs@springtidenet.com
                "
        DESCRIPTION     "This MIB module describes managed objects of
                         Spring Tide Networks Network Address Translation."
        ::= { stnRouterNAT 1 }


    --
    -- Top Level STN NAT MIB Objects
    --
    stnNatObjects        OBJECT IDENTIFIER ::= { stnNat 1 }
    stnNatMibConformance OBJECT IDENTIFIER ::= { stnNat 2 }
    stnNatMibTraps       OBJECT IDENTIFIER ::= { stnNat 3 }

    NatTransMode ::= TEXTUAL-CONVENTION
        STATUS    current
        DESCRIPTION
            "NAT translation mode."
        SYNTAX     INTEGER {
                            pooled(1),
                            static(2),
                            pat(3)
                        }

    --
    -- STN NAT / Layer 2 Table
    --
    stnNatL2Table OBJECT-TYPE
        SYNTAX        SEQUENCE OF StnNatL2Entry
        MAX-ACCESS    not-accessible
        STATUS        current
        DESCRIPTION   "A list of NAT L2 entries."
        ::= { stnNatObjects 1 }
 
    stnNatL2Entry OBJECT-TYPE
        SYNTAX          StnNatL2Entry
        MAX-ACCESS      not-accessible
        STATUS          current
        DESCRIPTION     "Entry contains information about a particular NAT L2."
        INDEX           { stnNatL2IfIndex }
        ::= { stnNatL2Table 1 }
 
    StnNatL2Entry ::= SEQUENCE {
        stnNatL2IfIndex                 InterfaceIndex,
        stnNatL2InsidePktMisses         Integer32,
        stnNatL2InsidePktHits           Integer32,
        stnNatL2OutsidePktMisses        Integer32,
        stnNatL2OutsidePktHits          Integer32,
        stnNatL2UntransInsidePkts       Integer32,
        stnNatL2UntransOutsidePkts      Integer32,
        stnNatL2InsideAlgPkts           Integer32,
        stnNatL2OutsideAlgPkts          Integer32,
        stnNatL2FlowId                  Integer32
    }

    stnNatL2IfIndex OBJECT-TYPE
        SYNTAX          InterfaceIndex
        MAX-ACCESS      read-only
        STATUS          current
        DESCRIPTION     "This ifIndex is that of the VcLink/L2 that was NAT 
                        Enabled."
        ::= { stnNatL2Entry 1 }

    stnNatL2InsidePktMisses OBJECT-TYPE
        SYNTAX          Integer32
        MAX-ACCESS      read-only
        STATUS          current
        DESCRIPTION     "The number of packets received from the 'inside'
                        whose translation was unknown and needed to be learned"
        ::= { stnNatL2Entry 2 }

    stnNatL2InsidePktHits OBJECT-TYPE
        SYNTAX          Integer32
        MAX-ACCESS      read-only
        STATUS          current
        DESCRIPTION     "The number of packets received from the 'inside'
                        whose translation was known."
        ::= { stnNatL2Entry 3 }

    stnNatL2OutsidePktMisses OBJECT-TYPE
        SYNTAX          Integer32
        MAX-ACCESS      read-only
        STATUS          current
        DESCRIPTION     "The number of packets received from the 'outside' 
                        whose translation was unknown."
        ::= { stnNatL2Entry 4 }

    stnNatL2OutsidePktHits OBJECT-TYPE
        SYNTAX          Integer32
        MAX-ACCESS      read-only
        STATUS          current
        DESCRIPTION     "The number of packets received from the 'outside'
                        whose translation was known."
        ::= { stnNatL2Entry 5 }

    stnNatL2UntransInsidePkts OBJECT-TYPE
        SYNTAX          Integer32
        MAX-ACCESS      read-only
        STATUS          current
        DESCRIPTION     "The number of packets received from the 'inside' that 
                        could not be translated because their source addresses 
                        were not among the valid inside addresses."
        ::= { stnNatL2Entry 6 }

    stnNatL2UntransOutsidePkts OBJECT-TYPE
        SYNTAX          Integer32
        MAX-ACCESS      read-only
        STATUS          current
        DESCRIPTION     "The number of packets received from the 'outside' 
                        that could not be translated because the was no 
                        existing translation availible."
        ::= { stnNatL2Entry 7 }

    stnNatL2InsideAlgPkts OBJECT-TYPE
        SYNTAX          Integer32
        MAX-ACCESS      read-only
        STATUS          current
        DESCRIPTION     "The number of packets received from the 'inside' that 
                        required Application Level Gateway (ALG) processing 
                        specific to protocol or application." 
        ::= { stnNatL2Entry 8 }

    stnNatL2OutsideAlgPkts OBJECT-TYPE
        SYNTAX          Integer32
        MAX-ACCESS      read-only
        STATUS          current
        DESCRIPTION     "The number of packets received from the 'outside' 
                        that required Application Level Gateway (ALG) 
                        processing specific to protocol or application."
        ::= { stnNatL2Entry 9 }

    stnNatL2FlowId OBJECT-TYPE
        SYNTAX          Integer32
        MAX-ACCESS      read-only
        STATUS          current
        DESCRIPTION     "This is the internal flow identifier associated with
                         this VcLink/L2 Interface.(STN use only)"
        ::= { stnNatL2Entry 10 }


    --
    -- STN NAT / Group Based Table
    --

    stnNatGroupTable OBJECT-TYPE
        SYNTAX        SEQUENCE OF StnNatGroupEntry
        MAX-ACCESS    not-accessible
        STATUS        current
        DESCRIPTION   "A list of group based NAT entries."
        ::= { stnNatObjects 2 }
 
    stnNatGroupEntry OBJECT-TYPE
        SYNTAX          StnNatGroupEntry
        MAX-ACCESS      not-accessible
        STATUS          current
        DESCRIPTION     "Entry contains information about a particular 
                         group based NAT."
        INDEX           { stnNatGroupSubnetIfInstance, 
                        stnNatGroupOutsideBaseAddress}
        ::= { stnNatGroupTable 1 } 
 
    StnNatGroupEntry ::= SEQUENCE {
        stnNatGroupSubnetIfInstance                 Integer32,
        stnNatGroupOutsideBaseAddress               IpAddress,
        stnNatGroupOutsideEndAddress                IpAddress,
        stnNatGroupInsideBaseAddress                IpAddress,
        stnNatGroupInsideEndAddress                 IpAddress,
        stnNatGroupTransMode                        NatTransMode,  
        stnNatGroupAddrIdleTime                     Integer32,
        stnNatGroupAddrTransAvailable               Integer32,
        stnNatGroupMaxFtpSessions                   Integer32,
        stnNatGroupMaxFtpSessionsPerInsideAddr      Integer32,
        stnNatGroupFtpControlSessionIdleTime        Integer32,
        stnNatGroupCurrentFtpSessions               Integer32,
        stnNatGroupTotalFtpSessions                 Integer32,
        stnNatGroupMissedFtpSessionLookups          Integer32,
        stnNatGroupNoIdleFtpSessions                Integer32,
        stnNatGroupNoIdleOutsideAddrs               Integer32,
        stnNatGroupFoundIdleOutsideAddrs            Integer32,
        stnNatGroupInsidePktMisses                  Integer32,
        stnNatGroupInsidePktHits                    Integer32,
        stnNatGroupOutsidePktMisses                 Integer32,
        stnNatGroupOutsidePktHits                   Integer32,
        stnNatGroupInvalidOutsidePktMisses          Integer32,
        stnNatGroupInsideFlowOrigin                 INTEGER,
        stnNatGroupPortBaseNumber                   Integer32,
        stnNatGroupPortEndNumber                    Integer32,
        stnNatGroupMaxInsideAddrs                   Integer32,
        stnNatGroupMaxPortsPerInsideAddr            Integer32,
        stnNatGroupPortLimitReached                 Integer32,
        stnNatGroupInsideAddrLimitReached           Integer32
        }

    stnNatGroupSubnetIfInstance OBJECT-TYPE
        SYNTAX          Integer32
        MAX-ACCESS      read-only
        STATUS          current
        DESCRIPTION     "A sequence number that identifies a sub-network
                         interface entry in the table."
        ::= { stnNatGroupEntry 1 }

    stnNatGroupOutsideBaseAddress OBJECT-TYPE     
        SYNTAX          IpAddress 
        MAX-ACCESS      read-only
        STATUS          current
        DESCRIPTION     "This is the first outside IP address in the range of 
                        outside addresses that packets from the inside have 
                        their source address translated to."
        ::= { stnNatGroupEntry 2 }

    stnNatGroupOutsideEndAddress OBJECT-TYPE
        SYNTAX          IpAddress
        MAX-ACCESS      read-only
        STATUS          current
        DESCRIPTION     "This is the last outside IP address in the range of 
                        outside addresses that packets from the inside have 
                        their source address translated to."
        ::= { stnNatGroupEntry 3 }

    stnNatGroupInsideBaseAddress OBJECT-TYPE     
        SYNTAX          IpAddress
        MAX-ACCESS      read-only
        STATUS          current
        DESCRIPTION     "This is the first inside IP address in the range of 
                        inside addresses that packets from the outside have 
                        their destination address."
        ::= { stnNatGroupEntry 4 }

    stnNatGroupInsideEndAddress OBJECT-TYPE     
        SYNTAX          IpAddress 
        MAX-ACCESS      read-only
        STATUS          current
        DESCRIPTION     "This is the last inside IP address in the range of 
                        inside addresses that packets from the outside have 
                        their destination address translated to."
        ::= { stnNatGroupEntry 5 }

    stnNatGroupTransMode OBJECT-TYPE     
        SYNTAX          NatTransMode
        MAX-ACCESS      read-only
        STATUS          current
        DESCRIPTION     "Indicates if translations for this NAT group are 
                        handled with a static address to address mapping, a 
                        pooled address mapping, or a port based mapping 
                        (PAT).  The translation is relinquished due to 
                        inactivity for the pooled and port based cases."
        ::= { stnNatGroupEntry 6 }

    stnNatGroupAddrIdleTime OBJECT-TYPE 
        SYNTAX          Integer32 
        MAX-ACCESS      read-only
        STATUS          current
        DESCRIPTION     "The number of seconds that a translation can be idle
                        This value is ignored for static NAT."
        ::= { stnNatGroupEntry 7 }

    stnNatGroupAddrTransAvailable OBJECT-TYPE 
        SYNTAX          Integer32 
        MAX-ACCESS      read-only
        STATUS          current
        DESCRIPTION     "The number of outside Addresses available in the 
                        pool for translation. This value is ignored for 
                        static NAT."
        ::= { stnNatGroupEntry 8 }

    stnNatGroupMaxFtpSessions OBJECT-TYPE 
        SYNTAX          Integer32 
        MAX-ACCESS      read-only
        STATUS          current
        DESCRIPTION     "The number of FTP Client sessions that can be 
                        translated from the 'inside' at one time. This value 
                        is only for client sessions initiated from the inside."
        ::= { stnNatGroupEntry 9 }

    stnNatGroupMaxFtpSessionsPerInsideAddr OBJECT-TYPE 
        SYNTAX          Integer32 
        MAX-ACCESS      read-only
        STATUS          current
        DESCRIPTION     "The number of FTP Client sessions that can be 
                        translated from one 'inside' address at one time. 
                        This value is only for client sessions initiated 
                        from the inside. (0 means field is ignored.)"
        ::= { stnNatGroupEntry 10 }

    stnNatGroupFtpControlSessionIdleTime OBJECT-TYPE 
        SYNTAX          Integer32 
        MAX-ACCESS      read-only
        STATUS          current
        DESCRIPTION     "The number of FTP Client sessions that can be 
                        translated from the 'inside' at one time. This value 
                        is only for client sessions initiated from the inside."
        ::= { stnNatGroupEntry 11 }

    stnNatGroupCurrentFtpSessions OBJECT-TYPE 
        SYNTAX          Integer32 
        MAX-ACCESS      read-only
        STATUS          current
        DESCRIPTION     "The number of FTP Client sessions that are currently 
                        being translated from the 'inside'."
        ::= { stnNatGroupEntry 12 }

    stnNatGroupTotalFtpSessions OBJECT-TYPE 
        SYNTAX          Integer32 
        MAX-ACCESS      read-only
        STATUS          current
        DESCRIPTION     "The number of FTP Client sessions that have been 
                        translated from the 'inside'."
        ::= { stnNatGroupEntry 13 }

    stnNatGroupMissedFtpSessionLookups OBJECT-TYPE 
        SYNTAX          Integer32 
        MAX-ACCESS      read-only
        STATUS          current
        DESCRIPTION     "The number of times an expired or unknown FTP client 
                        session was referenced."
        ::= { stnNatGroupEntry 14 }

    stnNatGroupNoIdleFtpSessions OBJECT-TYPE 
        SYNTAX          Integer32 
        MAX-ACCESS      read-only
        STATUS          current
        DESCRIPTION     "The number of times an FTP Client session was denied 
                        translation because there were no availible idle FTP 
                        sessions."
        ::= { stnNatGroupEntry 15 }

    stnNatGroupNoIdleOutsideAddrs OBJECT-TYPE 
        SYNTAX          Integer32 
        MAX-ACCESS      read-only
        STATUS          current
        DESCRIPTION     "The number of times a packet has arrived from a valid 
                        inside address, but a translation was not established 
                        because no outside address was availible. This value 
                        is ignored for static NAT."
        ::= { stnNatGroupEntry 16 }

    stnNatGroupFoundIdleOutsideAddrs OBJECT-TYPE 
        SYNTAX          Integer32 
        MAX-ACCESS      read-only
        STATUS          current
        DESCRIPTION     "The number of times a packet has arrived from a valid 
                        inside address and a translation was established due 
                        to the presence of an idle outside address. This value 
                        is ignored for static NAT."
        ::= { stnNatGroupEntry 17 }

    stnNatGroupInsidePktMisses OBJECT-TYPE 
        SYNTAX          Integer32 
        MAX-ACCESS      read-only
        STATUS          current
        DESCRIPTION     "The number of times a packet arrived from an inside 
                        address that did not have a translation programed.
                        This value is ignored for static NAT."
        ::= { stnNatGroupEntry 18 }

    stnNatGroupInsidePktHits OBJECT-TYPE 
        SYNTAX          Integer32 
        MAX-ACCESS      read-only
        STATUS          current
        DESCRIPTION     "The number of times a packet arrived for an inside 
                        address that was among any the known inside 
                        addresses configured for the interface."
        ::= { stnNatGroupEntry 19 }

    stnNatGroupOutsidePktMisses OBJECT-TYPE 
        SYNTAX          Integer32 
        MAX-ACCESS      read-only
        STATUS          current
        DESCRIPTION     "The number of times a packet arrived for an outside 
                        address that did not have a translation programed.
                        This value is ignored for static NAT."
        ::= { stnNatGroupEntry 20 }

    stnNatGroupOutsidePktHits OBJECT-TYPE 
        SYNTAX          Integer32 
        MAX-ACCESS      read-only
        STATUS          current
        DESCRIPTION     "The number of times a packet arrived for an outside 
                        address that was among any the known outside 
                        addresses configured for the interface."
        ::= { stnNatGroupEntry 21 }

    stnNatGroupInvalidOutsidePktMisses OBJECT-TYPE 
        SYNTAX          Integer32 
        MAX-ACCESS      read-only
        STATUS          current
        DESCRIPTION     "The number of times a packet arrived for an outside 
                        address that was not among any of the known outside 
                        addresses configured for the interface."
        ::= { stnNatGroupEntry 22 }

    stnNatGroupInsideFlowOrigin OBJECT-TYPE     
        SYNTAX          INTEGER {
                            ingress(1),
                            egress(2)
                        }
        MAX-ACCESS      read-only
        STATUS          current
        DESCRIPTION     "Indicates whether traffic entering (ingress) or  
                         leaving (egress) the router is considered to be
                         originating from the 'inside' for this interface"
        ::= { stnNatGroupEntry 23 }

    stnNatGroupPortBaseNumber OBJECT-TYPE     
        SYNTAX          Integer32 
        MAX-ACCESS      read-only
        STATUS          current
        DESCRIPTION     "This is the first port number in the range of port 
                        numbers that packets from the inside have their 
                        source port translated to.  This value is valid only 
                        for NAT type PAT."
        ::= { stnNatGroupEntry 24 }

    stnNatGroupPortEndNumber OBJECT-TYPE
        SYNTAX          Integer32
        MAX-ACCESS      read-only
        STATUS          current
        DESCRIPTION     "This is the first port number in the range of port 
                        numbers that packets from the inside have their 
                        source port translated to.  This value is valid only 
                        for NAT type PAT."
        ::= { stnNatGroupEntry 25 }

    stnNatGroupMaxInsideAddrs OBJECT-TYPE 
        SYNTAX          Integer32 
        MAX-ACCESS      read-only
        STATUS          current
        DESCRIPTION     "The number of inside addresses that can be translated 
                        from the 'inside' at one time. This value is valid
                        only for NAT type PAT."
        ::= { stnNatGroupEntry 26 }

    stnNatGroupMaxPortsPerInsideAddr OBJECT-TYPE 
        SYNTAX          Integer32 
        MAX-ACCESS      read-only
        STATUS          current
        DESCRIPTION     "The number of port translations allowed any single 
                        'inside' address at one time.  This value is valid
                        only for NAT type PAT."
        ::= { stnNatGroupEntry 27 }

    stnNatGroupPortLimitReached OBJECT-TYPE 
        SYNTAX          Integer32 
        MAX-ACCESS      read-only
        STATUS          current
        DESCRIPTION     "The number of times a packet has arrived from a valid 
                        inside address, but a translation was not established 
                        because the limit on the number of ports was reached.
                        This value is valid only for NAT type PAT."
        ::= { stnNatGroupEntry 28 }

    stnNatGroupInsideAddrLimitReached OBJECT-TYPE 
        SYNTAX          Integer32 
        MAX-ACCESS      read-only
        STATUS          current
        DESCRIPTION     "The number of times a packet has arrived from a valid 
                        inside address, but a translation was not established 
                        because the limit on the number of inside addresses 
                        was reached.  This value is valid only for NAT type 
                        PAT."
        ::= { stnNatGroupEntry 29 }



    --
    -- STN NAT Outside Translation Table
    --

    stnNatOutTransTable OBJECT-TYPE
        SYNTAX        SEQUENCE OF StnNatOutTransEntry
        MAX-ACCESS    not-accessible
        STATUS        current
        DESCRIPTION   "A list of NAT translation entries indexed by outside
                       address."
        ::= { stnNatObjects 3 }
 
    stnNatOutTransEntry OBJECT-TYPE
        SYNTAX          StnNatOutTransEntry
        MAX-ACCESS      not-accessible
        STATUS          current
        DESCRIPTION     "Entry contains information about a particular 
                         NAT translation."
        INDEX           { stnNatOutTransSubnetIfInstance,
                        stnNatOutTransOutsideBaseAddress, 
                        stnNatOutTransOutsideAddress,
                        stnNatOutTransOutsidePortNumber }
        ::= { stnNatOutTransTable 1 }
 
    StnNatOutTransEntry ::= SEQUENCE {
        stnNatOutTransSubnetIfInstance          Integer32,
        stnNatOutTransOutsideBaseAddress        IpAddress,
        stnNatOutTransOutsideAddress	        IpAddress,
        stnNatOutTransInsideAddress             IpAddress,
        stnNatOutTransMode                      NatTransMode,
        stnNatOutTransState                     INTEGER,
        stnNatOutTransUpTimeSec                 Integer32,
        stnNatOutTransSecsSinceLastHit          Integer32,
        stnNatOutTransCurrentFtpSessions        Integer32,
        stnNatOutTransTotalFtpSessions          Integer32,
        stnNatOutTransInsidePktHits             Integer32,
        stnNatOutTransOutsidePktHits            Integer32,
        stnNatOutTransOutsidePortNumber         Integer32,
        stnNatOutTransInsidePortNumber          Integer32,
        stnNatOutTransOutsidePortsInuse         Integer32,
        stnNatOutTransInsidePortsInuse          Integer32,
        stnNatOutTransInsidePortLimitReached    Integer32
    }

    stnNatOutTransSubnetIfInstance OBJECT-TYPE
        SYNTAX          Integer32
        MAX-ACCESS      read-only
        STATUS          current
        DESCRIPTION     "A sequence number that identifies a sub-network
                         interface entry in the table."
        ::= { stnNatOutTransEntry 1 }

    stnNatOutTransOutsideBaseAddress OBJECT-TYPE     
        SYNTAX          IpAddress 
        MAX-ACCESS      read-only
        STATUS          current
        DESCRIPTION     "This is the first outside IP address in the range of 
                        outside addresses that packets from the inside have 
                        their source address translated to."
        ::= { stnNatOutTransEntry 2 }

    stnNatOutTransOutsideAddress OBJECT-TYPE
        SYNTAX          IpAddress
        MAX-ACCESS      read-only
        STATUS          current
        DESCRIPTION     "This is the outside IP address for the translation."
        ::= { stnNatOutTransEntry 3 }

    stnNatOutTransInsideAddress OBJECT-TYPE 
        SYNTAX          IpAddress 
        MAX-ACCESS      read-only
        STATUS          current
        DESCRIPTION     "This is the inside IP address for the translation."
        ::= { stnNatOutTransEntry 4 }

    stnNatOutTransMode OBJECT-TYPE
        SYNTAX          NatTransMode
        MAX-ACCESS      read-only
        STATUS          current
        DESCRIPTION     "Indicates whether this translation is pooled, 
                        static or PAT"
        ::= { stnNatOutTransEntry 5 }

    stnNatOutTransState OBJECT-TYPE
        SYNTAX          INTEGER {
                            leased(1),
                            expired(2)
                        }
        MAX-ACCESS      read-only
        STATUS          current
        DESCRIPTION     "Indicates the translation state."
        ::= { stnNatOutTransEntry 6 }

    stnNatOutTransUpTimeSec OBJECT-TYPE 
        SYNTAX          Integer32
        MAX-ACCESS      read-only
        STATUS          current
        DESCRIPTION     "The number of seconds since this translation was 
                        started."
        ::= { stnNatOutTransEntry 7 }

    stnNatOutTransSecsSinceLastHit OBJECT-TYPE 
        SYNTAX          Integer32
        MAX-ACCESS      read-only
        STATUS          current
        DESCRIPTION     "The number of seconds since this translation was 
                         last used."
        ::= { stnNatOutTransEntry 8 }

    stnNatOutTransCurrentFtpSessions OBJECT-TYPE 
        SYNTAX          Integer32
        MAX-ACCESS      read-only
        STATUS          current
        DESCRIPTION     "The number of FTP Client sessions that are currently 
                        being translated from the 'inside' for this 
                        translation."
        ::= { stnNatOutTransEntry 9 }

    stnNatOutTransTotalFtpSessions OBJECT-TYPE 
        SYNTAX          Integer32
        MAX-ACCESS      read-only
        STATUS          current
        DESCRIPTION     "The number of FTP Client sessions that have been 
                        translated from the 'inside' for this translation."
        ::= { stnNatOutTransEntry 10 }

    stnNatOutTransInsidePktHits OBJECT-TYPE 
        SYNTAX          Integer32 
        MAX-ACCESS      read-only
        STATUS          current
        DESCRIPTION     "The number of times a packet arrived for this inside 
                        address."
        ::= { stnNatOutTransEntry 11 }

    stnNatOutTransOutsidePktHits OBJECT-TYPE 
        SYNTAX          Integer32 
        MAX-ACCESS      read-only
        STATUS          current
        DESCRIPTION     "The number of times a packet arrived for this outside 
                        address."
        ::= { stnNatOutTransEntry 12 }

    stnNatOutTransOutsidePortNumber OBJECT-TYPE
        SYNTAX          Integer32
        MAX-ACCESS      read-only
        STATUS          current
        DESCRIPTION     "This is the outside port number for the translation."
        ::= { stnNatOutTransEntry 13 }

    stnNatOutTransInsidePortNumber OBJECT-TYPE 
        SYNTAX          Integer32 
        MAX-ACCESS      read-only
        STATUS          current
        DESCRIPTION     "This is the inside port number for the translation."
        ::= { stnNatOutTransEntry 14 }

    stnNatOutTransOutsidePortsInuse OBJECT-TYPE 
        SYNTAX          Integer32 
        MAX-ACCESS      read-only
        STATUS          current
        DESCRIPTION     "This is the number of ports currently being used 
                        by the outside address."
        ::= { stnNatOutTransEntry 15 }

    stnNatOutTransInsidePortsInuse OBJECT-TYPE 
        SYNTAX          Integer32 
        MAX-ACCESS      read-only
        STATUS          current
        DESCRIPTION     "This is the number of ports currently being used 
                        by the inside address."
        ::= { stnNatOutTransEntry 16 }

    stnNatOutTransInsidePortLimitReached OBJECT-TYPE 
        SYNTAX          Integer32 
        MAX-ACCESS      read-only
        STATUS          current
        DESCRIPTION     "This is the number of times the inside address
                        reached its port limit."
        ::= { stnNatOutTransEntry 17 }



--
    -- STN NAT Inside Translation Table
    --

    stnNatInTransTable OBJECT-TYPE
        SYNTAX        SEQUENCE OF StnNatInTransEntry
        MAX-ACCESS    not-accessible
        STATUS        current
        DESCRIPTION   "A list of NAT translation entries indexed by inside  
                       address."
        ::= { stnNatObjects 4 }
 
    stnNatInTransEntry OBJECT-TYPE
        SYNTAX          StnNatInTransEntry
        MAX-ACCESS      not-accessible
        STATUS          current
        DESCRIPTION     "Entry contains information about a particular 
                         NAT translation."
        INDEX           { stnNatInTransSubnetIfInstance,
                        stnNatInTransOutsideBaseAddress, 
                        stnNatInTransInsideAddress,
                        stnNatInTransInsidePortNumber }
        ::= { stnNatInTransTable 1 }
 
    StnNatInTransEntry ::= SEQUENCE {
        stnNatInTransSubnetIfInstance           Integer32,
        stnNatInTransOutsideBaseAddress         IpAddress,
        stnNatInTransOutsideAddress	            IpAddress,
        stnNatInTransInsideAddress              IpAddress,
        stnNatInTransMode                       NatTransMode,
        stnNatInTransState                      INTEGER,
        stnNatInTransUpTimeSec                  Integer32,
        stnNatInTransSecsSinceLastHit           Integer32,
        stnNatInTransCurrentFtpSessions         Integer32,
        stnNatInTransTotalFtpSessions           Integer32,
        stnNatInTransInsidePktHits              Integer32,
        stnNatInTransOutsidePktHits             Integer32,
        stnNatInTransOutsidePortNumber          Integer32,
        stnNatInTransInsidePortNumber           Integer32,
        stnNatInTransOutsidePortsInuse          Integer32,
        stnNatInTransInsidePortsInuse           Integer32,
        stnNatInTransInsidePortLimitReached     Integer32
    }

    stnNatInTransSubnetIfInstance OBJECT-TYPE
        SYNTAX          Integer32
        MAX-ACCESS      read-only
        STATUS          current
        DESCRIPTION     "A sequence number that identifies a sub-network
                         interface entry in the table."
        ::= { stnNatInTransEntry 1 }

    stnNatInTransOutsideBaseAddress OBJECT-TYPE     
        SYNTAX          IpAddress 
        MAX-ACCESS      read-only
        STATUS          current
        DESCRIPTION     "This is the first outside IP address in the range of 
                        outside addresses that packets from the inside have 
                        their source address translated to."
        ::= { stnNatInTransEntry 2 }

    stnNatInTransOutsideAddress OBJECT-TYPE
        SYNTAX          IpAddress
        MAX-ACCESS      read-only
        STATUS          current
        DESCRIPTION     "This is the last outside IP address in the range of 
                        outside addresses that packets from the inside have 
                        their source address translated to."
        ::= { stnNatInTransEntry 3 }

    stnNatInTransInsideAddress OBJECT-TYPE 
        SYNTAX          IpAddress 
        MAX-ACCESS      read-only
        STATUS          current
        DESCRIPTION     "This is inside IP address for the translation."
        ::= { stnNatInTransEntry 4 }

    stnNatInTransMode OBJECT-TYPE
        SYNTAX          NatTransMode
        MAX-ACCESS      read-only
        STATUS          current
        DESCRIPTION     "Indicates whether this translation is pooled,  
                        static or port based."
        ::= { stnNatInTransEntry 5 }

    stnNatInTransState OBJECT-TYPE
        SYNTAX          INTEGER {
                            leased(1),
                            expired(2)
                        }
        MAX-ACCESS      read-only
        STATUS          current
        DESCRIPTION     "Indicates the translation state."
        ::= { stnNatInTransEntry 6 }

    stnNatInTransUpTimeSec OBJECT-TYPE 
        SYNTAX          Integer32
        MAX-ACCESS      read-only
        STATUS          current
        DESCRIPTION     "The number of seconds since this translation was 
                        started."
        ::= { stnNatInTransEntry 7 }

    stnNatInTransSecsSinceLastHit OBJECT-TYPE 
        SYNTAX          Integer32
        MAX-ACCESS      read-only
        STATUS          current
        DESCRIPTION     "The number of seconds since this translation was 
	                 last used."
        ::= { stnNatInTransEntry 8 }

    stnNatInTransCurrentFtpSessions OBJECT-TYPE 
        SYNTAX          Integer32
        MAX-ACCESS      read-only
        STATUS          current
        DESCRIPTION     "The number of FTP Client sessions that are currently 
                        being translated from the 'inside' for this 
                        translation."
        ::= { stnNatInTransEntry 9 }

    stnNatInTransTotalFtpSessions OBJECT-TYPE 
        SYNTAX          Integer32
        MAX-ACCESS      read-only
        STATUS          current
        DESCRIPTION     "The number of FTP Client sessions that have been 
                        translated from the 'inside' for this translation."
        ::= { stnNatInTransEntry 10 }

    stnNatInTransInsidePktHits OBJECT-TYPE 
        SYNTAX          Integer32 
        MAX-ACCESS      read-only
        STATUS          current
        DESCRIPTION     "The number of times a packet arrived for this inside 
                        address."
        ::= { stnNatInTransEntry 11 }

    stnNatInTransOutsidePktHits OBJECT-TYPE 
        SYNTAX          Integer32 
        MAX-ACCESS      read-only
        STATUS          current
        DESCRIPTION     "The number of times a packet arrived for this outside 
                        address."
        ::= { stnNatInTransEntry 12 }

    stnNatInTransOutsidePortNumber OBJECT-TYPE
        SYNTAX          Integer32
        MAX-ACCESS      read-only
        STATUS          current
        DESCRIPTION     "This is the outside port number for the translation."
        ::= { stnNatInTransEntry 13 }

    stnNatInTransInsidePortNumber OBJECT-TYPE 
        SYNTAX          Integer32 
        MAX-ACCESS      read-only
        STATUS          current
        DESCRIPTION     "This is the inside port number for the translation."
        ::= { stnNatInTransEntry 14 }

    stnNatInTransOutsidePortsInuse OBJECT-TYPE 
        SYNTAX          Integer32 
        MAX-ACCESS      read-only
        STATUS          current
        DESCRIPTION     "This is the number of ports currently being used 
                        by the outside address."
        ::= { stnNatInTransEntry 15 }

    stnNatInTransInsidePortsInuse OBJECT-TYPE 
        SYNTAX          Integer32 
        MAX-ACCESS      read-only
        STATUS          current
        DESCRIPTION     "This is the number of ports currently being used 
                        by the inside address."
        ::= { stnNatInTransEntry 16 }

    stnNatInTransInsidePortLimitReached OBJECT-TYPE 
        SYNTAX          Integer32 
        MAX-ACCESS      read-only
        STATUS          current
        DESCRIPTION     "This is the number of times the inside address
                        reached its port limit."
        ::= { stnNatInTransEntry 17 }

    --
    -- STN Traps & Notifications 
    --


    --
    -- Conformance Information
    --


END
