-- *****************************************************************
-- VISM specific extensions to XGCP MIB
--
-- May 1999
--
-- Copyright (c) 1999-2001 by cisco Systems, Inc.
-- All rights reserved.
--
-- *****************************************************************
--
--    LAST-UPDATED "200112261500Z"
--    DESCRIPTION
--        "VISM specific extensions to XGCP MIB. This MIB is an extension to 
--         the XGCP-MIB as defined by: External Media Gateway Control Protocol
--         MIB-XGCP-MIB <ietf-nguyen-xgcp-mib-01.txt> April 13, 1999"
--
--    REVISION    "200112261500Z"
--    DESCRIPTION "
--                Added new group vismXgcpEnhancementObjects with three new 
--                scalar objects for disconnected procedure for MGCP10 -
--                  vismXgcpRestartInProgressTdinit 
--                  vismXgcpRestartInProgressTdmin     
--                  vismXgcpRestartInProgressTdmax
--                "
--
--    REVISION    "200005251500Z"
--    DESCRIPTION "
--                Added vismXgcpRequestMaxTimeout
--                "
--
--    REVISION    "199908191500Z"
--    DESCRIPTION "
--                Changed vismXgcpAulnCnts to vismXgcpAucxCnts &
--                vismXgcpAulnFailCnts to vismXgcpAucxFailCnts
--                "
--
--    REVISION    "199905041500Z"
--    DESCRIPTION "
--                Initial creation.
--                "
--
-- 09/19/2001 Added new group vismXgcpEnhancementObjects
--            Added three new scalar objects for 
--            disconnected procedure for MGCP10 -
--                  vismXgcpRestartInProgressTdinit 
--                  vismXgcpRestartInProgressTdmin     
--                  vismXgcpRestartInProgressTdmax 
--
--
--    REVISION    "200203141500Z"
--    DESCRIPTION "Fix description for vismXgcpPort object."
--               
--


VISM-XGCP-EXTENSION-MIB DEFINITIONS ::= BEGIN

IMPORTS 
    Counter,IpAddress                   FROM RFC1155-SMI
    OBJECT-TYPE                         FROM RFC-1212
    voice                               FROM BASIS-MIB;

vismXgcpExtensionGrp    OBJECT IDENTIFIER ::= { voice 5 }
vismXgcpCoreObjects     OBJECT IDENTIFIER ::= { vismXgcpExtensionGrp 1 }
vismXgcpEnhancementsObjects     OBJECT IDENTIFIER ::= { vismXgcpExtensionGrp 2 }

-- *********************************************************************
-- The XGCP Core Group Extension
-- *********************************************************************

vismXgcpRequestMaxTimeout  OBJECT-TYPE
    SYNTAX      INTEGER (1..100000)
    ACCESS      read-write
    STATUS      mandatory
    DESCRIPTION
        "
          This object specifies the maximum timeout value.

          This timer value is used along with xgcpRequestTimeout and
          xgcpRequestRetries (in xgcpGrp.my) to determine the exponential 
          retry interval for retransmitting unacknowledged xgcp messages.

          The value of this timer has to be greater than or equal to
          xgcpRequestTimeout.

          The default value of this object is 500 milliseconds.

          When the value of this object changes vismXgcpCoreObjects changed
          trap will be sent.

        "
        DEFVAL{500}
        ::= {vismXgcpCoreObjects 1}

vismXgcpPort OBJECT-TYPE
    SYNTAX      INTEGER(1025..65535)
    ACCESS      read-write
    STATUS      mandatory
    DESCRIPTION
        "This object is used to configure the local UDP port on 
         VISM used by the SGCP and MGCP protocols to communicate
         with the call agent.

         The UDP port is used together with vismIpAddress to  
         identify the local end of a SGCP/MGCP connection.

         The default value of this object is 2427.
          
         In VISM 1.5 this object always defaults to 2427 and is 
         read-only.
        "
    DEFVAL { 2427 }
    ::= { vismXgcpCoreObjects 2 }

-- *********************************************************************
-- The XGCP Peer Configuration Table
-- *********************************************************************

vismXgcpPeerTable OBJECT-TYPE
    SYNTAX      SEQUENCE OF VismXgcpPeerEntry
    ACCESS      not-accessible
    STATUS      mandatory
    DESCRIPTION
         "This table is used to provision peer-specific XGCP 
          configuration information. Each table entry corresponds 
          to an XGCP peer name / peer XGCP variant combination.
	"
    ::= { vismXgcpCoreObjects 3 }


vismXgcpPeerEntry OBJECT-TYPE
    SYNTAX      VismXgcpPeerEntry
    ACCESS      not-accessible
    STATUS      mandatory
    DESCRIPTION
         "Each row is identified by XGCP peer name and peer XGCP 
          protocol number combination. This means, if an MGC uses
          more than one variant of XGCP (i.e MGCP, SGCP 1.0, 
          SGCP 1.1 etc), an entry will be maintained for each
          of the protocols. mgcNumber and mgcProtocolNumber from
          MGMIB are used as foreign index to this table. 

          Entries in this table are implicitly created by the 
          agent. An entry shall be created when an entry is created 
          in the mgcProtocolTable and when mgcProtocolNumber refers 
          to an XGCP variant (i.e MGCP, SGCP 1.0, SGCP 1.1 etc) as 
          supported protocol. An entry shall be deleted if the 
          corresponding entry in the mgcProtocolTable is deleted.

          As both mgcProtocolTable and vismXgcpPeerTable have 
          mgcNumber and mgcProtocolNumber as index, referential 
          integrity between the two tables is automatically ensured. 
	"
    INDEX   { vismXgcpPeerNumber, vismXgcpPeerProtocolNumber }
    ::= { vismXgcpPeerTable 1 }


VismXgcpPeerEntry ::= SEQUENCE {
        vismXgcpPeerNumber            INTEGER,
        vismXgcpPeerProtocolNumber    INTEGER,
        vismXgcpPeerPort              INTEGER
    }

vismXgcpPeerNumber  OBJECT-TYPE
    SYNTAX      INTEGER (1..8)
    ACCESS      read-only
    STATUS      mandatory
    DESCRIPTION
        "The value of this object is the same as mgcNumber from
         MGMIB.
        "
    ::= { vismXgcpPeerEntry 1 }


vismXgcpPeerProtocolNumber  OBJECT-TYPE
    SYNTAX      INTEGER (1..8)
    ACCESS      read-only
    STATUS      mandatory
    DESCRIPTION
        "The value of this object is the same as mgcProtocolNumber
         from MGMIB.
        "
    ::= { vismXgcpPeerEntry 2 }


vismXgcpPeerPort  OBJECT-TYPE
    SYNTAX      INTEGER (1025..65535)
    ACCESS      read-write
    STATUS      mandatory
    DESCRIPTION
        "This object is used to configure the local UDP port on
         VISM used by the SGCP and MGCP protocols to communicate
         with the call agent.

         The UDP port is used together with vismIpAddress to
         identify the local end of a SGCP/MGCP connection.

         If the protocol configured for the call agent is MGCP 1.0,
         the default port is 2727. In all other cases, the default
         value of this object is 2427.

         In VISM 1.5 this object always defaults to 2427 and is
         read-only.
        "
    DEFVAL { 2427 }
    ::= { vismXgcpPeerEntry 3 }


-- *****************************************************************
-- The XGCP Statistics table extension
-- *****************************************************************

vismXgcpMsgStatTable OBJECT-TYPE
    SYNTAX      SEQUENCE OF VismXgcpMsgStatEntry
    ACCESS      not-accessible
    STATUS      mandatory
    DESCRIPTION
        "This table is an extension to the xgcpMsgStatTable contained
         in the XGCP MIB. This table provides per-message type based
         detailed statistics information. 
	"
    ::= { vismXgcpCoreObjects 4 }

vismXgcpMsgStatEntry OBJECT-TYPE
    SYNTAX      VismXgcpMsgStatEntry
    ACCESS      not-accessible
    STATUS      mandatory
    DESCRIPTION
        "The row of the vismXgcpMsgStatTable contains 
         additional information about XGCP message statistics 
         beyond that provided by the XGCP MIB. 
	"
    INDEX   { vismXgcpIpAddress }
    ::= { vismXgcpMsgStatTable 1 }

VismXgcpMsgStatEntry ::= SEQUENCE {
        vismXgcpIpAddress               IpAddress,
        vismXgcpCrcxCnts                Counter,
        vismXgcpCrcxFailCnts            Counter,
        vismXgcpMdcxCnts                Counter,
        vismXgcpMdcxFailCnts            Counter,
        vismXgcpDlcxRcvCnts             Counter,
        vismXgcpDlcxRcvFailCnts         Counter,
        vismXgcpDlcxSentCnts            Counter,
        vismXgcpDlcxSentFailCnts        Counter,
        vismXgcpRqntCnts                Counter,
        vismXgcpRqntFailCnts            Counter,
        vismXgcpNtfyCnts                Counter,
        vismXgcpNtfyFailCnts            Counter,
        vismXgcpAuepCnts                Counter,
        vismXgcpAuepFailCnts            Counter,
        vismXgcpAucxCnts                Counter,
        vismXgcpAucxFailCnts            Counter,
        vismXgcpRsipCnts                Counter,
        vismXgcpRsipFailCnts            Counter
    }

vismXgcpIpAddress  OBJECT-TYPE
    SYNTAX      IpAddress
    ACCESS      read-only
    STATUS      mandatory
    DESCRIPTION
        " This object specifies the IP address of the  
          Media Gateway Controller. The value of this object is
          the same as xgcpIpAddress of XGCP-MIB.
        "
    ::= { vismXgcpMsgStatEntry 1 }
 
vismXgcpCrcxCnts  OBJECT-TYPE
    SYNTAX     Counter
    ACCESS     read-only
    STATUS     mandatory
    DESCRIPTION
        " This refers to the count of CRCX (Create Connection) 
          messages received from the call agent since reset.
        "
    ::= { vismXgcpMsgStatEntry 2 }
 
vismXgcpCrcxFailCnts  OBJECT-TYPE
    SYNTAX     Counter
    ACCESS     read-only
    STATUS     mandatory
    DESCRIPTION
        " This refers to the count of CRCX (Create Connection) 
          messages received from the call agent that were responded
          to with a failure return code.
        "
    ::= { vismXgcpMsgStatEntry 3 }
 
vismXgcpMdcxCnts  OBJECT-TYPE
    SYNTAX      Counter
    ACCESS      read-only
    STATUS      mandatory
    DESCRIPTION
        " This refers to the count of MDCX (Modify Connection) 
          messages received from the call agent since reset.
        "
    ::= { vismXgcpMsgStatEntry 4 }
 
vismXgcpMdcxFailCnts  OBJECT-TYPE
    SYNTAX      Counter
    ACCESS      read-only
    STATUS      mandatory
    DESCRIPTION
        " This refers to the count of MDCX (Modify Connection) 
          messages received from the call agent that were responded
          to with a failure return code.
        "
    ::= { vismXgcpMsgStatEntry 5 }
 
vismXgcpDlcxRcvCnts  OBJECT-TYPE
    SYNTAX      Counter
    ACCESS      read-only
    STATUS      mandatory
    DESCRIPTION
        " This refers to the count of DLCX (Delete Connection) 
          messages received from the call agent since reset.
        "
    ::= { vismXgcpMsgStatEntry 6 }
 
vismXgcpDlcxRcvFailCnts  OBJECT-TYPE
    SYNTAX      Counter
    ACCESS      read-only
    STATUS      mandatory
    DESCRIPTION
        " This refers to the count of DLCX (Delete Connection) 
          messages received from the call agent that were responded
          to with a failure return code.
        "
    ::= { vismXgcpMsgStatEntry 7 }
 
vismXgcpDlcxSentCnts  OBJECT-TYPE
    SYNTAX      Counter
    ACCESS      read-only
    STATUS      mandatory
    DESCRIPTION
        " This refers to the count of DLCX (Delete Connection) 
          messages sent to the call agent since reset.
        "
    ::= { vismXgcpMsgStatEntry 8 }
 
vismXgcpDlcxSentFailCnts  OBJECT-TYPE
    SYNTAX      Counter
    ACCESS      read-only
    STATUS      mandatory
    DESCRIPTION
        " This refers to the count of DLCX (Delete Connection) 
          messages sent to the call agent for which a response
          with failure return code was received or which timed
          out waiting for an acknowledgement.
        "
    ::= { vismXgcpMsgStatEntry 9 }

vismXgcpRqntCnts  OBJECT-TYPE
    SYNTAX      Counter
    ACCESS      read-only
    STATUS      mandatory
    DESCRIPTION
        " This refers to the count of RQNT (Request Notify) 
          messages received from the call agent since reset.
        "
    ::= { vismXgcpMsgStatEntry 10 }
 
vismXgcpRqntFailCnts  OBJECT-TYPE
    SYNTAX      Counter
    ACCESS      read-only
    STATUS      mandatory
    DESCRIPTION
        " This refers to the count of RQNT (Request Notify) 
          messages received from the call agent that were 
          responded to with a failure return code.
        "
    ::= { vismXgcpMsgStatEntry 11 }
 
vismXgcpNtfyCnts  OBJECT-TYPE
    SYNTAX      Counter
    ACCESS      read-only
    STATUS      mandatory
    DESCRIPTION
        " This refers to the count of NTFY (Notify) messages 
          sent to the call agent since reset.
        "
    ::= { vismXgcpMsgStatEntry 12 }
 
vismXgcpNtfyFailCnts  OBJECT-TYPE
    SYNTAX      Counter
    ACCESS      read-only
    STATUS      mandatory
    DESCRIPTION
        " This refers to the count of NTFY (Notify) messages 
          sent to the call agent for which a response with 
          failure return code was received or which timed out
          waiting for a response.
        "
    ::= { vismXgcpMsgStatEntry 13 }

vismXgcpAuepCnts  OBJECT-TYPE
    SYNTAX      Counter
    ACCESS      read-only
    STATUS      mandatory
    DESCRIPTION
        " This refers to the count of AUEP (Audit Endpoint) 
          messages received from the call agent since reset.
        "
    ::= { vismXgcpMsgStatEntry 14 }
 
vismXgcpAuepFailCnts  OBJECT-TYPE
    SYNTAX      Counter
    ACCESS      read-only
    STATUS      mandatory
    DESCRIPTION
        " This refers to the count of AUEP (Audit Endpoint) 
          messages received from the call agent that were 
          responded to with a failure return code.
        "
    ::= { vismXgcpMsgStatEntry 15 }
 
vismXgcpAucxCnts  OBJECT-TYPE
    SYNTAX      Counter
    ACCESS      read-only
    STATUS      mandatory
    DESCRIPTION
        " This refers to the count of AUCX (Audit Connection) 
          messages received from the call agent since reset.
        "
    ::= { vismXgcpMsgStatEntry 16 }
 
vismXgcpAucxFailCnts  OBJECT-TYPE
    SYNTAX      Counter
    ACCESS      read-only
    STATUS      mandatory
    DESCRIPTION
        " This refers to the count of AUCX (Audit Connection) 
          messages received from the call agent that were 
          responded to with a failure return code.
        "
    ::= { vismXgcpMsgStatEntry 17 }
 
vismXgcpRsipCnts  OBJECT-TYPE
    SYNTAX      Counter
    ACCESS      read-only
    STATUS      mandatory
    DESCRIPTION
        " This refers to the count of RSIP (Restart In Progress) 
          messages sent to the call agent since reset.
        "
    ::= { vismXgcpMsgStatEntry 18 }
 
vismXgcpRsipFailCnts  OBJECT-TYPE
    SYNTAX      Counter
    ACCESS      read-only
    STATUS      mandatory
    DESCRIPTION
        " This refers to the count of RSIP (Restart In Progress) 
          messages sent to the call agent for which a response 
          with failure return code was received or which timed out
          waiting for a response.
        "
    ::= { vismXgcpMsgStatEntry 19 }

-- *********************************************************************
-- The XGCP Enhancement Group 
-- *********************************************************************

vismXgcpRestartInProgressTdinit OBJECT-TYPE
    SYNTAX      INTEGER (1..100)
    ACCESS      read-write
    STATUS      mandatory
    DESCRIPTION
        "The endpoint becomes disconnected when it tries to communicate
         with the call agent and the retransmission procedure times out
         after retrying.

         The endpoint in disconnected state starts the disconnected timer
         initialised to the random value and uniformly distributed between
         1 and initial waiting delay (Tdinit) in seconds. 

         The gateway waits for either the end of this timer, or the reception
         of call agent command or the detection of local user activity for 
         the endpoint.

         When the disconnected timer elapses, or when a command is received
         from the call agent or when there is a local user activity, the 
         Media Gateway sends the Restart In Progress command with the restart 
         method as RM:disconnected to the Media Gateway Controller.
         
         The initial waiting delay (Tdinit) timeout value is defined by
         this MIB object.  

         The recommended value of this object is 15 seconds.
        "
    REFERENCE
         " Media Gateway Control Protocol (MGCP),
           version 1.0 bis, May 10, 2001 : Section 4.4.7
         "
    DEFVAL{ 15 }

    ::= { vismXgcpEnhancementsObjects 1 }


vismXgcpRestartInProgressTdmin OBJECT-TYPE
    SYNTAX      INTEGER (0..100)
    ACCESS      read-write
    STATUS      mandatory
    DESCRIPTION
         "The endpoint becomes disconnected when it tries to communicate
         with the call agent and the retransmission procedure times out
         after retrying.

         The endpoint in disconnected state starts the disconnected timer
         initialised to the random value and uniformly distributed between
         1 and initial waiting delay (Tdinit) in seconds. 

         The gateway waits for either the end of this timer, or the reception
         of call agent command or the detection of local user activity for 
         the endpoint.

         When the disconnected timer elapses, or when a command is received
         from the call agent or when there is a local user activity, the 
         Media Gateway sends the Restart In Progress command with the restart 
         method as RM:disconnected to the Media Gateway Controller.
         
         In case of local user activity, a provisionable disconnected
         minimum waiting delay (Tdmin) must have been elapsed since the
         gateway became disconnected. 
        
         The minimum waiting delay (Tdmin) timeout value used by the
         Media Gateway to send the Restart In Progress with the restart
         method as RM:disconnected to the Media Gateway Controller if
         there is any local user activity is defined by this object.

         Media Gateway initiated delete connection (DLCX) or restart in
         progress (RSIP) commands are not considered as local user
         activity.

         The events observed on the TDM interface or on the network 
         constitute the local user activity.

         The recommended value of this object is 15 seconds.
        "
    REFERENCE
         " Media Gateway Control Protocol (MGCP),
           version 1.0 bis, May 10, 2001 : Section 4.4.7
         "
    DEFVAL{ 15 }

    ::= { vismXgcpEnhancementsObjects 2 }


vismXgcpRestartInProgressTdmax OBJECT-TYPE
    SYNTAX      INTEGER (1..5000)
    ACCESS      read-write
    STATUS      mandatory
    DESCRIPTION
         "The maximum waiting delay (Tdmax) timeout value used by the
         Media Gateway to send the Restart In Progress with the restart
         method as RM:disconnected to the Media Gateway Controller when
         the endpoint has become disconnected is defined by this object.

         The endpoint becomes disconnected when it tries to communicate
         with the call agent and the retransmission procedure times out
         after retrying.

         The endpoint in disconnected state starts the disconnected timer
         initialised to the random value and uniformly distributed between
         1 and initial waiting delay (Tdinit) in seconds. 

         The gateway waits for either the end of this timer, or the reception
         of call agent command or the detection of local user activity for 
         the endpoint.

         When the disconnected timer elapses, or when a command is received
         from the call agent or when there is a local user activity, the 
         Media Gateway sends the Restart In Progress command with the restart 
         method as RM:disconnected to the Media Gateway Controller.

         If the disconnected procedure still left the endpoint disconnected,
         the disconnected timer is doubled subject to a provisionable
         disconnected maximum waiting delay (Tdmax) in seconds and the
         gateway starts the new disconnected procedure again.

         Once the maximum value is reached, the subsequent disconnected
         Restart In Progress commands use the maximum waiting delay (Tdmax).
         
         The recommended value of this object is 600 seconds.
        "
    REFERENCE
         " Media Gateway Control Protocol (MGCP),
           version 1.0 bis, May 10, 2001 : Section 4.4.7
         "
    DEFVAL{ 600 }

    ::= { vismXgcpEnhancementsObjects 3 }

END
