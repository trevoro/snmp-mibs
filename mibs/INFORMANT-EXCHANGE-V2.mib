INFORMANT-EXCHANGE-V2 DEFINITIONS ::= BEGIN

IMPORTS
    MODULE-IDENTITY, OBJECT-TYPE, OBJECT-IDENTITY, Gauge32
        FROM SNMPv2-SMI
    InstanceName, informant
        FROM WTCS;

exchangeV2 MODULE-IDENTITY
    LAST-UPDATED "200804080009Z"
    ORGANIZATION "Informant Systems, Inc."
    CONTACT-INFO
            "Garth Williams
             11135-23A Ave
             Edmonton, AB  T6J4W5  Canada
             Tel: +1 780 434 4113
             E-mail: garth.williams@wtcs.org"
    DESCRIPTION
            "The MIB module for informant standard entities."
    REVISION      "200804080009Z"
    DESCRIPTION
            "The initial revision of this MIB module."
    ::= { informant 15 }

ex2ADRMSPrelicensingAgent OBJECT-IDENTITY
    STATUS     current
    DESCRIPTION
	    "Performance counters for Exchange AD RMS
	    Prelicensing Agent"
    ::= { exchangeV2 1 }

ex2apaAvgProcessTimeLicenseRqst OBJECT-TYPE
    SYNTAX     Gauge32
    MAX-ACCESS read-only
    STATUS     current
    DESCRIPTION
	    "The Average Processing Time Per License
	    Request (ms) is the average amount of time in
	    milliseconds that it takes the AD RMS
	    Prelicensing agent to process a license."
    ::= { ex2ADRMSPrelicensingAgent 1 }

ex2apaMessageProcessSuccessfully OBJECT-TYPE
    SYNTAX     Gauge32
    MAX-ACCESS read-only
    STATUS     current
    DESCRIPTION
	    "Messages Processed Successfully is the total
	    number of protected messages that were
	    successfully processed by the AD RMS
	    Prelicensing agent."
    ::= { ex2ADRMSPrelicensingAgent 2 }

ex2apaPermanentFailLicenseRqsts OBJECT-TYPE
    SYNTAX     Gauge32
    MAX-ACCESS read-only
    STATUS     current
    DESCRIPTION
	    "Permanent Failure License Requests is the
	    total number of license requests that were made
	    by the AD RMS Prelicensing agent and resulted
	    in permanent failures."
    ::= { ex2ADRMSPrelicensingAgent 3 }

ex2apaSuccessfulLicenseRequests OBJECT-TYPE
    SYNTAX     Gauge32
    MAX-ACCESS read-only
    STATUS     current
    DESCRIPTION
	    "Successful License Requests is the total
	    number of successful license requests that were
	    made by the AD RMS Prelicensing agent."
    ::= { ex2ADRMSPrelicensingAgent 4 }

ex2apaTotalLicenseRequests OBJECT-TYPE
    SYNTAX     Gauge32
    MAX-ACCESS read-only
    STATUS     current
    DESCRIPTION
	    "Total License Requests is the total number of
	    license requests that were made by the AD RMS
	    Prelicensing agent."
    ::= { ex2ADRMSPrelicensingAgent 5 }

ex2apaTotalLicenseRqstsProcTime OBJECT-TYPE
    SYNTAX     Gauge32
    MAX-ACCESS read-only
    STATUS     current
    DESCRIPTION
	    "Total License Requests Processing Time (ms) is
	    the total time spent on license requests by the
	    AD RMS Prelicensing agent in milliseconds."
    ::= { ex2ADRMSPrelicensingAgent 6 }

ex2apaTotalLicenseRequestsPerSec OBJECT-TYPE
    SYNTAX     Gauge32
    MAX-ACCESS read-only
    STATUS     current
    DESCRIPTION
	    "Total License Requests/sec is the total number
	    of license requests that were made by the AD
	    RMS Prelicensing agent per second."
    ::= { ex2ADRMSPrelicensingAgent 7 }

ex2apaTotalMessages OBJECT-TYPE
    SYNTAX     Gauge32
    MAX-ACCESS read-only
    STATUS     current
    DESCRIPTION
	    "Total Messages is the total number of
	    protected messages that were processed by the
	    AD RMS Prelicensing agent."
    ::= { ex2ADRMSPrelicensingAgent 8 }

ex2apaTotalRecipients OBJECT-TYPE
    SYNTAX     Gauge32
    MAX-ACCESS read-only
    STATUS     current
    DESCRIPTION
	    "Total Recipients is the total number of
	    recipients from all protected e-mails that were
	    processed by the AD RMS Prelicensing agent."
    ::= { ex2ADRMSPrelicensingAgent 9 }

ex2ADAccessCachesTable OBJECT-TYPE
    SYNTAX     SEQUENCE OF Ex2ADAccessCachesEntry
    MAX-ACCESS not-accessible
    STATUS     current
    DESCRIPTION
	    "One instance per Cache Instance: global Cache
	    Instance data."
    ::= { exchangeV2 2 }

ex2ADAccessCachesEntry OBJECT-TYPE
    SYNTAX     Ex2ADAccessCachesEntry
    MAX-ACCESS not-accessible
    STATUS     current
    DESCRIPTION
	    "Performance information for one particular
	    instance of 'MSExchange ADAccess Caches'
	    object."
    INDEX      { ex2aacInstance }
    ::= { ex2ADAccessCachesTable 1 }

Ex2ADAccessCachesEntry ::= SEQUENCE {
    ex2aacInstance InstanceName,
    ex2aacCacheExpireTotalConfigData Gauge32,
    ex2aacCacheExpiriesTotalUserData Gauge32,
    ex2aacCacheExpiriesSecConfigData Gauge32,
    ex2aacCacheExpirePerSecUserData Gauge32,
    ex2aacCacheHitsTotal Gauge32,
    ex2aacCacheHitsPerSec Gauge32,
    ex2aacCacheInsertTotalConfigData Gauge32,
    ex2aacCacheInsertsTotalUserData Gauge32,
    ex2aacCacheInsertSecConfigurData Gauge32,
    ex2aacCacheInsertsPerSecUserData Gauge32,
    ex2aacCacheMissesTotal Gauge32,
    ex2aacCacheMissesPerSec Gauge32,
    ex2aacDNEntriesConfigurationData Gauge32,
    ex2aacDNEntriesUserData Gauge32,
    ex2aacDNEntriesMemoryConfigData Gauge32,
    ex2aacDNEntriesMemoryUserData Gauge32,
    ex2aacLDAPSearchesTotal Gauge32,
    ex2aacLDAPSearchesPerSec Gauge32,
    ex2aacNotFndDNEntriesConfigData Gauge32,
    ex2aacNotFoundDNEntriesUserData Gauge32,
    ex2aacNotFndDNEntryMemConfigData Gauge32,
    ex2aacNotFndDNEntriesMemUserData Gauge32,
    ex2aacNotFndGUIDEntryConfigData Gauge32,
    ex2aacNotFndGUIDEntriesUserData Gauge32,
    ex2aacNotFndGUIDEntryMemConfigDa Gauge32,
    ex2aacNotFndGUIDEntryMemUserData Gauge32,
    ex2aacOutstandingAsyncNotifies Gauge32,
    ex2aacOutstandingAsyncReads Gauge32,
    ex2aacOutstandingAsyncSearches Gauge32,
    ex2aacSearchEntriesConfigData Gauge32,
    ex2aacSearchEntriesUserData Gauge32,
    ex2aacSearchEntriesMemConfigData Gauge32,
    ex2aacSearchEntryMemoryUserData Gauge32,
    ex2aacTotalEntriesConfigData Gauge32,
    ex2aacTotalEntriesUserData Gauge32,
    ex2aacTotalEntriesMemConfigData Gauge32,
    ex2aacTotalEntriesMemoryUserData Gauge32
}

ex2aacInstance OBJECT-TYPE
    SYNTAX     InstanceName
    MAX-ACCESS read-only
    STATUS     current
    DESCRIPTION
	    "Instance name."
    ::= { ex2ADAccessCachesEntry 1 }

ex2aacCacheExpireTotalConfigData OBJECT-TYPE
    SYNTAX     Gauge32
    MAX-ACCESS read-only
    STATUS     current
    DESCRIPTION
	    "Cache Expiries Total (Configuration Data) is
	    the total number of configuration data objects
	    expired from the cache since system
	    initialization."
    ::= { ex2ADAccessCachesEntry 2 }

ex2aacCacheExpiriesTotalUserData OBJECT-TYPE
    SYNTAX     Gauge32
    MAX-ACCESS read-only
    STATUS     current
    DESCRIPTION
	    "Cache Expiries Total (User Data) is the total
	    number of user data objects expired from the
	    cache since system initialization."
    ::= { ex2ADAccessCachesEntry 3 }

ex2aacCacheExpiriesSecConfigData OBJECT-TYPE
    SYNTAX     Gauge32
    MAX-ACCESS read-only
    STATUS     current
    DESCRIPTION
	    "Cache Expiries/Sec (Configuration Data) is the
	    number of configuration data objects expired
	    from the cache per second."
    ::= { ex2ADAccessCachesEntry 4 }

ex2aacCacheExpirePerSecUserData OBJECT-TYPE
    SYNTAX     Gauge32
    MAX-ACCESS read-only
    STATUS     current
    DESCRIPTION
	    "Cache Expiries/Sec (User Data) is the number
	    of user data objects expired from the cache per
	    second."
    ::= { ex2ADAccessCachesEntry 5 }

ex2aacCacheHitsTotal OBJECT-TYPE
    SYNTAX     Gauge32
    MAX-ACCESS read-only
    STATUS     current
    DESCRIPTION
	    "Cache Hits Total is the total number of
	    'object found in cache' events since system
	    initialization."
    ::= { ex2ADAccessCachesEntry 6 }

ex2aacCacheHitsPerSec OBJECT-TYPE
    SYNTAX     Gauge32
    MAX-ACCESS read-only
    STATUS     current
    DESCRIPTION
	    "Cache Hits/Sec is the number of  'object found
	    in cache' events per second."
    ::= { ex2ADAccessCachesEntry 7 }

ex2aacCacheInsertTotalConfigData OBJECT-TYPE
    SYNTAX     Gauge32
    MAX-ACCESS read-only
    STATUS     current
    DESCRIPTION
	    "Cache Inserts Total (Configuration Data) is
	    the total number of configuration data objects
	    inserted into the cache since system
	    initialization."
    ::= { ex2ADAccessCachesEntry 8 }

ex2aacCacheInsertsTotalUserData OBJECT-TYPE
    SYNTAX     Gauge32
    MAX-ACCESS read-only
    STATUS     current
    DESCRIPTION
	    "Cache Inserts Total (User Data) is the total
	    number of user data objects inserted into the
	    cache since system initialization."
    ::= { ex2ADAccessCachesEntry 9 }

ex2aacCacheInsertSecConfigurData OBJECT-TYPE
    SYNTAX     Gauge32
    MAX-ACCESS read-only
    STATUS     current
    DESCRIPTION
	    "Cache Inserts/Sec (Configuration Data) is the
	    number of configuration data objects inserted
	    into the cache per second."
    ::= { ex2ADAccessCachesEntry 10 }

ex2aacCacheInsertsPerSecUserData OBJECT-TYPE
    SYNTAX     Gauge32
    MAX-ACCESS read-only
    STATUS     current
    DESCRIPTION
	    "Cache Inserts/Sec (User Data) is the number of
	    user data objects inserted into the cache per
	    second."
    ::= { ex2ADAccessCachesEntry 11 }

ex2aacCacheMissesTotal OBJECT-TYPE
    SYNTAX     Gauge32
    MAX-ACCESS read-only
    STATUS     current
    DESCRIPTION
	    "Cache Misses Total is the total number of
	    'object not found in cache' events since system
	    initialization."
    ::= { ex2ADAccessCachesEntry 12 }

ex2aacCacheMissesPerSec OBJECT-TYPE
    SYNTAX     Gauge32
    MAX-ACCESS read-only
    STATUS     current
    DESCRIPTION
	    "Cache Misses/Sec is the number of 'object not
	    found in cache' events per second."
    ::= { ex2ADAccessCachesEntry 13 }

ex2aacDNEntriesConfigurationData OBJECT-TYPE
    SYNTAX     Gauge32
    MAX-ACCESS read-only
    STATUS     current
    DESCRIPTION
	    "DN Entries (Configuration Data) is the total
	    number of configuration data DN object type
	    entries in the cache."
    ::= { ex2ADAccessCachesEntry 14 }

ex2aacDNEntriesUserData OBJECT-TYPE
    SYNTAX     Gauge32
    MAX-ACCESS read-only
    STATUS     current
    DESCRIPTION
	    "DN Entries (User Data) is the total number of
	    user data DN object type entries in the cache."
    ::= { ex2ADAccessCachesEntry 15 }

ex2aacDNEntriesMemoryConfigData OBJECT-TYPE
    SYNTAX     Gauge32
    MAX-ACCESS read-only
    STATUS     current
    DESCRIPTION
	    "DN Entries Memory (Configuration Data) is the
	    memory occupied by all configuration data DN
	    Entries in the cache (in bytes)"
    ::= { ex2ADAccessCachesEntry 16 }

ex2aacDNEntriesMemoryUserData OBJECT-TYPE
    SYNTAX     Gauge32
    MAX-ACCESS read-only
    STATUS     current
    DESCRIPTION
	    "DN Entries Memory (User Data) is the memory
	    occupied by all user data DN Entries in the
	    cache (in bytes)"
    ::= { ex2ADAccessCachesEntry 17 }

ex2aacLDAPSearchesTotal OBJECT-TYPE
    SYNTAX     Gauge32
    MAX-ACCESS read-only
    STATUS     current
    DESCRIPTION
	    "LDAP Searches Total is the total number of
	    LDAP search requests issued since system
	    initialization."
    ::= { ex2ADAccessCachesEntry 18 }

ex2aacLDAPSearchesPerSec OBJECT-TYPE
    SYNTAX     Gauge32
    MAX-ACCESS read-only
    STATUS     current
    DESCRIPTION
	    "LDAP Searches/Sec is the number of LDAP search
	    requests issued per second."
    ::= { ex2ADAccessCachesEntry 19 }

ex2aacNotFndDNEntriesConfigData OBJECT-TYPE
    SYNTAX     Gauge32
    MAX-ACCESS read-only
    STATUS     current
    DESCRIPTION
	    "Not Found DN Entries (Configuration Data) is
	    the total number of configuration data 'Not
	    Found DN' type entries in the cache."
    ::= { ex2ADAccessCachesEntry 20 }

ex2aacNotFoundDNEntriesUserData OBJECT-TYPE
    SYNTAX     Gauge32
    MAX-ACCESS read-only
    STATUS     current
    DESCRIPTION
	    "Not Found DN Entries (User Data) is the total
	    number of user data 'Not Found DN' type entries
	    in the cache."
    ::= { ex2ADAccessCachesEntry 21 }

ex2aacNotFndDNEntryMemConfigData OBJECT-TYPE
    SYNTAX     Gauge32
    MAX-ACCESS read-only
    STATUS     current
    DESCRIPTION
	    "Not Found DN Entries Memory (Configuration
	    Data) is the memory occupied by all
	    configuration data 'Not Found DN' Entries in
	    the cache (in bytes)"
    ::= { ex2ADAccessCachesEntry 22 }

ex2aacNotFndDNEntriesMemUserData OBJECT-TYPE
    SYNTAX     Gauge32
    MAX-ACCESS read-only
    STATUS     current
    DESCRIPTION
	    "Not Found DN Entries Memory (User Data) is the
	    memory occupied by all user data 'Not Found DN'
	    Entries in the cache (in bytes)"
    ::= { ex2ADAccessCachesEntry 23 }

ex2aacNotFndGUIDEntryConfigData OBJECT-TYPE
    SYNTAX     Gauge32
    MAX-ACCESS read-only
    STATUS     current
    DESCRIPTION
	    "Not Found GUID Entries (Configuration Data) is
	    the total number of configuration data 'Not
	    Found GUID' type entries in the cache."
    ::= { ex2ADAccessCachesEntry 24 }

ex2aacNotFndGUIDEntriesUserData OBJECT-TYPE
    SYNTAX     Gauge32
    MAX-ACCESS read-only
    STATUS     current
    DESCRIPTION
	    "Not Found GUID Entries (User Data) is the
	    total number of user data 'Not Found GUID' type
	    entries in the cache."
    ::= { ex2ADAccessCachesEntry 25 }

ex2aacNotFndGUIDEntryMemConfigDa OBJECT-TYPE
    SYNTAX     Gauge32
    MAX-ACCESS read-only
    STATUS     current
    DESCRIPTION
	    "Not Found GUID Entries Memory (Configuration
	    Data) is the memory occupied by all
	    configuration data 'Not Found GUID' Entries in
	    the cache (in bytes)"
    ::= { ex2ADAccessCachesEntry 26 }

ex2aacNotFndGUIDEntryMemUserData OBJECT-TYPE
    SYNTAX     Gauge32
    MAX-ACCESS read-only
    STATUS     current
    DESCRIPTION
	    "Not Found GUID Entries Memory (User Data) is
	    the memory occupied by all user data 'Not Found
	    GUID' Entries in the cache (in bytes)"
    ::= { ex2ADAccessCachesEntry 27 }

ex2aacOutstandingAsyncNotifies OBJECT-TYPE
    SYNTAX     Gauge32
    MAX-ACCESS read-only
    STATUS     current
    DESCRIPTION
	    "Outstanding Async Notifies is the number of
	    outstanding ldap notification requests."
    ::= { ex2ADAccessCachesEntry 28 }

ex2aacOutstandingAsyncReads OBJECT-TYPE
    SYNTAX     Gauge32
    MAX-ACCESS read-only
    STATUS     current
    DESCRIPTION
	    "Outstanding Async Reads is the number of
	    outstanding ldap read requests."
    ::= { ex2ADAccessCachesEntry 29 }

ex2aacOutstandingAsyncSearches OBJECT-TYPE
    SYNTAX     Gauge32
    MAX-ACCESS read-only
    STATUS     current
    DESCRIPTION
	    "Outstanding Async Searches is the number of
	    outstanding ldap search requests."
    ::= { ex2ADAccessCachesEntry 30 }

ex2aacSearchEntriesConfigData OBJECT-TYPE
    SYNTAX     Gauge32
    MAX-ACCESS read-only
    STATUS     current
    DESCRIPTION
	    "Search Entries (Configuration Data) is the
	    total number of configuration data search type
	    entries in the cache."
    ::= { ex2ADAccessCachesEntry 31 }

ex2aacSearchEntriesUserData OBJECT-TYPE
    SYNTAX     Gauge32
    MAX-ACCESS read-only
    STATUS     current
    DESCRIPTION
	    "Search Entries (User Data) is the total number
	    of user data search type entries in the cache."
    ::= { ex2ADAccessCachesEntry 32 }

ex2aacSearchEntriesMemConfigData OBJECT-TYPE
    SYNTAX     Gauge32
    MAX-ACCESS read-only
    STATUS     current
    DESCRIPTION
	    "Search Entries Memory (Configuration Data) is
	    the memory occupied by all configuration data
	    search entries in the cache (in bytes)"
    ::= { ex2ADAccessCachesEntry 33 }

ex2aacSearchEntryMemoryUserData OBJECT-TYPE
    SYNTAX     Gauge32
    MAX-ACCESS read-only
    STATUS     current
    DESCRIPTION
	    "Search Entries Memory (User Data) is the
	    memory occupied by all user data search entries
	    in the cache (in bytes)"
    ::= { ex2ADAccessCachesEntry 34 }

ex2aacTotalEntriesConfigData OBJECT-TYPE
    SYNTAX     Gauge32
    MAX-ACCESS read-only
    STATUS     current
    DESCRIPTION
	    "Total Entries (Configuration Data) is the
	    total number of configuration data entries in
	    the cache. This includes 'DN', 'Search', 'Not
	    Found DN' and 'Not Found GUID' type entries."
    ::= { ex2ADAccessCachesEntry 35 }

ex2aacTotalEntriesUserData OBJECT-TYPE
    SYNTAX     Gauge32
    MAX-ACCESS read-only
    STATUS     current
    DESCRIPTION
	    "Total Entries (User Data) is the total number
	    of user data entries in the cache. This
	    includes 'DN', 'Search', 'Not Found DN' and
	    'Not Found GUID' type entries."
    ::= { ex2ADAccessCachesEntry 36 }

ex2aacTotalEntriesMemConfigData OBJECT-TYPE
    SYNTAX     Gauge32
    MAX-ACCESS read-only
    STATUS     current
    DESCRIPTION
	    "Total Entries Memory (Configuration Data) is
	    the memory occupied by all configuration data
	    entry objects in the cache (in bytes)."
    ::= { ex2ADAccessCachesEntry 37 }

ex2aacTotalEntriesMemoryUserData OBJECT-TYPE
    SYNTAX     Gauge32
    MAX-ACCESS read-only
    STATUS     current
    DESCRIPTION
	    "Total Entries Memory (User Data) is the memory
	    occupied by all user data entry objects in the
	    cache (in bytes)."
    ::= { ex2ADAccessCachesEntry 38 }

ex2ADAccessDomainControllerTable OBJECT-TYPE
    SYNTAX     SEQUENCE OF Ex2ADAccessDomainControlEntry
    MAX-ACCESS not-accessible
    STATUS     current
    DESCRIPTION
	    "One instance per Domain Controller:
	    cross-process Domain Controller data."
    ::= { exchangeV2 3 }

ex2ADAccessDomainControllerEntry OBJECT-TYPE
    SYNTAX     Ex2ADAccessDomainControlEntry
    MAX-ACCESS not-accessible
    STATUS     current
    DESCRIPTION
	    "Performance information for one particular
	    instance of 'MSExchange ADAccess Domain
	    Controllers' object."
    INDEX      { ex2aadcInstance }
    ::= { ex2ADAccessDomainControllerTable 1 }

Ex2ADAccessDomainControlEntry ::= SEQUENCE {
    ex2aadcInstance InstanceName,
    ex2aadcBindFailuresPerMinute Gauge32,
    ex2aadcCriticalDataFlag Gauge32,
    ex2aadcDsGetDcNameElapsedTime Gauge32,
    ex2aadcGCCapableFlag Gauge32,
    ex2aadcIsSynchronizedFlag Gauge32,
    ex2aadcKerberosTicketLifetime Gauge32,
    ex2aadcLDAPDisconnectsPerMinute Gauge32,
    ex2aadcLDAPFatalErrorsPerMinute Gauge32,
    ex2aadcLDAPPagesPerSec Gauge32,
    ex2aadcLDAPReadTime Gauge32,
    ex2aadcLDAPReadCallsPerSec Gauge32,
    ex2aadcLDAPSearchTime Gauge32,
    ex2aadcLDAPSearchCallsPerSec Gauge32,
    ex2aadcLDAPSearchTimedOutPerMin Gauge32,
    ex2aadcLDAPVLVRequestsPerSec Gauge32,
    ex2aadcLDAPConnectionLifetime Gauge32,
    ex2aadcLocalSiteFlag Gauge32,
    ex2aadcLongRunningLDAPOperPerMin Gauge32,
    ex2aadcNetlogonFlag Gauge32,
    ex2aadcNumberOfOutstandRequests Gauge32,
    ex2aadcOSVersionFlag Gauge32,
    ex2aadcPDCFlag Gauge32,
    ex2aadcReachabilityBitmask Gauge32,
    ex2aadcSACLRightFlag Gauge32,
    ex2aadcUserSearchesFailPerMinute Gauge32,
    ex2aadcGethostbynameElapsedTime Gauge32
}

ex2aadcInstance OBJECT-TYPE
    SYNTAX     InstanceName
    MAX-ACCESS read-only
    STATUS     current
    DESCRIPTION
	    "Instance name."
    ::= { ex2ADAccessDomainControllerEntry 1 }

ex2aadcBindFailuresPerMinute OBJECT-TYPE
    SYNTAX     Gauge32
    MAX-ACCESS read-only
    STATUS     current
    DESCRIPTION
	    "Bind failures per minute is the number of LDAP
	    bind calls failed during the last minute"
    ::= { ex2ADAccessDomainControllerEntry 2 }

ex2aadcCriticalDataFlag OBJECT-TYPE
    SYNTAX     Gauge32
    MAX-ACCESS read-only
    STATUS     current
    DESCRIPTION
	    "Critical Data flag is 1 if the DC contains the
	    Exchange server account, 0 otherwise"
    ::= { ex2ADAccessDomainControllerEntry 3 }

ex2aadcDsGetDcNameElapsedTime OBJECT-TYPE
    SYNTAX     Gauge32
    MAX-ACCESS read-only
    STATUS     current
    DESCRIPTION
	    "DsGetDcName elapsed time is the total time (in
	    ms) spent in DsGetDcName call to the DC"
    ::= { ex2ADAccessDomainControllerEntry 4 }

ex2aadcGCCapableFlag OBJECT-TYPE
    SYNTAX     Gauge32
    MAX-ACCESS read-only
    STATUS     current
    DESCRIPTION
	    "GC capable flag is 1 if the DC is also a GC, 0
	    otherwise"
    ::= { ex2ADAccessDomainControllerEntry 5 }

ex2aadcIsSynchronizedFlag OBJECT-TYPE
    SYNTAX     Gauge32
    MAX-ACCESS read-only
    STATUS     current
    DESCRIPTION
	    "IsSynchronized flag is 1 if the DC is
	    synchronized, 0 otherwise"
    ::= { ex2ADAccessDomainControllerEntry 6 }

ex2aadcKerberosTicketLifetime OBJECT-TYPE
    SYNTAX     Gauge32
    MAX-ACCESS read-only
    STATUS     current
    DESCRIPTION
	    "Kerberos ticket lifetime (in seconds) is an
	    average life time of the last 16 connections
	    closed due to Kerberos ticket expiration"
    ::= { ex2ADAccessDomainControllerEntry 7 }

ex2aadcLDAPDisconnectsPerMinute OBJECT-TYPE
    SYNTAX     Gauge32
    MAX-ACCESS read-only
    STATUS     current
    DESCRIPTION
	    "LDAP Disconnects per minute is the number of
	    LDAP errors that caused Exchange Active
	    Directory Provider to mark the DC down during
	    the last minute"
    ::= { ex2ADAccessDomainControllerEntry 8 }

ex2aadcLDAPFatalErrorsPerMinute OBJECT-TYPE
    SYNTAX     Gauge32
    MAX-ACCESS read-only
    STATUS     current
    DESCRIPTION
	    "LDAP Fatal errors per minute is the number of
	    LDAP errors that caused Exchange Active
	    Directory Provider to close the LDAP connection
	    without marking the DC down during the last
	    minute"
    ::= { ex2ADAccessDomainControllerEntry 9 }

ex2aadcLDAPPagesPerSec OBJECT-TYPE
    SYNTAX     Gauge32
    MAX-ACCESS read-only
    STATUS     current
    DESCRIPTION
	    "LDAP Pages/Sec is the number of additional
	    pages that are retrieved from this DC per
	    second"
    ::= { ex2ADAccessDomainControllerEntry 10 }

ex2aadcLDAPReadTime OBJECT-TYPE
    SYNTAX     Gauge32
    MAX-ACCESS read-only
    STATUS     current
    DESCRIPTION
	    "LDAP Read Time for a given DC is the time (in
	    ms) taken to send an LDAP read request to the
	    specified DC and receive a response"
    ::= { ex2ADAccessDomainControllerEntry 11 }

ex2aadcLDAPReadCallsPerSec OBJECT-TYPE
    SYNTAX     Gauge32
    MAX-ACCESS read-only
    STATUS     current
    DESCRIPTION
	    "LDAP Read calls/Sec is the number of Depth 0
	    LDAP search calls made by this process per
	    second"
    ::= { ex2ADAccessDomainControllerEntry 12 }

ex2aadcLDAPSearchTime OBJECT-TYPE
    SYNTAX     Gauge32
    MAX-ACCESS read-only
    STATUS     current
    DESCRIPTION
	    "LDAP Search Time is the time (in ms) taken to
	    send an LDAP search request and receive a
	    response"
    ::= { ex2ADAccessDomainControllerEntry 13 }

ex2aadcLDAPSearchCallsPerSec OBJECT-TYPE
    SYNTAX     Gauge32
    MAX-ACCESS read-only
    STATUS     current
    DESCRIPTION
	    "LDAP Search calls/Sec is the number of Depth 1
	    or 2 LDAP Search calls made by this process per
	    second"
    ::= { ex2ADAccessDomainControllerEntry 14 }

ex2aadcLDAPSearchTimedOutPerMin OBJECT-TYPE
    SYNTAX     Gauge32
    MAX-ACCESS read-only
    STATUS     current
    DESCRIPTION
	    "LDAP Searches timed out per minute is the
	    number of LDAP searches returned LDAP_TIMEOUT
	    during the last minute"
    ::= { ex2ADAccessDomainControllerEntry 15 }

ex2aadcLDAPVLVRequestsPerSec OBJECT-TYPE
    SYNTAX     Gauge32
    MAX-ACCESS read-only
    STATUS     current
    DESCRIPTION
	    "LDAP VLV Requests/Sec is the number of Virtual
	    List View requests made to this DC per second.
	    Usually they are used for Addressbook browse
	    functionality in OWA."
    ::= { ex2ADAccessDomainControllerEntry 16 }

ex2aadcLDAPConnectionLifetime OBJECT-TYPE
    SYNTAX     Gauge32
    MAX-ACCESS read-only
    STATUS     current
    DESCRIPTION
	    "LDAP connection lifetime (in seconds) is an
	    average life time of the last 16 connections
	    closed (excludes ones closed due to Kerberos
	    ticket expiration)"
    ::= { ex2ADAccessDomainControllerEntry 17 }

ex2aadcLocalSiteFlag OBJECT-TYPE
    SYNTAX     Gauge32
    MAX-ACCESS read-only
    STATUS     current
    DESCRIPTION
	    "Local site flag is 1 if the DC belongs to the
	    local site, 0 otherwise"
    ::= { ex2ADAccessDomainControllerEntry 18 }

ex2aadcLongRunningLDAPOperPerMin OBJECT-TYPE
    SYNTAX     Gauge32
    MAX-ACCESS read-only
    STATUS     current
    DESCRIPTION
	    "Long running LDAP operations/Min is the number
	    of LDAP operations on this DC that took longer
	    than the specified threshold per minute
	    (default threshold is 15 seconds)"
    ::= { ex2ADAccessDomainControllerEntry 19 }

ex2aadcNetlogonFlag OBJECT-TYPE
    SYNTAX     Gauge32
    MAX-ACCESS read-only
    STATUS     current
    DESCRIPTION
	    "Netlogon flag is 1 when DsGetDcName to the DC
	    succeeds, indicating that NetLogon service is
	    running, 0 otherwise"
    ::= { ex2ADAccessDomainControllerEntry 20 }

ex2aadcNumberOfOutstandRequests OBJECT-TYPE
    SYNTAX     Gauge32
    MAX-ACCESS read-only
    STATUS     current
    DESCRIPTION
	    "Number of outstanding requests is the current
	    number of pending LDAP operations to the DC"
    ::= { ex2ADAccessDomainControllerEntry 21 }

ex2aadcOSVersionFlag OBJECT-TYPE
    SYNTAX     Gauge32
    MAX-ACCESS read-only
    STATUS     current
    DESCRIPTION
	    "OS Version flag is 1 when the DC satisfies
	    Exchange Active Directory Provider OS/Service
	    Pack requirements, 0 otherwise"
    ::= { ex2ADAccessDomainControllerEntry 22 }

ex2aadcPDCFlag OBJECT-TYPE
    SYNTAX     Gauge32
    MAX-ACCESS read-only
    STATUS     current
    DESCRIPTION
	    "PDC flag is 1if the DC is also a PDC, 0
	    otherwise"
    ::= { ex2ADAccessDomainControllerEntry 23 }

ex2aadcReachabilityBitmask OBJECT-TYPE
    SYNTAX     Gauge32
    MAX-ACCESS read-only
    STATUS     current
    DESCRIPTION
	    "Reachability bitmask shows how the DC is
	    reachable by using lowest 3 bits for DC, CDC
	    and GC-used ports."
    ::= { ex2ADAccessDomainControllerEntry 24 }

ex2aadcSACLRightFlag OBJECT-TYPE
    SYNTAX     Gauge32
    MAX-ACCESS read-only
    STATUS     current
    DESCRIPTION
	    "SACL right flag is 1 if the Exchange server
	    has a SeSecurityPrivilege on the DC, 0
	    otherwise"
    ::= { ex2ADAccessDomainControllerEntry 25 }

ex2aadcUserSearchesFailPerMinute OBJECT-TYPE
    SYNTAX     Gauge32
    MAX-ACCESS read-only
    STATUS     current
    DESCRIPTION
	    "User searches failed per minute is the number
	    of Exchange Active Directory Provider client's
	    searches failed during the last minute"
    ::= { ex2ADAccessDomainControllerEntry 26 }

ex2aadcGethostbynameElapsedTime OBJECT-TYPE
    SYNTAX     Gauge32
    MAX-ACCESS read-only
    STATUS     current
    DESCRIPTION
	    "gethostbyname elapsed time is the total time
	    (in ms) spent in gethostbyname call trying to
	    find the DC's IP address"
    ::= { ex2ADAccessDomainControllerEntry 27 }

ex2ADAccessGlobalCounters OBJECT-IDENTITY
    STATUS     current
    DESCRIPTION
	    "MSExchange ADAccess Global Counters contain
	    summary information that is not process or DC
	    specific"
    ::= { exchangeV2 4 }

ex2aagcDNSQueryDurationTime OBJECT-TYPE
    SYNTAX     Gauge32
    MAX-ACCESS read-only
    STATUS     current
    DESCRIPTION
	    "DNS Query duration time shows how long (in ms)
	    the most recent DNSQuery call took"
    ::= { ex2ADAccessGlobalCounters 1 }

ex2aagcInSiteDomainControllers OBJECT-TYPE
    SYNTAX     Gauge32
    MAX-ACCESS read-only
    STATUS     current
    DESCRIPTION
	    "In-site Domain Controllers is the number of
	    suitable Domain Controllers in the local site"
    ::= { ex2ADAccessGlobalCounters 2 }

ex2aagcInSiteGlobalCatalogs OBJECT-TYPE
    SYNTAX     Gauge32
    MAX-ACCESS read-only
    STATUS     current
    DESCRIPTION
	    "In-site Global Catalogs is the number of
	    suitable Global Catalogs in the local site"
    ::= { ex2ADAccessGlobalCounters 3 }

ex2aagcOutOfSiteDomainController OBJECT-TYPE
    SYNTAX     Gauge32
    MAX-ACCESS read-only
    STATUS     current
    DESCRIPTION
	    "Out-of-site Domain Controllers is the number
	    of suitable Domain Controllers outside the
	    local site"
    ::= { ex2ADAccessGlobalCounters 4 }

ex2aagcOutOfSiteGlobalCatalogs OBJECT-TYPE
    SYNTAX     Gauge32
    MAX-ACCESS read-only
    STATUS     current
    DESCRIPTION
	    "Out-of-site Global Catalogs is the number of
	    suitable Global Catalogs outside the local
	    site"
    ::= { ex2ADAccessGlobalCounters 5 }

ex2aagcTopologyDiscoveryDuraTime OBJECT-TYPE
    SYNTAX     Gauge32
    MAX-ACCESS read-only
    STATUS     current
    DESCRIPTION
	    "Topology Discovery duration time shows how
	    long (in msec) the most recent Topology
	    discovery took"
    ::= { ex2ADAccessGlobalCounters 6 }

ex2ADAccessProcessesTable OBJECT-TYPE
    SYNTAX     SEQUENCE OF Ex2ADAccessProcessesEntry
    MAX-ACCESS not-accessible
    STATUS     current
    DESCRIPTION
	    "One instance per client process"
    ::= { exchangeV2 5 }

ex2ADAccessProcessesEntry OBJECT-TYPE
    SYNTAX     Ex2ADAccessProcessesEntry
    MAX-ACCESS not-accessible
    STATUS     current
    DESCRIPTION
	    "Performance information for one particular
	    instance of 'MSExchange ADAccess Processes'
	    object."
    INDEX      { ex2aapInstance }
    ::= { ex2ADAccessProcessesTable 1 }

Ex2ADAccessProcessesEntry ::= SEQUENCE {
    ex2aapInstance InstanceName,
    ex2aapCriticlValidFailuresPerMin Gauge32,
    ex2aapIgnorValidatFailuresPerMin Gauge32,
    ex2aapLDAPNotFndConfigRdCallSec Gauge32,
    ex2aapLDAPPagesPerSec Gauge32,
    ex2aapLDAPReadTime Gauge32,
    ex2aapLDAPReadCallsPerSec Gauge32,
    ex2aapLDAPSearchTime Gauge32,
    ex2aapLDAPSearchCallsPerSec Gauge32,
    ex2aapLDAPTimeoutErrorsPerSec Gauge32,
    ex2aapLDAPVLVRequestsPerSec Gauge32,
    ex2aapLDAPWriteTime Gauge32,
    ex2aapLDAPWriteCallsPerSec Gauge32,
    ex2aapLDAPNotificaReportedPerSec Gauge32,
    ex2aapLDAPNotificaReceivedPerSec Gauge32,
    ex2aapLongRunningLDAPOperaPerMin Gauge32,
    ex2aapNonCriticalValidFailPerMin Gauge32,
    ex2aapNumberOfOutstandingRequest Gauge32,
    ex2aapOpenConnectionToDomainCtrl Gauge32,
    ex2aapOpenConnectionsToGlobalCat Gauge32,
    ex2aapProcessID Gauge32,
    ex2aapTopologyVersion Gauge32
}

ex2aapInstance OBJECT-TYPE
    SYNTAX     InstanceName
    MAX-ACCESS read-only
    STATUS     current
    DESCRIPTION
	    "Instance name."
    ::= { ex2ADAccessProcessesEntry 1 }

ex2aapCriticlValidFailuresPerMin OBJECT-TYPE
    SYNTAX     Gauge32
    MAX-ACCESS read-only
    STATUS     current
    DESCRIPTION
	    "Number of critical validation failures (that
	    cause DataValidationException to be thrown) per
	    minute"
    ::= { ex2ADAccessProcessesEntry 2 }

ex2aapIgnorValidatFailuresPerMin OBJECT-TYPE
    SYNTAX     Gauge32
    MAX-ACCESS read-only
    STATUS     current
    DESCRIPTION
	    "Number of non-critical validation failures
	    that cause an object to be removed from the
	    result set per minute"
    ::= { ex2ADAccessProcessesEntry 3 }

ex2aapLDAPNotFndConfigRdCallSec OBJECT-TYPE
    SYNTAX     Gauge32
    MAX-ACCESS read-only
    STATUS     current
    DESCRIPTION
	    "LDAP Not Found configuration read calls/Sec is
	    the number of Depth 0 LDAP search calls made by
	    this process that failed with 'Not found' per
	    second"
    ::= { ex2ADAccessProcessesEntry 4 }

ex2aapLDAPPagesPerSec OBJECT-TYPE
    SYNTAX     Gauge32
    MAX-ACCESS read-only
    STATUS     current
    DESCRIPTION
	    "LDAP Pages/Sec is the number of additional
	    pages that are retrieved by this process per
	    second"
    ::= { ex2ADAccessProcessesEntry 5 }

ex2aapLDAPReadTime OBJECT-TYPE
    SYNTAX     Gauge32
    MAX-ACCESS read-only
    STATUS     current
    DESCRIPTION
	    "LDAP Read Time is the time (in ms) taken to
	    send an LDAP read request and receive a
	    response"
    ::= { ex2ADAccessProcessesEntry 6 }

ex2aapLDAPReadCallsPerSec OBJECT-TYPE
    SYNTAX     Gauge32
    MAX-ACCESS read-only
    STATUS     current
    DESCRIPTION
	    "LDAP Read calls/Sec is the number of Depth 0
	    LDAP search calls made by this process per
	    second"
    ::= { ex2ADAccessProcessesEntry 7 }

ex2aapLDAPSearchTime OBJECT-TYPE
    SYNTAX     Gauge32
    MAX-ACCESS read-only
    STATUS     current
    DESCRIPTION
	    "LDAP Search Time is the time (in ms) taken to
	    send an LDAP search request and receive a
	    response"
    ::= { ex2ADAccessProcessesEntry 8 }

ex2aapLDAPSearchCallsPerSec OBJECT-TYPE
    SYNTAX     Gauge32
    MAX-ACCESS read-only
    STATUS     current
    DESCRIPTION
	    "LDAP Search calls/Sec is the number of Depth 1
	    or 2 LDAP Search calls made by this process per
	    second"
    ::= { ex2ADAccessProcessesEntry 9 }

ex2aapLDAPTimeoutErrorsPerSec OBJECT-TYPE
    SYNTAX     Gauge32
    MAX-ACCESS read-only
    STATUS     current
    DESCRIPTION
	    "LDAP Timeout errors/Sec is the number of LDAP
	    operations made by this process failed because
	    of exceeded Timeout per second"
    ::= { ex2ADAccessProcessesEntry 10 }

ex2aapLDAPVLVRequestsPerSec OBJECT-TYPE
    SYNTAX     Gauge32
    MAX-ACCESS read-only
    STATUS     current
    DESCRIPTION
	    "LDAP VLV requests/Sec is the number of Virtual
	    List View requests made by this process per
	    second. Usually they are used for Addressbook
	    browse functionality in OWA."
    ::= { ex2ADAccessProcessesEntry 11 }

ex2aapLDAPWriteTime OBJECT-TYPE
    SYNTAX     Gauge32
    MAX-ACCESS read-only
    STATUS     current
    DESCRIPTION
	    "LDAP Write Time is the time (in ms) taken to
	    send an LDAP Add/Modify/Delete request and
	    receive a response"
    ::= { ex2ADAccessProcessesEntry 12 }

ex2aapLDAPWriteCallsPerSec OBJECT-TYPE
    SYNTAX     Gauge32
    MAX-ACCESS read-only
    STATUS     current
    DESCRIPTION
	    "LDAP Write calls/Sec is the number of LDAP
	    Add/Modify/Delete calls made by this process
	    per second"
    ::= { ex2ADAccessProcessesEntry 13 }

ex2aapLDAPNotificaReportedPerSec OBJECT-TYPE
    SYNTAX     Gauge32
    MAX-ACCESS read-only
    STATUS     current
    DESCRIPTION
	    "LDAP notifications Reported/Sec is the number
	    of LDAP notification results reported by this
	    process to the end users per second"
    ::= { ex2ADAccessProcessesEntry 14 }

ex2aapLDAPNotificaReceivedPerSec OBJECT-TYPE
    SYNTAX     Gauge32
    MAX-ACCESS read-only
    STATUS     current
    DESCRIPTION
	    "LDAP notifications received/Sec is the number
	    of LDAP notification results received by this
	    process per second (does not necessarily equal
	    to the number of notifications reported to the
	    end users)"
    ::= { ex2ADAccessProcessesEntry 15 }

ex2aapLongRunningLDAPOperaPerMin OBJECT-TYPE
    SYNTAX     Gauge32
    MAX-ACCESS read-only
    STATUS     current
    DESCRIPTION
	    "Long running LDAP operations/Min is the number
	    of LDAP operations made by this process that
	    took longer than the specified threshold per
	    minute (default threshold is 15 seconds)"
    ::= { ex2ADAccessProcessesEntry 16 }

ex2aapNonCriticalValidFailPerMin OBJECT-TYPE
    SYNTAX     Gauge32
    MAX-ACCESS read-only
    STATUS     current
    DESCRIPTION
	    "Number of non-critical validation failures
	    (that do not cause exceptions) per minute"
    ::= { ex2ADAccessProcessesEntry 17 }

ex2aapNumberOfOutstandingRequest OBJECT-TYPE
    SYNTAX     Gauge32
    MAX-ACCESS read-only
    STATUS     current
    DESCRIPTION
	    "Number of outstanding requests is the current
	    number of pending LDAP searches in this
	    process"
    ::= { ex2ADAccessProcessesEntry 18 }

ex2aapOpenConnectionToDomainCtrl OBJECT-TYPE
    SYNTAX     Gauge32
    MAX-ACCESS read-only
    STATUS     current
    DESCRIPTION
	    "Open connections to Domain Controllers in this
	    process"
    ::= { ex2ADAccessProcessesEntry 19 }

ex2aapOpenConnectionsToGlobalCat OBJECT-TYPE
    SYNTAX     Gauge32
    MAX-ACCESS read-only
    STATUS     current
    DESCRIPTION
	    "Open connections to Global Catalogs in this
	    process"
    ::= { ex2ADAccessProcessesEntry 20 }

ex2aapProcessID OBJECT-TYPE
    SYNTAX     Gauge32
    MAX-ACCESS read-only
    STATUS     current
    DESCRIPTION
	    "The system Process ID of this process
	    instance"
    ::= { ex2ADAccessProcessesEntry 21 }

ex2aapTopologyVersion OBJECT-TYPE
    SYNTAX     Gauge32
    MAX-ACCESS read-only
    STATUS     current
    DESCRIPTION
	    "Current version of the Active Directory
	    topology data used by this process."
    ::= { ex2ADAccessProcessesEntry 22 }

ex2ActiveSync OBJECT-IDENTITY
    STATUS     current
    DESCRIPTION
	    "AirSync Counters Help"
    ::= { exchangeV2 6 }

ex2asAveragePingTime OBJECT-TYPE
    SYNTAX     Gauge32
    MAX-ACCESS read-only
    STATUS     current
    DESCRIPTION
	    "Average Ping Time is the average time elapsed,
	    in milliseconds, waiting for Ping and Hanging
	    Sync requests to complete."
    ::= { ex2ActiveSync 1 }

ex2asAverageRequestTime OBJECT-TYPE
    SYNTAX     Gauge32
    MAX-ACCESS read-only
    STATUS     current
    DESCRIPTION
	    "Average Request Time is the average time
	    elapsed, in milliseconds, waiting for a request
	    to complete."
    ::= { ex2ActiveSync 2 }

ex2asBadItemReportGeneratedTotal OBJECT-TYPE
    SYNTAX     Gauge32
    MAX-ACCESS read-only
    STATUS     current
    DESCRIPTION
	    "Bad Item Reports Generated Total is the total
	    number of bad item reports that were generated
	    since the service was started. This occurs when
	    items fail to convert from the server format to
	    the client format."
    ::= { ex2ActiveSync 3 }

ex2asBusyThreads OBJECT-TYPE
    SYNTAX     Gauge32
    MAX-ACCESS read-only
    STATUS     current
    DESCRIPTION
	    "Busy Threads is the number of worker threads
	    that are busy processing requests."
    ::= { ex2ActiveSync 4 }

ex2asConflictConcurrentSyncTotal OBJECT-TYPE
    SYNTAX     Gauge32
    MAX-ACCESS read-only
    STATUS     current
    DESCRIPTION
	    "Conflicting Concurrent Sync Total is the total
	    number of Sync commands which a concurrent sync
	    completed first for the same folder."
    ::= { ex2ActiveSync 5 }

ex2asConflictConcurrentSyncPrSec OBJECT-TYPE
    SYNTAX     Gauge32
    MAX-ACCESS read-only
    STATUS     current
    DESCRIPTION
	    "Conflicting Concurrent Sync/sec is the number
	    of Sync commands per second which a concurrent
	    sync completed first for the same folder."
    ::= { ex2ActiveSync 6 }

ex2asCreateCollectionCommandsSec OBJECT-TYPE
    SYNTAX     Gauge32
    MAX-ACCESS read-only
    STATUS     current
    DESCRIPTION
	    "Create Collection Commands/sec is the number
	    of CreateCollections commands that are
	    processed each second. Clients that are running
	    earlier versions of the ActiveSync protocol use
	    this command to create folders."
    ::= { ex2ActiveSync 7 }

ex2asCreateCollectionTotal OBJECT-TYPE
    SYNTAX     Gauge32
    MAX-ACCESS read-only
    STATUS     current
    DESCRIPTION
	    "Create Collection Total is the total number of
	    CreateCollection requests that have been
	    processed since the service was started."
    ::= { ex2ActiveSync 8 }

ex2asCurrentRequests OBJECT-TYPE
    SYNTAX     Gauge32
    MAX-ACCESS read-only
    STATUS     current
    DESCRIPTION
	    "Current Requests is the number of HTTP
	    requests received from ASP.NET."
    ::= { ex2ActiveSync 9 }

ex2asDeleteCollectionCommandsSec OBJECT-TYPE
    SYNTAX     Gauge32
    MAX-ACCESS read-only
    STATUS     current
    DESCRIPTION
	    "Delete Collection Commands/sec is the number
	    of	DeleteCollection commands that are
	    processed each second. Clients that are running
	    earlier versions of the ActiveSync protocol use
	    this command to delete folders."
    ::= { ex2ActiveSync 10 }

ex2asDeleteCollectionTotal OBJECT-TYPE
    SYNTAX     Gauge32
    MAX-ACCESS read-only
    STATUS     current
    DESCRIPTION
	    "Delete Collection Total is the total number of
	    DeleteCollections commands that have been
	    processed since the service was started.
	    Clients that are running earlier versions of
	    the Exchange ActiveSync protocol use this
	    command to delete folders."
    ::= { ex2ActiveSync 11 }

ex2asDocuLibraryFetchCommandsSec OBJECT-TYPE
    SYNTAX     Gauge32
    MAX-ACCESS read-only
    STATUS     current
    DESCRIPTION
	    "Document Library Fetches/sec is the number of
	    DocumentLibrary fetches that are processed each
	    second. This command is used by clients to
	    download Windows SharePoint Services or Windows
	    files shares files."
    ::= { ex2ActiveSync 12 }

ex2asDocumentLibraryFetchTotal OBJECT-TYPE
    SYNTAX     Gauge32
    MAX-ACCESS read-only
    STATUS     current
    DESCRIPTION
	    "Document Library Fetch Total is the total
	    number of DocumentLibrary Fetch requests that
	    have been processed since the service was
	    started."
    ::= { ex2ActiveSync 13 }

ex2asDocumentLibrarySearchTotal OBJECT-TYPE
    SYNTAX     Gauge32
    MAX-ACCESS read-only
    STATUS     current
    DESCRIPTION
	    "Document Library Search Total is the total
	    number of DocumentLibrary Search requests that
	    have been processed since the service was
	    started."
    ::= { ex2ActiveSync 14 }

ex2asDocumentLibrarySearchPerSec OBJECT-TYPE
    SYNTAX     Gauge32
    MAX-ACCESS read-only
    STATUS     current
    DESCRIPTION
	    "Document Library Searches Per Second is the
	    number of times per second that clients browse
	    Windows SharePoint Services or Windows file
	    shares items."
    ::= { ex2ActiveSync 15 }

ex2asEmptyFolderContentsTotal OBJECT-TYPE
    SYNTAX     Gauge32
    MAX-ACCESS read-only
    STATUS     current
    DESCRIPTION
	    "Empty Folder Contents Total is the total
	    number of Empty Folder Contents requests that
	    have been processed since the service was
	    started."
    ::= { ex2ActiveSync 16 }

ex2asFailedItemConversionTotal OBJECT-TYPE
    SYNTAX     Gauge32
    MAX-ACCESS read-only
    STATUS     current
    DESCRIPTION
	    "Failed Item Conversion Total is the total
	    number of items that failed to convert due to
	    modifications made by the server since the
	    service was started."
    ::= { ex2ActiveSync 17 }

ex2asFolderCreateCommandsPerSec OBJECT-TYPE
    SYNTAX     Gauge32
    MAX-ACCESS read-only
    STATUS     current
    DESCRIPTION
	    "Folder Create Commands/sec is the number of
	    FolderCreate commands that are processed each
	    second. Clients use this command to create
	    folders."
    ::= { ex2ActiveSync 18 }

ex2asFolderCreateTotal OBJECT-TYPE
    SYNTAX     Gauge32
    MAX-ACCESS read-only
    STATUS     current
    DESCRIPTION
	    "Folder Create Total is the total number of
	    FolderCreate requests that have been processed
	    since the service was started."
    ::= { ex2ActiveSync 19 }

ex2asFolderDeleteCommandsPerSec OBJECT-TYPE
    SYNTAX     Gauge32
    MAX-ACCESS read-only
    STATUS     current
    DESCRIPTION
	    "Folder Delete Commands/sec is the number of
	    FolderDelete commands that are processed each
	    second. Clients use this command to delete
	    folders."
    ::= { ex2ActiveSync 20 }

ex2asFolderDeleteTotal OBJECT-TYPE
    SYNTAX     Gauge32
    MAX-ACCESS read-only
    STATUS     current
    DESCRIPTION
	    "Folder Delete Totals is the total number of
	    FolderDelete commands that have been processed
	    since the service was started. Clients use this
	    command to delete folders."
    ::= { ex2ActiveSync 21 }

ex2asFolderSyncCommandsPerSec OBJECT-TYPE
    SYNTAX     Gauge32
    MAX-ACCESS read-only
    STATUS     current
    DESCRIPTION
	    "Folder Sync Commands/sec is the number of
	    FolderSync commands that are processed each
	    second. Clients use this command to synchronize
	    the folder hierarchy."
    ::= { ex2ActiveSync 22 }

ex2asFolderSyncTotal OBJECT-TYPE
    SYNTAX     Gauge32
    MAX-ACCESS read-only
    STATUS     current
    DESCRIPTION
	    "Folder Sync Total is the total number of
	    FolderSync requests that have been processed
	    since the service was started."
    ::= { ex2ActiveSync 23 }

ex2asFolderUpdateCommandsPerSec OBJECT-TYPE
    SYNTAX     Gauge32
    MAX-ACCESS read-only
    STATUS     current
    DESCRIPTION
	    "Folder Update Commands/sec is the number of
	    FolderUpdate commands that are processed per
	    second. Clients use this command to rename or
	    move folders."
    ::= { ex2ActiveSync 24 }

ex2asFolderUpdateTotal OBJECT-TYPE
    SYNTAX     Gauge32
    MAX-ACCESS read-only
    STATUS     current
    DESCRIPTION
	    "Folder Update Total is the total number of
	    FolderUpdate requests that have been  processed
	    since the service was started."
    ::= { ex2ActiveSync 25 }

ex2asGALSearchTotal OBJECT-TYPE
    SYNTAX     Gauge32
    MAX-ACCESS read-only
    STATUS     current
    DESCRIPTION
	    "GAL Search Total is the total number of GAL
	    Search requests that have been processed since
	    the service was started."
    ::= { ex2ActiveSync 26 }

ex2asGALSearchesPerSec OBJECT-TYPE
    SYNTAX     Gauge32
    MAX-ACCESS read-only
    STATUS     current
    DESCRIPTION
	    "GAL Searches/sec is the number of times that
	    the global address list is searched per
	    second."
    ::= { ex2ActiveSync 27 }

ex2asGetAttachmentCommandsPerSec OBJECT-TYPE
    SYNTAX     Gauge32
    MAX-ACCESS read-only
    STATUS     current
    DESCRIPTION
	    "Get Attachment Commands/sec is the number of
	    GetAttachment commands that are processed each
	    second. Clients that are running earlier
	    versions of the Exchange ActiveSync protocol
	    use this command to download e-mail
	    attachments."
    ::= { ex2ActiveSync 28 }

ex2asGetAttachmentTotal OBJECT-TYPE
    SYNTAX     Gauge32
    MAX-ACCESS read-only
    STATUS     current
    DESCRIPTION
	    "Get Attachment Total is the total number of
	    GetAttachments requests that have been
	    processed since the service was started."
    ::= { ex2ActiveSync 29 }

ex2asGetHierarchyCommandsPerSec OBJECT-TYPE
    SYNTAX     Gauge32
    MAX-ACCESS read-only
    STATUS     current
    DESCRIPTION
	    "Get Hierarchy Commands/sec is the number of
	    GetHierarchy commands that are processed each
	    second. Clients that are running earlier
	    versions of the ActiveSync protocol use this
	    command to synchronize the folder hierarchy."
    ::= { ex2ActiveSync 30 }

ex2asGetHierarchyTotal OBJECT-TYPE
    SYNTAX     Gauge32
    MAX-ACCESS read-only
    STATUS     current
    DESCRIPTION
	    "Get Hierarchy Total is the total number of
	    GetHierarchy commands that have been received
	    since the service was started."
    ::= { ex2ActiveSync 31 }

ex2asGetItemEstimatCommandPerSec OBJECT-TYPE
    SYNTAX     Gauge32
    MAX-ACCESS read-only
    STATUS     current
    DESCRIPTION
	    "Get Item Estimate Commands/sec is the number
	    of GetItemEstimate commands that are processed
	    each second. The GetItemEstimate command is
	    used by clients to display synchronization
	    progress."
    ::= { ex2ActiveSync 32 }

ex2asGetItemEstimateTotal OBJECT-TYPE
    SYNTAX     Gauge32
    MAX-ACCESS read-only
    STATUS     current
    DESCRIPTION
	    "Get Item Estimate Total is the total number of
	    GetItemEstimate requests that have been
	    processed since the service was started."
    ::= { ex2ActiveSync 33 }

ex2asHeartbeatInterval OBJECT-TYPE
    SYNTAX     Gauge32
    MAX-ACCESS read-only
    STATUS     current
    DESCRIPTION
	    "Heartbeat Interval is the heartbeat interval,
	    in seconds, specified by the client that
	    connected most recently."
    ::= { ex2ActiveSync 34 }

ex2asIdleThreads OBJECT-TYPE
    SYNTAX     Gauge32
    MAX-ACCESS read-only
    STATUS     current
    DESCRIPTION
	    "Idle Threads is the number of worker threads
	    that are idle."
    ::= { ex2ActiveSync 35 }

ex2asIncomingProxyRequestsTotal OBJECT-TYPE
    SYNTAX     Gauge32
    MAX-ACCESS read-only
    STATUS     current
    DESCRIPTION
	    "Incoming Proxy Requests Total is the total
	    number of HTTP requests received from ASP.NET
	    and proxied to another ActiveSync server since
	    the service was restarted."
    ::= { ex2ActiveSync 36 }

ex2asItemOperationsCommandPerSec OBJECT-TYPE
    SYNTAX     Gauge32
    MAX-ACCESS read-only
    STATUS     current
    DESCRIPTION
	    "Item Operations Commands/sec is the number of
	    ItemOperations commands that are processed each
	    second."
    ::= { ex2ActiveSync 37 }

ex2asItemOperationsTotal OBJECT-TYPE
    SYNTAX     Gauge32
    MAX-ACCESS read-only
    STATUS     current
    DESCRIPTION
	    "Item Operations Total is the total number of
	    ItemOperations requests that have been
	    processed since the service was started."
    ::= { ex2ActiveSync 38 }

ex2asMailboxAttchFetchCommandSec OBJECT-TYPE
    SYNTAX     Gauge32
    MAX-ACCESS read-only
    STATUS     current
    DESCRIPTION
	    "Mailbox Attachment Fetch Commands/sec is the
	    number of Mailbox Attachment Fetches that are
	    processed each second."
    ::= { ex2ActiveSync 39 }

ex2asMailboxAttachmentFetchTotal OBJECT-TYPE
    SYNTAX     Gauge32
    MAX-ACCESS read-only
    STATUS     current
    DESCRIPTION
	    "Mailbox Attachment Fetch Total is the total
	    number of Mailbox Attachment Fetch commands
	    that have been processed since the service was
	    started. This command is used by clients to
	    download e-mail attachments."
    ::= { ex2ActiveSync 40 }

ex2asMailboxItemFetchCommandsSec OBJECT-TYPE
    SYNTAX     Gauge32
    MAX-ACCESS read-only
    STATUS     current
    DESCRIPTION
	    "Number of Mailbox Item Fetches/sec is the
	    number of times that clients download whole
	    Exchange items each second."
    ::= { ex2ActiveSync 41 }

ex2asMailboxItemFetchTotal OBJECT-TYPE
    SYNTAX     Gauge32
    MAX-ACCESS read-only
    STATUS     current
    DESCRIPTION
	    "Mailbox Item Fetch Total is the total number
	    of mailbox item fetch requests that have been
	    processed since the service was started."
    ::= { ex2ActiveSync 42 }

ex2asMailboxSearchTotal OBJECT-TYPE
    SYNTAX     Gauge32
    MAX-ACCESS read-only
    STATUS     current
    DESCRIPTION
	    "Mailbox Search Total is the total number of
	    Mailbox Search requests that have been
	    processed since the service was started."
    ::= { ex2ActiveSync 43 }

ex2asMailboxSearchesPerSec OBJECT-TYPE
    SYNTAX     Gauge32
    MAX-ACCESS read-only
    STATUS     current
    DESCRIPTION
	    "Mailbox Searches/sec is the number of times
	    that mailboxes are searched per second."
    ::= { ex2ActiveSync 44 }

ex2asMeetingResponsCommandPerSec OBJECT-TYPE
    SYNTAX     Gauge32
    MAX-ACCESS read-only
    STATUS     current
    DESCRIPTION
	    "Meeting Response Commands/sec is the number of
	    MeetingResponse commands that are processed per
	    second. The client uses this command to
	    designate a meeting as Accepted, Declined, or
	    Tentative."
    ::= { ex2ActiveSync 45 }

ex2asMeetingResponseTotal OBJECT-TYPE
    SYNTAX     Gauge32
    MAX-ACCESS read-only
    STATUS     current
    DESCRIPTION
	    "Meeting Response Total is the total number of
	    MeetingResponse commands that have been
	    received since the service was started."
    ::= { ex2ActiveSync 46 }

ex2asMoveCollectionCommandPerSec OBJECT-TYPE
    SYNTAX     Gauge32
    MAX-ACCESS read-only
    STATUS     current
    DESCRIPTION
	    "Move Collection Commands/sec is the number of
	    MoveCollection commands that are processed each
	    second. Clients that are running earlier
	    versions of the Exchange ActiveSync protocol
	    use this command to move folders."
    ::= { ex2ActiveSync 47 }

ex2asMoveCollectionTotal OBJECT-TYPE
    SYNTAX     Gauge32
    MAX-ACCESS read-only
    STATUS     current
    DESCRIPTION
	    "Move Collection Total is the total number of 
	    MoveCollections requests that have been
	    processed since the service was started."
    ::= { ex2ActiveSync 48 }

ex2asMoveItemsCommandsPerSec OBJECT-TYPE
    SYNTAX     Gauge32
    MAX-ACCESS read-only
    STATUS     current
    DESCRIPTION
	    "Move Items Commands/sec is the number of
	    MoveItems commands that are processed each
	    second. Clients use this command to move
	    Exchange items between folders."
    ::= { ex2ActiveSync 49 }

ex2asMoveItemsTotal OBJECT-TYPE
    SYNTAX     Gauge32
    MAX-ACCESS read-only
    STATUS     current
    DESCRIPTION
	    "Move Items Total is the total number of
	    MoveItems commands that have been received
	    since the service was started."
    ::= { ex2ActiveSync 50 }

ex2asNumEmptyFoldrContentProcSec OBJECT-TYPE
    SYNTAX     Gauge32
    MAX-ACCESS read-only
    STATUS     current
    DESCRIPTION
	    "Number of Empty Folder Contents Processed/sec
	    is the number of number of Empty Folder
	    commands that are processed each second. This
	    command is used by clients to delete all items
	    in a folder."
    ::= { ex2ActiveSync 51 }

ex2asOptionsCommandsPerSec OBJECT-TYPE
    SYNTAX     Gauge32
    MAX-ACCESS read-only
    STATUS     current
    DESCRIPTION
	    "Options Commands/sec is the number of Options
	    commands that are processed each second.
	    Clients can use the Options command to discover
	    the ActiveSync protocol version that is
	    supported by the server."
    ::= { ex2ActiveSync 52 }

ex2asOptionsTotal OBJECT-TYPE
    SYNTAX     Gauge32
    MAX-ACCESS read-only
    STATUS     current
    DESCRIPTION
	    "Options Total is the total number of options
	    requests that have been processed since the
	    service was started."
    ::= { ex2ActiveSync 53 }

ex2asOutgoingProxyRequestsTotal OBJECT-TYPE
    SYNTAX     Gauge32
    MAX-ACCESS read-only
    STATUS     current
    DESCRIPTION
	    "Outgoing Proxy Requests Total is the total
	    number of HTTP requests received by ASP.NET
	    from another ActiveSync server since the
	    service was restarted."
    ::= { ex2ActiveSync 54 }

ex2asPID OBJECT-TYPE
    SYNTAX     Gauge32
    MAX-ACCESS read-only
    STATUS     current
    DESCRIPTION
	    "PID the process ID that is hosting
	    ActiveSync."
    ::= { ex2ActiveSync 55 }

ex2asPingCommandsDroppedPerSec OBJECT-TYPE
    SYNTAX     Gauge32
    MAX-ACCESS read-only
    STATUS     current
    DESCRIPTION
	    "Ping Commands Dropped/sec is the number of
	    Ping commands per second whose connection to
	    the client was dropped before a response could
	    be issued."
    ::= { ex2ActiveSync 56 }

ex2asPingCommandsPending OBJECT-TYPE
    SYNTAX     Gauge32
    MAX-ACCESS read-only
    STATUS     current
    DESCRIPTION
	    "Ping Commands Pending is the number of Ping
	    commands that are currently pending on the
	    server."
    ::= { ex2ActiveSync 57 }

ex2asPingCommandsPerSec OBJECT-TYPE
    SYNTAX     Gauge32
    MAX-ACCESS read-only
    STATUS     current
    DESCRIPTION
	    "Ping Commands/sec is the number of Ping
	    commands that are processed by the server each
	    second. This command is used to send clients
	    notifications about new e-mail messages or
	    changed items."
    ::= { ex2ActiveSync 58 }

ex2asPingDroppedTotal OBJECT-TYPE
    SYNTAX     Gauge32
    MAX-ACCESS read-only
    STATUS     current
    DESCRIPTION
	    "Ping Dropped Total is the total number of Ping
	    commands whose connection to the client was
	    dropped before a response could be issued."
    ::= { ex2ActiveSync 59 }

ex2asPingTotal OBJECT-TYPE
    SYNTAX     Gauge32
    MAX-ACCESS read-only
    STATUS     current
    DESCRIPTION
	    "Ping Total is the total number of Ping
	    commands that have been processed since the
	    service was started."
    ::= { ex2ActiveSync 60 }

ex2asProvisionCommandsPerSec OBJECT-TYPE
    SYNTAX     Gauge32
    MAX-ACCESS read-only
    STATUS     current
    DESCRIPTION
	    "Provision Commands/sec is the number of
	    Provision commands that are processed each
	    second. The server uses this command to enforce
	    mobile policies."
    ::= { ex2ActiveSync 61 }

ex2asProvisionTotal OBJECT-TYPE
    SYNTAX     Gauge32
    MAX-ACCESS read-only
    STATUS     current
    DESCRIPTION
	    "Provision Total is the total number of
	    Provision requests that have been processed
	    since the service was started."
    ::= { ex2ActiveSync 62 }

ex2asProxyLogonCommandsSentTotal OBJECT-TYPE
    SYNTAX     Gauge32
    MAX-ACCESS read-only
    STATUS     current
    DESCRIPTION
	    "Proxy Logon Commands Sent Total is the total
	    number of proxy logon commands that were sent
	    from this server to another server. This can
	    happen when a user's mailbox is located on an
	    Exchange 2003 server. It can also happen when
	    the Exchange 2007 Client Access server in the
	    same Active Directory site as the user's
	    Mailbox server is not Internet facing."
    ::= { ex2ActiveSync 63 }

ex2asProxyLogonReceivedTotal OBJECT-TYPE
    SYNTAX     Gauge32
    MAX-ACCESS read-only
    STATUS     current
    DESCRIPTION
	    "Proxy Logon Received Total is the number of
	    ProxyLogon commands that have been received by
	    this server from another server since the
	    service was started."
    ::= { ex2ActiveSync 64 }

ex2asRecoverySyncCommandsPerSec OBJECT-TYPE
    SYNTAX     Gauge32
    MAX-ACCESS read-only
    STATUS     current
    DESCRIPTION
	    "Recovery Sync Commands/sec is the number of
	    Recovery Sync requests that are processed each
	    second. The recovery sync process happens to
	    compensate for a failed synchronization with
	    the client."
    ::= { ex2ActiveSync 65 }

ex2asRecoverySyncTotal OBJECT-TYPE
    SYNTAX     Gauge32
    MAX-ACCESS read-only
    STATUS     current
    DESCRIPTION
	    "Recovery Sync Total is the total number of
	    Recovery Sync requests that have been processed
	    since the service was started."
    ::= { ex2ActiveSync 66 }

ex2asRequestsQueued OBJECT-TYPE
    SYNTAX     Gauge32
    MAX-ACCESS read-only
    STATUS     current
    DESCRIPTION
	    "Requests Queued is the number of HTTP requests
	    that are waiting to be assigned to a thread."
    ::= { ex2ActiveSync 67 }

ex2asRequestsTotal OBJECT-TYPE
    SYNTAX     Gauge32
    MAX-ACCESS read-only
    STATUS     current
    DESCRIPTION
	    "Requests Total is the total number of HTTP
	    requests received from ASP.NET since the
	    service was restarted."
    ::= { ex2ActiveSync 68 }

ex2asRequestsPerSec OBJECT-TYPE
    SYNTAX     Gauge32
    MAX-ACCESS read-only
    STATUS     current
    DESCRIPTION
	    "Requests/sec is the number of HTTP requests
	    that are received from the client via ASP.NET
	    per second."
    ::= { ex2ActiveSync 69 }

ex2asSearchCommandsPerSec OBJECT-TYPE
    SYNTAX     Gauge32
    MAX-ACCESS read-only
    STATUS     current
    DESCRIPTION
	    "Search Commands/sec is the number of Search
	    commands that are processed each second. This
	    counter represents the total number of global
	    address list, document library and mailbox
	    searches that are issued by the client."
    ::= { ex2ActiveSync 70 }

ex2asSearchTotal OBJECT-TYPE
    SYNTAX     Gauge32
    MAX-ACCESS read-only
    STATUS     current
    DESCRIPTION
	    "Search Total is the total number of Search
	    requests that have been processed since the
	    service was started."
    ::= { ex2ActiveSync 71 }

ex2asSendMailCommandsPerSec OBJECT-TYPE
    SYNTAX     Gauge32
    MAX-ACCESS read-only
    STATUS     current
    DESCRIPTION
	    "Send Mail Commands/sec is the number of
	    SendMail commands that are processed per
	    second."
    ::= { ex2ActiveSync 72 }

ex2asSendMailTotal OBJECT-TYPE
    SYNTAX     Gauge32
    MAX-ACCESS read-only
    STATUS     current
    DESCRIPTION
	    "Send Mail Total is the total number of
	    SendMail commands that are processed."
    ::= { ex2ActiveSync 73 }

ex2asSettingsCommandsPerSec OBJECT-TYPE
    SYNTAX     Gauge32
    MAX-ACCESS read-only
    STATUS     current
    DESCRIPTION
	    "Settings Commands/sec is the number of
	    Settings commands that are processed each
	    second."
    ::= { ex2ActiveSync 74 }

ex2asSettingsTotal OBJECT-TYPE
    SYNTAX     Gauge32
    MAX-ACCESS read-only
    STATUS     current
    DESCRIPTION
	    "Settings Total is the total number of Settings
	    commands that have been received since the
	    service was started."
    ::= { ex2ActiveSync 75 }

ex2asSmartForwardCommandsPerSec OBJECT-TYPE
    SYNTAX     Gauge32
    MAX-ACCESS read-only
    STATUS     current
    DESCRIPTION
	    "Smart Forward Commands/sec is the number of
	    SmartForward commands that are processed each
	    second. Clients use this command to forward
	    items without having to upload them to the
	    server."
    ::= { ex2ActiveSync 76 }

ex2asSmartForwardTotal OBJECT-TYPE
    SYNTAX     Gauge32
    MAX-ACCESS read-only
    STATUS     current
    DESCRIPTION
	    "Smart Forward Total is the total number of
	    SmartForward requests that have been processed
	    since the service was started."
    ::= { ex2ActiveSync 77 }

ex2asSmartReplyCommandsPerSec OBJECT-TYPE
    SYNTAX     Gauge32
    MAX-ACCESS read-only
    STATUS     current
    DESCRIPTION
	    "Smart Reply Commands/sec is the number of
	    SmartReply commands that are processed each
	    second. Clients use this command to reply with
	    items without having to upload them to the
	    server."
    ::= { ex2ActiveSync 78 }

ex2asSmartReplyTotal OBJECT-TYPE
    SYNTAX     Gauge32
    MAX-ACCESS read-only
    STATUS     current
    DESCRIPTION
	    "Smart Reply Total is the total number of
	    SmartReply requests that have been processed
	    since the service was started."
    ::= { ex2ActiveSync 79 }

ex2asSyncCommandsDroppedPerSec OBJECT-TYPE
    SYNTAX     Gauge32
    MAX-ACCESS read-only
    STATUS     current
    DESCRIPTION
	    "Sync Commands Dropped/sec is the number of
	    Sync commands per second whose connection to
	    the client was dropped before a response could
	    be issued."
    ::= { ex2ActiveSync 80 }

ex2asSyncCommandsPending OBJECT-TYPE
    SYNTAX     Gauge32
    MAX-ACCESS read-only
    STATUS     current
    DESCRIPTION
	    "Sync Commands Pending is the number of Sync
	    commands that are currently pending on the
	    server."
    ::= { ex2ActiveSync 81 }

ex2asSyncCommandsPerSec OBJECT-TYPE
    SYNTAX     Gauge32
    MAX-ACCESS read-only
    STATUS     current
    DESCRIPTION
	    "Sync Commands/sec is the number of Sync
	    commands that are processed per second. Clients
	    use this command to synchronize items within a
	    folder."
    ::= { ex2ActiveSync 82 }

ex2asSyncDroppedTotal OBJECT-TYPE
    SYNTAX     Gauge32
    MAX-ACCESS read-only
    STATUS     current
    DESCRIPTION
	    "Sync Dropped Total is the total number of Sync
	    commands whose connection to the client was
	    dropped before a response could be issued."
    ::= { ex2ActiveSync 83 }

ex2asSyncStateKBytesLeftCompress OBJECT-TYPE
    SYNTAX     Gauge32
    MAX-ACCESS read-only
    STATUS     current
    DESCRIPTION
	    "Sync State KBytes Left Compressed is the total
	    amount of sync state data that was left
	    compressed since the service was started. This
	    value contributes to the total amount of memory
	    consumed."
    ::= { ex2ActiveSync 84 }

ex2asSyncStateKBytesTotal OBJECT-TYPE
    SYNTAX     Gauge32
    MAX-ACCESS read-only
    STATUS     current
    DESCRIPTION
	    "Sync State KBytes Total is the total amount of
	    sync state data that was loaded since the
	    service was started. This value contributes to
	    the total amount of memory that is being
	    consumed."
    ::= { ex2ActiveSync 85 }

ex2asSyncTotal OBJECT-TYPE
    SYNTAX     Gauge32
    MAX-ACCESS read-only
    STATUS     current
    DESCRIPTION
	    "Sync Total is the total number of Sync
	    requests that have been processed since the
	    service was started."
    ::= { ex2ActiveSync 86 }

ex2asWrongCASProxyRequestsTotal OBJECT-TYPE
    SYNTAX     Gauge32
    MAX-ACCESS read-only
    STATUS     current
    DESCRIPTION
	    "Wrong CAS Proxy Requests Total tracks the
	    total number of mobile clients that are
	    misconfigured. These clients point to a Client
	    Access server URL that is not in the same
	    Active Directory site as the user's mailbox.
	    Users must make sure that their devices are
	    configured with the URL that points directly to
	    the Client Access server that is located in the
	    same Active Directory site as their Mailbox
	    server."
    ::= { ex2ActiveSync 87 }

ex2AssistantsTable OBJECT-TYPE
    SYNTAX     SEQUENCE OF Ex2AssistantsEntry
    MAX-ACCESS not-accessible
    STATUS     current
    DESCRIPTION
	    "Performance counters for Assistants"
    ::= { exchangeV2 7 }

ex2AssistantsEntry OBJECT-TYPE
    SYNTAX     Ex2AssistantsEntry
    MAX-ACCESS not-accessible
    STATUS     current
    DESCRIPTION
	    "Performance information for one particular
	    instance of 'MSExchange Assistants' object."
    INDEX      { ex2aInstance }
    ::= { ex2AssistantsTable 1 }

Ex2AssistantsEntry ::= SEQUENCE {
    ex2aInstance InstanceName,
    ex2aAvgEventProcessTimeInSeconds Gauge32,
    ex2aAvgEventQueueTimeInSeconds Gauge32,
    ex2aAvgMailboxProcessTimeSeconds Gauge32,
    ex2aAvgQueueSizeEventDispatchers Gauge32,
    ex2aEventsPolled Gauge32,
    ex2aEventsPolledPerSec Gauge32,
    ex2aEventsProcessed Gauge32,
    ex2aEventsInQueue Gauge32,
    ex2aHighestEventCounterPolled Gauge32,
    ex2aMailboxesProcessed Gauge32,
    ex2aMailboxesProcessedPerSec Gauge32,
    ex2aNumberOfEventDispatchers Gauge32,
    ex2aNumberOfFailEventDispatchers Gauge32,
    ex2aNumberOfHandledExceptions Gauge32,
    ex2aNumberOfThreadsUsed Gauge32,
    ex2aNumberEventsProcessPerSecond Gauge32,
    ex2aPercentageFailEventDispatchr Gauge32,
    ex2aPercentageOfInterestingEvent Gauge32,
    ex2aPollingDelay Gauge32
}

ex2aInstance OBJECT-TYPE
    SYNTAX     InstanceName
    MAX-ACCESS read-only
    STATUS     current
    DESCRIPTION
	    "Instance name."
    ::= { ex2AssistantsEntry 1 }

ex2aAvgEventProcessTimeInSeconds OBJECT-TYPE
    SYNTAX     Gauge32
    MAX-ACCESS read-only
    STATUS     current
    DESCRIPTION
	    "Average processing time of the events chosen
	    as interesting."
    ::= { ex2AssistantsEntry 2 }

ex2aAvgEventQueueTimeInSeconds OBJECT-TYPE
    SYNTAX     Gauge32
    MAX-ACCESS read-only
    STATUS     current
    DESCRIPTION
	    "Average time (in seconds) that the event lives
	    in the dispatcher queue."
    ::= { ex2AssistantsEntry 3 }

ex2aAvgMailboxProcessTimeSeconds OBJECT-TYPE
    SYNTAX     Gauge32
    MAX-ACCESS read-only
    STATUS     current
    DESCRIPTION
	    "Average Mailbox Processing Time In seconds is
	    the average processing time of mailboxes for
	    time-based assistants/sec."
    ::= { ex2AssistantsEntry 4 }

ex2aAvgQueueSizeEventDispatchers OBJECT-TYPE
    SYNTAX     Gauge32
    MAX-ACCESS read-only
    STATUS     current
    DESCRIPTION
	    "Average queue size of event dispatchers."
    ::= { ex2AssistantsEntry 5 }

ex2aEventsPolled OBJECT-TYPE
    SYNTAX     Gauge32
    MAX-ACCESS read-only
    STATUS     current
    DESCRIPTION
	    "The number of events polled by the
	    assistants."
    ::= { ex2AssistantsEntry 6 }

ex2aEventsPolledPerSec OBJECT-TYPE
    SYNTAX     Gauge32
    MAX-ACCESS read-only
    STATUS     current
    DESCRIPTION
	    "The number of events polled per second."
    ::= { ex2AssistantsEntry 7 }

ex2aEventsProcessed OBJECT-TYPE
    SYNTAX     Gauge32
    MAX-ACCESS read-only
    STATUS     current
    DESCRIPTION
	    "Number of events processed by the assistants."
    ::= { ex2AssistantsEntry 8 }

ex2aEventsInQueue OBJECT-TYPE
    SYNTAX     Gauge32
    MAX-ACCESS read-only
    STATUS     current
    DESCRIPTION
	    "Events in queue is the current number of
	    events in the in-memory queue waiting to be
	    processed by the assistants."
    ::= { ex2AssistantsEntry 9 }

ex2aHighestEventCounterPolled OBJECT-TYPE
    SYNTAX     Gauge32
    MAX-ACCESS read-only
    STATUS     current
    DESCRIPTION
	    "Highest Event Counter Polled is the highest
	    event counter polled from the database."
    ::= { ex2AssistantsEntry 10 }

ex2aMailboxesProcessed OBJECT-TYPE
    SYNTAX     Gauge32
    MAX-ACCESS read-only
    STATUS     current
    DESCRIPTION
	    "The number of mailboxes processed by
	    time-based assistants."
    ::= { ex2AssistantsEntry 11 }

ex2aMailboxesProcessedPerSec OBJECT-TYPE
    SYNTAX     Gauge32
    MAX-ACCESS read-only
    STATUS     current
    DESCRIPTION
	    "Mailboxes processed/sec is the rate of
	    mailboxes processed by time-based assistants
	    per second."
    ::= { ex2AssistantsEntry 12 }

ex2aNumberOfEventDispatchers OBJECT-TYPE
    SYNTAX     Gauge32
    MAX-ACCESS read-only
    STATUS     current
    DESCRIPTION
	    "The current number of event dispatchers in
	    memory."
    ::= { ex2AssistantsEntry 13 }

ex2aNumberOfFailEventDispatchers OBJECT-TYPE
    SYNTAX     Gauge32
    MAX-ACCESS read-only
    STATUS     current
    DESCRIPTION
	    "The number of event dispatchers that are in
	    failed state."
    ::= { ex2AssistantsEntry 14 }

ex2aNumberOfHandledExceptions OBJECT-TYPE
    SYNTAX     Gauge32
    MAX-ACCESS read-only
    STATUS     current
    DESCRIPTION
	    "The number of CLR exceptions handled by the
	    code."
    ::= { ex2AssistantsEntry 15 }

ex2aNumberOfThreadsUsed OBJECT-TYPE
    SYNTAX     Gauge32
    MAX-ACCESS read-only
    STATUS     current
    DESCRIPTION
	    "Number of Threads used from the CLR thread
	    pool."
    ::= { ex2AssistantsEntry 16 }

ex2aNumberEventsProcessPerSecond OBJECT-TYPE
    SYNTAX     Gauge32
    MAX-ACCESS read-only
    STATUS     current
    DESCRIPTION
	    "The number of events processed per second."
    ::= { ex2AssistantsEntry 17 }

ex2aPercentageFailEventDispatchr OBJECT-TYPE
    SYNTAX     Gauge32
    MAX-ACCESS read-only
    STATUS     current
    DESCRIPTION
	    "Percentage of Failed Event Dispatchers is the
	    percentage of Event Dispatchers that are in
	    failure mode."
    ::= { ex2AssistantsEntry 18 }

ex2aPercentageOfInterestingEvent OBJECT-TYPE
    SYNTAX     Gauge32
    MAX-ACCESS read-only
    STATUS     current
    DESCRIPTION
	    "Percentage of Interesting Events is the
	    percentage of events generated on the database
	    that are processed by the assistants."
    ::= { ex2AssistantsEntry 19 }

ex2aPollingDelay OBJECT-TYPE
    SYNTAX     Gauge32
    MAX-ACCESS read-only
    STATUS     current
    DESCRIPTION
	    "Polling Delay is the latency between when the
	    most recent Mapi Event was polled and when the
	    event was created in seconds."
    ::= { ex2AssistantsEntry 20 }

ex2AvailabilityService OBJECT-IDENTITY
    STATUS     current
    DESCRIPTION
	    "Performance counters for the Availability
	    service"
    ::= { exchangeV2 8 }

ex2aserAvailabilityRequestsSec OBJECT-TYPE
    SYNTAX     Gauge32
    MAX-ACCESS read-only
    STATUS     current
    DESCRIPTION
	    "Availability Requests per second is the number
	     of requests serviced per second. The request
	    can be only for free busy or include
	    suggestions. One request may contain multiple
	    mailboxes."
    ::= { ex2AvailabilityService 1 }

ex2aserAvgNumMailboxProcessReqst OBJECT-TYPE
    SYNTAX     Gauge32
    MAX-ACCESS read-only
    STATUS     current
    DESCRIPTION
	    "Average Number of Mailboxes Processed per
	    Request is the average number of mailboxes
	    processed per request. Some of the mailboxes
	    may have errors during processing."
    ::= { ex2AvailabilityService 2 }

ex2aserAvgTimProCrsFrstFreBsyReq OBJECT-TYPE
    SYNTAX     Gauge32
    MAX-ACCESS read-only
    STATUS     current
    DESCRIPTION
	    "Average Time to Process a Cross-Forest Free
	    Busy Request is the average time to process a
	    cross-forest free busy request in seconds. One
	    request may contain multiple mailboxes. Free
	    busy responses do not have meeting
	    suggestions."
    ::= { ex2AvailabilityService 3 }

ex2aserAvgTimProCrsSiteFreBsyReq OBJECT-TYPE
    SYNTAX     Gauge32
    MAX-ACCESS read-only
    STATUS     current
    DESCRIPTION
	    "Average Time to Process a Cross-Site Free Busy
	    Request is the average time to process a
	    cross-site free busy request in seconds. One
	    request may contain multiple mailboxes. Free
	    busy responses do not have meeting
	    suggestions."
    ::= { ex2AvailabilityService 4 }

ex2aserAvgTimeProcessFreeBusyReq OBJECT-TYPE
    SYNTAX     Gauge32
    MAX-ACCESS read-only
    STATUS     current
    DESCRIPTION
	    "Average Time to Process a Free Busy Request is
	    the average time to process a free busy request
	    in seconds. One request may contain multiple
	    mailboxes. Free busy responses do not have
	    meeting suggestions."
    ::= { ex2AvailabilityService 5 }

ex2aserAvgTimeProcessMtgSuggRequ OBJECT-TYPE
    SYNTAX     Gauge32
    MAX-ACCESS read-only
    STATUS     current
    DESCRIPTION
	    "Average Time to Process a Meeting Suggestions
	    Request is the average time to process a
	    meeting suggestions request in seconds. One
	    request may contain multiple mailboxes. This
	    time includes time for fetching free busy."
    ::= { ex2AvailabilityService 6 }

ex2aserCrsFrstCalendarFailureSec OBJECT-TYPE
    SYNTAX     Gauge32
    MAX-ACCESS read-only
    STATUS     current
    DESCRIPTION
	    "Cross-Forest Calendar Failures per second is
	    the number of cross-forest mailbox queries that
	    failed per second. These mailboxes require
	    proxying to another instance of the service in
	    a different forest."
    ::= { ex2AvailabilityService 7 }

ex2aserCrsFrstCalendarQueriesSec OBJECT-TYPE
    SYNTAX     Gauge32
    MAX-ACCESS read-only
    STATUS     current
    DESCRIPTION
	    "Cross-Forest Calendar Queries per second is
	    the number of cross-forest mailboxes queried
	    per second. These mailboxes require proxying to
	    another instance of the service in a different
	    forest."
    ::= { ex2AvailabilityService 8 }

ex2aserCrsSiteCalendarFailureSec OBJECT-TYPE
    SYNTAX     Gauge32
    MAX-ACCESS read-only
    STATUS     current
    DESCRIPTION
	    "Cross-Site Calendar Failures per second is the
	    number of cross-site mailbox queries failed per
	    second. These mailboxes require proxying to
	    another instance of the service in a different
	    site."
    ::= { ex2AvailabilityService 9 }

ex2aserCrsSiteCalendarQueriesSec OBJECT-TYPE
    SYNTAX     Gauge32
    MAX-ACCESS read-only
    STATUS     current
    DESCRIPTION
	    "Cross-Site Calendar Queries per second is the
	    number of cross-site mailboxes queried per
	    second. These mailboxes require proxying to
	    another instance of the service in a different
	    site."
    ::= { ex2AvailabilityService 10 }

ex2aserForeignConnectorQuerySec OBJECT-TYPE
    SYNTAX     Gauge32
    MAX-ACCESS read-only
    STATUS     current
    DESCRIPTION
	    "Foreign Connector Queries per second is the
	    number of mailboxes for which free busy
	    information is requested from a foreign
	    connector per second."
    ::= { ex2AvailabilityService 11 }

ex2aserForeignConnectReqFailRate OBJECT-TYPE
    SYNTAX     Gauge32
    MAX-ACCESS read-only
    STATUS     current
    DESCRIPTION
	    "Foreign Connector Request Failure Rate is the
	    number of Foreign connector free busy requests
	    failed per second."
    ::= { ex2AvailabilityService 12 }

ex2aserIntraSiteCalendarFailSec OBJECT-TYPE
    SYNTAX     Gauge32
    MAX-ACCESS read-only
    STATUS     current
    DESCRIPTION
	    "Intra-Site Calendar Failures per second is the
	    number  of intra-site mailbox queries failed
	    per second. These mailboxes do not require
	    proxying to another instance of the service."
    ::= { ex2AvailabilityService 13 }

ex2aserIntraSiteCalendarQuerySec OBJECT-TYPE
    SYNTAX     Gauge32
    MAX-ACCESS read-only
    STATUS     current
    DESCRIPTION
	    "Intra-Site Calendar Queries per second is the
	    number of intra-site mailboxes queried per
	    second. These mailboxes do not require proxying
	    to another instance of the service."
    ::= { ex2AvailabilityService 14 }

ex2aserPublicFolderQueriesSec OBJECT-TYPE
    SYNTAX     Gauge32
    MAX-ACCESS read-only
    STATUS     current
    DESCRIPTION
	    "Public Folder Queries per second is the number
	    of mailboxes for which free busy information is
	    requested from the public folders per second."
    ::= { ex2AvailabilityService 15 }

ex2aserPublicFolderReqFailSec OBJECT-TYPE
    SYNTAX     Gauge32
    MAX-ACCESS read-only
    STATUS     current
    DESCRIPTION
	    "Public Folder Request Failures per second is
	    the number of public folder free busy requests
	    failed per second."
    ::= { ex2AvailabilityService 16 }

ex2aserSuggestionsRequestsSec OBJECT-TYPE
    SYNTAX     Gauge32
    MAX-ACCESS read-only
    STATUS     current
    DESCRIPTION
	    "Suggestions Requests per second is the number
	    of requests per second, specifically for
	    meeting suggestions. The request can be only
	    for free busy or include suggestions. One
	    request may contain multiple mailboxes."
    ::= { ex2AvailabilityService 17 }

ex2CalendarAttendant OBJECT-IDENTITY
    STATUS     current
    DESCRIPTION
	    "Performance counters for the Calendar
	    Attendant"
    ::= { exchangeV2 9 }

ex2caAvgCalendarAttendntProcTime OBJECT-TYPE
    SYNTAX     Gauge32
    MAX-ACCESS read-only
    STATUS     current
    DESCRIPTION
	    "Average Calendar Attendant Processing Time is
	    the average  time to process an event in the
	    Calendar Attendant."
    ::= { ex2CalendarAttendant 1 }

ex2caLastCalendarAttendtProcTime OBJECT-TYPE
    SYNTAX     Gauge32
    MAX-ACCESS read-only
    STATUS     current
    DESCRIPTION
	    "Last Calendar Attendant Processing Time is the
	    latest time to to process an event	in the
	    Calendar Attendant."
    ::= { ex2CalendarAttendant 2 }

ex2caLostRaces OBJECT-TYPE
    SYNTAX     Gauge32
    MAX-ACCESS read-only
    STATUS     current
    DESCRIPTION
	    "Lost Races is the total number of times the
	    Calendar Attendant processed items after
	    Outlook already reached it."
    ::= { ex2CalendarAttendant 3 }

ex2caMeetingCancellations OBJECT-TYPE
    SYNTAX     Gauge32
    MAX-ACCESS read-only
    STATUS     current
    DESCRIPTION
	    "Meeting Cancellations is the total number of
	    meeting cancellations processed by Calendar
	    Attendant."
    ::= { ex2CalendarAttendant 4 }

ex2caMeetingMessagesDeleted OBJECT-TYPE
    SYNTAX     Gauge32
    MAX-ACCESS read-only
    STATUS     current
    DESCRIPTION
	    "Meeting Messages Deleted is the number of
	    meeting messages deleted from noise reduction."
    ::= { ex2CalendarAttendant 5 }

ex2caMeetingMessagesProcessed OBJECT-TYPE
    SYNTAX     Gauge32
    MAX-ACCESS read-only
    STATUS     current
    DESCRIPTION
	    "Meeting Messages Processed is the total number
	    of meeting messages processed by Calendar
	    Attendant."
    ::= { ex2CalendarAttendant 6 }

ex2caMeetingRequests OBJECT-TYPE
    SYNTAX     Gauge32
    MAX-ACCESS read-only
    STATUS     current
    DESCRIPTION
	    "Meeting Requests is the total number of
	    meeting requests processed by Calendar
	    Attendant."
    ::= { ex2CalendarAttendant 7 }

ex2caMeetingResponses OBJECT-TYPE
    SYNTAX     Gauge32
    MAX-ACCESS read-only
    STATUS     current
    DESCRIPTION
	    "Meeting Responses is the  total number of
	    meeting responses processed by Calendar
	    Attendant."
    ::= { ex2CalendarAttendant 8 }

ex2caRequestsFailed OBJECT-TYPE
    SYNTAX     Gauge32
    MAX-ACCESS read-only
    STATUS     current
    DESCRIPTION
	    "Requests Failed is the total number of
	    failures that occurred while Calendar Attendant
	    was processing events."
    ::= { ex2CalendarAttendant 9 }

ex2ConnectionFilteringAgent OBJECT-IDENTITY
    STATUS     current
    DESCRIPTION
	    "Performance counters for the Connection
	    Filtering Agent"
    ::= { exchangeV2 10 }

ex2cfaConnectionsOnIPAllowList OBJECT-TYPE
    SYNTAX     Gauge32
    MAX-ACCESS read-only
    STATUS     current
    DESCRIPTION
	    "Connections on IP Allow List is the total
	    number of connections on the IP Allow list."
    ::= { ex2ConnectionFilteringAgent 1 }

ex2cfaConnOnIPAllowListProviders OBJECT-TYPE
    SYNTAX     Gauge32
    MAX-ACCESS read-only
    STATUS     current
    DESCRIPTION
	    "Connections on IP Allow List Providers is the
	    total number of connections on the IP Allow
	    List providers."
    ::= { ex2ConnectionFilteringAgent 2 }

ex2cfaConnOnIPAllowListProvidSec OBJECT-TYPE
    SYNTAX     Gauge32
    MAX-ACCESS read-only
    STATUS     current
    DESCRIPTION
	    "Connections on IP Allow List Providers/sec is
	    the number of connections on the IP Allow List
	    providers per second."
    ::= { ex2ConnectionFilteringAgent 3 }

ex2cfaConnOnIPAllowListSec OBJECT-TYPE
    SYNTAX     Gauge32
    MAX-ACCESS read-only
    STATUS     current
    DESCRIPTION
	    "Connections on the IP Allow List per second is
	    the number of connections on the IP Allow List
	    per second."
    ::= { ex2ConnectionFilteringAgent 4 }

ex2cfaConnectionsOnIPBlockList OBJECT-TYPE
    SYNTAX     Gauge32
    MAX-ACCESS read-only
    STATUS     current
    DESCRIPTION
	    "Connections on IP Block List is the total
	    number of connections on the IP Block list."
    ::= { ex2ConnectionFilteringAgent 5 }

ex2cfaConnOnIPBlockListProviders OBJECT-TYPE
    SYNTAX     Gauge32
    MAX-ACCESS read-only
    STATUS     current
    DESCRIPTION
	    "Connections on IP Block List Providers is the
	    total number of connections on the IP Block
	    List providers."
    ::= { ex2ConnectionFilteringAgent 6 }

ex2cfaConnOnIPBlockListProvidSec OBJECT-TYPE
    SYNTAX     Gauge32
    MAX-ACCESS read-only
    STATUS     current
    DESCRIPTION
	    "Connections on IP Block List Providers/sec is
	    the number of connections on the IP Block List
	    providers per second."
    ::= { ex2ConnectionFilteringAgent 7 }

ex2cfaConnOnIPBlockListPerSec OBJECT-TYPE
    SYNTAX     Gauge32
    MAX-ACCESS read-only
    STATUS     current
    DESCRIPTION
	    "Connections on IP Block List/sec is the number
	    of connections on the IP Block list per
	    second."
    ::= { ex2ConnectionFilteringAgent 8 }

ex2cfaMsgOrigIPIPAllowList OBJECT-TYPE
    SYNTAX     Gauge32
    MAX-ACCESS read-only
    STATUS     current
    DESCRIPTION
	    "Messages with Originating IP on IP Allow List
	    is the total number of messages with an
	    originating IP address on the IP Allow list."
    ::= { ex2ConnectionFilteringAgent 9 }

ex2cfaMsgOrigIPIPAllowListPrv OBJECT-TYPE
    SYNTAX     Gauge32
    MAX-ACCESS read-only
    STATUS     current
    DESCRIPTION
	    "Messages with Originating IP on IP Allow List
	    Providers is the  total number of messages with
	    an originating IP address on the IP Allow List
	    providers."
    ::= { ex2ConnectionFilteringAgent 10 }

ex2cfaMsgOrigIPIPAllowListPrvSec OBJECT-TYPE
    SYNTAX     Gauge32
    MAX-ACCESS read-only
    STATUS     current
    DESCRIPTION
	    "Messages with Originating IP on IP Allow List
	    Providers/sec is the number of messages with an
	    originating IP address on the IP Allow List
	    providers list per second."
    ::= { ex2ConnectionFilteringAgent 11 }

ex2cfaMsgOrigIPIPAllowListSec OBJECT-TYPE
    SYNTAX     Gauge32
    MAX-ACCESS read-only
    STATUS     current
    DESCRIPTION
	    "Messages with Originating IP on IP Allow
	    List/sec is the number of messages with an
	    originating IP address on the IP Allow list per
	    second."
    ::= { ex2ConnectionFilteringAgent 12 }

ex2cfaMsgOrigIPIPBlockList OBJECT-TYPE
    SYNTAX     Gauge32
    MAX-ACCESS read-only
    STATUS     current
    DESCRIPTION
	    "Messages with Originating IP on IP Block List
	    is the total number of messages with an
	    originating IP address on the IP Block list."
    ::= { ex2ConnectionFilteringAgent 13 }

ex2cfaMsgOrigIPIPBlockListPrv OBJECT-TYPE
    SYNTAX     Gauge32
    MAX-ACCESS read-only
    STATUS     current
    DESCRIPTION
	    "Messages with Originating IP on IP Block List
	    Providers is the total number of messages with
	    originating IP on the IP Block List providers."
    ::= { ex2ConnectionFilteringAgent 14 }

ex2cfaMsgOrigIPIPBlockListPrvSec OBJECT-TYPE
    SYNTAX     Gauge32
    MAX-ACCESS read-only
    STATUS     current
    DESCRIPTION
	    "Messages with Originating IP on IP Block List
	    Providers/sec is the number of messages with an
	    originating IP address on the IP Block List
	    providers list per second."
    ::= { ex2ConnectionFilteringAgent 15 }

ex2cfaMsgOrigIPIPBlockListSec OBJECT-TYPE
    SYNTAX     Gauge32
    MAX-ACCESS read-only
    STATUS     current
    DESCRIPTION
	    "Messages with Originating IP on IP Block List
	    Providers/sec is the number of messages with an
	    originating IP address on the IP Block List
	    providers list per second."
    ::= { ex2ConnectionFilteringAgent 16 }

ex2ContentFilterAgent OBJECT-IDENTITY
    STATUS     current
    DESCRIPTION
	    "Performance counters for the Content Filter
	    Agent"
    ::= { exchangeV2 11 }

ex2ctfaBypassRecptDueRecptSafSnd OBJECT-TYPE
    SYNTAX     Gauge32
    MAX-ACCESS read-only
    STATUS     current
    DESCRIPTION
	    "Bypassed recipients due to per-recipient Safe
	    Senders is the total number of recipients that
	    bypassed content filtering due to a
	    per-recipient safe sender."
    ::= { ex2ContentFilterAgent 1 }

ex2ctfaMessagesDeleted OBJECT-TYPE
    SYNTAX     Gauge32
    MAX-ACCESS read-only
    STATUS     current
    DESCRIPTION
	    "Messages Deleted is the total number of
	    messages that were deleted by Content Filter
	    Agent."
    ::= { ex2ContentFilterAgent 2 }

ex2ctfaMessagesQuarantined OBJECT-TYPE
    SYNTAX     Gauge32
    MAX-ACCESS read-only
    STATUS     current
    DESCRIPTION
	    "Messages Quarantined is the total number of
	    messages that were quarantined by Content
	    Filter Agent."
    ::= { ex2ContentFilterAgent 3 }

ex2ctfaMessagesRejected OBJECT-TYPE
    SYNTAX     Gauge32
    MAX-ACCESS read-only
    STATUS     current
    DESCRIPTION
	    "Messages Rejected is the total number of
	    messages that were rejected by Content Filter
	    Agent."
    ::= { ex2ContentFilterAgent 4 }

ex2ctfaMessagesScanned OBJECT-TYPE
    SYNTAX     Gauge32
    MAX-ACCESS read-only
    STATUS     current
    DESCRIPTION
	    "Messages Scanned is the total number of
	    messages scanned by Content Filter Agent."
    ::= { ex2ContentFilterAgent 5 }

ex2ctfaMessagesScannedPerSecond OBJECT-TYPE
    SYNTAX     Gauge32
    MAX-ACCESS read-only
    STATUS     current
    DESCRIPTION
	    "The number of messages scanned per second"
    ::= { ex2ContentFilterAgent 6 }

ex2ctfaMessageThatBypassScanning OBJECT-TYPE
    SYNTAX     Gauge32
    MAX-ACCESS read-only
    STATUS     current
    DESCRIPTION
	    "The total number of messages that bypass
	    scanning"
    ::= { ex2ContentFilterAgent 7 }

ex2ctfaMsgBypassScanOrgWideSafe OBJECT-TYPE
    SYNTAX     Gauge32
    MAX-ACCESS read-only
    STATUS     current
    DESCRIPTION
	    "The total number of messages that bypassed
	    scanning due to an organization-wide safe
	    sender"
    ::= { ex2ContentFilterAgent 8 }

ex2ctfaMsgIncOtlkEMailPMNotValid OBJECT-TYPE
    SYNTAX     Gauge32
    MAX-ACCESS read-only
    STATUS     current
    DESCRIPTION
	    "Messages that included an Outlook E-mail
	    Postmark property, but the postmark did not
	    validate successfully"
    ::= { ex2ContentFilterAgent 9 }

ex2ctfaMsgIncOtlkEMailPMValidScs OBJECT-TYPE
    SYNTAX     Gauge32
    MAX-ACCESS read-only
    STATUS     current
    DESCRIPTION
	    "Messages that include an Outlook E-mail
	    Postmark and the postmark was successfully
	    validated"
    ::= { ex2ContentFilterAgent 10 }

ex2ctfaMessagesWithSCL0 OBJECT-TYPE
    SYNTAX     Gauge32
    MAX-ACCESS read-only
    STATUS     current
    DESCRIPTION
	    "Messages with SCL 0 is the total number of
	    messages assigned an SCL rating of 0."
    ::= { ex2ContentFilterAgent 11 }

ex2ctfaMessagesWithSCL1 OBJECT-TYPE
    SYNTAX     Gauge32
    MAX-ACCESS read-only
    STATUS     current
    DESCRIPTION
	    "Messages with SCL 1 is the total number of
	    messages assigned an SCL rating of 1."
    ::= { ex2ContentFilterAgent 12 }

ex2ctfaMessagesWithSCL2 OBJECT-TYPE
    SYNTAX     Gauge32
    MAX-ACCESS read-only
    STATUS     current
    DESCRIPTION
	    "Messages with SCL 2 is the total number of
	    messages assigned an SCL rating of 2."
    ::= { ex2ContentFilterAgent 13 }

ex2ctfaMessagesWithSCL3 OBJECT-TYPE
    SYNTAX     Gauge32
    MAX-ACCESS read-only
    STATUS     current
    DESCRIPTION
	    "Messages with SCL 3 is the total number of
	    messages assigned an SCL rating of 3."
    ::= { ex2ContentFilterAgent 14 }

ex2ctfaMessagesWithSCL4 OBJECT-TYPE
    SYNTAX     Gauge32
    MAX-ACCESS read-only
    STATUS     current
    DESCRIPTION
	    "Messages with SCL 4 is the total number of
	    messages assigned an SCL rating of 4."
    ::= { ex2ContentFilterAgent 15 }

ex2ctfaMessagesWithSCL5 OBJECT-TYPE
    SYNTAX     Gauge32
    MAX-ACCESS read-only
    STATUS     current
    DESCRIPTION
	    "Messages with SCL 5 is the total number of
	    messages assigned an SCL rating of 5."
    ::= { ex2ContentFilterAgent 16 }

ex2ctfaMessagesWithSCL6 OBJECT-TYPE
    SYNTAX     Gauge32
    MAX-ACCESS read-only
    STATUS     current
    DESCRIPTION
	    "Messages with SCL 6 is the total number of
	    messages assigned an SCL rating of 6."
    ::= { ex2ContentFilterAgent 17 }

ex2ctfaMessagesWithSCL7 OBJECT-TYPE
    SYNTAX     Gauge32
    MAX-ACCESS read-only
    STATUS     current
    DESCRIPTION
	    "Messages with SCL 7 is the total number of
	    messages assigned an SCL rating of 7."
    ::= { ex2ContentFilterAgent 18 }

ex2ctfaMessagesWithSCL8 OBJECT-TYPE
    SYNTAX     Gauge32
    MAX-ACCESS read-only
    STATUS     current
    DESCRIPTION
	    "Messages with SCL 8 is the total number of
	    messages assigned an SCL rating of 8."
    ::= { ex2ContentFilterAgent 19 }

ex2ctfaMessagesWithSCL9 OBJECT-TYPE
    SYNTAX     Gauge32
    MAX-ACCESS read-only
    STATUS     current
    DESCRIPTION
	    "Messages with SCL 9 is the total number of
	    messages assigned an SCL rating of 9."
    ::= { ex2ContentFilterAgent 20 }

ex2ctfaMessagesWithSCLUnknown OBJECT-TYPE
    SYNTAX     Gauge32
    MAX-ACCESS read-only
    STATUS     current
    DESCRIPTION
	    "Messages with SCL Unknown is the total number
	    of messages that could not be scanned by the
	    filter."
    ::= { ex2ContentFilterAgent 21 }

ex2ctfaMessageWithPreexistingSCL OBJECT-TYPE
    SYNTAX     Gauge32
    MAX-ACCESS read-only
    STATUS     current
    DESCRIPTION
	    "Total messages with a pre-existing SCL"
    ::= { ex2ContentFilterAgent 22 }

ex2DatabaseTable OBJECT-TYPE
    SYNTAX     SEQUENCE OF Ex2DatabaseEntry
    MAX-ACCESS not-accessible
    STATUS     current
    DESCRIPTION
	    "Database provides performance statistics for
	    each process using the ESE high performance
	    embedded database management system."
    ::= { exchangeV2 12 }

ex2DatabaseEntry OBJECT-TYPE
    SYNTAX     Ex2DatabaseEntry
    MAX-ACCESS not-accessible
    STATUS     current
    DESCRIPTION
	    "Performance information for one particular
	    instance of 'MSExchange Database' object."
    INDEX      { ex2dbInstance }
    ::= { ex2DatabaseTable 1 }

Ex2DatabaseEntry ::= SEQUENCE {
    ex2dbInstance InstanceName,
    ex2dbDatabaseCachePercentHit Gauge32,
    ex2dbDatabaseCacheSize Gauge32,
    ex2dbDatabaseCacheSizeMB Gauge32,
    ex2dbDatabasePageEvictionsPerSec Gauge32,
    ex2dbDatabasePgFaultStallPerSec Gauge32,
    ex2dbDatabasePageFaultsPerSec Gauge32,
    ex2dbIODatabaseReadsAvgLatency Gauge32,
    ex2dbIODatabaseReadsPerSec Gauge32,
    ex2dbIODatabaseWriteAvgLatency Gauge32,
    ex2dbIODatabaseWritesPerSec Gauge32,
    ex2dbIOLogReadsPerSec Gauge32,
    ex2dbIOLogWritesAverageLatency Gauge32,
    ex2dbIOLogWritesPerSec Gauge32,
    ex2dbLogBytesWritePerSec Gauge32,
    ex2dbLogRecordStallsPerSec Gauge32,
    ex2dbLogThreadsWaiting Gauge32,
    ex2dbLogWritesPerSec Gauge32,
    ex2dbPagesConverted Gauge32,
    ex2dbPagesConvertedPerSec Gauge32,
    ex2dbRecordsConverted Gauge32,
    ex2dbRecordsConvertedPerSec Gauge32,
    ex2dbSessionsPercentUsed Gauge32,
    ex2dbSessionsInUse Gauge32,
    ex2dbTableOpenCachePercentHit Gauge32,
    ex2dbTableOpenCacheHitsPerSec Gauge32,
    ex2dbTableOpenCacheMissesPerSec Gauge32,
    ex2dbTableOpensPerSec Gauge32,
    ex2dbVersionBucketsAllocated Gauge32
}

ex2dbInstance OBJECT-TYPE
    SYNTAX     InstanceName
    MAX-ACCESS read-only
    STATUS     current
    DESCRIPTION
	    "Instance name."
    ::= { ex2DatabaseEntry 1 }

ex2dbDatabaseCachePercentHit OBJECT-TYPE
    SYNTAX     Gauge32
    MAX-ACCESS read-only
    STATUS     current
    DESCRIPTION
	    "Database Cache % Hit is the percentage of
	    database file page requests that were fulfilled
	    by the database cache without causing a file
	    operation.	If this percentage is too low, the
	    database cache size may be too small."
    ::= { ex2DatabaseEntry 2 }

ex2dbDatabaseCacheSize OBJECT-TYPE
    SYNTAX     Gauge32
    MAX-ACCESS read-only
    STATUS     current
    DESCRIPTION
	    "Database Cache Size is the amount of system
	    memory used by the database cache manager to
	    hold commonly used information from the
	    database file(s) to prevent file operations. 
	    If the database cache size seems to be too
	    small for optimal performance and there is very
	    little available memory on the system (see
	    Memory/Available Bytes), adding more memory to
	    the system may increase performance.  If there
	    is a lot of available memory on the system and
	    the database cache size is not growing beyond a
	    certain point, the database cache size may be
	    capped at an artificially low limit. 
	    Increasing this limit may increase
	    performance."
    ::= { ex2DatabaseEntry 3 }

ex2dbDatabaseCacheSizeMB OBJECT-TYPE
    SYNTAX     Gauge32
    MAX-ACCESS read-only
    STATUS     current
    DESCRIPTION
	    "Database Cache Size (MB) is the amount of
	    system memory (in MegaBytes) used by the
	    database cache manager to hold commonly used
	    information from the database file(s) to
	    prevent file operations.  If the database cache
	    size seems to be too small for optimal
	    performance and there is very little available
	    memory on the system (see Memory/Available
	    Bytes), adding more memory to the system may
	    increase performance.  If there is a lot of
	    available memory on the system and the database
	    cache size is not growing beyond a certain
	    point, the database cache size may be capped at
	    an artificially low limit.	Increasing this
	    limit may increase performance."
    ::= { ex2DatabaseEntry 4 }

ex2dbDatabasePageEvictionsPerSec OBJECT-TYPE
    SYNTAX     Gauge32
    MAX-ACCESS read-only
    STATUS     current
    DESCRIPTION
	    "Database Page Evictions/sec is the rate that
	    database file page requests that require the
	    database cache manager to allocate a new page
	    from the database cache force another database
	    page out of the cache.  The eviction count is
	    charged when the page is allocated and not when
	    the previous owner of that page was actually
	    evicted from the cache.  If this rate is too
	    high, the database cache size may be too
	    small."
    ::= { ex2DatabaseEntry 5 }

ex2dbDatabasePgFaultStallPerSec OBJECT-TYPE
    SYNTAX     Gauge32
    MAX-ACCESS read-only
    STATUS     current
    DESCRIPTION
	    "Database Page Fault Stalls/sec is the rate of
	    page faults that cannot be serviced because
	    there are no pages available for allocation
	    from the database cache.  If this counter is
	    non-zero most of the time, the clean threshold
	    may be too low."
    ::= { ex2DatabaseEntry 6 }

ex2dbDatabasePageFaultsPerSec OBJECT-TYPE
    SYNTAX     Gauge32
    MAX-ACCESS read-only
    STATUS     current
    DESCRIPTION
	    "Database Page Faults/sec is the rate that
	    database file page requests require the
	    database cache manager to allocate a new page
	    from the database cache."
    ::= { ex2DatabaseEntry 7 }

ex2dbIODatabaseReadsAvgLatency OBJECT-TYPE
    SYNTAX     Gauge32
    MAX-ACCESS read-only
    STATUS     current
    DESCRIPTION
	    "I/O Database Reads Average Latency is the
	    average length of time,  in milliseconds, per
	    database read operation."
    ::= { ex2DatabaseEntry 8 }

ex2dbIODatabaseReadsPerSec OBJECT-TYPE
    SYNTAX     Gauge32
    MAX-ACCESS read-only
    STATUS     current
    DESCRIPTION
	    "I/O Database Reads/sec is the rate of database
	    read operations completed."
    ::= { ex2DatabaseEntry 9 }

ex2dbIODatabaseWriteAvgLatency OBJECT-TYPE
    SYNTAX     Gauge32
    MAX-ACCESS read-only
    STATUS     current
    DESCRIPTION
	    "I/O Database Writes Average Latency is the
	    average length of time,  in milliseconds, per
	    database write operation."
    ::= { ex2DatabaseEntry 10 }

ex2dbIODatabaseWritesPerSec OBJECT-TYPE
    SYNTAX     Gauge32
    MAX-ACCESS read-only
    STATUS     current
    DESCRIPTION
	    "I/O Database Writes/sec is the rate of
	    database write operations completed."
    ::= { ex2DatabaseEntry 11 }

ex2dbIOLogReadsPerSec OBJECT-TYPE
    SYNTAX     Gauge32
    MAX-ACCESS read-only
    STATUS     current
    DESCRIPTION
	    "I/O Log Reads/sec is the rate of logfile read
	    operations completed."
    ::= { ex2DatabaseEntry 12 }

ex2dbIOLogWritesAverageLatency OBJECT-TYPE
    SYNTAX     Gauge32
    MAX-ACCESS read-only
    STATUS     current
    DESCRIPTION
	    "I/O Log Writes Average Latency is the average
	    length of time, in milliseconds, per logfile
	    write operation."
    ::= { ex2DatabaseEntry 13 }

ex2dbIOLogWritesPerSec OBJECT-TYPE
    SYNTAX     Gauge32
    MAX-ACCESS read-only
    STATUS     current
    DESCRIPTION
	    "I/O Log Writes/sec is the rate of logfile
	    write operations completed."
    ::= { ex2DatabaseEntry 14 }

ex2dbLogBytesWritePerSec OBJECT-TYPE
    SYNTAX     Gauge32
    MAX-ACCESS read-only
    STATUS     current
    DESCRIPTION
	    "Log Bytes Write per second is the rate bytes
	    are written to the log."
    ::= { ex2DatabaseEntry 15 }

ex2dbLogRecordStallsPerSec OBJECT-TYPE
    SYNTAX     Gauge32
    MAX-ACCESS read-only
    STATUS     current
    DESCRIPTION
	    "Log Record Stalls/sec is the number of log
	    records that cannot be added to the log buffers
	    per second because they are full.  If this
	    counter is non-zero most of the time, the log
	    buffer size may be a bottleneck."
    ::= { ex2DatabaseEntry 16 }

ex2dbLogThreadsWaiting OBJECT-TYPE
    SYNTAX     Gauge32
    MAX-ACCESS read-only
    STATUS     current
    DESCRIPTION
	    "Log Threads Waiting is the number of threads
	    waiting for their data to be written to the log
	    in order to complete an update of the database.
	     If this number is too high, the log may be a
	    bottleneck."
    ::= { ex2DatabaseEntry 17 }

ex2dbLogWritesPerSec OBJECT-TYPE
    SYNTAX     Gauge32
    MAX-ACCESS read-only
    STATUS     current
    DESCRIPTION
	    "Log Writes/sec is the number of times the log
	    buffers are written to the log file(s) per
	    second.  If this number approaches the maximum
	    write rate for the media holding the log
	    file(s), the log may be a bottleneck."
    ::= { ex2DatabaseEntry 18 }

ex2dbPagesConverted OBJECT-TYPE
    SYNTAX     Gauge32
    MAX-ACCESS read-only
    STATUS     current
    DESCRIPTION
	    "Pages Converted is the count of database pages
	    that have been converted from an older format"
    ::= { ex2DatabaseEntry 19 }

ex2dbPagesConvertedPerSec OBJECT-TYPE
    SYNTAX     Gauge32
    MAX-ACCESS read-only
    STATUS     current
    DESCRIPTION
	    "Pages Converted/sec is the count of times per
	    second a database page is converted from an
	    older database format"
    ::= { ex2DatabaseEntry 20 }

ex2dbRecordsConverted OBJECT-TYPE
    SYNTAX     Gauge32
    MAX-ACCESS read-only
    STATUS     current
    DESCRIPTION
	    "Records Converted is the count of database
	    records that have been converted from an older
	    format"
    ::= { ex2DatabaseEntry 21 }

ex2dbRecordsConvertedPerSec OBJECT-TYPE
    SYNTAX     Gauge32
    MAX-ACCESS read-only
    STATUS     current
    DESCRIPTION
	    "Records Converted/sec is the count of times
	    per second a database record is converted from
	    an older database format"
    ::= { ex2DatabaseEntry 22 }

ex2dbSessionsPercentUsed OBJECT-TYPE
    SYNTAX     Gauge32
    MAX-ACCESS read-only
    STATUS     current
    DESCRIPTION
	    "Sessions % Used is the percentage of database
	    sessions currently open for use by client
	    threads.  [Dev Only]"
    ::= { ex2DatabaseEntry 23 }

ex2dbSessionsInUse OBJECT-TYPE
    SYNTAX     Gauge32
    MAX-ACCESS read-only
    STATUS     current
    DESCRIPTION
	    "Sessions In Use is the number of database
	    sessions currently open for use by client
	    threads.  [Dev Only]"
    ::= { ex2DatabaseEntry 24 }

ex2dbTableOpenCachePercentHit OBJECT-TYPE
    SYNTAX     Gauge32
    MAX-ACCESS read-only
    STATUS     current
    DESCRIPTION
	    "Table Open Cache % Hit is the percentage of
	    database tables opened using cached schema
	    information.  If this percentage is too low,
	    the table cache size may be too small."
    ::= { ex2DatabaseEntry 25 }

ex2dbTableOpenCacheHitsPerSec OBJECT-TYPE
    SYNTAX     Gauge32
    MAX-ACCESS read-only
    STATUS     current
    DESCRIPTION
	    "Table Open Cache Hits/sec is the number of
	    database tables opened using cached schema
	    information per second.  If this rate is too
	    low, the table cache size may be too small."
    ::= { ex2DatabaseEntry 26 }

ex2dbTableOpenCacheMissesPerSec OBJECT-TYPE
    SYNTAX     Gauge32
    MAX-ACCESS read-only
    STATUS     current
    DESCRIPTION
	    "Table Open Cache Misses/sec is the number of
	    database tables opened without using cached
	    schema information per second.  If this rate is
	    too high, the table cache size may be too
	    small."
    ::= { ex2DatabaseEntry 27 }

ex2dbTableOpensPerSec OBJECT-TYPE
    SYNTAX     Gauge32
    MAX-ACCESS read-only
    STATUS     current
    DESCRIPTION
	    "Table Opens/sec is the number of database
	    tables opened per second."
    ::= { ex2DatabaseEntry 28 }

ex2dbVersionBucketsAllocated OBJECT-TYPE
    SYNTAX     Gauge32
    MAX-ACCESS read-only
    STATUS     current
    DESCRIPTION
	    "Total number of version buckets allocated"
    ::= { ex2DatabaseEntry 29 }

ex2DatabaseInstancesTable OBJECT-TYPE
    SYNTAX     SEQUENCE OF Ex2DatabaseInstancesEntry
    MAX-ACCESS not-accessible
    STATUS     current
    DESCRIPTION
	    "Instances in this process"
    ::= { exchangeV2 13 }

ex2DatabaseInstancesEntry OBJECT-TYPE
    SYNTAX     Ex2DatabaseInstancesEntry
    MAX-ACCESS not-accessible
    STATUS     current
    DESCRIPTION
	    "Performance information for one particular
	    instance of 'MSExchange Database ==> Instances'
	    object."
    INDEX      { ex2dbiInstance }
    ::= { ex2DatabaseInstancesTable 1 }

Ex2DatabaseInstancesEntry ::= SEQUENCE {
    ex2dbiInstance InstanceName,
    ex2dbiIODatabaseRdAvgLatency Gauge32,
    ex2dbiIODatabaseReadsPerSec Gauge32,
    ex2dbiIODatabsWriteAvgLatency Gauge32,
    ex2dbiIODatabaseWritesPerSec Gauge32,
    ex2dbiIOLogReadsPerSec Gauge32,
    ex2dbiIOLogWritesAvgLatency Gauge32,
    ex2dbiIOLogWritesPerSec Gauge32,
    ex2dbiLogBytesWritePerSec Gauge32,
    ex2dbiLogFileCurrentGeneration Gauge32,
    ex2dbiLogFilesGenerated Gauge32,
    ex2dbiLogFilesGeneratedPremature Gauge32,
    ex2dbiLogGenerationCheckptDepth Gauge32,
    ex2dbiLogGeneratnCheckptDepthMax Gauge32,
    ex2dbiLogGeneratLossResilient Gauge32,
    ex2dbiLogRecordStallsPerSec Gauge32,
    ex2dbiLogThreadsWaiting Gauge32,
    ex2dbiLogWritesPerSec Gauge32,
    ex2dbiPagesConverted Gauge32,
    ex2dbiPagesConvertedPerSec Gauge32,
    ex2dbiRecordsConverted Gauge32,
    ex2dbiRecordsConvertedPerSec Gauge32,
    ex2dbiSessionsPercentUsed Gauge32,
    ex2dbiSessionsInUse Gauge32,
    ex2dbiStreamBackupPageReadPerSec Gauge32,
    ex2dbiTableOpenCachePercentHit Gauge32,
    ex2dbiTableOpenCacheHitsPerSec Gauge32,
    ex2dbiTableOpenCacheMissesPerSec Gauge32,
    ex2dbiTableOpensPerSec Gauge32,
    ex2dbiVersionBucketsAllocated Gauge32
}

ex2dbiInstance OBJECT-TYPE
    SYNTAX     InstanceName
    MAX-ACCESS read-only
    STATUS     current
    DESCRIPTION
	    "Instance name."
    ::= { ex2DatabaseInstancesEntry 1 }

ex2dbiIODatabaseRdAvgLatency OBJECT-TYPE
    SYNTAX     Gauge32
    MAX-ACCESS read-only
    STATUS     current
    DESCRIPTION
	    "I/O Database Reads Average Latency is the
	    average length of time,  in milliseconds, per
	    database read operation."
    ::= { ex2DatabaseInstancesEntry 2 }

ex2dbiIODatabaseReadsPerSec OBJECT-TYPE
    SYNTAX     Gauge32
    MAX-ACCESS read-only
    STATUS     current
    DESCRIPTION
	    "I/O Database Reads/sec is the rate of database
	    read operations completed."
    ::= { ex2DatabaseInstancesEntry 3 }

ex2dbiIODatabsWriteAvgLatency OBJECT-TYPE
    SYNTAX     Gauge32
    MAX-ACCESS read-only
    STATUS     current
    DESCRIPTION
	    "I/O Database Writes Average Latency is the
	    average length of time,  in milliseconds, per
	    database write operation."
    ::= { ex2DatabaseInstancesEntry 4 }

ex2dbiIODatabaseWritesPerSec OBJECT-TYPE
    SYNTAX     Gauge32
    MAX-ACCESS read-only
    STATUS     current
    DESCRIPTION
	    "I/O Database Writes/sec is the rate of
	    database write operations completed."
    ::= { ex2DatabaseInstancesEntry 5 }

ex2dbiIOLogReadsPerSec OBJECT-TYPE
    SYNTAX     Gauge32
    MAX-ACCESS read-only
    STATUS     current
    DESCRIPTION
	    "I/O Log Reads/sec is the rate of logfile read
	    operations completed."
    ::= { ex2DatabaseInstancesEntry 6 }

ex2dbiIOLogWritesAvgLatency OBJECT-TYPE
    SYNTAX     Gauge32
    MAX-ACCESS read-only
    STATUS     current
    DESCRIPTION
	    "I/O Log Writes Average Latency is the average
	    length of time, in milliseconds, per logfile
	    write operation."
    ::= { ex2DatabaseInstancesEntry 7 }

ex2dbiIOLogWritesPerSec OBJECT-TYPE
    SYNTAX     Gauge32
    MAX-ACCESS read-only
    STATUS     current
    DESCRIPTION
	    "I/O Log Writes/sec is the rate of logfile
	    write operations completed."
    ::= { ex2DatabaseInstancesEntry 8 }

ex2dbiLogBytesWritePerSec OBJECT-TYPE
    SYNTAX     Gauge32
    MAX-ACCESS read-only
    STATUS     current
    DESCRIPTION
	    "Log Bytes Write per second is the rate bytes
	    are written to the log."
    ::= { ex2DatabaseInstancesEntry 9 }

ex2dbiLogFileCurrentGeneration OBJECT-TYPE
    SYNTAX     Gauge32
    MAX-ACCESS read-only
    STATUS     current
    DESCRIPTION
	    "Log File Current Generation gives the
	    generation number of the current log file of an
	    instance."
    ::= { ex2DatabaseInstancesEntry 10 }

ex2dbiLogFilesGenerated OBJECT-TYPE
    SYNTAX     Gauge32
    MAX-ACCESS read-only
    STATUS     current
    DESCRIPTION
	    "Log Files Generated represents the total
	    number of log files generated by an instance
	    since that instance was last initialized."
    ::= { ex2DatabaseInstancesEntry 11 }

ex2dbiLogFilesGeneratedPremature OBJECT-TYPE
    SYNTAX     Gauge32
    MAX-ACCESS read-only
    STATUS     current
    DESCRIPTION
	    "Log Files Generated Prematurely represents the
	    total number of log files generated by an
	    instance since that instance was last
	    initialized and that have not been entirely
	    filled with useful data.  Under certain
	    conditions the database engine will choose to
	    switch to a new log file before it has been
	    completely filled with useful data."
    ::= { ex2DatabaseInstancesEntry 12 }

ex2dbiLogGenerationCheckptDepth OBJECT-TYPE
    SYNTAX     Gauge32
    MAX-ACCESS read-only
    STATUS     current
    DESCRIPTION
	    "Log Generation Checkpoint Depth represents the
	    amount of work, in count of log files, that
	    will need to be redone or undone to the
	    database file(s) if the process crashes."
    ::= { ex2DatabaseInstancesEntry 13 }

ex2dbiLogGeneratnCheckptDepthMax OBJECT-TYPE
    SYNTAX     Gauge32
    MAX-ACCESS read-only
    STATUS     current
    DESCRIPTION
	    "Log Generation Checkpoint Depth Max represents
	    the maximum allowable amount of work, in count
	    of log files, that may be redone or undone to
	    the database file(s) if the process crashes."
    ::= { ex2DatabaseInstancesEntry 14 }

ex2dbiLogGeneratLossResilient OBJECT-TYPE
    SYNTAX     Gauge32
    MAX-ACCESS read-only
    STATUS     current
    DESCRIPTION
	    "Log Generation Loss Resiliency Depth
	    represents the amount of work, in count of log
	    files, that may be lost while still allowing
	    the database file(s) to recover (with data
	    loss) if the process crashes."
    ::= { ex2DatabaseInstancesEntry 15 }

ex2dbiLogRecordStallsPerSec OBJECT-TYPE
    SYNTAX     Gauge32
    MAX-ACCESS read-only
    STATUS     current
    DESCRIPTION
	    "Log Record Stalls/sec is the number of log
	    records that cannot be added to the log buffers
	    per second because they are full.  If this
	    counter is non-zero most of the time, the log
	    buffer size may be a bottleneck."
    ::= { ex2DatabaseInstancesEntry 16 }

ex2dbiLogThreadsWaiting OBJECT-TYPE
    SYNTAX     Gauge32
    MAX-ACCESS read-only
    STATUS     current
    DESCRIPTION
	    "Log Threads Waiting is the number of threads
	    waiting for their data to be written to the log
	    in order to complete an update of the database.
	     If this number is too high, the log may be a
	    bottleneck."
    ::= { ex2DatabaseInstancesEntry 17 }

ex2dbiLogWritesPerSec OBJECT-TYPE
    SYNTAX     Gauge32
    MAX-ACCESS read-only
    STATUS     current
    DESCRIPTION
	    "Log Writes/sec is the number of times the log
	    buffers are written to the log file(s) per
	    second.  If this number approaches the maximum
	    write rate for the media holding the log
	    file(s), the log may be a bottleneck."
    ::= { ex2DatabaseInstancesEntry 18 }

ex2dbiPagesConverted OBJECT-TYPE
    SYNTAX     Gauge32
    MAX-ACCESS read-only
    STATUS     current
    DESCRIPTION
	    "Pages Converted is the count of database pages
	    that have been converted from an older format"
    ::= { ex2DatabaseInstancesEntry 19 }

ex2dbiPagesConvertedPerSec OBJECT-TYPE
    SYNTAX     Gauge32
    MAX-ACCESS read-only
    STATUS     current
    DESCRIPTION
	    "Pages Converted/sec is the count of times per
	    second a database page is converted from an
	    older database format"
    ::= { ex2DatabaseInstancesEntry 20 }

ex2dbiRecordsConverted OBJECT-TYPE
    SYNTAX     Gauge32
    MAX-ACCESS read-only
    STATUS     current
    DESCRIPTION
	    "Records Converted is the count of database
	    records that have been converted from an older
	    format"
    ::= { ex2DatabaseInstancesEntry 21 }

ex2dbiRecordsConvertedPerSec OBJECT-TYPE
    SYNTAX     Gauge32
    MAX-ACCESS read-only
    STATUS     current
    DESCRIPTION
	    "Records Converted/sec is the count of times
	    per second a database record is converted from
	    an older database format"
    ::= { ex2DatabaseInstancesEntry 22 }

ex2dbiSessionsPercentUsed OBJECT-TYPE
    SYNTAX     Gauge32
    MAX-ACCESS read-only
    STATUS     current
    DESCRIPTION
	    "Sessions % Used is the percentage of database
	    sessions currently open for use by client
	    threads.  [Dev Only]"
    ::= { ex2DatabaseInstancesEntry 23 }

ex2dbiSessionsInUse OBJECT-TYPE
    SYNTAX     Gauge32
    MAX-ACCESS read-only
    STATUS     current
    DESCRIPTION
	    "Sessions In Use is the number of database
	    sessions currently open for use by client
	    threads.  [Dev Only]"
    ::= { ex2DatabaseInstancesEntry 24 }

ex2dbiStreamBackupPageReadPerSec OBJECT-TYPE
    SYNTAX     Gauge32
    MAX-ACCESS read-only
    STATUS     current
    DESCRIPTION
	    "Streaming Backup Pages Read/sec is the rate of
	    database read operationsperformed for the
	    purpose of streaming backups."
    ::= { ex2DatabaseInstancesEntry 25 }

ex2dbiTableOpenCachePercentHit OBJECT-TYPE
    SYNTAX     Gauge32
    MAX-ACCESS read-only
    STATUS     current
    DESCRIPTION
	    "Table Open Cache % Hit is the percentage of
	    database tables opened using cached schema
	    information.  If this percentage is too low,
	    the table cache size may be too small."
    ::= { ex2DatabaseInstancesEntry 26 }

ex2dbiTableOpenCacheHitsPerSec OBJECT-TYPE
    SYNTAX     Gauge32
    MAX-ACCESS read-only
    STATUS     current
    DESCRIPTION
	    "Table Open Cache Hits/sec is the number of
	    database tables opened using cached schema
	    information per second.  If this rate is too
	    low, the table cache size may be too small."
    ::= { ex2DatabaseInstancesEntry 27 }

ex2dbiTableOpenCacheMissesPerSec OBJECT-TYPE
    SYNTAX     Gauge32
    MAX-ACCESS read-only
    STATUS     current
    DESCRIPTION
	    "Table Open Cache Misses/sec is the number of
	    database tables opened without using cached
	    schema information per second.  If this rate is
	    too high, the table cache size may be too
	    small."
    ::= { ex2DatabaseInstancesEntry 28 }

ex2dbiTableOpensPerSec OBJECT-TYPE
    SYNTAX     Gauge32
    MAX-ACCESS read-only
    STATUS     current
    DESCRIPTION
	    "Table Opens/sec is the number of database
	    tables opened per second."
    ::= { ex2DatabaseInstancesEntry 29 }

ex2dbiVersionBucketsAllocated OBJECT-TYPE
    SYNTAX     Gauge32
    MAX-ACCESS read-only
    STATUS     current
    DESCRIPTION
	    "Total number of version buckets allocated"
    ::= { ex2DatabaseInstancesEntry 30 }

ex2DatabaseTableClassesTable OBJECT-TYPE
    SYNTAX     SEQUENCE OF Ex2DatabaseTableClassesEntry
    MAX-ACCESS not-accessible
    STATUS     current
    DESCRIPTION
	    "Statistics for the ESE high performance
	    embedded database management system by Table
	    Class"
    ::= { exchangeV2 14 }

ex2DatabaseTableClassesEntry OBJECT-TYPE
    SYNTAX     Ex2DatabaseTableClassesEntry
    MAX-ACCESS not-accessible
    STATUS     current
    DESCRIPTION
	    "Performance information for one particular
	    instance of 'MSExchange Database ==>
	    TableClasses' object."
    INDEX      { ex2dbtcInstance }
    ::= { ex2DatabaseTableClassesTable 1 }

Ex2DatabaseTableClassesEntry ::= SEQUENCE {
    ex2dbtcInstance InstanceName,
    ex2dbtcDatabaseCacheSizeMB Gauge32
}

ex2dbtcInstance OBJECT-TYPE
    SYNTAX     InstanceName
    MAX-ACCESS read-only
    STATUS     current
    DESCRIPTION
	    "Instance name."
    ::= { ex2DatabaseTableClassesEntry 1 }

ex2dbtcDatabaseCacheSizeMB OBJECT-TYPE
    SYNTAX     Gauge32
    MAX-ACCESS read-only
    STATUS     current
    DESCRIPTION
	    "Database Cache Size (MB) is the amount of
	    system memory (in MegaBytes) used by the
	    database cache manager to hold commonly used
	    information from the database file(s) to
	    prevent file operations.  If the database cache
	    size seems to be too small for optimal
	    performance and there is very little available
	    memory on the system (see Memory/Available
	    Bytes), adding more memory to the system may
	    increase performance.  If there is a lot of
	    available memory on the system and the database
	    cache size is not growing beyond a certain
	    point, the database cache size may be capped at
	    an artificially low limit.	Increasing this
	    limit may increase performance."
    ::= { ex2DatabaseTableClassesEntry 2 }

ex2ExtensibilityAgentsTable OBJECT-TYPE
    SYNTAX     SEQUENCE OF Ex2ExtensibilityAgentsEntry
    MAX-ACCESS not-accessible
    STATUS     current
    DESCRIPTION
	    "Exchange MEx runtime performance counters"
    ::= { exchangeV2 15 }

ex2ExtensibilityAgentsEntry OBJECT-TYPE
    SYNTAX     Ex2ExtensibilityAgentsEntry
    MAX-ACCESS not-accessible
    STATUS     current
    DESCRIPTION
	    "Performance information for one particular
	    instance of 'MSExchange Extensibility Agents'
	    object."
    INDEX      { ex2eaInstance }
    ::= { ex2ExtensibilityAgentsTable 1 }

Ex2ExtensibilityAgentsEntry ::= SEQUENCE {
    ex2eaInstance InstanceName,
    ex2eaAverageAgentProcessTimeSec Gauge32,
    ex2eaTotalAgentInvocations Gauge32
}

ex2eaInstance OBJECT-TYPE
    SYNTAX     InstanceName
    MAX-ACCESS read-only
    STATUS     current
    DESCRIPTION
	    "Instance name."
    ::= { ex2ExtensibilityAgentsEntry 1 }

ex2eaAverageAgentProcessTimeSec OBJECT-TYPE
    SYNTAX     Gauge32
    MAX-ACCESS read-only
    STATUS     current
    DESCRIPTION
	    "Average agent processing time in seconds per
	    event."
    ::= { ex2ExtensibilityAgentsEntry 2 }

ex2eaTotalAgentInvocations OBJECT-TYPE
    SYNTAX     Gauge32
    MAX-ACCESS read-only
    STATUS     current
    DESCRIPTION
	    "Total number of agent invocations since the
	    last restart."
    ::= { ex2ExtensibilityAgentsEntry 3 }

ex2JournalingAgent OBJECT-IDENTITY
    STATUS     current
    DESCRIPTION
	    "Counters for the Exchange message journaling
	    feature."
    ::= { exchangeV2 16 }

ex2jaJournalReportsCreatedPerSec OBJECT-TYPE
    SYNTAX     Gauge32
    MAX-ACCESS read-only
    STATUS     current
    DESCRIPTION
	    "Journal Reports Generated Rate is the number
	    of journal reports created per second."
    ::= { ex2JournalingAgent 1 }

ex2jaJournalReportsCreatedTotal OBJECT-TYPE
    SYNTAX     Gauge32
    MAX-ACCESS read-only
    STATUS     current
    DESCRIPTION
	    "Journal Reports Generated is the number of
	    journal  reports that were generated."
    ::= { ex2JournalingAgent 2 }

ex2jaJournalingProcessingTime OBJECT-TYPE
    SYNTAX     Gauge32
    MAX-ACCESS read-only
    STATUS     current
    DESCRIPTION
	    "Processing Time is the total time spent
	    executing journaling rules and creating reports
	    in milliseconds."
    ::= { ex2JournalingAgent 3 }

ex2jaJournalProcesTimePerMessage OBJECT-TYPE
    SYNTAX     Gauge32
    MAX-ACCESS read-only
    STATUS     current
    DESCRIPTION
	    "Average journaling processing time/message
	    base is the average time in milliseconds spent
	    in journaling per message. This includes the
	    time spent executing journaling rules and
	    creating journal reports."
    ::= { ex2JournalingAgent 4 }

ex2jaMessagesProcessByJournaling OBJECT-TYPE
    SYNTAX     Gauge32
    MAX-ACCESS read-only
    STATUS     current
    DESCRIPTION
	    "Messages Processed is the number of messages
	    processed by journaling including those that
	    were not journaled."
    ::= { ex2JournalingAgent 5 }

ex2jaUsersJournaled OBJECT-TYPE
    SYNTAX     Gauge32
    MAX-ACCESS read-only
    STATUS     current
    DESCRIPTION
	    "Users Journaled is the number of message
	    senders and recipients for which journal
	    reports were generated."
    ::= { ex2JournalingAgent 6 }

ex2jaUsersJournaledPerSec OBJECT-TYPE
    SYNTAX     Gauge32
    MAX-ACCESS read-only
    STATUS     current
    DESCRIPTION
	    "Users Journaled Rate is the number of message
	    senders and recipients for which journal
	    reports were generated per second."
    ::= { ex2JournalingAgent 7 }

ex2ManagedFolderAssistant OBJECT-IDENTITY
    STATUS     current
    DESCRIPTION
	    "Performance counters for the Microsoft
	    Exchange Managed Folder Assistant"
    ::= { exchangeV2 17 }

ex2mfaItemsDeletedButRecoverable OBJECT-TYPE
    SYNTAX     Gauge32
    MAX-ACCESS read-only
    STATUS     current
    DESCRIPTION
	    "Items Deleted but Recoverable is the total
	    number of items deleted but recoverable through
	    the dumpster by the Managed Folder Assistant
	    since the start of the most recent schedule
	    interval. The number includes items in both the
	    mailboxes that were scheduled for processing
	    during the schedule interval and any mailboxes
	    that the administrator specified for
	    processing. This counter is reset to zero at
	    the start of each schedule interval."
    ::= { ex2ManagedFolderAssistant 1 }

ex2mfaItemsJournaled OBJECT-TYPE
    SYNTAX     Gauge32
    MAX-ACCESS read-only
    STATUS     current
    DESCRIPTION
	    "Items Journaled is the total number of items
	    journaled by the Managed Folder Assistant since
	    the start of the most recent schedule interval.
	    The number includes items in both the mailboxes
	    that were scheduled for processing during the
	    schedule interval and any mailboxes that the
	    administrator specified for processing. This
	    counter is reset to zero at the start of each
	    schedule interval."
    ::= { ex2ManagedFolderAssistant 2 }

ex2mfaItemsMarkPastRetentionDate OBJECT-TYPE
    SYNTAX     Gauge32
    MAX-ACCESS read-only
    STATUS     current
    DESCRIPTION
	    "Items Marked as Past Retention Date is the
	    total number of items marked as past their
	    retention date by the Managed Folder Assistant
	    since the start of the most recent schedule
	    interval. The number includes items in both the
	    mailboxes that were scheduled for processing
	    during the schedule interval and any mailboxes
	    that the administrator specified for
	    processing. This counter is reset to zero at
	    the start of each schedule interval."
    ::= { ex2ManagedFolderAssistant 3 }

ex2mfaItemsMoved OBJECT-TYPE
    SYNTAX     Gauge32
    MAX-ACCESS read-only
    STATUS     current
    DESCRIPTION
	    "Items Moved is the total number of items moved
	    by the Managed Folder Assistant since the start
	    of the most recent schedule interval. The
	    number includes items in both the mailboxes
	    that were scheduled for processing during the
	    schedule interval and any mailboxes that the
	    administrator specified for processing. This
	    counter is reset to zero at the start of each
	    schedule interval."
    ::= { ex2ManagedFolderAssistant 4 }

ex2mfaItemsPermanentlyDeleted OBJECT-TYPE
    SYNTAX     Gauge32
    MAX-ACCESS read-only
    STATUS     current
    DESCRIPTION
	    "Items Permanently Deleted is the total number
	    of items permanently deleted by the Managed
	    Folder Assistant since the beginning of the
	    most recent schedule interval. The number
	    includes items in both the mailboxes that were
	    scheduled for processing during the schedule
	    interval and any mailboxes that the
	    administrator specified for processing. This
	    counter is reset to zero at the beginning of
	    each schedule interval."
    ::= { ex2ManagedFolderAssistant 5 }

ex2mfaItemSubjectRetentionPolicy OBJECT-TYPE
    SYNTAX     Gauge32
    MAX-ACCESS read-only
    STATUS     current
    DESCRIPTION
	    "Items Subject to Retention Policy is the total
	    number of items subject to retention policy by
	    the Managed Folder Assistant since the start of
	    the most recent schedule interval. The number
	    includes items in both the mailboxes that were
	    scheduled for processing during the schedule
	    interval and any mailboxes that the
	    administrator specified for processing. This
	    counter is reset to zero at the start of each
	    schedule interval."
    ::= { ex2ManagedFolderAssistant 6 }

ex2OWA OBJECT-IDENTITY
    STATUS     current
    DESCRIPTION
	    "The MSExchange OWA performance object includes
	    counters that monitor Outlook Web Access."
    ::= { exchangeV2 18 }

ex2OWAASQueries OBJECT-TYPE
    SYNTAX     Gauge32
    MAX-ACCESS read-only
    STATUS     current
    DESCRIPTION
	    "AS Queries is the total number of Availability
	    Service queries since the process was started."
    ::= { ex2OWA 1 }

ex2OWAASQueriesFailurePercent OBJECT-TYPE
    SYNTAX     Gauge32
    MAX-ACCESS read-only
    STATUS     current
    DESCRIPTION
	    "AS Queries Failure % is the percentage of the
	    last 100 Availability Service lookups that have
	    failed."
    ::= { ex2OWA 2 }

ex2OWAActiveConversions OBJECT-TYPE
    SYNTAX     Gauge32
    MAX-ACCESS read-only
    STATUS     current
    DESCRIPTION
	    "Active Conversions is the number of
	    conversions that are currently being processed
	    by the WebReady Document Viewing service."
    ::= { ex2OWA 3 }

ex2OWAAttachmentUploadedOWAStart OBJECT-TYPE
    SYNTAX     Gauge32
    MAX-ACCESS read-only
    STATUS     current
    DESCRIPTION
	    "Attachments Uploaded is the total number of
	    attachments that have been uploaded since the
	    process was restarted."
    ::= { ex2OWA 4 }

ex2OWAAverageCheckSpellingTime OBJECT-TYPE
    SYNTAX     Gauge32
    MAX-ACCESS read-only
    STATUS     current
    DESCRIPTION
	    "Average Check Spelling Time is the average
	    time that elapsed while waiting for a check
	    spelling operation to complete."
    ::= { ex2OWA 5 }

ex2OWAAverageConversionQueueTime OBJECT-TYPE
    SYNTAX     Gauge32
    MAX-ACCESS read-only
    STATUS     current
    DESCRIPTION
	    "Average Conversion Queuing Time is the average
	    length of time, in milliseconds, that documents
	    waited for the WebReady Document Viewing
	    service to process the attachment conversion
	    request since the process was restarted."
    ::= { ex2OWA 6 }

ex2OWAAverageConversionTime OBJECT-TYPE
    SYNTAX     Gauge32
    MAX-ACCESS read-only
    STATUS     current
    DESCRIPTION
	    "Average Conversion Time is the average length
	    of time, in milliseconds, it has taken to
	    convert a document since the process was
	    restarted."
    ::= { ex2OWA 7 }

ex2OWAAverageResponseTime OBJECT-TYPE
    SYNTAX     Gauge32
    MAX-ACCESS read-only
    STATUS     current
    DESCRIPTION
	    "Average Response Time is the average time (in
	    milliseconds) that elapsed between the
	    beginning and end of an OEH or ASPX request."
    ::= { ex2OWA 8 }

ex2OWAAverageSearchTime OBJECT-TYPE
    SYNTAX     Gauge32
    MAX-ACCESS read-only
    STATUS     current
    DESCRIPTION
	    "Average Search Time is the average time that
	    elapsed while waiting for a search to
	    complete."
    ::= { ex2OWA 9 }

ex2OWACalendarViewRefreshed OBJECT-TYPE
    SYNTAX     Gauge32
    MAX-ACCESS read-only
    STATUS     current
    DESCRIPTION
	    "Calendar View Refreshes is the total number of
	    times calendar views have been refreshed since
	    the process was restarted."
    ::= { ex2OWA 10 }

ex2OWACalendarViewsLoaded OBJECT-TYPE
    SYNTAX     Gauge32
    MAX-ACCESS read-only
    STATUS     current
    DESCRIPTION
	    "Calendar Views Loaded is the total number of
	    times the calendar view has been loaded since
	    the process was restarted."
    ::= { ex2OWA 11 }

ex2OWAConversionRequestsKBPerSec OBJECT-TYPE
    SYNTAX     Gauge32
    MAX-ACCESS read-only
    STATUS     current
    DESCRIPTION
	    "Conversion Requests KB/sec is the total number
	    of conversion requests, in kilobytes, that are
	    waiting for conversion by the WebReady Document
	    Viewing service per second. It does not include
	    blocked items and queued items that have timed
	    out."
    ::= { ex2OWA 12 }

ex2OWAConversionResponseKBPerSec OBJECT-TYPE
    SYNTAX     Gauge32
    MAX-ACCESS read-only
    STATUS     current
    DESCRIPTION
	    "Conversion Responses KB/sec is the total
	    number of conversion responses, in kilobytes
	    per second, that are written to an output HTML
	    file."
    ::= { ex2OWA 13 }

ex2OWAConversions OBJECT-TYPE
    SYNTAX     Gauge32
    MAX-ACCESS read-only
    STATUS     current
    DESCRIPTION
	    "Conversions is the total number of requests
	    that were received for conversion since the
	    process was restarted. It includes the items
	    that were rejected because they are in the
	    Block list."
    ::= { ex2OWA 14 }

ex2OWAConversionsEndedByTimeOut OBJECT-TYPE
    SYNTAX     Gauge32
    MAX-ACCESS read-only
    STATUS     current
    DESCRIPTION
	    "Conversions Ended By Time-out is the total
	    number of conversions that ended because the
	    queue timed out or the conversion timed out."
    ::= { ex2OWA 15 }

ex2OWAConversionsEndedWithErrors OBJECT-TYPE
    SYNTAX     Gauge32
    MAX-ACCESS read-only
    STATUS     current
    DESCRIPTION
	    "Conversions Ended with Errors is the number of
	    conversions that failed and returned errors
	    without output."
    ::= { ex2OWA 16 }

ex2OWACurrentProxyUsers OBJECT-TYPE
    SYNTAX     Gauge32
    MAX-ACCESS read-only
    STATUS     current
    DESCRIPTION
	    "Current Proxy Users is the number of users who
	    are logged on whose mailbox access is being
	    proxied to another server."
    ::= { ex2OWA 17 }

ex2OWACurrentUniqueUsers OBJECT-TYPE
    SYNTAX     Gauge32
    MAX-ACCESS read-only
    STATUS     current
    DESCRIPTION
	    "Current Unique Users is the number of unique
	    users currently logged on to Outlook Web
	    Access. This value monitors the number of
	    unique active user sessions, so that users are
	    only removed from this count after they log off
	    or their session times out."
    ::= { ex2OWA 18 }

ex2OWACurrentUniqueUsersLight OBJECT-TYPE
    SYNTAX     Gauge32
    MAX-ACCESS read-only
    STATUS     current
    DESCRIPTION
	    "Current Unique Users Light is the number of
	    unique users currently logged on to OWA. This
	    value monitors the number of unique active user
	    sessions, so that users are only removed from
	    this count after they log off or their session
	    times out."
    ::= { ex2OWA 19 }

ex2OWACurrentUniqueUsersPremium OBJECT-TYPE
    SYNTAX     Gauge32
    MAX-ACCESS read-only
    STATUS     current
    DESCRIPTION
	    "Current Unique Users Premium is the number of
	    unique users currently logged on to Outlook Web
	    Access Premium. This value monitors the number
	    of unique active user sessions, so that users
	    are only removed from this count after they log
	    off or their session times out."
    ::= { ex2OWA 20 }

ex2OWACurrentUsers OBJECT-TYPE
    SYNTAX     Gauge32
    MAX-ACCESS read-only
    STATUS     current
    DESCRIPTION
	    "Current User Count is the number of users who
	    are currently logged on to Outlook Web Access.
	    This value monitors the number of active user
	    sessions, so that users are only removed from
	    this count after they log off or their session
	    times out."
    ::= { ex2OWA 21 }

ex2OWACurrentUsersLight OBJECT-TYPE
    SYNTAX     Gauge32
    MAX-ACCESS read-only
    STATUS     current
    DESCRIPTION
	    "Current User Count Light is the number of
	    users currently logged on to Outlook Web
	    Access. This value monitors the number of
	    active user sessions, so that users are only
	    removed from this count after they log off or
	    their session times out."
    ::= { ex2OWA 22 }

ex2OWACurrentUsersPremium OBJECT-TYPE
    SYNTAX     Gauge32
    MAX-ACCESS read-only
    STATUS     current
    DESCRIPTION
	    "Current User Count Premium is the number of
	    users that are currently logged on to Outlook
	    Web Access. This value monitors the number of
	    active user sessions, so that users are only
	    removed from this count after they log off or
	    their session times out."
    ::= { ex2OWA 23 }

ex2OWAFailedRequestsPerSec OBJECT-TYPE
    SYNTAX     Gauge32
    MAX-ACCESS read-only
    STATUS     current
    DESCRIPTION
	    "Requests/sec Failed is the number of Outlook
	    Web Access requests that failed, per second."
    ::= { ex2OWA 24 }

ex2OWAInvalidCanaryRequests OBJECT-TYPE
    SYNTAX     Gauge32
    MAX-ACCESS read-only
    STATUS     current
    DESCRIPTION
	    "Invalid Canary Requests is the number of
	    requests that included a canary value that is
	    not valid since the process was restarted."
    ::= { ex2OWA 25 }

ex2OWAItemsCreatedSinceOWAStart OBJECT-TYPE
    SYNTAX     Gauge32
    MAX-ACCESS read-only
    STATUS     current
    DESCRIPTION
	    "Items Created is the total number of items of
	    any type that have been created by users since
	    the process was restarted."
    ::= { ex2OWA 26 }

ex2OWAItemsDeletedSinceOWAStart OBJECT-TYPE
    SYNTAX     Gauge32
    MAX-ACCESS read-only
    STATUS     current
    DESCRIPTION
	    "Items Deleted is the total number of items of
	    any type that have been deleted by users since
	    the process was restarted."
    ::= { ex2OWA 27 }

ex2OWAItemsUpdatedSinceOWAStart OBJECT-TYPE
    SYNTAX     Gauge32
    MAX-ACCESS read-only
    STATUS     current
    DESCRIPTION
	    "Items Updated is the total number of items of
	    any type that have been updated by users since
	    the process was restarted."
    ::= { ex2OWA 28 }

ex2OWALogonsPerSec OBJECT-TYPE
    SYNTAX     Gauge32
    MAX-ACCESS read-only
    STATUS     current
    DESCRIPTION
	    "Logons/sec is the number of Outlook Web Access
	    user sessions that are created per second."
    ::= { ex2OWA 29 }

ex2OWALogonsPerSecLight OBJECT-TYPE
    SYNTAX     Gauge32
    MAX-ACCESS read-only
    STATUS     current
    DESCRIPTION
	    "Logons/sec Light is the number of Outlook Web
	    Access user sessions that are created per
	    second."
    ::= { ex2OWA 30 }

ex2OWALogonsPerSecPremium OBJECT-TYPE
    SYNTAX     Gauge32
    MAX-ACCESS read-only
    STATUS     current
    DESCRIPTION
	    "Logons/sec Premium is the number of Outlook
	    Web Access user sessions that are created per
	    second."
    ::= { ex2OWA 31 }

ex2OWAMailViewRefreshes OBJECT-TYPE
    SYNTAX     Gauge32
    MAX-ACCESS read-only
    STATUS     current
    DESCRIPTION
	    "Mail View Refreshes is the total number of
	    times mail views have been refreshed since the
	    process was restarted."
    ::= { ex2OWA 32 }

ex2OWAMailViewsLoaded OBJECT-TYPE
    SYNTAX     Gauge32
    MAX-ACCESS read-only
    STATUS     current
    DESCRIPTION
	    "Mail Views Loaded is the total number of times
	    the mail view has been loaded since the process
	    was restarted."
    ::= { ex2OWA 33 }

ex2OWAMessagesSent OBJECT-TYPE
    SYNTAX     Gauge32
    MAX-ACCESS read-only
    STATUS     current
    DESCRIPTION
	    "Messages Sent is the total number of messages
	    that have been sent by users since the process
	    was restarted."
    ::= { ex2OWA 34 }

ex2OWANamesChecked OBJECT-TYPE
    SYNTAX     Gauge32
    MAX-ACCESS read-only
    STATUS     current
    DESCRIPTION
	    "Names Checked is the total number of recipient
	    names that were attempted to be resolved since
	    the process was started."
    ::= { ex2OWA 35 }

ex2OWAPID OBJECT-TYPE
    SYNTAX     Gauge32
    MAX-ACCESS read-only
    STATUS     current
    DESCRIPTION
	    "PID is the process ID that is hosting Outlook
	    Web Access."
    ::= { ex2OWA 36 }

ex2OWAPasswordChanges OBJECT-TYPE
    SYNTAX     Gauge32
    MAX-ACCESS read-only
    STATUS     current
    DESCRIPTION
	    "Password Changes is the number of times a user
	    has changed their password since the process
	    was started."
    ::= { ex2OWA 37 }

ex2OWAPeakUserCount OBJECT-TYPE
    SYNTAX     Gauge32
    MAX-ACCESS read-only
    STATUS     current
    DESCRIPTION
	    "Peak User Count is the largest number of users
	    simultaneously connected to Outlook Web Access
	    since the process was restarted."
    ::= { ex2OWA 38 }

ex2OWAPeakUserCountLight OBJECT-TYPE
    SYNTAX     Gauge32
    MAX-ACCESS read-only
    STATUS     current
    DESCRIPTION
	    "Peak User Count Light is the largest number of
	    users that were simultaneously connected to
	    Outlook Web Access since the process was
	    restarted."
    ::= { ex2OWA 39 }

ex2OWAPeakUserCountPremium OBJECT-TYPE
    SYNTAX     Gauge32
    MAX-ACCESS read-only
    STATUS     current
    DESCRIPTION
	    "Peak User Count Premium is the largest number
	    of users that were simultaneously connected to
	    Outlook Web Access since the process was
	    restarted."
    ::= { ex2OWA 40 }

ex2OWAProxyRequestBytes OBJECT-TYPE
    SYNTAX     Gauge32
    MAX-ACCESS read-only
    STATUS     current
    DESCRIPTION
	    "Proxy Request Bytes is the total number of
	    HTTP header and content bytes in requests that
	    have been proxied since the process was
	    started."
    ::= { ex2OWA 41 }

ex2OWAProxyResponseBytes OBJECT-TYPE
    SYNTAX     Gauge32
    MAX-ACCESS read-only
    STATUS     current
    DESCRIPTION
	    "Proxy Response Bytes is the total number of
	    HTTP header and content bytes in responses that
	    have been proxied since the process was
	    started."
    ::= { ex2OWA 42 }

ex2OWAProxyResponseTimeAverage OBJECT-TYPE
    SYNTAX     Gauge32
    MAX-ACCESS read-only
    STATUS     current
    DESCRIPTION
	    "Proxy Response Time Average is the average
	    time (in milliseconds) elapsed between the
	    beginning and end of proxied requests."
    ::= { ex2OWA 43 }

ex2OWAProxyUserRequests OBJECT-TYPE
    SYNTAX     Gauge32
    MAX-ACCESS read-only
    STATUS     current
    DESCRIPTION
	    "Proxy User Requests is the total number of
	    requests made on behalf of proxied users since
	    the process was started."
    ::= { ex2OWA 44 }

ex2OWAProxyUserRequestsPerSec OBJECT-TYPE
    SYNTAX     Gauge32
    MAX-ACCESS read-only
    STATUS     current
    DESCRIPTION
	    "Proxy User Requests/sec is the number of
	    proxied requests made per second."
    ::= { ex2OWA 45 }

ex2OWAQueuedConversionRequests OBJECT-TYPE
    SYNTAX     Gauge32
    MAX-ACCESS read-only
    STATUS     current
    DESCRIPTION
	    "Queued Conversion Requests is the number of
	    requests for conversion that are currently
	    waiting to be processed."
    ::= { ex2OWA 46 }

ex2OWARejectedConversions OBJECT-TYPE
    SYNTAX     Gauge32
    MAX-ACCESS read-only
    STATUS     current
    DESCRIPTION
	    "Rejected Conversions is the total number of
	    conversion requests that were rejected because
	    the documents are in the Block list."
    ::= { ex2OWA 47 }

ex2OWARequests OBJECT-TYPE
    SYNTAX     Gauge32
    MAX-ACCESS read-only
    STATUS     current
    DESCRIPTION
	    "Requests is the number of requests that have
	    been executed since the process was restarted."
    ::= { ex2OWA 48 }

ex2OWARequestsFailed OBJECT-TYPE
    SYNTAX     Gauge32
    MAX-ACCESS read-only
    STATUS     current
    DESCRIPTION
	    "Requests Failed is the number of requests that
	    failed since the process was restarted."
    ::= { ex2OWA 49 }

ex2OWARequestsPerSec OBJECT-TYPE
    SYNTAX     Gauge32
    MAX-ACCESS read-only
    STATUS     current
    DESCRIPTION
	    "Requests/sec is the number of requests handled
	    by Outlook Web Access per second."
    ::= { ex2OWA 50 }

ex2OWASearches OBJECT-TYPE
    SYNTAX     Gauge32
    MAX-ACCESS read-only
    STATUS     current
    DESCRIPTION
	    "Searches is the number of searches that have
	    been executed since the process was restarted."
    ::= { ex2OWA 51 }

ex2OWASearchesExecuted OBJECT-TYPE
    SYNTAX     Gauge32
    MAX-ACCESS read-only
    STATUS     current
    DESCRIPTION
	    "Searches Executed is the total number of times
	    a user has requested a search since the process
	    was started."
    ::= { ex2OWA 52 }

ex2OWASearchesTimedOut OBJECT-TYPE
    SYNTAX     Gauge32
    MAX-ACCESS read-only
    STATUS     current
    DESCRIPTION
	    "Searches Timed Out is the number of searches
	    that did not complete in the maximum time
	    allowed since the process was restarted."
    ::= { ex2OWA 53 }

ex2OWASessionsEndedByLogoff OBJECT-TYPE
    SYNTAX     Gauge32
    MAX-ACCESS read-only
    STATUS     current
    DESCRIPTION
	    "Sessions Ended by Logoff is the total number
	    of user sessions that have been ended because
	    the user logged off, since the process was
	    restarted."
    ::= { ex2OWA 54 }

ex2OWASessionsEndedByTimeOut OBJECT-TYPE
    SYNTAX     Gauge32
    MAX-ACCESS read-only
    STATUS     current
    DESCRIPTION
	    "Sessions Ended by Time-out is the total number
	    of user sessions that have been ended because
	    of a timeout since the process was restarted."
    ::= { ex2OWA 55 }

ex2OWASpellingChecks OBJECT-TYPE
    SYNTAX     Gauge32
    MAX-ACCESS read-only
    STATUS     current
    DESCRIPTION
	    "Spelling Checks is the number of Check
	    Spelling operations that have been executed
	    since the process was restarted."
    ::= { ex2OWA 56 }

ex2OWAStoreLogonFailurePercent OBJECT-TYPE
    SYNTAX     Gauge32
    MAX-ACCESS read-only
    STATUS     current
    DESCRIPTION
	    "Store Logon Failure % is the percentage of the
	    last 100 Outlook Web Access user logons to
	    Microsoft Exchange Mailbox servers that have
	    failed."
    ::= { ex2OWA 57 }

ex2OWASuccessConversnReqKBPerSec OBJECT-TYPE
    SYNTAX     Gauge32
    MAX-ACCESS read-only
    STATUS     current
    DESCRIPTION
	    "Successful Conversion Requests KB/sec is the
	    number of successful conversion requests in
	    kilobytes per second."
    ::= { ex2OWA 58 }

ex2OWATotalUniqueUsers OBJECT-TYPE
    SYNTAX     Gauge32
    MAX-ACCESS read-only
    STATUS     current
    DESCRIPTION
	    "Total Unique Users  is the total number of
	    unique users who have connected to Outlook Web
	    Access since the process was restarted."
    ::= { ex2OWA 59 }

ex2OWATotalUniqueUsersLight OBJECT-TYPE
    SYNTAX     Gauge32
    MAX-ACCESS read-only
    STATUS     current
    DESCRIPTION
	    "Total Unique Users Light is the total number
	    of unique users who have connected to Outlook
	    Web Access since the process was restarted."
    ::= { ex2OWA 60 }

ex2OWATotalUniqueUsersPremium OBJECT-TYPE
    SYNTAX     Gauge32
    MAX-ACCESS read-only
    STATUS     current
    DESCRIPTION
	    "Total Unique Users Premium is the total number
	    of unique users who have connected to Outlook
	    Web Access since the process was restarted."
    ::= { ex2OWA 61 }

ex2OWATotalUsers OBJECT-TYPE
    SYNTAX     Gauge32
    MAX-ACCESS read-only
    STATUS     current
    DESCRIPTION
	    "Total Users is the total number of users who
	    have connected to Outlook Web Access since the
	    process was started."
    ::= { ex2OWA 62 }

ex2OWATotalUsersLight OBJECT-TYPE
    SYNTAX     Gauge32
    MAX-ACCESS read-only
    STATUS     current
    DESCRIPTION
	    "Total Users Light is the total number of users
	    who have connected to Outlook Web Access since
	    the process was restarted."
    ::= { ex2OWA 63 }

ex2OWATotalUsersPremium OBJECT-TYPE
    SYNTAX     Gauge32
    MAX-ACCESS read-only
    STATUS     current
    DESCRIPTION
	    "Total Users Premium is the total number of
	    users who have connected to Outlook Web Access
	    since the process was restarted."
    ::= { ex2OWA 64 }

ex2OWAUNCRequests OBJECT-TYPE
    SYNTAX     Gauge32
    MAX-ACCESS read-only
    STATUS     current
    DESCRIPTION
	    "UNC Requests is the total number of Windows
	    file share requests through Outlook Web Access
	    since the process was started."
    ::= { ex2OWA 65 }

ex2OWAUNCResponseBytes OBJECT-TYPE
    SYNTAX     Gauge32
    MAX-ACCESS read-only
    STATUS     current
    DESCRIPTION
	    "UNC Response Bytes is the total number of file
	    content bytes accessed in Windows file shares
	    since the process was started."
    ::= { ex2OWA 66 }

ex2OWAUNCResponseBytesPerSec OBJECT-TYPE
    SYNTAX     Gauge32
    MAX-ACCESS read-only
    STATUS     current
    DESCRIPTION
	    "UNC Response Bytes/sec is the number of bytes
	    in responses to Windows file shares requests,
	    per second."
    ::= { ex2OWA 67 }

ex2OWAWSSRequests OBJECT-TYPE
    SYNTAX     Gauge32
    MAX-ACCESS read-only
    STATUS     current
    DESCRIPTION
	    "WSS Requests is the total number of Windows
	    SharePoint Services requests through Outlook
	    Web Access since the process was started."
    ::= { ex2OWA 68 }

ex2OWAWSSResponseBytes OBJECT-TYPE
    SYNTAX     Gauge32
    MAX-ACCESS read-only
    STATUS     current
    DESCRIPTION
	    "WSS Response Bytes is the total number of file
	    content bytes accessed in Windows SharePoint
	    Services since the process was started."
    ::= { ex2OWA 69 }

ex2OWAWSSResponseBytesPerSec OBJECT-TYPE
    SYNTAX     Gauge32
    MAX-ACCESS read-only
    STATUS     current
    DESCRIPTION
	    "WSS Response Bytes/sec is the number of bytes
	    in responses to Windows SharePoint Services
	    requests, per second."
    ::= { ex2OWA 70 }

ex2OledbEventsTable OBJECT-TYPE
    SYNTAX     SEQUENCE OF Ex2OledbEventsEntry
    MAX-ACCESS not-accessible
    STATUS     current
    DESCRIPTION
	    "The ExOledb Events object type contains
	    counters specific to the ExOledb Events"
    ::= { exchangeV2 19 }

ex2OledbEventsEntry OBJECT-TYPE
    SYNTAX     Ex2OledbEventsEntry
    MAX-ACCESS not-accessible
    STATUS     current
    DESCRIPTION
	    "Performance information for one particular
	    instance of 'MSExchange Oledb Events' object."
    INDEX      { ex2oeInstance }
    ::= { ex2OledbEventsTable 1 }

Ex2OledbEventsEntry ::= SEQUENCE {
    ex2oeInstance InstanceName,
    ex2oeEventsCompletionRate Gauge32,
    ex2oeEventsCompletionTotal Gauge32,
    ex2oeEventsSubmissionRate Gauge32,
    ex2oeEventsSubmissionTotal Gauge32
}

ex2oeInstance OBJECT-TYPE
    SYNTAX     InstanceName
    MAX-ACCESS read-only
    STATUS     current
    DESCRIPTION
	    "Instance name."
    ::= { ex2OledbEventsEntry 1 }

ex2oeEventsCompletionRate OBJECT-TYPE
    SYNTAX     Gauge32
    MAX-ACCESS read-only
    STATUS     current
    DESCRIPTION
	    "The number of events completed per second."
    ::= { ex2OledbEventsEntry 2 }

ex2oeEventsCompletionTotal OBJECT-TYPE
    SYNTAX     Gauge32
    MAX-ACCESS read-only
    STATUS     current
    DESCRIPTION
	    "The total number of events that have been
	    completed."
    ::= { ex2OledbEventsEntry 3 }

ex2oeEventsSubmissionRate OBJECT-TYPE
    SYNTAX     Gauge32
    MAX-ACCESS read-only
    STATUS     current
    DESCRIPTION
	    "The number of events submitted per second."
    ::= { ex2OledbEventsEntry 4 }

ex2oeEventsSubmissionTotal OBJECT-TYPE
    SYNTAX     Gauge32
    MAX-ACCESS read-only
    STATUS     current
    DESCRIPTION
	    "The total number of events that have been
	    submitted."
    ::= { ex2OledbEventsEntry 5 }

ex2OledbResourceTable OBJECT-TYPE
    SYNTAX     SEQUENCE OF Ex2OledbResourceEntry
    MAX-ACCESS not-accessible
    STATUS     current
    DESCRIPTION
	    "The ExOledb Resource object type contains
	    counters specific to the ExOledb Resources"
    ::= { exchangeV2 20 }

ex2OledbResourceEntry OBJECT-TYPE
    SYNTAX     Ex2OledbResourceEntry
    MAX-ACCESS not-accessible
    STATUS     current
    DESCRIPTION
	    "Performance information for one particular
	    instance of 'MSExchange Oledb Resource'
	    object."
    INDEX      { ex2orInstance }
    ::= { ex2OledbResourceTable 1 }

Ex2OledbResourceEntry ::= SEQUENCE {
    ex2orInstance InstanceName,
    ex2orActiveCommands Gauge32,
    ex2orActiveDataSources Gauge32,
    ex2orActiveRows Gauge32,
    ex2orActiveRowsets Gauge32,
    ex2orActiveSessions Gauge32,
    ex2orActiveStreams Gauge32,
    ex2orResourceBindingsRate Gauge32,
    ex2orResourceBindingsTotal Gauge32,
    ex2orRowsetsOpenedRate Gauge32,
    ex2orRowsetsOpenedTotal Gauge32,
    ex2orTransactionsAbortedRate Gauge32,
    ex2orTransactionsAbortedTotal Gauge32,
    ex2orTransactionsCommittedRate Gauge32,
    ex2orTransactionsCommittedTotal Gauge32,
    ex2orTransactionsStartedRate Gauge32,
    ex2orTransactionsStartedTotal Gauge32
}

ex2orInstance OBJECT-TYPE
    SYNTAX     InstanceName
    MAX-ACCESS read-only
    STATUS     current
    DESCRIPTION
	    "Instance name."
    ::= { ex2OledbResourceEntry 1 }

ex2orActiveCommands OBJECT-TYPE
    SYNTAX     Gauge32
    MAX-ACCESS read-only
    STATUS     current
    DESCRIPTION
	    "The number of Command objects which are
	    currently active."
    ::= { ex2OledbResourceEntry 2 }

ex2orActiveDataSources OBJECT-TYPE
    SYNTAX     Gauge32
    MAX-ACCESS read-only
    STATUS     current
    DESCRIPTION
	    "The number of Data Source objects which are
	    currently active."
    ::= { ex2OledbResourceEntry 3 }

ex2orActiveRows OBJECT-TYPE
    SYNTAX     Gauge32
    MAX-ACCESS read-only
    STATUS     current
    DESCRIPTION
	    "The number of Row objects which are currently
	    active."
    ::= { ex2OledbResourceEntry 4 }

ex2orActiveRowsets OBJECT-TYPE
    SYNTAX     Gauge32
    MAX-ACCESS read-only
    STATUS     current
    DESCRIPTION
	    "The number of Rowset objects which are
	    currently active."
    ::= { ex2OledbResourceEntry 5 }

ex2orActiveSessions OBJECT-TYPE
    SYNTAX     Gauge32
    MAX-ACCESS read-only
    STATUS     current
    DESCRIPTION
	    "The number of Session objects which are
	    currently active."
    ::= { ex2OledbResourceEntry 6 }

ex2orActiveStreams OBJECT-TYPE
    SYNTAX     Gauge32
    MAX-ACCESS read-only
    STATUS     current
    DESCRIPTION
	    "The number of Stream objects which are
	    currently active."
    ::= { ex2OledbResourceEntry 7 }

ex2orResourceBindingsRate OBJECT-TYPE
    SYNTAX     Gauge32
    MAX-ACCESS read-only
    STATUS     current
    DESCRIPTION
	    "The number of successful resource bindings per
	    second."
    ::= { ex2OledbResourceEntry 8 }

ex2orResourceBindingsTotal OBJECT-TYPE
    SYNTAX     Gauge32
    MAX-ACCESS read-only
    STATUS     current
    DESCRIPTION
	    "The total number of successful resource
	    bindings."
    ::= { ex2OledbResourceEntry 9 }

ex2orRowsetsOpenedRate OBJECT-TYPE
    SYNTAX     Gauge32
    MAX-ACCESS read-only
    STATUS     current
    DESCRIPTION
	    "The number of times that rowsets are opened
	    per second."
    ::= { ex2OledbResourceEntry 10 }

ex2orRowsetsOpenedTotal OBJECT-TYPE
    SYNTAX     Gauge32
    MAX-ACCESS read-only
    STATUS     current
    DESCRIPTION
	    "The total number of times that rowsets have
	    been opened."
    ::= { ex2OledbResourceEntry 11 }

ex2orTransactionsAbortedRate OBJECT-TYPE
    SYNTAX     Gauge32
    MAX-ACCESS read-only
    STATUS     current
    DESCRIPTION
	    "The number of transactions aborted
	    successfully per second."
    ::= { ex2OledbResourceEntry 12 }

ex2orTransactionsAbortedTotal OBJECT-TYPE
    SYNTAX     Gauge32
    MAX-ACCESS read-only
    STATUS     current
    DESCRIPTION
	    "The total number of transactions that have
	    been successfully aborted."
    ::= { ex2OledbResourceEntry 13 }

ex2orTransactionsCommittedRate OBJECT-TYPE
    SYNTAX     Gauge32
    MAX-ACCESS read-only
    STATUS     current
    DESCRIPTION
	    "The number of transactions committed
	    successfully per second."
    ::= { ex2OledbResourceEntry 14 }

ex2orTransactionsCommittedTotal OBJECT-TYPE
    SYNTAX     Gauge32
    MAX-ACCESS read-only
    STATUS     current
    DESCRIPTION
	    "The total number of transactions that have
	    been successfully committed."
    ::= { ex2OledbResourceEntry 15 }

ex2orTransactionsStartedRate OBJECT-TYPE
    SYNTAX     Gauge32
    MAX-ACCESS read-only
    STATUS     current
    DESCRIPTION
	    "The number of transactions started per
	    second."
    ::= { ex2OledbResourceEntry 16 }

ex2orTransactionsStartedTotal OBJECT-TYPE
    SYNTAX     Gauge32
    MAX-ACCESS read-only
    STATUS     current
    DESCRIPTION
	    "The total number of transactions that have
	    been started."
    ::= { ex2OledbResourceEntry 17 }

ex2ProtocolAnalysisAgent OBJECT-IDENTITY
    STATUS     current
    DESCRIPTION
	    "Performance counters for Protocol Analysis
	    Agent"
    ::= { exchangeV2 21 }

ex2paaCalculationsAtSRL0 OBJECT-TYPE
    SYNTAX     Gauge32
    MAX-ACCESS read-only
    STATUS     current
    DESCRIPTION
	    "Calculations at SRL 0 is the total number of
	    calculations at SRL 0."
    ::= { ex2ProtocolAnalysisAgent 1 }

ex2paaCalculationsAtSRL1 OBJECT-TYPE
    SYNTAX     Gauge32
    MAX-ACCESS read-only
    STATUS     current
    DESCRIPTION
	    "Calculations at SRL 1 is the total number of
	    calculations at SRL 1."
    ::= { ex2ProtocolAnalysisAgent 2 }

ex2paaCalculationsAtSRL2 OBJECT-TYPE
    SYNTAX     Gauge32
    MAX-ACCESS read-only
    STATUS     current
    DESCRIPTION
	    "Calculations at SRL 2 is the total number of
	    calculations at SRL 2."
    ::= { ex2ProtocolAnalysisAgent 3 }

ex2paaCalculationsAtSRL3 OBJECT-TYPE
    SYNTAX     Gauge32
    MAX-ACCESS read-only
    STATUS     current
    DESCRIPTION
	    "Calculations at SRL 3 is the total number of
	    calculations at SRL 3."
    ::= { ex2ProtocolAnalysisAgent 4 }

ex2paaCalculationsAtSRL4 OBJECT-TYPE
    SYNTAX     Gauge32
    MAX-ACCESS read-only
    STATUS     current
    DESCRIPTION
	    "Calculations at SRL 4 is the total number of
	    calculations at SRL 4."
    ::= { ex2ProtocolAnalysisAgent 5 }

ex2paaCalculationsAtSRL5 OBJECT-TYPE
    SYNTAX     Gauge32
    MAX-ACCESS read-only
    STATUS     current
    DESCRIPTION
	    "Calculations at SRL 5 is the total number of
	    calculations at SRL 5."
    ::= { ex2ProtocolAnalysisAgent 6 }

ex2paaCalculationsAtSRL6 OBJECT-TYPE
    SYNTAX     Gauge32
    MAX-ACCESS read-only
    STATUS     current
    DESCRIPTION
	    "Calculations at SRL 6 is the total number of
	    calculations at SRL 6."
    ::= { ex2ProtocolAnalysisAgent 7 }

ex2paaCalculationsAtSRL7 OBJECT-TYPE
    SYNTAX     Gauge32
    MAX-ACCESS read-only
    STATUS     current
    DESCRIPTION
	    "Calculations at SRL 7 is the total number of
	    calculations at SRL 7."
    ::= { ex2ProtocolAnalysisAgent 8 }

ex2paaCalculationsAtSRL8 OBJECT-TYPE
    SYNTAX     Gauge32
    MAX-ACCESS read-only
    STATUS     current
    DESCRIPTION
	    "Calculations at SRL 8 is the total number of
	    calculations at SRL 8."
    ::= { ex2ProtocolAnalysisAgent 9 }

ex2paaCalculationsAtSRL9 OBJECT-TYPE
    SYNTAX     Gauge32
    MAX-ACCESS read-only
    STATUS     current
    DESCRIPTION
	    "Calculations at SRL 9 s the total number of
	    calculations at SRL 9."
    ::= { ex2ProtocolAnalysisAgent 10 }

ex2paaSendersBlockLocalOpenProxy OBJECT-TYPE
    SYNTAX     Gauge32
    MAX-ACCESS read-only
    STATUS     current
    DESCRIPTION
	    "Senders Blocked Because of Local Open Proxy is
	    the total number of senders blocked because of
	    a local open proxy."
    ::= { ex2ProtocolAnalysisAgent 11 }

ex2paaSendersBlockedOfLocalSRL OBJECT-TYPE
    SYNTAX     Gauge32
    MAX-ACCESS read-only
    STATUS     current
    DESCRIPTION
	    "Senders Blocked Because of Local SRL is the
	    total number of senders blocked because of
	    local sender reputation level (SRL)."
    ::= { ex2ProtocolAnalysisAgent 12 }

ex2paaSenderBlockRemoteOpenProxy OBJECT-TYPE
    SYNTAX     Gauge32
    MAX-ACCESS read-only
    STATUS     current
    DESCRIPTION
	    "Senders Blocked Because of Remote Open Proxy
	    is the total number of senders blocked because
	    of a remote open proxy."
    ::= { ex2ProtocolAnalysisAgent 13 }

ex2paaSendersBlockedOfRemoteSRL OBJECT-TYPE
    SYNTAX     Gauge32
    MAX-ACCESS read-only
    STATUS     current
    DESCRIPTION
	    "Senders Blocked Because of Remote SRL is the
	    total number of senders blocked because of
	    remote sender reputation level (SRL)."
    ::= { ex2ProtocolAnalysisAgent 14 }

ex2paaSendersBypassLocalSRLCalc OBJECT-TYPE
    SYNTAX     Gauge32
    MAX-ACCESS read-only
    STATUS     current
    DESCRIPTION
	    "Senders Bypass Local SRL Calculation is the
	    total number of senders that bypass local
	    Sender Reputation Level (SRL) calculation."
    ::= { ex2ProtocolAnalysisAgent 15 }

ex2paaSendersProcessed OBJECT-TYPE
    SYNTAX     Gauge32
    MAX-ACCESS read-only
    STATUS     current
    DESCRIPTION
	    "Senders Processed is the total number of
	    senders processed."
    ::= { ex2ProtocolAnalysisAgent 16 }

ex2ProtocolAnalysisBackgndAgent OBJECT-IDENTITY
    STATUS     current
    DESCRIPTION
	    "Performance counters for Protocol Analysis
	    Background Agent"
    ::= { exchangeV2 22 }

ex2RecipientCacheTable OBJECT-TYPE
    SYNTAX     SEQUENCE OF Ex2RecipientCacheEntry
    MAX-ACCESS not-accessible
    STATUS     current
    DESCRIPTION
	    "Performance counters for the AD recipient
	    cache"
    ::= { exchangeV2 23 }

ex2RecipientCacheEntry OBJECT-TYPE
    SYNTAX     Ex2RecipientCacheEntry
    MAX-ACCESS not-accessible
    STATUS     current
    DESCRIPTION
	    "Performance information for one particular
	    instance of 'MSExchange Recipient Cache'
	    object."
    INDEX      { ex2rcInstance }
    ::= { ex2RecipientCacheTable 1 }

Ex2RecipientCacheEntry ::= SEQUENCE {
    ex2rcInstance InstanceName,
    ex2rcAddressLookupsPending Gauge32,
    ex2rcBatchedAddressLookups Gauge32,
    ex2rcExpandGroupRequests Gauge32,
    ex2rcIndividualAddressLookups Gauge32
}

ex2rcInstance OBJECT-TYPE
    SYNTAX     InstanceName
    MAX-ACCESS read-only
    STATUS     current
    DESCRIPTION
	    "Instance name."
    ::= { ex2RecipientCacheEntry 1 }

ex2rcAddressLookupsPending OBJECT-TYPE
    SYNTAX     Gauge32
    MAX-ACCESS read-only
    STATUS     current
    DESCRIPTION
	    "Address Lookups Pending is the total number of
	    pending address lookups."
    ::= { ex2RecipientCacheEntry 2 }

ex2rcBatchedAddressLookups OBJECT-TYPE
    SYNTAX     Gauge32
    MAX-ACCESS read-only
    STATUS     current
    DESCRIPTION
	    "Batched Address Lookups is the total number of
	    batched address lookups."
    ::= { ex2RecipientCacheEntry 3 }

ex2rcExpandGroupRequests OBJECT-TYPE
    SYNTAX     Gauge32
    MAX-ACCESS read-only
    STATUS     current
    DESCRIPTION
	    "Expand Group Requests is the total number of
	    requests to expand groups."
    ::= { ex2RecipientCacheEntry 4 }

ex2rcIndividualAddressLookups OBJECT-TYPE
    SYNTAX     Gauge32
    MAX-ACCESS read-only
    STATUS     current
    DESCRIPTION
	    "Individual Address Lookups is the total number
	    of individual address lookups."
    ::= { ex2RecipientCacheEntry 5 }

ex2RecipientFilterAgent OBJECT-IDENTITY
    STATUS     current
    DESCRIPTION
	    "Performance counters for the Recipient Filter
	    Agent"
    ::= { exchangeV2 24 }

ex2rfaRecipientsRejectBlockList OBJECT-TYPE
    SYNTAX     Gauge32
    MAX-ACCESS read-only
    STATUS     current
    DESCRIPTION
	    "Recipients Rejected by Block List is the total
	    number of recipients rejected by block list."
    ::= { ex2RecipientFilterAgent 1 }

ex2rfaRecipientRejectBlockLstSec OBJECT-TYPE
    SYNTAX     Gauge32
    MAX-ACCESS read-only
    STATUS     current
    DESCRIPTION
	    "Recipients Rejected by Block List per second
	    is the number of recipients rejected by block
	    list per second."
    ::= { ex2RecipientFilterAgent 2 }

ex2rfaRecpntRejectRecipientValid OBJECT-TYPE
    SYNTAX     Gauge32
    MAX-ACCESS read-only
    STATUS     current
    DESCRIPTION
	    "Recipients Rejected by Recipient Validation is
	    the total number of recipients rejected by
	    recipient validation."
    ::= { ex2RecipientFilterAgent 3 }

ex2rfaRecpntRejectRecpntValidSec OBJECT-TYPE
    SYNTAX     Gauge32
    MAX-ACCESS read-only
    STATUS     current
    DESCRIPTION
	    "Recipients Rejected by Recipient Validation
	    per second is the number of recipients rejected
	    by recipient validation per second."
    ::= { ex2RecipientFilterAgent 4 }

ex2ReplicaSeederTable OBJECT-TYPE
    SYNTAX     SEQUENCE OF Ex2ReplicaSeederEntry
    MAX-ACCESS not-accessible
    STATUS     current
    DESCRIPTION
	    "Performance counters for Replica Seeder"
    ::= { exchangeV2 25 }

ex2ReplicaSeederEntry OBJECT-TYPE
    SYNTAX     Ex2ReplicaSeederEntry
    MAX-ACCESS not-accessible
    STATUS     current
    DESCRIPTION
	    "Performance information for one particular
	    instance of 'MSExchange Replica Seeder'
	    object."
    INDEX      { ex2rsInstance }
    ::= { ex2ReplicaSeederTable 1 }

Ex2ReplicaSeederEntry ::= SEQUENCE {
    ex2rsInstance InstanceName,
    ex2rsSeedingFinishedPercent Gauge32
}

ex2rsInstance OBJECT-TYPE
    SYNTAX     InstanceName
    MAX-ACCESS read-only
    STATUS     current
    DESCRIPTION
	    "Instance name."
    ::= { ex2ReplicaSeederEntry 1 }

ex2rsSeedingFinishedPercent OBJECT-TYPE
    SYNTAX     Gauge32
    MAX-ACCESS read-only
    STATUS     current
    DESCRIPTION
	    "Seeding Finished % is the finished percentage
	    of seeding. Its value is from 0 to 100
	    percent."
    ::= { ex2ReplicaSeederEntry 2 }

ex2ReplicationTable OBJECT-TYPE
    SYNTAX     SEQUENCE OF Ex2ReplicationEntry
    MAX-ACCESS not-accessible
    STATUS     current
    DESCRIPTION
	    "A table containing performance information for
	    instances of 'MSExchange Replication' objects."
    ::= { exchangeV2 26 }

ex2ReplicationEntry OBJECT-TYPE
    SYNTAX     Ex2ReplicationEntry
    MAX-ACCESS not-accessible
    STATUS     current
    DESCRIPTION
	    "Performance information for one particular
	    instance of 'MSExchange Replication' object."
    INDEX      { ex2rInstance }
    ::= { ex2ReplicationTable 1 }

Ex2ReplicationEntry ::= SEQUENCE {
    ex2rInstance InstanceName,
    ex2rCopyQueExceedMntThresholdCCR Gauge32,
    ex2rCopyGenerationNumber Gauge32,
    ex2rCopyNotifiyGenerationNumber Gauge32,
    ex2rCopyQueueLength Gauge32,
    ex2rFailed Gauge32,
    ex2rInitializing Gauge32,
    ex2rInspectorGenerationNumber Gauge32,
    ex2rReplayBatchSize Gauge32,
    ex2rReplayGenerationNumber Gauge32,
    ex2rReplayGenerationsComplete Gauge32,
    ex2rReplayGenerationsPerMinute Gauge32,
    ex2rReplayGenerationsRemaining Gauge32,
    ex2rReplayNotifyGenerationNumber Gauge32,
    ex2rReplayQueueLength Gauge32,
    ex2rSuspended Gauge32,
    ex2rTruncatedGenerationNumber Gauge32
}

ex2rInstance OBJECT-TYPE
    SYNTAX     InstanceName
    MAX-ACCESS read-only
    STATUS     current
    DESCRIPTION
	    "Instance name."
    ::= { ex2ReplicationEntry 1 }

ex2rCopyQueExceedMntThresholdCCR OBJECT-TYPE
    SYNTAX     Gauge32
    MAX-ACCESS read-only
    STATUS     current
    DESCRIPTION
	    "Copy Queue Exceeds Mount Threshold (CCR Only)
	    is 1 if the copy queue length is larger than
	    the Mount Threshold specified by the Auto
	    Database Mount Dial.  This counter is only used
	    with cluster continuous replication (CCR). It
	    will always be 0 with local continuous
	    replication (LCR)."
    ::= { ex2ReplicationEntry 2 }

ex2rCopyGenerationNumber OBJECT-TYPE
    SYNTAX     Gauge32
    MAX-ACCESS read-only
    STATUS     current
    DESCRIPTION
	    "Copy Generation Number is the generation of
	    the last log file which has been copied."
    ::= { ex2ReplicationEntry 3 }

ex2rCopyNotifiyGenerationNumber OBJECT-TYPE
    SYNTAX     Gauge32
    MAX-ACCESS read-only
    STATUS     current
    DESCRIPTION
	    "Copy Notification Generation Number is the
	    generation of the last log file which copier
	    knows about."
    ::= { ex2ReplicationEntry 4 }

ex2rCopyQueueLength OBJECT-TYPE
    SYNTAX     Gauge32
    MAX-ACCESS read-only
    STATUS     current
    DESCRIPTION
	    "Copy Queue Length is the number of log
	    generations waiting to be both copied and
	    inspected successfully."
    ::= { ex2ReplicationEntry 5 }

ex2rFailed OBJECT-TYPE
    SYNTAX     Gauge32
    MAX-ACCESS read-only
    STATUS     current
    DESCRIPTION
	    "Failed is 1 if the replica instance is set to
	    failed, otherwise 0."
    ::= { ex2ReplicationEntry 6 }

ex2rInitializing OBJECT-TYPE
    SYNTAX     Gauge32
    MAX-ACCESS read-only
    STATUS     current
    DESCRIPTION
	    "Initializing is 1 if the replica instance is
	    in initial startup checking or incremental
	    reseeding, otherwise 0."
    ::= { ex2ReplicationEntry 7 }

ex2rInspectorGenerationNumber OBJECT-TYPE
    SYNTAX     Gauge32
    MAX-ACCESS read-only
    STATUS     current
    DESCRIPTION
	    "Inspector Generation Number is the generation
	    of the last log file which has been inspected."
    ::= { ex2ReplicationEntry 8 }

ex2rReplayBatchSize OBJECT-TYPE
    SYNTAX     Gauge32
    MAX-ACCESS read-only
    STATUS     current
    DESCRIPTION
	    "Replay Batch Size is the number of log
	    generations replayed together."
    ::= { ex2ReplicationEntry 9 }

ex2rReplayGenerationNumber OBJECT-TYPE
    SYNTAX     Gauge32
    MAX-ACCESS read-only
    STATUS     current
    DESCRIPTION
	    "Replay Generation Number is the generation of
	    the last log file which has been replayed
	    successfully."
    ::= { ex2ReplicationEntry 10 }

ex2rReplayGenerationsComplete OBJECT-TYPE
    SYNTAX     Gauge32
    MAX-ACCESS read-only
    STATUS     current
    DESCRIPTION
	    "Replay Generations Complete is the number of
	    log generations already played in the current
	    replay batch."
    ::= { ex2ReplicationEntry 11 }

ex2rReplayGenerationsPerMinute OBJECT-TYPE
    SYNTAX     Gauge32
    MAX-ACCESS read-only
    STATUS     current
    DESCRIPTION
	    "Replay Generations per minute is the rate of
	    replay in log generations per minute in the
	    current replay batch."
    ::= { ex2ReplicationEntry 12 }

ex2rReplayGenerationsRemaining OBJECT-TYPE
    SYNTAX     Gauge32
    MAX-ACCESS read-only
    STATUS     current
    DESCRIPTION
	    "Replay Generations Remaining is the number of
	    log generations remaining to be played in
	    current replay batch."
    ::= { ex2ReplicationEntry 13 }

ex2rReplayNotifyGenerationNumber OBJECT-TYPE
    SYNTAX     Gauge32
    MAX-ACCESS read-only
    STATUS     current
    DESCRIPTION
	    "Replay Notification Generation Number is the
	    generation of the last log file that the
	    Microsoft Exchange Replication service knows
	    about."
    ::= { ex2ReplicationEntry 14 }

ex2rReplayQueueLength OBJECT-TYPE
    SYNTAX     Gauge32
    MAX-ACCESS read-only
    STATUS     current
    DESCRIPTION
	    "Replay Queue Length is the number of log
	    generations waiting to be replayed."
    ::= { ex2ReplicationEntry 15 }

ex2rSuspended OBJECT-TYPE
    SYNTAX     Gauge32
    MAX-ACCESS read-only
    STATUS     current
    DESCRIPTION
	    "Suspended is 1 if the continuous replication
	    is suspended.  When the continuous replication
	    is suspended logs are not being copied and
	    replayed into the passive copy."
    ::= { ex2ReplicationEntry 16 }

ex2rTruncatedGenerationNumber OBJECT-TYPE
    SYNTAX     Gauge32
    MAX-ACCESS read-only
    STATUS     current
    DESCRIPTION
	    "Truncated Generation Number is the generation
	    of the last log file to which truncation has
	    been completed."
    ::= { ex2ReplicationEntry 17 }

ex2ResourceBooking OBJECT-IDENTITY
    STATUS     current
    DESCRIPTION
	    "Performance counters for the Microsoft
	    Exchange Resource Booking Attendant"
    ::= { exchangeV2 27 }

ex2rbAccepted OBJECT-TYPE
    SYNTAX     Gauge32
    MAX-ACCESS read-only
    STATUS     current
    DESCRIPTION
	    "Accepted is the total number of meeting
	    requests accepted by Resource Booking
	    Attendant."
    ::= { ex2ResourceBooking 1 }

ex2rbAvgResourceBookProcessTime OBJECT-TYPE
    SYNTAX     Gauge32
    MAX-ACCESS read-only
    STATUS     current
    DESCRIPTION
	    "Average Resource Booking Processing Time is
	    the average time to process an event in the
	    Resource Booking Attendant."
    ::= { ex2ResourceBooking 2 }

ex2rbCancelled OBJECT-TYPE
    SYNTAX     Gauge32
    MAX-ACCESS read-only
    STATUS     current
    DESCRIPTION
	    "Cancelled is the total number of meeting
	    cancellations processed by Resource Booking
	    Attendant."
    ::= { ex2ResourceBooking 3 }

ex2rbDeclined OBJECT-TYPE
    SYNTAX     Gauge32
    MAX-ACCESS read-only
    STATUS     current
    DESCRIPTION
	    "Declined is the total number of meeting
	    requests declined by Resource Booking
	    Attendant."
    ::= { ex2ResourceBooking 4 }

ex2rbEvents OBJECT-TYPE
    SYNTAX     Gauge32
    MAX-ACCESS read-only
    STATUS     current
    DESCRIPTION
	    "Events is the total number of events submitted
	    to Resource Booking Attendant for processing."
    ::= { ex2ResourceBooking 5 }

ex2rbRequestsFailed OBJECT-TYPE
    SYNTAX     Gauge32
    MAX-ACCESS read-only
    STATUS     current
    DESCRIPTION
	    "Requests Failed is the  total number of
	    failures that occurred while Resource Booking
	    Attendant was processing events."
    ::= { ex2ResourceBooking 6 }

ex2rbRequestsProcessed OBJECT-TYPE
    SYNTAX     Gauge32
    MAX-ACCESS read-only
    STATUS     current
    DESCRIPTION
	    "Requests Processed is the	total number of
	    meeting requests processed by Resource Booking
	    Attendant."
    ::= { ex2ResourceBooking 7 }

ex2rbRequestsSubmitted OBJECT-TYPE
    SYNTAX     Gauge32
    MAX-ACCESS read-only
    STATUS     current
    DESCRIPTION
	    "Requests Submitted is the	total number of
	    meeting requests submitted to Resource Booking
	    Attendant for processing."
    ::= { ex2ResourceBooking 8 }

ex2SearchIndexer OBJECT-IDENTITY
    STATUS     current
    DESCRIPTION
	    "Performance counters for Exchange Search
	    Indexer (MSExchangeSearch)"
    ::= { exchangeV2 28 }

ex2sAverageBatchLatency OBJECT-TYPE
    SYNTAX     Gauge32
    MAX-ACCESS read-only
    STATUS     current
    DESCRIPTION
	    "Average Batch Latency is the average latency
	    (in seconds) between the time a document batch
	    is given to the Microsoft Exchange Search
	    Indexer service and when that document batch
	    has been completely processed."
    ::= { ex2SearchIndexer 1 }

ex2siAverageBatchSize OBJECT-TYPE
    SYNTAX     Gauge32
    MAX-ACCESS read-only
    STATUS     current
    DESCRIPTION
	    "Average Batch Size is the average size of the
	    document batches that are indexed through the
	    Microsoft Exchange Search Indexer service."
    ::= { ex2SearchIndexer 2 }

ex2siNumberDatabasesBeingCrawled OBJECT-TYPE
    SYNTAX     Gauge32
    MAX-ACCESS read-only
    STATUS     current
    DESCRIPTION
	    "Number of Databases Being Crawled is the total
	    number of databases that are being crawled
	    currently."
    ::= { ex2SearchIndexer 3 }

ex2siNumberDatabasesBeingIndexed OBJECT-TYPE
    SYNTAX     Gauge32
    MAX-ACCESS read-only
    STATUS     current
    DESCRIPTION
	    "Number of Databases Being Indexed is the 
	    total number of databases that are being
	    actively indexed by Exchange Search Indexer."
    ::= { ex2SearchIndexer 4 }

ex2siNumberOfDisabledDatabases OBJECT-TYPE
    SYNTAX     Gauge32
    MAX-ACCESS read-only
    STATUS     current
    DESCRIPTION
	    "Number of Disabled Databases is the total
	    number of databases that are currently disabled
	    in Exchange Search Indexer configuration."
    ::= { ex2SearchIndexer 5 }

ex2siNumIndexDatabaseUpDateNotif OBJECT-TYPE
    SYNTAX     Gauge32
    MAX-ACCESS read-only
    STATUS     current
    DESCRIPTION
	    "Number of Indexed Databases Being Kept
	    Up-to-Date by Notifications is the total number
	    of databases whose content index is currently
	    kept up-to-date by notifications."
    ::= { ex2SearchIndexer 6 }

ex2SearchIndicesTable OBJECT-TYPE
    SYNTAX     SEQUENCE OF Ex2SearchIndicesEntry
    MAX-ACCESS not-accessible
    STATUS     current
    DESCRIPTION
	    "Performance counters for the Exchange Search
	    Indexer (MSExchangeSearch) search indices."
    ::= { exchangeV2 29 }

ex2SearchIndicesEntry OBJECT-TYPE
    SYNTAX     Ex2SearchIndicesEntry
    MAX-ACCESS not-accessible
    STATUS     current
    DESCRIPTION
	    "Performance information for one particular
	    instance of 'MSExchange Search Indices'
	    object."
    INDEX      { ex2sidInstance }
    ::= { ex2SearchIndicesTable 1 }

Ex2SearchIndicesEntry ::= SEQUENCE {
    ex2sidInstance InstanceName,
    ex2sidAgeLastNotificationIndexed Gauge32,
    ex2sidAgeLastNotificationProcess Gauge32,
    ex2sidAvgLatencyRPCsDuringCrawl Gauge32,
    ex2sidAvgLatencyRPCObtainContent Gauge32,
    ex2sidAverageDocumentIndexngTime Gauge32,
    ex2sidAvgLatencyRPCsToGetNotific Gauge32,
    ex2sidAvgSizeOfIndexedAttachment Gauge32,
    ex2sidDocumentIndexingRate Gauge32,
    ex2sidFullCrawlModeStatus Gauge32,
    ex2sidNumContentConversionsDone Gauge32,
    ex2sidNumCreateNotifications Gauge32,
    ex2sidNumCreateNotificationPrSec Gauge32,
    ex2sidNumDeleteNotifications Gauge32,
    ex2sidNumDeleteNotificationPrSec Gauge32,
    ex2sidNumDocumentsSuccessIndexed Gauge32,
    ex2sidNumDocumentFailDuringIndex Gauge32,
    ex2sidNumberOfFailedRetries Gauge32,
    ex2sidNumberOfHTMLMessageBodies Gauge32,
    ex2sidNumberOfIndexedAttachments Gauge32,
    ex2sidNumItemInNotificationQueue Gauge32,
    ex2sidNumMailboxesLeftToCrawl Gauge32,
    ex2sidNumberOfMoveNotifications Gauge32,
    ex2sidNumMoveNotificationsPerSec Gauge32,
    ex2sidNumberOfOutstandingBatches Gauge32,
    ex2sidNumOutstandingDocuments Gauge32,
    ex2sidNumPlainTextMessageBodies Gauge32,
    ex2sidNumberOfRTFMessageBodies Gauge32,
    ex2sidNumRecentMoveMailboxCrawl Gauge32,
    ex2sidNumberOfRetries Gauge32,
    ex2sidNumberOfSuccessfulRetries Gauge32,
    ex2sidNumUpdateNotifications Gauge32,
    ex2sidNumUpdateNotificationPrSec Gauge32,
    ex2sidPercentageNotificOptimize Gauge32,
    ex2sidRecentAvgLatencyRPCUseObta Gauge32,
    ex2sidThrottlingDelayValue Gauge32
}

ex2sidInstance OBJECT-TYPE
    SYNTAX     InstanceName
    MAX-ACCESS read-only
    STATUS     current
    DESCRIPTION
	    "Instance name."
    ::= { ex2SearchIndicesEntry 1 }

ex2sidAgeLastNotificationIndexed OBJECT-TYPE
    SYNTAX     Gauge32
    MAX-ACCESS read-only
    STATUS     current
    DESCRIPTION
	    "Age of the Last Notification Indexed is the
	    age (in seconds) of the last notification we
	    have successfully indexed for the given
	    database."
    ::= { ex2SearchIndicesEntry 2 }

ex2sidAgeLastNotificationProcess OBJECT-TYPE
    SYNTAX     Gauge32
    MAX-ACCESS read-only
    STATUS     current
    DESCRIPTION
	    "Age of the Last Notification Processed is the
	    age (in seconds) of the last notification we
	    have successfully processed for the given
	    database."
    ::= { ex2SearchIndicesEntry 3 }

ex2sidAvgLatencyRPCsDuringCrawl OBJECT-TYPE
    SYNTAX     Gauge32
    MAX-ACCESS read-only
    STATUS     current
    DESCRIPTION
	    "Average Latency of RPCs During Crawling is the
	    average latency of RPCs (in milliseconds) to
	    the Exchange Information Store service. These
	    calls are used for crawling purposes for the
	    given database."
    ::= { ex2SearchIndicesEntry 4 }

ex2sidAvgLatencyRPCObtainContent OBJECT-TYPE
    SYNTAX     Gauge32
    MAX-ACCESS read-only
    STATUS     current
    DESCRIPTION
	    "Average Latency of RPCs Used to Obtain Content
	    is the average latency (in milliseconds) of RPC
	    calls to the Exchange Information Store
	    service. These calls are used to obtain content
	    for the filter daemon for the given database."
    ::= { ex2SearchIndicesEntry 5 }

ex2sidAverageDocumentIndexngTime OBJECT-TYPE
    SYNTAX     Gauge32
    MAX-ACCESS read-only
    STATUS     current
    DESCRIPTION
	    "Average Document Indexing Time is the average
	    (in milliseconds) of how long it takes to index
	    documents."
    ::= { ex2SearchIndicesEntry 6 }

ex2sidAvgLatencyRPCsToGetNotific OBJECT-TYPE
    SYNTAX     Gauge32
    MAX-ACCESS read-only
    STATUS     current
    DESCRIPTION
	    "Average Latency of RPCs Used to Obtain
	    Notifications is the average latency (in
	    milliseconds) of RPC calls to the Exchange
	    Information Store service. These calls are used
	    to obtain new notifications for the given
	    database."
    ::= { ex2SearchIndicesEntry 7 }

ex2sidAvgSizeOfIndexedAttachment OBJECT-TYPE
    SYNTAX     Gauge32
    MAX-ACCESS read-only
    STATUS     current
    DESCRIPTION
	    "Average Size of Indexed Attachments is the
	    average size of attachments that have been
	    content indexed since the filter daemon
	    started."
    ::= { ex2SearchIndicesEntry 8 }

ex2sidDocumentIndexingRate OBJECT-TYPE
    SYNTAX     Gauge32
    MAX-ACCESS read-only
    STATUS     current
    DESCRIPTION
	    "Document Indexing Rate is the rate at which
	    documents are indexed (number of documents
	    successfully indexed per second)."
    ::= { ex2SearchIndicesEntry 9 }

ex2sidFullCrawlModeStatus OBJECT-TYPE
    SYNTAX     Gauge32
    MAX-ACCESS read-only
    STATUS     current
    DESCRIPTION
	    "Full Crawl Mode Status indicates whether this
	    MDB is going through a full crawl (value=1) or
	    not (value=0)."
    ::= { ex2SearchIndicesEntry 10 }

ex2sidNumContentConversionsDone OBJECT-TYPE
    SYNTAX     Gauge32
    MAX-ACCESS read-only
    STATUS     current
    DESCRIPTION
	    "Number of Content Conversions Done is the
	    total number of content conversions that have
	    been done in the filter daemon since the
	    Exchange Content Indexing service started."
    ::= { ex2SearchIndicesEntry 11 }

ex2sidNumCreateNotifications OBJECT-TYPE
    SYNTAX     Gauge32
    MAX-ACCESS read-only
    STATUS     current
    DESCRIPTION
	    "Number of Create Notifications is the total
	    number of create notifications received by
	    MSSearch."
    ::= { ex2SearchIndicesEntry 12 }

ex2sidNumCreateNotificationPrSec OBJECT-TYPE
    SYNTAX     Gauge32
    MAX-ACCESS read-only
    STATUS     current
    DESCRIPTION
	    "Number of Create Notifications/sec is the
	    number of create notifications received by
	    MSSearch per second."
    ::= { ex2SearchIndicesEntry 13 }

ex2sidNumDeleteNotifications OBJECT-TYPE
    SYNTAX     Gauge32
    MAX-ACCESS read-only
    STATUS     current
    DESCRIPTION
	    "Number of Delete Notifications is the total
	    number of delete notifications received by
	    MSSearch."
    ::= { ex2SearchIndicesEntry 14 }

ex2sidNumDeleteNotificationPrSec OBJECT-TYPE
    SYNTAX     Gauge32
    MAX-ACCESS read-only
    STATUS     current
    DESCRIPTION
	    "Number of Delete Notifications/sec is the
	    number of delete notifications received by
	    MSSearch per second."
    ::= { ex2SearchIndicesEntry 15 }

ex2sidNumDocumentsSuccessIndexed OBJECT-TYPE
    SYNTAX     Gauge32
    MAX-ACCESS read-only
    STATUS     current
    DESCRIPTION
	    "Number of Documents Successfully Indexed is
	    the total number of documents that have been
	    successfully indexed since the Exchange Search
	    Indexer started."
    ::= { ex2SearchIndicesEntry 16 }

ex2sidNumDocumentFailDuringIndex OBJECT-TYPE
    SYNTAX     Gauge32
    MAX-ACCESS read-only
    STATUS     current
    DESCRIPTION
	    "Number of Documents That Failed During
	    Indexing is the total number of documents that
	    have not been indexed since the Exchange Search
	    Indexer started."
    ::= { ex2SearchIndicesEntry 17 }

ex2sidNumberOfFailedRetries OBJECT-TYPE
    SYNTAX     Gauge32
    MAX-ACCESS read-only
    STATUS     current
    DESCRIPTION
	    "Number of Failed Retries is the total number
	    of retries that have failed for documents that
	    originally failed during indexing."
    ::= { ex2SearchIndicesEntry 18 }

ex2sidNumberOfHTMLMessageBodies OBJECT-TYPE
    SYNTAX     Gauge32
    MAX-ACCESS read-only
    STATUS     current
    DESCRIPTION
	    "Number of HTML Message Bodies is the total
	    number of HTML message bodies that have been
	    content indexed since the filter daemon
	    started."
    ::= { ex2SearchIndicesEntry 19 }

ex2sidNumberOfIndexedAttachments OBJECT-TYPE
    SYNTAX     Gauge32
    MAX-ACCESS read-only
    STATUS     current
    DESCRIPTION
	    "Number of Indexed Attachments is the total
	    number of attachments that have been content
	    indexed since the filter daemon started."
    ::= { ex2SearchIndicesEntry 20 }

ex2sidNumItemInNotificationQueue OBJECT-TYPE
    SYNTAX     Gauge32
    MAX-ACCESS read-only
    STATUS     current
    DESCRIPTION
	    "Number of Items in a Notification Queue is the
	    total number of items (notifications) that are
	    in a notification queue."
    ::= { ex2SearchIndicesEntry 21 }

ex2sidNumMailboxesLeftToCrawl OBJECT-TYPE
    SYNTAX     Gauge32
    MAX-ACCESS read-only
    STATUS     current
    DESCRIPTION
	    "Number of Mailboxes Left to Crawl is the total
	    number of mailboxes that are left to be crawled
	    on this database."
    ::= { ex2SearchIndicesEntry 22 }

ex2sidNumberOfMoveNotifications OBJECT-TYPE
    SYNTAX     Gauge32
    MAX-ACCESS read-only
    STATUS     current
    DESCRIPTION
	    "Number of Move Notifications is the total
	    number of move notifications received by
	    MSSearch."
    ::= { ex2SearchIndicesEntry 23 }

ex2sidNumMoveNotificationsPerSec OBJECT-TYPE
    SYNTAX     Gauge32
    MAX-ACCESS read-only
    STATUS     current
    DESCRIPTION
	    "Number of Move Notifications/sec is the 
	    number of move notifications received by
	    MSSearch per second."
    ::= { ex2SearchIndicesEntry 24 }

ex2sidNumberOfOutstandingBatches OBJECT-TYPE
    SYNTAX     Gauge32
    MAX-ACCESS read-only
    STATUS     current
    DESCRIPTION
	    "Number of Outstanding Batches is the total
	    number of batches sent to MSSearch that are
	    still being processed."
    ::= { ex2SearchIndicesEntry 25 }

ex2sidNumOutstandingDocuments OBJECT-TYPE
    SYNTAX     Gauge32
    MAX-ACCESS read-only
    STATUS     current
    DESCRIPTION
	    "Number of Outstanding Documents is the total
	    number of documents that are being actively
	    indexed."
    ::= { ex2SearchIndicesEntry 26 }

ex2sidNumPlainTextMessageBodies OBJECT-TYPE
    SYNTAX     Gauge32
    MAX-ACCESS read-only
    STATUS     current
    DESCRIPTION
	    "Number of Plain Text Message Bodies is the
	    total number of plain text format message
	    bodies that have been content indexed since the
	    filter daemon started."
    ::= { ex2SearchIndicesEntry 27 }

ex2sidNumberOfRTFMessageBodies OBJECT-TYPE
    SYNTAX     Gauge32
    MAX-ACCESS read-only
    STATUS     current
    DESCRIPTION
	    "Number of RTF Message Bodies is the  total
	    number of rich text format (RTF) message bodies
	    that have been content indexed since the filter
	    daemon started."
    ::= { ex2SearchIndicesEntry 28 }

ex2sidNumRecentMoveMailboxCrawl OBJECT-TYPE
    SYNTAX     Gauge32
    MAX-ACCESS read-only
    STATUS     current
    DESCRIPTION
	    "Number of Recently Moved Mailboxes Being
	    Crawled is the total number of mailboxes
	    recently moved to this database that are  being
	    crawled."
    ::= { ex2SearchIndicesEntry 29 }

ex2sidNumberOfRetries OBJECT-TYPE
    SYNTAX     Gauge32
    MAX-ACCESS read-only
    STATUS     current
    DESCRIPTION
	    "Number of Retries is the total number of
	    retries that have been tried for the documents
	    that have failed during indexing."
    ::= { ex2SearchIndicesEntry 30 }

ex2sidNumberOfSuccessfulRetries OBJECT-TYPE
    SYNTAX     Gauge32
    MAX-ACCESS read-only
    STATUS     current
    DESCRIPTION
	    "Number of Successful Retries is the total
	    number of retries that have succeeded for
	    documents that originally failed during
	    indexing."
    ::= { ex2SearchIndicesEntry 31 }

ex2sidNumUpdateNotifications OBJECT-TYPE
    SYNTAX     Gauge32
    MAX-ACCESS read-only
    STATUS     current
    DESCRIPTION
	    "Number of Update Notifications is the total
	    number of update notifications received by
	    MSSearch."
    ::= { ex2SearchIndicesEntry 32 }

ex2sidNumUpdateNotificationPrSec OBJECT-TYPE
    SYNTAX     Gauge32
    MAX-ACCESS read-only
    STATUS     current
    DESCRIPTION
	    "Number of Update Notifications/sec is the
	    number of update notifications received by
	    MSSearch per second."
    ::= { ex2SearchIndicesEntry 33 }

ex2sidPercentageNotificOptimize OBJECT-TYPE
    SYNTAX     Gauge32
    MAX-ACCESS read-only
    STATUS     current
    DESCRIPTION
	    "Percentage of Notifications Optimized is the
	    percentage of notifications that were optimized
	    (marked as done without being processed)."
    ::= { ex2SearchIndicesEntry 34 }

ex2sidRecentAvgLatencyRPCUseObta OBJECT-TYPE
    SYNTAX     Gauge32
    MAX-ACCESS read-only
    STATUS     current
    DESCRIPTION
	    "Recent Average Latency of RPCs Used to Obtain
	    Content is the average latency (in
	    milliseconds) of the most recent RPCs to the
	    Exchange Information Store service. These RPCs
	    are used to get content for the filter daemon
	    for the given database."
    ::= { ex2SearchIndicesEntry 35 }

ex2sidThrottlingDelayValue OBJECT-TYPE
    SYNTAX     Gauge32
    MAX-ACCESS read-only
    STATUS     current
    DESCRIPTION
	    "Throttling Delay Value is the total Total time
	    (in milliseconds) a worker thread sleeps before
	    it retrieves a document from the Exchange
	    Information Store service. This is set by the
	    throttling monitor thread."
    ::= { ex2SearchIndicesEntry 36 }

ex2SecureMailTransportTable OBJECT-TYPE
    SYNTAX     SEQUENCE OF Ex2SecureMailTransportEntry
    MAX-ACCESS not-accessible
    STATUS     current
    DESCRIPTION
	    "A table containing performance information for
	    instances of 'MSExchange Secure Mail Transport'
	    objects."
    ::= { exchangeV2 30 }

ex2SecureMailTransportEntry OBJECT-TYPE
    SYNTAX     Ex2SecureMailTransportEntry
    MAX-ACCESS not-accessible
    STATUS     current
    DESCRIPTION
	    "Performance information for one particular
	    instance of 'MSExchange Secure Mail Transport'
	    object."
    INDEX      { ex2smtInstance }
    ::= { ex2SecureMailTransportTable 1 }

Ex2SecureMailTransportEntry ::= SEQUENCE {
    ex2smtInstance InstanceName,
    ex2smtDomainSecureMessageReceive Gauge32,
    ex2smtDomainSecureMessagesSent Gauge32,
    ex2smtDomSecureOutbndSessionFail Gauge32
}

ex2smtInstance OBJECT-TYPE
    SYNTAX     InstanceName
    MAX-ACCESS read-only
    STATUS     current
    DESCRIPTION
	    "Instance name."
    ::= { ex2SecureMailTransportEntry 1 }

ex2smtDomainSecureMessageReceive OBJECT-TYPE
    SYNTAX     Gauge32
    MAX-ACCESS read-only
    STATUS     current
    DESCRIPTION
	    "Domain Secure Messages Received is the number
	    of domain-secured messages received by the SMTP
	    server."
    ::= { ex2SecureMailTransportEntry 2 }

ex2smtDomainSecureMessagesSent OBJECT-TYPE
    SYNTAX     Gauge32
    MAX-ACCESS read-only
    STATUS     current
    DESCRIPTION
	    "Domain Secure Messages Sent is the number of
	    domain-secured messages sent by the SMTP
	    server."
    ::= { ex2SecureMailTransportEntry 3 }

ex2smtDomSecureOutbndSessionFail OBJECT-TYPE
    SYNTAX     Gauge32
    MAX-ACCESS read-only
    STATUS     current
    DESCRIPTION
	    "Domain Secure Outbound Session Failures is the
	    number of domain-secured outbound session
	    failures."
    ::= { ex2SecureMailTransportEntry 4 }

ex2SenderFilterAgent OBJECT IDENTIFIER
    ::= { exchangeV2 31 }

ex2sfaMessagesEvalBySenderFilter OBJECT-TYPE
    SYNTAX     Gauge32
    MAX-ACCESS read-only
    STATUS     current
    DESCRIPTION
	    "Messages Evaluated by Sender Filter is the
	    total number of messages evaluated by the
	    Sender Filter agent."
    ::= { ex2SenderFilterAgent 1 }

ex2sfaMsgEvaluatSendFilterPerSec OBJECT-TYPE
    SYNTAX     Gauge32
    MAX-ACCESS read-only
    STATUS     current
    DESCRIPTION
	    "Messages Evaluated by Sender Filter per second
	    is the number of messages evaluated by the
	    Sender Filter agent per second."
    ::= { ex2SenderFilterAgent 2 }

ex2sfaMsgFilteredBySenderFilter OBJECT-TYPE
    SYNTAX     Gauge32
    MAX-ACCESS read-only
    STATUS     current
    DESCRIPTION
	    "Messages Filtered by Sender Filter is the
	    total number of messages filtered by the Sender
	    Filter agent."
    ::= { ex2SenderFilterAgent 3 }

ex2sfaMsgFilterSenderFilterPrSec OBJECT-TYPE
    SYNTAX     Gauge32
    MAX-ACCESS read-only
    STATUS     current
    DESCRIPTION
	    "Messages Filtered by Sender Filter per second
	    is the number of messages filtered by the
	    Sender Filter agent per second."
    ::= { ex2SenderFilterAgent 4 }

ex2SenderIdAgent OBJECT IDENTIFIER
    ::= { exchangeV2 32 }

ex2siaDNSQueries OBJECT-TYPE
    SYNTAX     Gauge32
    MAX-ACCESS read-only
    STATUS     current
    DESCRIPTION
	    "DNS Queries is the total number of DNS queries
	    performed by the Sender Id agent."
    ::= { ex2SenderIdAgent 1 }

ex2siaDNSQueriesPerSec OBJECT-TYPE
    SYNTAX     Gauge32
    MAX-ACCESS read-only
    STATUS     current
    DESCRIPTION
	    "DNS Queries per second is the number of DNS
	    queries per second performed by the Sender Id
	    agent."
    ::= { ex2SenderIdAgent 2 }

ex2siaMsgMissingOriginatingIP OBJECT-TYPE
    SYNTAX     Gauge32
    MAX-ACCESS read-only
    STATUS     current
    DESCRIPTION
	    "Messages Missing Originating IP is the total
	    number of messages for which the originating IP
	    could not be determined."
    ::= { ex2SenderIdAgent 3 }

ex2siaMsgMissngOriginateIPPerSec OBJECT-TYPE
    SYNTAX     Gauge32
    MAX-ACCESS read-only
    STATUS     current
    DESCRIPTION
	    "Messages Missing Originating IP per second is
	    the number of messages per second for which the
	    originating IP could not be determined."
    ::= { ex2SenderIdAgent 4 }

ex2siaMsgThatBypassedValidation OBJECT-TYPE
    SYNTAX     Gauge32
    MAX-ACCESS read-only
    STATUS     current
    DESCRIPTION
	    "Messages That Bypassed Validation is the total
	    number of messages that bypassed validation by
	    the Sender Id agent."
    ::= { ex2SenderIdAgent 5 }

ex2siaMsgThatBypassValidatePrSec OBJECT-TYPE
    SYNTAX     Gauge32
    MAX-ACCESS read-only
    STATUS     current
    DESCRIPTION
	    "Messages That Bypassed Validation per second
	    is the number of messages that bypassed
	    validation per second."
    ::= { ex2SenderIdAgent 6 }

ex2siaMessagesValidated OBJECT-TYPE
    SYNTAX     Gauge32
    MAX-ACCESS read-only
    STATUS     current
    DESCRIPTION
	    "Messages Validated is the total number of
	    messages validated by the Sender Id agent."
    ::= { ex2SenderIdAgent 7 }

ex2siaMsgValidFailMalformDomRes OBJECT-TYPE
    SYNTAX     Gauge32
    MAX-ACCESS read-only
    STATUS     current
    DESCRIPTION
	    "Messages Validated with a Fail - Malformed
	    Domain Result is the total number of messages
	    validated with a result of Fail - Malformed
	    Domain."
    ::= { ex2SenderIdAgent 8 }

ex2siaMsgValidFailNonExistDomRes OBJECT-TYPE
    SYNTAX     Gauge32
    MAX-ACCESS read-only
    STATUS     current
    DESCRIPTION
	    "Messages Validated with a Fail - Non-Existent
	    Domain Result is the number of messages
	    validated with a result of Fail - Non-existent
	    Domain."
    ::= { ex2SenderIdAgent 9 }

ex2siaMsgValidFailNotPermittRes OBJECT-TYPE
    SYNTAX     Gauge32
    MAX-ACCESS read-only
    STATUS     current
    DESCRIPTION
	    "Messages Validated with a Fail - Not Permitted
	    Result is the total number of messages
	    validated with a result of Fail - Not
	    Permitted."
    ::= { ex2SenderIdAgent 10 }

ex2siaMsgValidWithANeutralResult OBJECT-TYPE
    SYNTAX     Gauge32
    MAX-ACCESS read-only
    STATUS     current
    DESCRIPTION
	    "Messages Validated with a Neutral Result is
	    the total number of messages validated with a
	    result of Neutral."
    ::= { ex2SenderIdAgent 11 }

ex2siaMsgValidWithANoneResult OBJECT-TYPE
    SYNTAX     Gauge32
    MAX-ACCESS read-only
    STATUS     current
    DESCRIPTION
	    "Messages Validated with a None Result is the
	    total number of messages validated with a
	    result of None."
    ::= { ex2SenderIdAgent 12 }

ex2siaMsgValidWithAPassResult OBJECT-TYPE
    SYNTAX     Gauge32
    MAX-ACCESS read-only
    STATUS     current
    DESCRIPTION
	    "Messages Validated with a Pass Result is the
	    total number of messages validated with a
	    result of Pass."
    ::= { ex2SenderIdAgent 13 }

ex2siaMsgValidPermErrorResult OBJECT-TYPE
    SYNTAX     Gauge32
    MAX-ACCESS read-only
    STATUS     current
    DESCRIPTION
	    "Messages Validated with a PermError Result is
	    the total number of messages validated with a
	    result of PermError."
    ::= { ex2SenderIdAgent 14 }

ex2siaMsgValidSoftFailResult OBJECT-TYPE
    SYNTAX     Gauge32
    MAX-ACCESS read-only
    STATUS     current
    DESCRIPTION
	    "Messages Validated with a SoftFail Result is
	    the total number of messages validated with a
	    result of SoftFail."
    ::= { ex2SenderIdAgent 15 }

ex2siaMsgValidTempErrorResult OBJECT-TYPE
    SYNTAX     Gauge32
    MAX-ACCESS read-only
    STATUS     current
    DESCRIPTION
	    "Messages Validated with a TempError Result is
	    the total number of messages validated with a
	    result of TempError."
    ::= { ex2SenderIdAgent 16 }

ex2siaMessagesValidatedPerSec OBJECT-TYPE
    SYNTAX     Gauge32
    MAX-ACCESS read-only
    STATUS     current
    DESCRIPTION
	    "Messages Validated per second is the number of
	    messages validated per second."
    ::= { ex2SenderIdAgent 17 }

ex2siaMsgValidFailMlfrmDomResSec OBJECT-TYPE
    SYNTAX     Gauge32
    MAX-ACCESS read-only
    STATUS     current
    DESCRIPTION
	    "Messages Validated per Second with a Fail -
	    Malformed Result is the number of messages
	    validated per second with a result of Fail -
	    Malformed Domain."
    ::= { ex2SenderIdAgent 18 }

ex2siaMsgValidFailNExstDomResSec OBJECT-TYPE
    SYNTAX     Gauge32
    MAX-ACCESS read-only
    STATUS     current
    DESCRIPTION
	    "Messages Validated per Second with a Fail -
	    Non-Existent Domain Result is the number of
	    messages validated per second with a result of
	    Fail - Non-existent Domain."
    ::= { ex2SenderIdAgent 19 }

ex2siaMsgValidFailNotPermitRes OBJECT-TYPE
    SYNTAX     Gauge32
    MAX-ACCESS read-only
    STATUS     current
    DESCRIPTION
	    "Messages Validated per Second with a Fail Not
	    - Permitted Result is the number of messages
	    validated per second with a result of Fail -
	    Not Permitted."
    ::= { ex2SenderIdAgent 20 }

ex2siaMsgValidPerSecNeutrlResult OBJECT-TYPE
    SYNTAX     Gauge32
    MAX-ACCESS read-only
    STATUS     current
    DESCRIPTION
	    "Messages Validated per Second with a Neutral
	    Result is the number of messages validated per
	    second with a result of Neutral."
    ::= { ex2SenderIdAgent 21 }

ex2siaMsgValidPerSecNoneResult OBJECT-TYPE
    SYNTAX     Gauge32
    MAX-ACCESS read-only
    STATUS     current
    DESCRIPTION
	    "Messages Validated per Second with a None
	    Result is the number of messages validated per
	    second with a result of None."
    ::= { ex2SenderIdAgent 22 }

ex2siaMsgValidPerSecPassResult OBJECT-TYPE
    SYNTAX     Gauge32
    MAX-ACCESS read-only
    STATUS     current
    DESCRIPTION
	    "Messages Validated per Second with a Pass
	    Result is the number of messages validated per
	    second with a result of Pass."
    ::= { ex2SenderIdAgent 23 }

ex2siaMsgValidSecPermErrorResult OBJECT-TYPE
    SYNTAX     Gauge32
    MAX-ACCESS read-only
    STATUS     current
    DESCRIPTION
	    "Messages Validated per Second with a PermError
	    Result is the number of messages validated per
	    second with a result of PermError."
    ::= { ex2SenderIdAgent 24 }

ex2siaMsgValidPerSecSoftFailRes OBJECT-TYPE
    SYNTAX     Gauge32
    MAX-ACCESS read-only
    STATUS     current
    DESCRIPTION
	    "Messages Validated per Second with a SoftFail
	    Result is the number of messages validated per
	    second with a result of SoftFail."
    ::= { ex2SenderIdAgent 25 }

ex2siaMsgValidSecTempErrorResult OBJECT-TYPE
    SYNTAX     Gauge32
    MAX-ACCESS read-only
    STATUS     current
    DESCRIPTION
	    "Messages Validated per Second with a TempError
	    Result is the number of messages validated per
	    second with a result of TempError."
    ::= { ex2SenderIdAgent 26 }

ex2siaMessagesWithNoPRAPerSec OBJECT-TYPE
    SYNTAX     Gauge32
    MAX-ACCESS read-only
    STATUS     current
    DESCRIPTION
	    "Messages With No PRA per second is the number
	    of messages per second that do not have a valid
	    PRA."
    ::= { ex2SenderIdAgent 27 }

ex2siaMessagesWithNoPRA OBJECT-TYPE
    SYNTAX     Gauge32
    MAX-ACCESS read-only
    STATUS     current
    DESCRIPTION
	    "Messages with No PRA is the total number of
	    messages that do not have a valid PRA."
    ::= { ex2SenderIdAgent 28 }

ex2StoreDriverTable OBJECT-TYPE
    SYNTAX     SEQUENCE OF Ex2StoreDriverEntry
    MAX-ACCESS not-accessible
    STATUS     current
    DESCRIPTION
	    "A table containing performance information for
	    instances of 'MSExchange Store Driver'
	    objects."
    ::= { exchangeV2 33 }

ex2StoreDriverEntry OBJECT-TYPE
    SYNTAX     Ex2StoreDriverEntry
    MAX-ACCESS not-accessible
    STATUS     current
    DESCRIPTION
	    "Performance information for one particular
	    instance of 'MSExchange Store Driver' object."
    INDEX      { ex2sdInstance }
    ::= { ex2StoreDriverTable 1 }

Ex2StoreDriverEntry ::= SEQUENCE {
    ex2sdInstance InstanceName,
    ex2sdInboundBytesDelivered Gauge32,
    ex2sdInboundDuplicateDeliveries Gauge32,
    ex2sdInboundFailedRecipients Gauge32,
    ex2sdInboundLocalDeliveryCalls Gauge32,
    ex2sdInboundLocalDelivCallSecond Gauge32,
    ex2sdInboundMsgDeliveryAttempts Gauge32,
    ex2sdInboundMsgDelvrAttmptSecond Gauge32,
    ex2sdInboundNumDeliveringThreads Gauge32,
    ex2sdInboundRecipientsDelivered Gauge32,
    ex2sdInboundRecipntDeliverSecond Gauge32,
    ex2sdInboundReroutedRecipients Gauge32,
    ex2sdInboundRetriedRecipients Gauge32,
    ex2sdInboundSucceededRecipients Gauge32,
    ex2sdInboundTotalMeetingFailures Gauge32,
    ex2sdInboundTotalMeetingMessages Gauge32,
    ex2sdOutboundMapiEventWithoutMsg Gauge32,
    ex2sdOutboundSubmittedMailItems Gauge32,
    ex2sdOutboundSubmtMailItemSecond Gauge32,
    ex2sdOutboundTotalRecipients Gauge32
}

ex2sdInstance OBJECT-TYPE
    SYNTAX     InstanceName
    MAX-ACCESS read-only
    STATUS     current
    DESCRIPTION
	    "Instance name."
    ::= { ex2StoreDriverEntry 1 }

ex2sdInboundBytesDelivered OBJECT-TYPE
    SYNTAX     Gauge32
    MAX-ACCESS read-only
    STATUS     current
    DESCRIPTION
	    "Inbound: Bytes Delivered is the number of
	    bytes delivered."
    ::= { ex2StoreDriverEntry 2 }

ex2sdInboundDuplicateDeliveries OBJECT-TYPE
    SYNTAX     Gauge32
    MAX-ACCESS read-only
    STATUS     current
    DESCRIPTION
	    "Inbound: Duplicate Deliveries detected by
	    store."
    ::= { ex2StoreDriverEntry 3 }

ex2sdInboundFailedRecipients OBJECT-TYPE
    SYNTAX     Gauge32
    MAX-ACCESS read-only
    STATUS     current
    DESCRIPTION
	    "Inbound: Failed Recipients is the number of
	    failed deliveries."
    ::= { ex2StoreDriverEntry 4 }

ex2sdInboundLocalDeliveryCalls OBJECT-TYPE
    SYNTAX     Gauge32
    MAX-ACCESS read-only
    STATUS     current
    DESCRIPTION
	    "Inbound: Local Delivery Calls is the number of
	    local delivery calls."
    ::= { ex2StoreDriverEntry 5 }

ex2sdInboundLocalDelivCallSecond OBJECT-TYPE
    SYNTAX     Gauge32
    MAX-ACCESS read-only
    STATUS     current
    DESCRIPTION
	    "Local delivery calls per second"
    ::= { ex2StoreDriverEntry 6 }

ex2sdInboundMsgDeliveryAttempts OBJECT-TYPE
    SYNTAX     Gauge32
    MAX-ACCESS read-only
    STATUS     current
    DESCRIPTION
	    "Inbound: Message Delivery Attempts is the
	    number of attempt for delivering transport
	    mailitem."
    ::= { ex2StoreDriverEntry 7 }

ex2sdInboundMsgDelvrAttmptSecond OBJECT-TYPE
    SYNTAX     Gauge32
    MAX-ACCESS read-only
    STATUS     current
    DESCRIPTION
	    "Inbound: Message Delivery Attempts Per Second
	    is the number of attempts for delivering
	    transport mailitem per second."
    ::= { ex2StoreDriverEntry 8 }

ex2sdInboundNumDeliveringThreads OBJECT-TYPE
    SYNTAX     Gauge32
    MAX-ACCESS read-only
    STATUS     current
    DESCRIPTION
	    "Inbound: Number of Delivering Threads is the
	    number of threads in delivery."
    ::= { ex2StoreDriverEntry 9 }

ex2sdInboundRecipientsDelivered OBJECT-TYPE
    SYNTAX     Gauge32
    MAX-ACCESS read-only
    STATUS     current
    DESCRIPTION
	    "Recipients delivered"
    ::= { ex2StoreDriverEntry 10 }

ex2sdInboundRecipntDeliverSecond OBJECT-TYPE
    SYNTAX     Gauge32
    MAX-ACCESS read-only
    STATUS     current
    DESCRIPTION
	    "Recipients delivered per second"
    ::= { ex2StoreDriverEntry 11 }

ex2sdInboundReroutedRecipients OBJECT-TYPE
    SYNTAX     Gauge32
    MAX-ACCESS read-only
    STATUS     current
    DESCRIPTION
	    "Inbound: Rerouted Recipients is the number of
	    delivery reroutes."
    ::= { ex2StoreDriverEntry 12 }

ex2sdInboundRetriedRecipients OBJECT-TYPE
    SYNTAX     Gauge32
    MAX-ACCESS read-only
    STATUS     current
    DESCRIPTION
	    "Inbound: Retried Recipients is the number of
	    delivery retries."
    ::= { ex2StoreDriverEntry 13 }

ex2sdInboundSucceededRecipients OBJECT-TYPE
    SYNTAX     Gauge32
    MAX-ACCESS read-only
    STATUS     current
    DESCRIPTION
	    "Inbound: Succeeded Recipients is the number of
	    successful deliveries."
    ::= { ex2StoreDriverEntry 14 }

ex2sdInboundTotalMeetingFailures OBJECT-TYPE
    SYNTAX     Gauge32
    MAX-ACCESS read-only
    STATUS     current
    DESCRIPTION
	    "Inbound: Total Meeting Failures is the number
	    of errors seen while processing meeting
	    messages."
    ::= { ex2StoreDriverEntry 15 }

ex2sdInboundTotalMeetingMessages OBJECT-TYPE
    SYNTAX     Gauge32
    MAX-ACCESS read-only
    STATUS     current
    DESCRIPTION
	    "Inbound: Total Meeting Messages is the total
	    number of meeting messages processed."
    ::= { ex2StoreDriverEntry 16 }

ex2sdOutboundMapiEventWithoutMsg OBJECT-TYPE
    SYNTAX     Gauge32
    MAX-ACCESS read-only
    STATUS     current
    DESCRIPTION
	    "Outbound: Mapi Events Without Message is the
	    number of submitted MAPI events without message
	    item."
    ::= { ex2StoreDriverEntry 17 }

ex2sdOutboundSubmittedMailItems OBJECT-TYPE
    SYNTAX     Gauge32
    MAX-ACCESS read-only
    STATUS     current
    DESCRIPTION
	    "Outbound: Submitted Mail Items is the number
	    of submitted mail items."
    ::= { ex2StoreDriverEntry 18 }

ex2sdOutboundSubmtMailItemSecond OBJECT-TYPE
    SYNTAX     Gauge32
    MAX-ACCESS read-only
    STATUS     current
    DESCRIPTION
	    "Outbound: Submitted Mail Items Per Second is
	    the number of mail items per second being
	    submitted."
    ::= { ex2StoreDriverEntry 19 }

ex2sdOutboundTotalRecipients OBJECT-TYPE
    SYNTAX     Gauge32
    MAX-ACCESS read-only
    STATUS     current
    DESCRIPTION
	    "Outbound: Total Recipients is the total number
	    of recipients handled."
    ::= { ex2StoreDriverEntry 20 }

ex2StoreInterfaceTable OBJECT-TYPE
    SYNTAX     SEQUENCE OF Ex2StoreInterfaceEntry
    MAX-ACCESS not-accessible
    STATUS     current
    DESCRIPTION
	    "A table containing performance information for
	    instances of 'MSExchange Store Interface'
	    objects."
    ::= { exchangeV2 34 }

ex2StoreInterfaceEntry OBJECT-TYPE
    SYNTAX     Ex2StoreInterfaceEntry
    MAX-ACCESS not-accessible
    STATUS     current
    DESCRIPTION
	    "Performance information for one particular
	    instance of 'MSExchange Store Interface'
	    object."
    INDEX      { ex2sifInstance }
    ::= { ex2StoreInterfaceTable 1 }

Ex2StoreInterfaceEntry ::= SEQUENCE {
    ex2sifInstance InstanceName,
    ex2sifConnCacheActiveConns Gauge32,
    ex2sifConnCacheIdleConns Gauge32,
    ex2sifConnectionCacheNumCaches Gauge32,
    ex2sifConnCacheOutLimitCreations Gauge32,
    ex2sifConnCacheTotalCapacity Gauge32,
    ex2sifExRpcConnCreationEvents Gauge32,
    ex2sifExRpcConnDisposalEvents Gauge32,
    ex2sifExRpcConnectionOutstanding Gauge32,
    ex2sifROPRequestsComplete Gauge32,
    ex2sifROPRequestsOutstanding Gauge32,
    ex2sifROPRequestsSent Gauge32,
    ex2sifRPCBytesReceived Gauge32,
    ex2sifRPCBytesReceivedAverage Gauge32,
    ex2sifRPCBytesSent Gauge32,
    ex2sifRPCBytesSentAverage Gauge32,
    ex2sifRPCLatencyAverageMsec Gauge32,
    ex2sifRPCLatencyTotalMsec Gauge32,
    ex2sifRPCRequestsFailed Gauge32,
    ex2sifRPCRequestsFailedPercent Gauge32,
    ex2sifRPCRequestsFailedException Gauge32,
    ex2sifRPCRequestsOutstanding Gauge32,
    ex2sifRPCRequestsSent Gauge32,
    ex2sifRPCRequestsSentPerSec Gauge32,
    ex2sifRPCRequestsSucceeded Gauge32,
    ex2sifRPCSlowRequests Gauge32,
    ex2sifRPCSlowRequestsPercent Gauge32,
    ex2sifRPCSlowReqLatencyAvgMsec Gauge32,
    ex2sifRPCSlowReqLatencyTotalMsec Gauge32,
    ex2sifUNKFolders Gauge32,
    ex2sifUNKLogons Gauge32,
    ex2sifUNKMessages Gauge32,
    ex2sifUNKObjectsTotal Gauge32
}

ex2sifInstance OBJECT-TYPE
    SYNTAX     InstanceName
    MAX-ACCESS read-only
    STATUS     current
    DESCRIPTION
	    "Instance name."
    ::= { ex2StoreInterfaceEntry 1 }

ex2sifConnCacheActiveConns OBJECT-TYPE
    SYNTAX     Gauge32
    MAX-ACCESS read-only
    STATUS     current
    DESCRIPTION
	    "ConnectionCache active connections is the
	    number of active connections in all connection
	    caches."
    ::= { ex2StoreInterfaceEntry 2 }

ex2sifConnCacheIdleConns OBJECT-TYPE
    SYNTAX     Gauge32
    MAX-ACCESS read-only
    STATUS     current
    DESCRIPTION
	    "ConnectionCache idle connections is the number
	    of idle connections in all connection caches."
    ::= { ex2StoreInterfaceEntry 3 }

ex2sifConnectionCacheNumCaches OBJECT-TYPE
    SYNTAX     Gauge32
    MAX-ACCESS read-only
    STATUS     current
    DESCRIPTION
	    "ConnectionCache num caches is the total number
	    of ConnectionCache objects."
    ::= { ex2StoreInterfaceEntry 4 }

ex2sifConnCacheOutLimitCreations OBJECT-TYPE
    SYNTAX     Gauge32
    MAX-ACCESS read-only
    STATUS     current
    DESCRIPTION
	    "Some instances of connection caches allow
	    creation of extra connections even if all slots
	    in cache are occupied. This counter shows
	    number of cases when such connections were
	    created."
    ::= { ex2StoreInterfaceEntry 5 }

ex2sifConnCacheTotalCapacity OBJECT-TYPE
    SYNTAX     Gauge32
    MAX-ACCESS read-only
    STATUS     current
    DESCRIPTION
	    "ConnectionCache total capacity is the total
	    capacity of all ConnectionCache objects."
    ::= { ex2StoreInterfaceEntry 6 }

ex2sifExRpcConnCreationEvents OBJECT-TYPE
    SYNTAX     Gauge32
    MAX-ACCESS read-only
    STATUS     current
    DESCRIPTION
	    "Number of ExRpcConnection objects creation
	    events."
    ::= { ex2StoreInterfaceEntry 7 }

ex2sifExRpcConnDisposalEvents OBJECT-TYPE
    SYNTAX     Gauge32
    MAX-ACCESS read-only
    STATUS     current
    DESCRIPTION
	    "Number of ExRpcConnection objects disposal
	    events."
    ::= { ex2StoreInterfaceEntry 8 }

ex2sifExRpcConnectionOutstanding OBJECT-TYPE
    SYNTAX     Gauge32
    MAX-ACCESS read-only
    STATUS     current
    DESCRIPTION
	    "ExRpcConnection outstanding is the total
	    number of outstanding ExRpcConnection objects.
	    This value shows number of managed connection
	    objects in GC heap."
    ::= { ex2StoreInterfaceEntry 9 }

ex2sifROPRequestsComplete OBJECT-TYPE
    SYNTAX     Gauge32
    MAX-ACCESS read-only
    STATUS     current
    DESCRIPTION
	    "ROP Requests complete is the total number of
	    completed ROP requests."
    ::= { ex2StoreInterfaceEntry 10 }

ex2sifROPRequestsOutstanding OBJECT-TYPE
    SYNTAX     Gauge32
    MAX-ACCESS read-only
    STATUS     current
    DESCRIPTION
	    "ROP Requests outstanding is the total number
	    of outstanding ROP requests."
    ::= { ex2StoreInterfaceEntry 11 }

ex2sifROPRequestsSent OBJECT-TYPE
    SYNTAX     Gauge32
    MAX-ACCESS read-only
    STATUS     current
    DESCRIPTION
	    "ROP Requests sent is the total number of ROP
	    requests, buffered for delivery."
    ::= { ex2StoreInterfaceEntry 12 }

ex2sifRPCBytesReceived OBJECT-TYPE
    SYNTAX     Gauge32
    MAX-ACCESS read-only
    STATUS     current
    DESCRIPTION
	    "RPC Bytes received is the total number of
	    bytes, received from the server since exrpc32
	    was loaded."
    ::= { ex2StoreInterfaceEntry 13 }

ex2sifRPCBytesReceivedAverage OBJECT-TYPE
    SYNTAX     Gauge32
    MAX-ACCESS read-only
    STATUS     current
    DESCRIPTION
	    "RPC Bytes received average is the average
	    number of bytes, received from the server in
	    one succeeded RPC call."
    ::= { ex2StoreInterfaceEntry 14 }

ex2sifRPCBytesSent OBJECT-TYPE
    SYNTAX     Gauge32
    MAX-ACCESS read-only
    STATUS     current
    DESCRIPTION
	    "RPC Bytes sent is the total number of bytes,
	    sent to the server since exrpc32 was loaded."
    ::= { ex2StoreInterfaceEntry 15 }

ex2sifRPCBytesSentAverage OBJECT-TYPE
    SYNTAX     Gauge32
    MAX-ACCESS read-only
    STATUS     current
    DESCRIPTION
	    "RPC Bytes sent average is the average number
	    of bytes, sent to the server in one RPC call."
    ::= { ex2StoreInterfaceEntry 16 }

ex2sifRPCLatencyAverageMsec OBJECT-TYPE
    SYNTAX     Gauge32
    MAX-ACCESS read-only
    STATUS     current
    DESCRIPTION
	    "RPC Latency average (msec) is the average
	    latency in milliseconds of RPC requests.
	    Average is calculated over all RPCs since
	    exrpc32 was loaded."
    ::= { ex2StoreInterfaceEntry 17 }

ex2sifRPCLatencyTotalMsec OBJECT-TYPE
    SYNTAX     Gauge32
    MAX-ACCESS read-only
    STATUS     current
    DESCRIPTION
	    "RPC Latency total (msec) is the total amount
	    of time in milliseconds spent inside RPC calls.
	    Note that since many threads can call PRCs at
	    the same time, this value can grow faster than
	    elapsed time."
    ::= { ex2StoreInterfaceEntry 18 }

ex2sifRPCRequestsFailed OBJECT-TYPE
    SYNTAX     Gauge32
    MAX-ACCESS read-only
    STATUS     current
    DESCRIPTION
	    "RPC Requests failed is the total number of RPC
	    requests that returned with non 0 result from
	    the server."
    ::= { ex2StoreInterfaceEntry 19 }

ex2sifRPCRequestsFailedPercent OBJECT-TYPE
    SYNTAX     Gauge32
    MAX-ACCESS read-only
    STATUS     current
    DESCRIPTION
	    "RPC Requests failed (%) is the percent of
	    failed requests in total number of RPC
	    requests. Here, failed means the sum of failed
	    with error code plus failed with exception."
    ::= { ex2StoreInterfaceEntry 20 }

ex2sifRPCRequestsFailedException OBJECT-TYPE
    SYNTAX     Gauge32
    MAX-ACCESS read-only
    STATUS     current
    DESCRIPTION
	    "Total number of RPC requests that failed with
	    exception."
    ::= { ex2StoreInterfaceEntry 21 }

ex2sifRPCRequestsOutstanding OBJECT-TYPE
    SYNTAX     Gauge32
    MAX-ACCESS read-only
    STATUS     current
    DESCRIPTION
	    "RPC Requests outstanding is the current number
	    of outstanding RPC requests."
    ::= { ex2StoreInterfaceEntry 22 }

ex2sifRPCRequestsSent OBJECT-TYPE
    SYNTAX     Gauge32
    MAX-ACCESS read-only
    STATUS     current
    DESCRIPTION
	    "RPC Requests sent is the total number of
	    initiated RPC requests."
    ::= { ex2StoreInterfaceEntry 23 }

ex2sifRPCRequestsSentPerSec OBJECT-TYPE
    SYNTAX     Gauge32
    MAX-ACCESS read-only
    STATUS     current
    DESCRIPTION
	    "RPC Requests sent/sec is the current rate of
	    initiated RPC requests per second."
    ::= { ex2StoreInterfaceEntry 24 }

ex2sifRPCRequestsSucceeded OBJECT-TYPE
    SYNTAX     Gauge32
    MAX-ACCESS read-only
    STATUS     current
    DESCRIPTION
	    "RPC Requests succeeded is the total number of
	    succeeded RPC requests (ec == 0)."
    ::= { ex2StoreInterfaceEntry 25 }

ex2sifRPCSlowRequests OBJECT-TYPE
    SYNTAX     Gauge32
    MAX-ACCESS read-only
    STATUS     current
    DESCRIPTION
	    "RPC Slow requests is the total number of slow
	    RPC requests."
    ::= { ex2StoreInterfaceEntry 26 }

ex2sifRPCSlowRequestsPercent OBJECT-TYPE
    SYNTAX     Gauge32
    MAX-ACCESS read-only
    STATUS     current
    DESCRIPTION
	    "RPC Slow requests (%) is the percent of slow
	    RPC requests among all RPC requests."
    ::= { ex2StoreInterfaceEntry 27 }

ex2sifRPCSlowReqLatencyAvgMsec OBJECT-TYPE
    SYNTAX     Gauge32
    MAX-ACCESS read-only
    STATUS     current
    DESCRIPTION
	    "RPC Slow requests latency average (msec) is
	    the average latency in milliseconds of slow RPC
	    requests."
    ::= { ex2StoreInterfaceEntry 28 }

ex2sifRPCSlowReqLatencyTotalMsec OBJECT-TYPE
    SYNTAX     Gauge32
    MAX-ACCESS read-only
    STATUS     current
    DESCRIPTION
	    "RPC Slow requests latency total (msec) is the
	    total amount of time in milliseconds spent
	    inside slow RPC calls."
    ::= { ex2StoreInterfaceEntry 29 }

ex2sifUNKFolders OBJECT-TYPE
    SYNTAX     Gauge32
    MAX-ACCESS read-only
    STATUS     current
    DESCRIPTION
	    "UNK Folders is the current number of Folder
	    objects. (C++ objects in exrpc32.)"
    ::= { ex2StoreInterfaceEntry 30 }

ex2sifUNKLogons OBJECT-TYPE
    SYNTAX     Gauge32
    MAX-ACCESS read-only
    STATUS     current
    DESCRIPTION
	    "UNK Logons is the current number of Logon
	    objects. (C++ objects in exrpc32.)"
    ::= { ex2StoreInterfaceEntry 31 }

ex2sifUNKMessages OBJECT-TYPE
    SYNTAX     Gauge32
    MAX-ACCESS read-only
    STATUS     current
    DESCRIPTION
	    "UNK Messages is the current number of Message
	    objects. (C++ objects in exrpc32.)"
    ::= { ex2StoreInterfaceEntry 32 }

ex2sifUNKObjectsTotal OBJECT-TYPE
    SYNTAX     Gauge32
    MAX-ACCESS read-only
    STATUS     current
    DESCRIPTION
	    "UNK Objects total is the current number of all
	    objects that are derived from UNK. (C++ objects
	    in exrpc32.)"
    ::= { ex2StoreInterfaceEntry 33 }

ex2TopologyTable OBJECT-TYPE
    SYNTAX     SEQUENCE OF Ex2TopologyEntry
    MAX-ACCESS not-accessible
    STATUS     current
    DESCRIPTION
	    "A table containing performance information for
	    instances of 'MSExchange Topology' objects."
    ::= { exchangeV2 35 }

ex2TopologyEntry OBJECT-TYPE
    SYNTAX     Ex2TopologyEntry
    MAX-ACCESS not-accessible
    STATUS     current
    DESCRIPTION
	    "Performance information for one particular
	    instance of 'MSExchange Topology' object."
    INDEX      { ex2tpInstance }
    ::= { ex2TopologyTable 1 }

Ex2TopologyEntry ::= SEQUENCE {
    ex2tpInstance InstanceName,
    ex2tpLatestExchgTopologyDisTime Gauge32,
    ex2tpNumExchangeTopologyDiscover Gauge32,
    ex2tpNumberOfSitelessServers Gauge32
}

ex2tpInstance OBJECT-TYPE
    SYNTAX     InstanceName
    MAX-ACCESS read-only
    STATUS     current
    DESCRIPTION
	    "Instance name."
    ::= { ex2TopologyEntry 1 }

ex2tpLatestExchgTopologyDisTime OBJECT-TYPE
    SYNTAX     Gauge32
    MAX-ACCESS read-only
    STATUS     current
    DESCRIPTION
	    "Latest Exchange Topology Discovery Time in
	    Seconds"
    ::= { ex2TopologyEntry 2 }

ex2tpNumExchangeTopologyDiscover OBJECT-TYPE
    SYNTAX     Gauge32
    MAX-ACCESS read-only
    STATUS     current
    DESCRIPTION
	    "Number of Exchange Topology Discoveries
	    occurred in this process."
    ::= { ex2TopologyEntry 3 }

ex2tpNumberOfSitelessServers OBJECT-TYPE
    SYNTAX     Gauge32
    MAX-ACCESS read-only
    STATUS     current
    DESCRIPTION
	    "Number of Siteless Servers is the number of
	    Exchange Servers that could not be mapped to a
	    site."
    ::= { ex2TopologyEntry 4 }

ex2TransportRulesTable OBJECT-TYPE
    SYNTAX     SEQUENCE OF Ex2TransportRulesEntry
    MAX-ACCESS not-accessible
    STATUS     current
    DESCRIPTION
	    "A table containing performance information for
	    instances of 'MSExchange Transport Rules'
	    objects."
    ::= { exchangeV2 36 }

ex2TransportRulesEntry OBJECT-TYPE
    SYNTAX     Ex2TransportRulesEntry
    MAX-ACCESS not-accessible
    STATUS     current
    DESCRIPTION
	    "Performance information for one particular
	    instance of 'MSExchange Transport Rules'
	    object."
    INDEX      { ex2trInstance }
    ::= { ex2TransportRulesTable 1 }

Ex2TransportRulesEntry ::= SEQUENCE {
    ex2trInstance InstanceName,
    ex2trMessagesEvaluated Gauge32,
    ex2trMessagesEvaluatedPerSec Gauge32,
    ex2trMessagesProcessed Gauge32,
    ex2trMessagesProcessedPerSec Gauge32
}

ex2trInstance OBJECT-TYPE
    SYNTAX     InstanceName
    MAX-ACCESS read-only
    STATUS     current
    DESCRIPTION
	    "Instance name."
    ::= { ex2TransportRulesEntry 1 }

ex2trMessagesEvaluated OBJECT-TYPE
    SYNTAX     Gauge32
    MAX-ACCESS read-only
    STATUS     current
    DESCRIPTION
	    "Messages Evaluated is the number of messages
	    the rule has evaluated."
    ::= { ex2TransportRulesEntry 2 }

ex2trMessagesEvaluatedPerSec OBJECT-TYPE
    SYNTAX     Gauge32
    MAX-ACCESS read-only
    STATUS     current
    DESCRIPTION
	    "Messages Evaluated per second is the number of
	    messages the rule has evaluated per second."
    ::= { ex2TransportRulesEntry 3 }

ex2trMessagesProcessed OBJECT-TYPE
    SYNTAX     Gauge32
    MAX-ACCESS read-only
    STATUS     current
    DESCRIPTION
	    "Messages Processed is the number of messages
	    the rule has processed."
    ::= { ex2TransportRulesEntry 4 }

ex2trMessagesProcessedPerSec OBJECT-TYPE
    SYNTAX     Gauge32
    MAX-ACCESS read-only
    STATUS     current
    DESCRIPTION
	    "Messages Processed per second is the number of
	    messages the rule has processed per second."
    ::= { ex2TransportRulesEntry 5 }

ex2UpdateAgent OBJECT IDENTIFIER
    ::= { exchangeV2 37 }

ex2uaTotalSRLParameterUpdates OBJECT-TYPE
    SYNTAX     Gauge32
    MAX-ACCESS read-only
    STATUS     current
    DESCRIPTION
	    "Number of Total SRL Parameter Updates"
    ::= { ex2UpdateAgent 1 }

ex2uaTotalUpdates OBJECT-TYPE
    SYNTAX     Gauge32
    MAX-ACCESS read-only
    STATUS     current
    DESCRIPTION
	    "Number of Total Updates"
    ::= { ex2UpdateAgent 2 }

ex2WebMailTable OBJECT-TYPE
    SYNTAX     SEQUENCE OF Ex2WebMailEntry
    MAX-ACCESS not-accessible
    STATUS     current
    DESCRIPTION
	    "A table containing performance information for
	    instances of 'MSExchange Web Mail' objects."
    ::= { exchangeV2 38 }

ex2WebMailEntry OBJECT-TYPE
    SYNTAX     Ex2WebMailEntry
    MAX-ACCESS not-accessible
    STATUS     current
    DESCRIPTION
	    "Performance information for one particular
	    instance of 'MSExchange Web Mail' object."
    INDEX      { ex2wmInstance }
    ::= { ex2WebMailTable 1 }

Ex2WebMailEntry ::= SEQUENCE {
    ex2wmInstance InstanceName,
    ex2wmApptmtAcceptPerDeclineTotal Gauge32,
    ex2wmApptmtAcceptPrDeclinePerSec Gauge32,
    ex2wmApptmtAttachmentEditsTotal Gauge32,
    ex2wmApptmtAttachmentEditsPerSec Gauge32,
    ex2wmApptmtDataRetrievesTotal Gauge32,
    ex2wmApptmtDataRetrievesPerSec Gauge32,
    ex2wmApptmtEditRecurrenceTotal Gauge32,
    ex2wmApptmtEditRecurrencePerSec Gauge32,
    ex2wmAppointmentOpensTotal Gauge32,
    ex2wmAppointmentOpensPerSec Gauge32,
    ex2wmApptmtResolveFreeBusyTotal Gauge32,
    ex2wmApptmtResolveFreeBusyPerSec Gauge32,
    ex2wmApptmtSaveRecurrencesTotal Gauge32,
    ex2wmApptmtSaveRecurrencesPerSec Gauge32,
    ex2wmAppointmentSavesTotal Gauge32,
    ex2wmAppointmentSavesPerSec Gauge32,
    ex2wmAppointmentSendsTotal Gauge32,
    ex2wmAppointmentSendsPerSec Gauge32,
    ex2wmAppointmentUpdatesTotal Gauge32,
    ex2wmAppointmentUpdatesPerSec Gauge32,
    ex2wmAttachmentsDeletedTotal Gauge32,
    ex2wmAttachmentsDeletedPerSec Gauge32,
    ex2wmAuthenticationCacheHitTotal Gauge32,
    ex2wmAuthenticationCacheHitPrSec Gauge32,
    ex2wmAuthenticationsInCache Gauge32,
    ex2wmAuthenticationsTotal Gauge32,
    ex2wmAuthenticationsPerSec Gauge32,
    ex2wmFolderCreatesTotal Gauge32,
    ex2wmFolderCreatesPerSec Gauge32,
    ex2wmFolderGetContentsTotal Gauge32,
    ex2wmFolderGetContentsPerSec Gauge32,
    ex2wmFolderGetViewTotal Gauge32,
    ex2wmFolderGetViewPerSec Gauge32,
    ex2wmFolderRenamesTotal Gauge32,
    ex2wmFolderRenamesPerSec Gauge32,
    ex2wmFormsSentTotal Gauge32,
    ex2wmFormsSentPerSec Gauge32,
    ex2wmGetAppFrameTotal Gauge32,
    ex2wmGetAppFramePerSec Gauge32,
    ex2wmGetNavBarTotal Gauge32,
    ex2wmGetNavBarPerSec Gauge32,
    ex2wmMessageAttachmentEditsTotal Gauge32,
    ex2wmMessageAttachmentEditPerSec Gauge32,
    ex2wmMessageMovesPerCopiesTotal Gauge32,
    ex2wmMessageMovesPerCopyPerSec Gauge32,
    ex2wmMessageOpensTotal Gauge32,
    ex2wmMessageOpensPerSec Gauge32,
    ex2wmMessageSavesTotal Gauge32,
    ex2wmMessageSavesPerSec Gauge32,
    ex2wmMessageSendsTotal Gauge32,
    ex2wmMessageSendsPerSec Gauge32,
    ex2wmMsgPerApptmtDeletesTotal Gauge32,
    ex2wmMsgPerApptmtDeletesPerSec Gauge32,
    ex2wmMsgPerAppointmentOpensTotal Gauge32,
    ex2wmMsgPerAppointmentOpenPerSec Gauge32,
    ex2wmMsgPerAppointmentSavesTotal Gauge32,
    ex2wmMsgPerAppointmentSavePerSec Gauge32,
    ex2wmNamesCheckedTotal Gauge32,
    ex2wmNamesCheckedPerSec Gauge32,
    ex2wmNavigationOptionsSavesTotal Gauge32,
    ex2wmNavigationOptionsSavePerSec Gauge32,
    ex2wmNewFolderTemplateDataTotal Gauge32,
    ex2wmNewFolderTemplateDataPerSec Gauge32,
    ex2wmNewItemURLTotal Gauge32,
    ex2wmNewItemURLPerSec Gauge32,
    ex2wmPostsSubmittedTotal Gauge32,
    ex2wmPostsSubmittedPerSec Gauge32,
    ex2wmRecipientsEditedTotal Gauge32,
    ex2wmRecipientsEditedPerSec Gauge32,
    ex2wmRecipientsSavedTotal Gauge32,
    ex2wmRecipientsSavedPerSec Gauge32,
    ex2wmViewsOfCalendarsTotal Gauge32,
    ex2wmViewsOfCalendarsPerSec Gauge32,
    ex2wmViewsOfMailFoldersTotal Gauge32,
    ex2wmViewsOfMailFoldersPerSec Gauge32
}

ex2wmInstance OBJECT-TYPE
    SYNTAX     InstanceName
    MAX-ACCESS read-only
    STATUS     current
    DESCRIPTION
	    "Instance name."
    ::= { ex2WebMailEntry 1 }

ex2wmApptmtAcceptPerDeclineTotal OBJECT-TYPE
    SYNTAX     Gauge32
    MAX-ACCESS read-only
    STATUS     current
    DESCRIPTION
	    "Total number of Appointment accept/decline."
    ::= { ex2WebMailEntry 2 }

ex2wmApptmtAcceptPrDeclinePerSec OBJECT-TYPE
    SYNTAX     Gauge32
    MAX-ACCESS read-only
    STATUS     current
    DESCRIPTION
	    "Rate of Appointment accept/decline per
	    second."
    ::= { ex2WebMailEntry 3 }

ex2wmApptmtAttachmentEditsTotal OBJECT-TYPE
    SYNTAX     Gauge32
    MAX-ACCESS read-only
    STATUS     current
    DESCRIPTION
	    "Total number of Appointment attachment edits."
    ::= { ex2WebMailEntry 4 }

ex2wmApptmtAttachmentEditsPerSec OBJECT-TYPE
    SYNTAX     Gauge32
    MAX-ACCESS read-only
    STATUS     current
    DESCRIPTION
	    "Rate of Appointment attachment edits per
	    second."
    ::= { ex2WebMailEntry 5 }

ex2wmApptmtDataRetrievesTotal OBJECT-TYPE
    SYNTAX     Gauge32
    MAX-ACCESS read-only
    STATUS     current
    DESCRIPTION
	    "Total number of Appointment data retrieves."
    ::= { ex2WebMailEntry 6 }

ex2wmApptmtDataRetrievesPerSec OBJECT-TYPE
    SYNTAX     Gauge32
    MAX-ACCESS read-only
    STATUS     current
    DESCRIPTION
	    "Rate of Appointment data retrieves per
	    second."
    ::= { ex2WebMailEntry 7 }

ex2wmApptmtEditRecurrenceTotal OBJECT-TYPE
    SYNTAX     Gauge32
    MAX-ACCESS read-only
    STATUS     current
    DESCRIPTION
	    "Total number of Appointment edit recurrence."
    ::= { ex2WebMailEntry 8 }

ex2wmApptmtEditRecurrencePerSec OBJECT-TYPE
    SYNTAX     Gauge32
    MAX-ACCESS read-only
    STATUS     current
    DESCRIPTION
	    "Rate of Appointment edit recurrence per
	    second."
    ::= { ex2WebMailEntry 9 }

ex2wmAppointmentOpensTotal OBJECT-TYPE
    SYNTAX     Gauge32
    MAX-ACCESS read-only
    STATUS     current
    DESCRIPTION
	    "Total number of Appointment opens."
    ::= { ex2WebMailEntry 10 }

ex2wmAppointmentOpensPerSec OBJECT-TYPE
    SYNTAX     Gauge32
    MAX-ACCESS read-only
    STATUS     current
    DESCRIPTION
	    "Rate of Appointment opens per second."
    ::= { ex2WebMailEntry 11 }

ex2wmApptmtResolveFreeBusyTotal OBJECT-TYPE
    SYNTAX     Gauge32
    MAX-ACCESS read-only
    STATUS     current
    DESCRIPTION
	    "Total number of Appointment resolve
	    Free-Busy."
    ::= { ex2WebMailEntry 12 }

ex2wmApptmtResolveFreeBusyPerSec OBJECT-TYPE
    SYNTAX     Gauge32
    MAX-ACCESS read-only
    STATUS     current
    DESCRIPTION
	    "Rate of Appointment resolve Free-Busy per
	    second."
    ::= { ex2WebMailEntry 13 }

ex2wmApptmtSaveRecurrencesTotal OBJECT-TYPE
    SYNTAX     Gauge32
    MAX-ACCESS read-only
    STATUS     current
    DESCRIPTION
	    "Total number of Appointment save recurrences."
    ::= { ex2WebMailEntry 14 }

ex2wmApptmtSaveRecurrencesPerSec OBJECT-TYPE
    SYNTAX     Gauge32
    MAX-ACCESS read-only
    STATUS     current
    DESCRIPTION
	    "Rate of Appointment save recurrences per
	    second."
    ::= { ex2WebMailEntry 15 }

ex2wmAppointmentSavesTotal OBJECT-TYPE
    SYNTAX     Gauge32
    MAX-ACCESS read-only
    STATUS     current
    DESCRIPTION
	    "Total number of Appointment saves."
    ::= { ex2WebMailEntry 16 }

ex2wmAppointmentSavesPerSec OBJECT-TYPE
    SYNTAX     Gauge32
    MAX-ACCESS read-only
    STATUS     current
    DESCRIPTION
	    "Rate of Appointment saves per second."
    ::= { ex2WebMailEntry 17 }

ex2wmAppointmentSendsTotal OBJECT-TYPE
    SYNTAX     Gauge32
    MAX-ACCESS read-only
    STATUS     current
    DESCRIPTION
	    "Total number of Appointment sends."
    ::= { ex2WebMailEntry 18 }

ex2wmAppointmentSendsPerSec OBJECT-TYPE
    SYNTAX     Gauge32
    MAX-ACCESS read-only
    STATUS     current
    DESCRIPTION
	    "Rate of Appointment sends per second."
    ::= { ex2WebMailEntry 19 }

ex2wmAppointmentUpdatesTotal OBJECT-TYPE
    SYNTAX     Gauge32
    MAX-ACCESS read-only
    STATUS     current
    DESCRIPTION
	    "Total number of Appointment updates."
    ::= { ex2WebMailEntry 20 }

ex2wmAppointmentUpdatesPerSec OBJECT-TYPE
    SYNTAX     Gauge32
    MAX-ACCESS read-only
    STATUS     current
    DESCRIPTION
	    "Rate of Appointment updates per second."
    ::= { ex2WebMailEntry 21 }

ex2wmAttachmentsDeletedTotal OBJECT-TYPE
    SYNTAX     Gauge32
    MAX-ACCESS read-only
    STATUS     current
    DESCRIPTION
	    "Total number of Attachments deleted."
    ::= { ex2WebMailEntry 22 }

ex2wmAttachmentsDeletedPerSec OBJECT-TYPE
    SYNTAX     Gauge32
    MAX-ACCESS read-only
    STATUS     current
    DESCRIPTION
	    "Rate of Attachments deleted per second."
    ::= { ex2WebMailEntry 23 }

ex2wmAuthenticationCacheHitTotal OBJECT-TYPE
    SYNTAX     Gauge32
    MAX-ACCESS read-only
    STATUS     current
    DESCRIPTION
	    "Total number of Authentication cache hits.
	    This is the number of times that the needed
	    authentication is retrieved from a cache."
    ::= { ex2WebMailEntry 24 }

ex2wmAuthenticationCacheHitPrSec OBJECT-TYPE
    SYNTAX     Gauge32
    MAX-ACCESS read-only
    STATUS     current
    DESCRIPTION
	    "Rate of Authentication cache hits per second.
	    This is the number of times that the needed
	    authentication is retrieved from a cache."
    ::= { ex2WebMailEntry 25 }

ex2wmAuthenticationsInCache OBJECT-TYPE
    SYNTAX     Gauge32
    MAX-ACCESS read-only
    STATUS     current
    DESCRIPTION
	    "Total number of Authentications (in cache).
	    This gives the number of different users who
	    have accessed the Exchange store via DAV in the
	    last few minutes."
    ::= { ex2WebMailEntry 26 }

ex2wmAuthenticationsTotal OBJECT-TYPE
    SYNTAX     Gauge32
    MAX-ACCESS read-only
    STATUS     current
    DESCRIPTION
	    "Total number of Authentications. This is the
	    total number of times authentication is
	    needed."
    ::= { ex2WebMailEntry 27 }

ex2wmAuthenticationsPerSec OBJECT-TYPE
    SYNTAX     Gauge32
    MAX-ACCESS read-only
    STATUS     current
    DESCRIPTION
	    "Rate of Authentications per second. This is
	    the total number of times authentication is
	    needed."
    ::= { ex2WebMailEntry 28 }

ex2wmFolderCreatesTotal OBJECT-TYPE
    SYNTAX     Gauge32
    MAX-ACCESS read-only
    STATUS     current
    DESCRIPTION
	    "Total number of Folder creates*. This action
	    is handled in HTTP-DAV for IE5 browers"
    ::= { ex2WebMailEntry 29 }

ex2wmFolderCreatesPerSec OBJECT-TYPE
    SYNTAX     Gauge32
    MAX-ACCESS read-only
    STATUS     current
    DESCRIPTION
	    "Rate of Folder creates* per second. This
	    action is handled in HTTP-DAV for IE5 browers"
    ::= { ex2WebMailEntry 30 }

ex2wmFolderGetContentsTotal OBJECT-TYPE
    SYNTAX     Gauge32
    MAX-ACCESS read-only
    STATUS     current
    DESCRIPTION
	    "Total number of Folder get contents."
    ::= { ex2WebMailEntry 31 }

ex2wmFolderGetContentsPerSec OBJECT-TYPE
    SYNTAX     Gauge32
    MAX-ACCESS read-only
    STATUS     current
    DESCRIPTION
	    "Rate of Folder get contents per second."
    ::= { ex2WebMailEntry 32 }

ex2wmFolderGetViewTotal OBJECT-TYPE
    SYNTAX     Gauge32
    MAX-ACCESS read-only
    STATUS     current
    DESCRIPTION
	    "Total number of Folder get view*. This is only
	    incremented by IE5 clients.  Changing the view
	    from non-IE5 clients increments 'Folder get
	    contents'."
    ::= { ex2WebMailEntry 33 }

ex2wmFolderGetViewPerSec OBJECT-TYPE
    SYNTAX     Gauge32
    MAX-ACCESS read-only
    STATUS     current
    DESCRIPTION
	    "Rate of Folder get view* per second. This is
	    only incremented by IE5 clients.  Changing the
	    view from non-IE5 clients increments 'Folder
	    get contents'."
    ::= { ex2WebMailEntry 34 }

ex2wmFolderRenamesTotal OBJECT-TYPE
    SYNTAX     Gauge32
    MAX-ACCESS read-only
    STATUS     current
    DESCRIPTION
	    "Total number of Folder renames*. This action
	    is handled in HTTP-DAV for IE5 browers"
    ::= { ex2WebMailEntry 35 }

ex2wmFolderRenamesPerSec OBJECT-TYPE
    SYNTAX     Gauge32
    MAX-ACCESS read-only
    STATUS     current
    DESCRIPTION
	    "Rate of Folder renames* per second. This
	    action is handled in HTTP-DAV for IE5 browers"
    ::= { ex2WebMailEntry 36 }

ex2wmFormsSentTotal OBJECT-TYPE
    SYNTAX     Gauge32
    MAX-ACCESS read-only
    STATUS     current
    DESCRIPTION
	    "Total number of Forms sent."
    ::= { ex2WebMailEntry 37 }

ex2wmFormsSentPerSec OBJECT-TYPE
    SYNTAX     Gauge32
    MAX-ACCESS read-only
    STATUS     current
    DESCRIPTION
	    "Rate of Forms sent per second."
    ::= { ex2WebMailEntry 38 }

ex2wmGetAppFrameTotal OBJECT-TYPE
    SYNTAX     Gauge32
    MAX-ACCESS read-only
    STATUS     current
    DESCRIPTION
	    "Total number of Get app frame."
    ::= { ex2WebMailEntry 39 }

ex2wmGetAppFramePerSec OBJECT-TYPE
    SYNTAX     Gauge32
    MAX-ACCESS read-only
    STATUS     current
    DESCRIPTION
	    "Rate of Get app frame per second."
    ::= { ex2WebMailEntry 40 }

ex2wmGetNavBarTotal OBJECT-TYPE
    SYNTAX     Gauge32
    MAX-ACCESS read-only
    STATUS     current
    DESCRIPTION
	    "Total number of Get nav bar."
    ::= { ex2WebMailEntry 41 }

ex2wmGetNavBarPerSec OBJECT-TYPE
    SYNTAX     Gauge32
    MAX-ACCESS read-only
    STATUS     current
    DESCRIPTION
	    "Rate of Get nav bar per second."
    ::= { ex2WebMailEntry 42 }

ex2wmMessageAttachmentEditsTotal OBJECT-TYPE
    SYNTAX     Gauge32
    MAX-ACCESS read-only
    STATUS     current
    DESCRIPTION
	    "Total number of Message attachment edits."
    ::= { ex2WebMailEntry 43 }

ex2wmMessageAttachmentEditPerSec OBJECT-TYPE
    SYNTAX     Gauge32
    MAX-ACCESS read-only
    STATUS     current
    DESCRIPTION
	    "Rate of Message attachment edits per second."
    ::= { ex2WebMailEntry 44 }

ex2wmMessageMovesPerCopiesTotal OBJECT-TYPE
    SYNTAX     Gauge32
    MAX-ACCESS read-only
    STATUS     current
    DESCRIPTION
	    "Total number of Message moves/copies*. This
	    action is handled in HTTP-DAV for IE5 browers"
    ::= { ex2WebMailEntry 45 }

ex2wmMessageMovesPerCopyPerSec OBJECT-TYPE
    SYNTAX     Gauge32
    MAX-ACCESS read-only
    STATUS     current
    DESCRIPTION
	    "Rate of Message moves/copies* per second. This
	    action is handled in HTTP-DAV for IE5 browers"
    ::= { ex2WebMailEntry 46 }

ex2wmMessageOpensTotal OBJECT-TYPE
    SYNTAX     Gauge32
    MAX-ACCESS read-only
    STATUS     current
    DESCRIPTION
	    "Total number of Message opens."
    ::= { ex2WebMailEntry 47 }

ex2wmMessageOpensPerSec OBJECT-TYPE
    SYNTAX     Gauge32
    MAX-ACCESS read-only
    STATUS     current
    DESCRIPTION
	    "Rate of Message opens per second."
    ::= { ex2WebMailEntry 48 }

ex2wmMessageSavesTotal OBJECT-TYPE
    SYNTAX     Gauge32
    MAX-ACCESS read-only
    STATUS     current
    DESCRIPTION
	    "Total number of Message saves."
    ::= { ex2WebMailEntry 49 }

ex2wmMessageSavesPerSec OBJECT-TYPE
    SYNTAX     Gauge32
    MAX-ACCESS read-only
    STATUS     current
    DESCRIPTION
	    "Rate of Message saves per second."
    ::= { ex2WebMailEntry 50 }

ex2wmMessageSendsTotal OBJECT-TYPE
    SYNTAX     Gauge32
    MAX-ACCESS read-only
    STATUS     current
    DESCRIPTION
	    "Total number of Message sends."
    ::= { ex2WebMailEntry 51 }

ex2wmMessageSendsPerSec OBJECT-TYPE
    SYNTAX     Gauge32
    MAX-ACCESS read-only
    STATUS     current
    DESCRIPTION
	    "Rate of Message sends per second."
    ::= { ex2WebMailEntry 52 }

ex2wmMsgPerApptmtDeletesTotal OBJECT-TYPE
    SYNTAX     Gauge32
    MAX-ACCESS read-only
    STATUS     current
    DESCRIPTION
	    "Total number of Message/Appointment deletes*.
	    This action is handled in HTTP-DAV for IE5
	    browers"
    ::= { ex2WebMailEntry 53 }

ex2wmMsgPerApptmtDeletesPerSec OBJECT-TYPE
    SYNTAX     Gauge32
    MAX-ACCESS read-only
    STATUS     current
    DESCRIPTION
	    "Rate of Message/Appointment deletes* per
	    second. This action is handled in HTTP-DAV for
	    IE5 browers"
    ::= { ex2WebMailEntry 54 }

ex2wmMsgPerAppointmentOpensTotal OBJECT-TYPE
    SYNTAX     Gauge32
    MAX-ACCESS read-only
    STATUS     current
    DESCRIPTION
	    "Total number of Message/Appointment opens."
    ::= { ex2WebMailEntry 55 }

ex2wmMsgPerAppointmentOpenPerSec OBJECT-TYPE
    SYNTAX     Gauge32
    MAX-ACCESS read-only
    STATUS     current
    DESCRIPTION
	    "Rate of Message/Appointment opens per second."
    ::= { ex2WebMailEntry 56 }

ex2wmMsgPerAppointmentSavesTotal OBJECT-TYPE
    SYNTAX     Gauge32
    MAX-ACCESS read-only
    STATUS     current
    DESCRIPTION
	    "Total number of Message/Appointment saves."
    ::= { ex2WebMailEntry 57 }

ex2wmMsgPerAppointmentSavePerSec OBJECT-TYPE
    SYNTAX     Gauge32
    MAX-ACCESS read-only
    STATUS     current
    DESCRIPTION
	    "Rate of Message/Appointment saves per second."
    ::= { ex2WebMailEntry 58 }

ex2wmNamesCheckedTotal OBJECT-TYPE
    SYNTAX     Gauge32
    MAX-ACCESS read-only
    STATUS     current
    DESCRIPTION
	    "Total number of Names checked."
    ::= { ex2WebMailEntry 59 }

ex2wmNamesCheckedPerSec OBJECT-TYPE
    SYNTAX     Gauge32
    MAX-ACCESS read-only
    STATUS     current
    DESCRIPTION
	    "Rate of Names checked per second."
    ::= { ex2WebMailEntry 60 }

ex2wmNavigationOptionsSavesTotal OBJECT-TYPE
    SYNTAX     Gauge32
    MAX-ACCESS read-only
    STATUS     current
    DESCRIPTION
	    "Total number of Navigation options saves.
	    These are the per-user options including Out of
	    Office Assistant, Calander Options and Contact
	    Options."
    ::= { ex2WebMailEntry 61 }

ex2wmNavigationOptionsSavePerSec OBJECT-TYPE
    SYNTAX     Gauge32
    MAX-ACCESS read-only
    STATUS     current
    DESCRIPTION
	    "Rate of Navigation options saves per second.
	    These are the per-user options including Out of
	    Office Assistant, Calander Options and Contact
	    Options."
    ::= { ex2WebMailEntry 62 }

ex2wmNewFolderTemplateDataTotal OBJECT-TYPE
    SYNTAX     Gauge32
    MAX-ACCESS read-only
    STATUS     current
    DESCRIPTION
	    "Total number of New folder template data. This
	    is not incremented by IE5 clients."
    ::= { ex2WebMailEntry 63 }

ex2wmNewFolderTemplateDataPerSec OBJECT-TYPE
    SYNTAX     Gauge32
    MAX-ACCESS read-only
    STATUS     current
    DESCRIPTION
	    "Rate of New folder template data per second.
	    This is not incremented by IE5 clients."
    ::= { ex2WebMailEntry 64 }

ex2wmNewItemURLTotal OBJECT-TYPE
    SYNTAX     Gauge32
    MAX-ACCESS read-only
    STATUS     current
    DESCRIPTION
	    "Total number of New item URL. This is not
	    incremented by IE5 clients."
    ::= { ex2WebMailEntry 65 }

ex2wmNewItemURLPerSec OBJECT-TYPE
    SYNTAX     Gauge32
    MAX-ACCESS read-only
    STATUS     current
    DESCRIPTION
	    "Rate of New item URL per second. This is not
	    incremented by IE5 clients."
    ::= { ex2WebMailEntry 66 }

ex2wmPostsSubmittedTotal OBJECT-TYPE
    SYNTAX     Gauge32
    MAX-ACCESS read-only
    STATUS     current
    DESCRIPTION
	    "Total number of Posts submitted."
    ::= { ex2WebMailEntry 67 }

ex2wmPostsSubmittedPerSec OBJECT-TYPE
    SYNTAX     Gauge32
    MAX-ACCESS read-only
    STATUS     current
    DESCRIPTION
	    "Rate of Posts submitted per second."
    ::= { ex2WebMailEntry 68 }

ex2wmRecipientsEditedTotal OBJECT-TYPE
    SYNTAX     Gauge32
    MAX-ACCESS read-only
    STATUS     current
    DESCRIPTION
	    "Total number of Recipients edited."
    ::= { ex2WebMailEntry 69 }

ex2wmRecipientsEditedPerSec OBJECT-TYPE
    SYNTAX     Gauge32
    MAX-ACCESS read-only
    STATUS     current
    DESCRIPTION
	    "Rate of Recipients edited per second."
    ::= { ex2WebMailEntry 70 }

ex2wmRecipientsSavedTotal OBJECT-TYPE
    SYNTAX     Gauge32
    MAX-ACCESS read-only
    STATUS     current
    DESCRIPTION
	    "Total number of Recipients saved."
    ::= { ex2WebMailEntry 71 }

ex2wmRecipientsSavedPerSec OBJECT-TYPE
    SYNTAX     Gauge32
    MAX-ACCESS read-only
    STATUS     current
    DESCRIPTION
	    "Rate of Recipients saved per second."
    ::= { ex2WebMailEntry 72 }

ex2wmViewsOfCalendarsTotal OBJECT-TYPE
    SYNTAX     Gauge32
    MAX-ACCESS read-only
    STATUS     current
    DESCRIPTION
	    "Total number of Views of Calendars."
    ::= { ex2WebMailEntry 73 }

ex2wmViewsOfCalendarsPerSec OBJECT-TYPE
    SYNTAX     Gauge32
    MAX-ACCESS read-only
    STATUS     current
    DESCRIPTION
	    "Rate of Views of Calendars per second."
    ::= { ex2WebMailEntry 74 }

ex2wmViewsOfMailFoldersTotal OBJECT-TYPE
    SYNTAX     Gauge32
    MAX-ACCESS read-only
    STATUS     current
    DESCRIPTION
	    "Total number of Views of Mail Folders."
    ::= { ex2WebMailEntry 75 }

ex2wmViewsOfMailFoldersPerSec OBJECT-TYPE
    SYNTAX     Gauge32
    MAX-ACCESS read-only
    STATUS     current
    DESCRIPTION
	    "Rate of Views of Mail Folders per second."
    ::= { ex2WebMailEntry 76 }

ex2ALTable OBJECT-TYPE
    SYNTAX     SEQUENCE OF Ex2ALEntry
    MAX-ACCESS not-accessible
    STATUS     current
    DESCRIPTION
	    "A table containing performance information for
	    instances of 'MSExchangeAL' objects."
    ::= { exchangeV2 39 }

ex2ALEntry OBJECT-TYPE
    SYNTAX     Ex2ALEntry
    MAX-ACCESS not-accessible
    STATUS     current
    DESCRIPTION
	    "Performance information for one particular
	    instance of 'MSExchangeAL' object."
    INDEX      { ex2ALInstance }
    ::= { ex2ALTable 1 }

Ex2ALEntry ::= SEQUENCE {
    ex2ALInstance InstanceName,
    ex2ALActiveRPCThreads Gauge32,
    ex2ALLDAPResults Gauge32,
    ex2ALLDAPResultsPerSec Gauge32,
    ex2ALLDAPSearchCalls Gauge32,
    ex2ALLDAPSearchCallsPerSec Gauge32
}

ex2ALInstance OBJECT-TYPE
    SYNTAX     InstanceName
    MAX-ACCESS read-only
    STATUS     current
    DESCRIPTION
	    "Instance name."
    ::= { ex2ALEntry 1 }

ex2ALActiveRPCThreads OBJECT-TYPE
    SYNTAX     Gauge32
    MAX-ACCESS read-only
    STATUS     current
    DESCRIPTION
	    "Active RPC threads"
    ::= { ex2ALEntry 2 }

ex2ALLDAPResults OBJECT-TYPE
    SYNTAX     Gauge32
    MAX-ACCESS read-only
    STATUS     current
    DESCRIPTION
	    "LDAP Results"
    ::= { ex2ALEntry 3 }

ex2ALLDAPResultsPerSec OBJECT-TYPE
    SYNTAX     Gauge32
    MAX-ACCESS read-only
    STATUS     current
    DESCRIPTION
	    "LDAP Results/sec"
    ::= { ex2ALEntry 4 }

ex2ALLDAPSearchCalls OBJECT-TYPE
    SYNTAX     Gauge32
    MAX-ACCESS read-only
    STATUS     current
    DESCRIPTION
	    "LDAP Search calls"
    ::= { ex2ALEntry 5 }

ex2ALLDAPSearchCallsPerSec OBJECT-TYPE
    SYNTAX     Gauge32
    MAX-ACCESS read-only
    STATUS     current
    DESCRIPTION
	    "LDAP Search calls/sec"
    ::= { ex2ALEntry 6 }

ex2Autodiscover OBJECT IDENTIFIER
    ::= { exchangeV2 40 }

ex2adErrorResponses OBJECT-TYPE
    SYNTAX     Gauge32
    MAX-ACCESS read-only
    STATUS     current
    DESCRIPTION
	    "Error responses is the total number of
	    Autodiscover error responses."
    ::= { ex2Autodiscover 1 }

ex2adErrorResponsesPerSec OBJECT-TYPE
    SYNTAX     Gauge32
    MAX-ACCESS read-only
    STATUS     current
    DESCRIPTION
	    "Error Responses/sec is the number of
	    Autodiscover error responses that occur each
	    second."
    ::= { ex2Autodiscover 2 }

ex2adProcessID OBJECT-TYPE
    SYNTAX     Gauge32
    MAX-ACCESS read-only
    STATUS     current
    DESCRIPTION
	    "Process ID is the process ID that is hosting
	    Autodiscover."
    ::= { ex2Autodiscover 3 }

ex2adRequestsPerSec OBJECT-TYPE
    SYNTAX     Gauge32
    MAX-ACCESS read-only
    STATUS     current
    DESCRIPTION
	    "Requests/sec is the number of Autodiscover
	    requests that have been processed each second."
    ::= { ex2Autodiscover 4 }

ex2adTotalRequests OBJECT-TYPE
    SYNTAX     Gauge32
    MAX-ACCESS read-only
    STATUS     current
    DESCRIPTION
	    "Total Requests is the total number of
	    Autodiscover requests that have been
	    processed."
    ::= { ex2Autodiscover 5 }

ex2EdgeSyncJobTable OBJECT-TYPE
    SYNTAX     SEQUENCE OF Ex2EdgeSyncJobEntry
    MAX-ACCESS not-accessible
    STATUS     current
    DESCRIPTION
	    "A table containing performance information for
	    instances of 'MSExchangeEdgeSync Job' objects."
    ::= { exchangeV2 41 }

ex2EdgeSyncJobEntry OBJECT-TYPE
    SYNTAX     Ex2EdgeSyncJobEntry
    MAX-ACCESS not-accessible
    STATUS     current
    DESCRIPTION
	    "Performance information for one particular
	    instance of 'MSExchangeEdgeSync Job' object."
    INDEX      { ex2esjInstance }
    ::= { ex2EdgeSyncJobTable 1 }

Ex2EdgeSyncJobEntry ::= SEQUENCE {
    ex2esjInstance InstanceName,
    ex2esjEdgeObjectsAddedTotal Gauge32,
    ex2esjEdgeObjectsAddedPerSec Gauge32,
    ex2esjEdgeObjectsDeletedTotal Gauge32,
    ex2esjEdgeObjectsDeletedPerSec Gauge32,
    ex2esjEdgeObjectsUpdatedTotal Gauge32,
    ex2esjEdgeObjectsUpdatedPerSec Gauge32,
    ex2esjScanJobCompletSuccessTotal Gauge32,
    ex2esjScanJobFailNotExtLockTotal Gauge32,
    ex2esjScanJobFailDirctErrorTotal Gauge32,
    ex2esjScanJobNotStartNotLockTotl Gauge32,
    ex2esjScanJobsStartedTotal Gauge32,
    ex2esjSourceObjectsScannedTotal Gauge32,
    ex2esjSourceObjectsScannedPerSec Gauge32,
    ex2esjTargetObjectsScannedTotal Gauge32,
    ex2esjTargetObjectsScannedPerSec Gauge32
}

ex2esjInstance OBJECT-TYPE
    SYNTAX     InstanceName
    MAX-ACCESS read-only
    STATUS     current
    DESCRIPTION
	    "Instance name."
    ::= { ex2EdgeSyncJobEntry 1 }

ex2esjEdgeObjectsAddedTotal OBJECT-TYPE
    SYNTAX     Gauge32
    MAX-ACCESS read-only
    STATUS     current
    DESCRIPTION
	    "Edge objects added total is the total number
	    of objects added to Edges by EdgeSync."
    ::= { ex2EdgeSyncJobEntry 2 }

ex2esjEdgeObjectsAddedPerSec OBJECT-TYPE
    SYNTAX     Gauge32
    MAX-ACCESS read-only
    STATUS     current
    DESCRIPTION
	    "Edge objects added/sec is the rate of Edge
	    objects added per second by EdgeSync."
    ::= { ex2EdgeSyncJobEntry 3 }

ex2esjEdgeObjectsDeletedTotal OBJECT-TYPE
    SYNTAX     Gauge32
    MAX-ACCESS read-only
    STATUS     current
    DESCRIPTION
	    "Edge objects deleted total is the total number
	    of objects deleted from Edge Transport servers
	    by EdgeSync."
    ::= { ex2EdgeSyncJobEntry 4 }

ex2esjEdgeObjectsDeletedPerSec OBJECT-TYPE
    SYNTAX     Gauge32
    MAX-ACCESS read-only
    STATUS     current
    DESCRIPTION
	    "Edge objects deleted/sec is the rate of Edge
	    objects deleted per second by EdgeSync."
    ::= { ex2EdgeSyncJobEntry 5 }

ex2esjEdgeObjectsUpdatedTotal OBJECT-TYPE
    SYNTAX     Gauge32
    MAX-ACCESS read-only
    STATUS     current
    DESCRIPTION
	    "Edge objects updated total is the total number
	    of Edge objects updated by EdgeSync."
    ::= { ex2EdgeSyncJobEntry 6 }

ex2esjEdgeObjectsUpdatedPerSec OBJECT-TYPE
    SYNTAX     Gauge32
    MAX-ACCESS read-only
    STATUS     current
    DESCRIPTION
	    "Edge objects updated/sec is the rate of Edge
	    objects updated per second by EdgeSync."
    ::= { ex2EdgeSyncJobEntry 7 }

ex2esjScanJobCompletSuccessTotal OBJECT-TYPE
    SYNTAX     Gauge32
    MAX-ACCESS read-only
    STATUS     current
    DESCRIPTION
	    "Scan jobs completed successfully total is the
	    total number of scan jobs completed
	    successfully by EdgeSync."
    ::= { ex2EdgeSyncJobEntry 8 }

ex2esjScanJobFailNotExtLockTotal OBJECT-TYPE
    SYNTAX     Gauge32
    MAX-ACCESS read-only
    STATUS     current
    DESCRIPTION
	    "Scan jobs failed because could not extend lock
	    total is the total number of EdgeSync scan jobs
	    that failed because EdgeSync could not extend
	    its lease of an Edge Transport server."
    ::= { ex2EdgeSyncJobEntry 9 }

ex2esjScanJobFailDirctErrorTotal OBJECT-TYPE
    SYNTAX     Gauge32
    MAX-ACCESS read-only
    STATUS     current
    DESCRIPTION
	    "Scan jobs failed because of directory error
	    total is the total number of EdgeSync directory
	    errors."
    ::= { ex2EdgeSyncJobEntry 10 }

ex2esjScanJobNotStartNotLockTotl OBJECT-TYPE
    SYNTAX     Gauge32
    MAX-ACCESS read-only
    STATUS     current
    DESCRIPTION
	    "Edge objects deleted total is the total number
	    of EdgeSync scan jobs that were not started
	    because Edge Transport servers could not be
	    locked."
    ::= { ex2EdgeSyncJobEntry 11 }

ex2esjScanJobsStartedTotal OBJECT-TYPE
    SYNTAX     Gauge32
    MAX-ACCESS read-only
    STATUS     current
    DESCRIPTION
	    "Scan jobs started total is the total number of
	    scan jobs started by EdgeSync."
    ::= { ex2EdgeSyncJobEntry 12 }

ex2esjSourceObjectsScannedTotal OBJECT-TYPE
    SYNTAX     Gauge32
    MAX-ACCESS read-only
    STATUS     current
    DESCRIPTION
	    "Source objects scanned total is the total
	    number of Active Directory objects scanned by
	    EdgeSync."
    ::= { ex2EdgeSyncJobEntry 13 }

ex2esjSourceObjectsScannedPerSec OBJECT-TYPE
    SYNTAX     Gauge32
    MAX-ACCESS read-only
    STATUS     current
    DESCRIPTION
	    "Source objects scanned/sec is the rate of
	    Active Directory objects scanned per second by
	    EdgeSync."
    ::= { ex2EdgeSyncJobEntry 14 }

ex2esjTargetObjectsScannedTotal OBJECT-TYPE
    SYNTAX     Gauge32
    MAX-ACCESS read-only
    STATUS     current
    DESCRIPTION
	    "Target objects scanned total is the total
	    number of Edge objects scanned by EdgeSync."
    ::= { ex2EdgeSyncJobEntry 15 }

ex2esjTargetObjectsScannedPerSec OBJECT-TYPE
    SYNTAX     Gauge32
    MAX-ACCESS read-only
    STATUS     current
    DESCRIPTION
	    "Target objects scanned/sec is the rate of Edge
	    objects scanned per second by EdgeSync."
    ::= { ex2EdgeSyncJobEntry 16 }

ex2EdgeSyncTopology OBJECT IDENTIFIER
    ::= { exchangeV2 42 }

ex2estCompletedScansTotal OBJECT-TYPE
    SYNTAX     Gauge32
    MAX-ACCESS read-only
    STATUS     current
    DESCRIPTION
	    "Completed scans total is the total number of
	    topology scans completed by EdgeSync."
    ::= { ex2EdgeSyncTopology 1 }

ex2estEdgeServersLeasedTotal OBJECT-TYPE
    SYNTAX     Gauge32
    MAX-ACCESS read-only
    STATUS     current
    DESCRIPTION
	    "Edge Servers leased total is the total number
	    of Edge Transport servers leased by EdgeSync."
    ::= { ex2EdgeSyncTopology 2 }

ex2estEdgeServersTotal OBJECT-TYPE
    SYNTAX     Gauge32
    MAX-ACCESS read-only
    STATUS     current
    DESCRIPTION
	    "Edge Servers total is the total number of Edge
	    Transport servers found by EdgeSync."
    ::= { ex2EdgeSyncTopology 3 }

ex2estExchangeServersTotal OBJECT-TYPE
    SYNTAX     Gauge32
    MAX-ACCESS read-only
    STATUS     current
    DESCRIPTION
	    "Exchange Servers total is the total number of
	    Exchange Servers found by EdgeSync."
    ::= { ex2EdgeSyncTopology 4 }

ex2estHubTransportServersTotal OBJECT-TYPE
    SYNTAX     Gauge32
    MAX-ACCESS read-only
    STATUS     current
    DESCRIPTION
	    "Hub Transport Servers total is the total
	    number of Hub Transport servers found by
	    EdgeSync."
    ::= { ex2EdgeSyncTopology 5 }

ex2estJobsExecutingTotal OBJECT-TYPE
    SYNTAX     Gauge32
    MAX-ACCESS read-only
    STATUS     current
    DESCRIPTION
	    "Jobs executing total is the total number of
	    EdgeSync jobs currently executing."
    ::= { ex2EdgeSyncTopology 6 }

ex2estJobsSuspendingTotal OBJECT-TYPE
    SYNTAX     Gauge32
    MAX-ACCESS read-only
    STATUS     current
    DESCRIPTION
	    "Jobs suspending total is the total number of
	    EdgeSync jobs suspended."
    ::= { ex2EdgeSyncTopology 7 }

ex2estJobsWaitingTotal OBJECT-TYPE
    SYNTAX     Gauge32
    MAX-ACCESS read-only
    STATUS     current
    DESCRIPTION
	    "Jobs waiting total is the total number of
	    EdgeSync jobs currently waiting."
    ::= { ex2EdgeSyncTopology 8 }

ex2estSyncNowEdgeNotCompletTotal OBJECT-TYPE
    SYNTAX     Gauge32
    MAX-ACCESS read-only
    STATUS     current
    DESCRIPTION
	    "SyncNow Edges not completed total is the total
	    number of Edge Transport servers still pending
	    sync after a start-edgesynchronization
	    operation."
    ::= { ex2EdgeSyncTopology 9 }

ex2estSyncNowStartedTotal OBJECT-TYPE
    SYNTAX     Gauge32
    MAX-ACCESS read-only
    STATUS     current
    DESCRIPTION
	    "SyncNow started total is the total number of
	    Start-EdgeSynchronization tasks that have been
	    executed."
    ::= { ex2EdgeSyncTopology 10 }

ex2FDSOABTable OBJECT-TYPE
    SYNTAX     SEQUENCE OF Ex2FDSOABEntry
    MAX-ACCESS not-accessible
    STATUS     current
    DESCRIPTION
	    "A table containing performance information for
	    instances of 'MSExchangeFDS:OAB' objects."
    ::= { exchangeV2 43 }

ex2FDSOABEntry OBJECT-TYPE
    SYNTAX     Ex2FDSOABEntry
    MAX-ACCESS not-accessible
    STATUS     current
    DESCRIPTION
	    "Performance information for one particular
	    instance of 'MSExchangeFDS:OAB' object."
    INDEX      { ex2FDSOABInstance }
    ::= { ex2FDSOABTable 1 }

Ex2FDSOABEntry ::= SEQUENCE {
    ex2FDSOABInstance InstanceName,
    ex2FDSOABBytesDownloaded Gauge32,
    ex2FDSOABDownloadTaskQueued Gauge32,
    ex2FDSOABDownloadTasksCompleted Gauge32,
    ex2FDSOABTotalBytesToDownload Gauge32
}

ex2FDSOABInstance OBJECT-TYPE
    SYNTAX     InstanceName
    MAX-ACCESS read-only
    STATUS     current
    DESCRIPTION
	    "Instance name."
    ::= { ex2FDSOABEntry 1 }

ex2FDSOABBytesDownloaded OBJECT-TYPE
    SYNTAX     Gauge32
    MAX-ACCESS read-only
    STATUS     current
    DESCRIPTION
	    "Bytes Downloaded is the number of bytes
	    downloaded so far by current task."
    ::= { ex2FDSOABEntry 2 }

ex2FDSOABDownloadTaskQueued OBJECT-TYPE
    SYNTAX     Gauge32
    MAX-ACCESS read-only
    STATUS     current
    DESCRIPTION
	    "Download Task Queued is '1' if task is queued
	    for execution, otherwise '0.'"
    ::= { ex2FDSOABEntry 3 }

ex2FDSOABDownloadTasksCompleted OBJECT-TYPE
    SYNTAX     Gauge32
    MAX-ACCESS read-only
    STATUS     current
    DESCRIPTION
	    "Download Tasks Completed is the number of OAB
	    download tasks completed."
    ::= { ex2FDSOABEntry 4 }

ex2FDSOABTotalBytesToDownload OBJECT-TYPE
    SYNTAX     Gauge32
    MAX-ACCESS read-only
    STATUS     current
    DESCRIPTION
	    "Total Bytes To Download is the total number of
	    bytes to be downloaded by current task."
    ::= { ex2FDSOABEntry 5 }

ex2FDSUMTable OBJECT-TYPE
    SYNTAX     SEQUENCE OF Ex2FDSUMEntry
    MAX-ACCESS not-accessible
    STATUS     current
    DESCRIPTION
	    "A table containing performance information for
	    instances of 'MSExchangeFDS:UM' objects."
    ::= { exchangeV2 44 }

ex2FDSUMEntry OBJECT-TYPE
    SYNTAX     Ex2FDSUMEntry
    MAX-ACCESS not-accessible
    STATUS     current
    DESCRIPTION
	    "Performance information for one particular
	    instance of 'MSExchangeFDS:UM' object."
    INDEX      { ex2FDSUMInstance }
    ::= { ex2FDSUMTable 1 }

Ex2FDSUMEntry ::= SEQUENCE {
    ex2FDSUMInstance InstanceName,
    ex2FDSUMBytesDownloaded Gauge32,
    ex2FDSUMDownloadTaskQueued Gauge32,
    ex2FDSUMDownloadTasksCompleted Gauge32,
    ex2FDSUMTotalBytesToDownload Gauge32
}

ex2FDSUMInstance OBJECT-TYPE
    SYNTAX     InstanceName
    MAX-ACCESS read-only
    STATUS     current
    DESCRIPTION
	    "Instance name."
    ::= { ex2FDSUMEntry 1 }

ex2FDSUMBytesDownloaded OBJECT-TYPE
    SYNTAX     Gauge32
    MAX-ACCESS read-only
    STATUS     current
    DESCRIPTION
	    "Bytes Downloaded is the number of bytes
	    downloaded from the publishing point for the UM
	    dial plan."
    ::= { ex2FDSUMEntry 2 }

ex2FDSUMDownloadTaskQueued OBJECT-TYPE
    SYNTAX     Gauge32
    MAX-ACCESS read-only
    STATUS     current
    DESCRIPTION
	    "Download Task Queued has a value of 1 if a
	    download task is waiting to start running.
	    Otherwise, the value is 0."
    ::= { ex2FDSUMEntry 3 }

ex2FDSUMDownloadTasksCompleted OBJECT-TYPE
    SYNTAX     Gauge32
    MAX-ACCESS read-only
    STATUS     current
    DESCRIPTION
	    "Download Tasks Completed is a count of the
	    number of UM dial plan downloads that have been
	    completed since the service started."
    ::= { ex2FDSUMEntry 4 }

ex2FDSUMTotalBytesToDownload OBJECT-TYPE
    SYNTAX     Gauge32
    MAX-ACCESS read-only
    STATUS     current
    DESCRIPTION
	    "Total Bytes To Download is the total number of
	    bytes to be downloaded by the current task."
    ::= { ex2FDSUMEntry 5 }

ex2InformationStore OBJECT IDENTIFIER
    ::= { exchangeV2 45 }

ex2ISACLUpgradeCompletedUpgrades OBJECT-TYPE
    SYNTAX     Gauge32
    MAX-ACCESS read-only
    STATUS     current
    DESCRIPTION
	    "The total number of ACL upgrades that have
	    fully completed; a fully upgraded folder will
	    not need another ACL upgrade."
    ::= { ex2InformationStore 1 }

ex2ISACLUpgradeFailures OBJECT-TYPE
    SYNTAX     Gauge32
    MAX-ACCESS read-only
    STATUS     current
    DESCRIPTION
	    "The total number of ACL upgrades that have
	    failed; a failure to upgrade a folder leaves
	    the folder with default rights only."
    ::= { ex2InformationStore 2 }

ex2ISACLUpgrdHitACLUpgrdRtryList OBJECT-TYPE
    SYNTAX     Gauge32
    MAX-ACCESS read-only
    STATUS     current
    DESCRIPTION
	    "The total number of ACL upgrades that were not
	    attempted based on the retry list."
    ::= { ex2InformationStore 3 }

ex2ISACLUpgradePartialUpgrades OBJECT-TYPE
    SYNTAX     Gauge32
    MAX-ACCESS read-only
    STATUS     current
    DESCRIPTION
	    "The total number of ACL upgrades that have not
	    fully completed; a partially upgraded folder
	    will still have to go through the ACL upgrade
	    process."
    ::= { ex2InformationStore 4 }

ex2ISACLUpgradeTimesAttempted OBJECT-TYPE
    SYNTAX     Gauge32
    MAX-ACCESS read-only
    STATUS     current
    DESCRIPTION
	    "The total number of ACL upgrades attempted."
    ::= { ex2InformationStore 5 }

ex2ISActiveAnonymousUserCount OBJECT-TYPE
    SYNTAX     Gauge32
    MAX-ACCESS read-only
    STATUS     current
    DESCRIPTION
	    "Number of active users."
    ::= { ex2InformationStore 6 }

ex2ISActiveConnectionCount OBJECT-TYPE
    SYNTAX     Gauge32
    MAX-ACCESS read-only
    STATUS     current
    DESCRIPTION
	    "Number of connections that have shown some
	    activity in the last 10 minutes."
    ::= { ex2InformationStore 7 }

ex2ISActiveUserCount OBJECT-TYPE
    SYNTAX     Gauge32
    MAX-ACCESS read-only
    STATUS     current
    DESCRIPTION
	    "Number of user connections that have shown
	    some activity in the last 10 minutes."
    ::= { ex2InformationStore 8 }

ex2ISAdminRPCRequests OBJECT-TYPE
    SYNTAX     Gauge32
    MAX-ACCESS read-only
    STATUS     current
    DESCRIPTION
	    "Admin RPC Requests is the number of admin
	    requests that are currently being processed by
	    the information store."
    ::= { ex2InformationStore 9 }

ex2ISAdminRPCRequestsPeak OBJECT-TYPE
    SYNTAX     Gauge32
    MAX-ACCESS read-only
    STATUS     current
    DESCRIPTION
	    "Admin RPC Requests Peak is the maximum number
	    of admin requests that were processed
	    simultaneously by the information store since
	    it was started."
    ::= { ex2InformationStore 10 }

ex2ISAnonymousUserCount OBJECT-TYPE
    SYNTAX     Gauge32
    MAX-ACCESS read-only
    STATUS     current
    DESCRIPTION
	    "Anonymous User Count is the number of
	    anonymous users connected to the information
	    store."
    ::= { ex2InformationStore 11 }

ex2ISApptmtInstanceCreationRate OBJECT-TYPE
    SYNTAX     Gauge32
    MAX-ACCESS read-only
    STATUS     current
    DESCRIPTION
	    "Number of appointment instances created/sec"
    ::= { ex2InformationStore 12 }

ex2ISApptmtInstanceDeletionRate OBJECT-TYPE
    SYNTAX     Gauge32
    MAX-ACCESS read-only
    STATUS     current
    DESCRIPTION
	    "Number of appointment instances deleted/sec"
    ::= { ex2InformationStore 13 }

ex2ISAppointmentInstancesCreated OBJECT-TYPE
    SYNTAX     Gauge32
    MAX-ACCESS read-only
    STATUS     current
    DESCRIPTION
	    "Number of appointment instances created"
    ::= { ex2InformationStore 14 }

ex2ISAppointmentInstancesDeleted OBJECT-TYPE
    SYNTAX     Gauge32
    MAX-ACCESS read-only
    STATUS     current
    DESCRIPTION
	    "Number of appointment instances deleted"
    ::= { ex2InformationStore 15 }

ex2ISAsyncNotificationsCacheSize OBJECT-TYPE
    SYNTAX     Gauge32
    MAX-ACCESS read-only
    STATUS     current
    DESCRIPTION
	    "The current size of the Async Notifications
	    Cache."
    ::= { ex2InformationStore 16 }

ex2ISAsyncNotificatGeneratPerSec OBJECT-TYPE
    SYNTAX     Gauge32
    MAX-ACCESS read-only
    STATUS     current
    DESCRIPTION
	    "Async Notifications Generated/sec is the rate
	    at which parked async notifications are being
	    completed."
    ::= { ex2InformationStore 17 }

ex2ISAsyncRPCRequests OBJECT-TYPE
    SYNTAX     Gauge32
    MAX-ACCESS read-only
    STATUS     current
    DESCRIPTION
	    "Async RPC Requests is the number of
	    asynchronous requests that are currently being
	    processed by the information store."
    ::= { ex2InformationStore 18 }

ex2ISAsyncRPCRequestsPeak OBJECT-TYPE
    SYNTAX     Gauge32
    MAX-ACCESS read-only
    STATUS     current
    DESCRIPTION
	    "Async RPC Requests Peak is the maximum number
	    of asynchronous requests that were processed
	    simultaneously by the information store since
	    it was started."
    ::= { ex2InformationStore 19 }

ex2ISBackgroundExpanQueueLength OBJECT-TYPE
    SYNTAX     Gauge32
    MAX-ACCESS read-only
    STATUS     current
    DESCRIPTION
	    "Number of calendars that are queued for
	    background expansion"
    ::= { ex2InformationStore 20 }

ex2ISCIQPThreads OBJECT-TYPE
    SYNTAX     Gauge32
    MAX-ACCESS read-only
    STATUS     current
    DESCRIPTION
	    "Number of Query Processor threads currently
	    running CI queries."
    ::= { ex2InformationStore 21 }

ex2ISClientBackgroundRPCsFailed OBJECT-TYPE
    SYNTAX     Gauge32
    MAX-ACCESS read-only
    STATUS     current
    DESCRIPTION
	    "The client-reported number of failed
	    background RPCs (since the store was started)."
    ::= { ex2InformationStore 22 }

ex2ISClientBackgroundRPCsFailSec OBJECT-TYPE
    SYNTAX     Gauge32
    MAX-ACCESS read-only
    STATUS     current
    DESCRIPTION
	    "The client-reported rate of failed background
	    RPCs (since the store was started)."
    ::= { ex2InformationStore 23 }

ex2ISClientBackgroundRPCsSucceed OBJECT-TYPE
    SYNTAX     Gauge32
    MAX-ACCESS read-only
    STATUS     current
    DESCRIPTION
	    "The client-reported total number of successful
	    background RPCs (since the store was started)."
    ::= { ex2InformationStore 24 }

ex2ISClientBgRPCSucceedPerSec OBJECT-TYPE
    SYNTAX     Gauge32
    MAX-ACCESS read-only
    STATUS     current
    DESCRIPTION
	    "The client-reported rate of successful
	    background RPCs (since the store was started)."
    ::= { ex2InformationStore 25 }

ex2ISClientForegroundRPCsFailed OBJECT-TYPE
    SYNTAX     Gauge32
    MAX-ACCESS read-only
    STATUS     current
    DESCRIPTION
	    "The client-reported number of failed
	    foreground RPCs (since the store was started)."
    ::= { ex2InformationStore 26 }

ex2ISClientFgRPCsFailedPerSec OBJECT-TYPE
    SYNTAX     Gauge32
    MAX-ACCESS read-only
    STATUS     current
    DESCRIPTION
	    "The client-reported rate of failed foreground
	    RPCs (since the store was started)."
    ::= { ex2InformationStore 27 }

ex2ISClientFgRPCsSucceeded OBJECT-TYPE
    SYNTAX     Gauge32
    MAX-ACCESS read-only
    STATUS     current
    DESCRIPTION
	    "The client-reported total number of successful
	    foreground RPCs (since the store was started)."
    ::= { ex2InformationStore 28 }

ex2ISClientFgRPCsSucceededPerSec OBJECT-TYPE
    SYNTAX     Gauge32
    MAX-ACCESS read-only
    STATUS     current
    DESCRIPTION
	    "The client-reported rate of successful
	    foreground RPCs (since the store was started)."
    ::= { ex2InformationStore 29 }

ex2ISClientLatencyGT10SecRPCs OBJECT-TYPE
    SYNTAX     Gauge32
    MAX-ACCESS read-only
    STATUS     current
    DESCRIPTION
	    "The client-reported number of successful RPCs
	    with latencies > 10 seconds."
    ::= { ex2InformationStore 30 }

ex2ISClientLatencyGT2SecRPCs OBJECT-TYPE
    SYNTAX     Gauge32
    MAX-ACCESS read-only
    STATUS     current
    DESCRIPTION
	    "The client-reported number of successful RPCs
	    with latencies > 2 seconds."
    ::= { ex2InformationStore 31 }

ex2ISClientLatencyGT5SecRPCs OBJECT-TYPE
    SYNTAX     Gauge32
    MAX-ACCESS read-only
    STATUS     current
    DESCRIPTION
	    "The client-reported number of successful RPCs
	    with latencies > 5 seconds."
    ::= { ex2InformationStore 32 }

ex2ISClientRPCsFailed OBJECT-TYPE
    SYNTAX     Gauge32
    MAX-ACCESS read-only
    STATUS     current
    DESCRIPTION
	    "The client-reported number of failed RPCs
	    (since the store was started)."
    ::= { ex2InformationStore 33 }

ex2ISClientRPCsFailedPerSec OBJECT-TYPE
    SYNTAX     Gauge32
    MAX-ACCESS read-only
    STATUS     current
    DESCRIPTION
	    "The client-reported rate of failed RPCs (since
	    the store was started)."
    ::= { ex2InformationStore 34 }

ex2ISClientRPCFailedAccessDenied OBJECT-TYPE
    SYNTAX     Gauge32
    MAX-ACCESS read-only
    STATUS     current
    DESCRIPTION
	    "The client-reported number of failed RPCs
	    (since the store was started) due to the Access
	    Denied RPC error."
    ::= { ex2InformationStore 35 }

ex2ISClientRPCFailAccessDenySec OBJECT-TYPE
    SYNTAX     Gauge32
    MAX-ACCESS read-only
    STATUS     current
    DESCRIPTION
	    "The client-reported rate of failed RPCs (since
	    the store was started) due to the Access Denied
	    RPC error."
    ::= { ex2InformationStore 36 }

ex2ISClientRPCFailAllOtherErrors OBJECT-TYPE
    SYNTAX     Gauge32
    MAX-ACCESS read-only
    STATUS     current
    DESCRIPTION
	    "The client-reported number of failed RPCs
	    (since the store was started) due to all other
	    RPC errors."
    ::= { ex2InformationStore 37 }

ex2ISClientRPCFailOtherErrorSec OBJECT-TYPE
    SYNTAX     Gauge32
    MAX-ACCESS read-only
    STATUS     current
    DESCRIPTION
	    "The client-reported rate of failed RPCs (since
	    the store was started) due to all other RPC
	    errors."
    ::= { ex2InformationStore 38 }

ex2ISClientRPCFailCallCancelled OBJECT-TYPE
    SYNTAX     Gauge32
    MAX-ACCESS read-only
    STATUS     current
    DESCRIPTION
	    "The client-reported number of failed RPCs
	    (since the store was started) due to the Call
	    Cancelled RPC error."
    ::= { ex2InformationStore 39 }

ex2ISClientRPCFailCallCancelSec OBJECT-TYPE
    SYNTAX     Gauge32
    MAX-ACCESS read-only
    STATUS     current
    DESCRIPTION
	    "The client-reported rate of failed RPCs (since
	    the store was started) due to the Call
	    Cancelled RPC error."
    ::= { ex2InformationStore 40 }

ex2ISClientRPCsFailedCallFailed OBJECT-TYPE
    SYNTAX     Gauge32
    MAX-ACCESS read-only
    STATUS     current
    DESCRIPTION
	    "The client-reported number of failed RPCs
	    (since the store was started) due to the Call
	    Failed RPC error."
    ::= { ex2InformationStore 41 }

ex2ISClientRPCFailCallFailedSec OBJECT-TYPE
    SYNTAX     Gauge32
    MAX-ACCESS read-only
    STATUS     current
    DESCRIPTION
	    "The client-reported rate of failed RPCs (since
	    the store was started) due to the Call Failed
	    RPC error."
    ::= { ex2InformationStore 42 }

ex2ISClientRPCFailServerTooBusy OBJECT-TYPE
    SYNTAX     Gauge32
    MAX-ACCESS read-only
    STATUS     current
    DESCRIPTION
	    "The client-reported number of failed RPCs
	    (since the store was started) due to the Server
	    Too Busy RPC error."
    ::= { ex2InformationStore 43 }

ex2ISClientRPCFailServerToBsySec OBJECT-TYPE
    SYNTAX     Gauge32
    MAX-ACCESS read-only
    STATUS     current
    DESCRIPTION
	    "The client-reported rate of failed RPCs (since
	    the store was started) due to the Server Too
	    Busy RPC error."
    ::= { ex2InformationStore 44 }

ex2ISClientRPCFailServerUnavail OBJECT-TYPE
    SYNTAX     Gauge32
    MAX-ACCESS read-only
    STATUS     current
    DESCRIPTION
	    "The client-reported number of failed RPCs
	    (since the store was started) due to the Server
	    Unavailable RPC error."
    ::= { ex2InformationStore 45 }

ex2ISClientRPCFailServUnavailSec OBJECT-TYPE
    SYNTAX     Gauge32
    MAX-ACCESS read-only
    STATUS     current
    DESCRIPTION
	    "The client-reported rate of failed RPCs (since
	    the store was started) due to the Server
	    Unavailable RPC error."
    ::= { ex2InformationStore 46 }

ex2ISClientRPCsAttempted OBJECT-TYPE
    SYNTAX     Gauge32
    MAX-ACCESS read-only
    STATUS     current
    DESCRIPTION
	    "The client-reported total number of RPCs
	    attempted by the users (since the store was
	    started)."
    ::= { ex2InformationStore 47 }

ex2ISClientRPCsAttemptedPerSec OBJECT-TYPE
    SYNTAX     Gauge32
    MAX-ACCESS read-only
    STATUS     current
    DESCRIPTION
	    "Client The client-reported rate of RPCs
	    attempted by the users (since the store was
	    started)."
    ::= { ex2InformationStore 48 }

ex2ISClientRPCsSucceeded OBJECT-TYPE
    SYNTAX     Gauge32
    MAX-ACCESS read-only
    STATUS     current
    DESCRIPTION
	    "The client-reported total number of successful
	    RPCs (since the store was started)."
    ::= { ex2InformationStore 49 }

ex2ISClientRPCsSucceededPerSec OBJECT-TYPE
    SYNTAX     Gauge32
    MAX-ACCESS read-only
    STATUS     current
    DESCRIPTION
	    "The client-reported rate of successful RPCs
	    (since the store was started)."
    ::= { ex2InformationStore 50 }

ex2ISClientTotalReportedLatency OBJECT-TYPE
    SYNTAX     Gauge32
    MAX-ACCESS read-only
    STATUS     current
    DESCRIPTION
	    "The client-reported total latency (in seconds)
	    for all RPCs (since the store was started)."
    ::= { ex2InformationStore 51 }

ex2ISConnectionCount OBJECT-TYPE
    SYNTAX     Gauge32
    MAX-ACCESS read-only
    STATUS     current
    DESCRIPTION
	    "Connection Count is the number of client
	    processes connected to the information store."
    ::= { ex2InformationStore 52 }

ex2ISDLMembershipCacheEntryCount OBJECT-TYPE
    SYNTAX     Gauge32
    MAX-ACCESS read-only
    STATUS     current
    DESCRIPTION
	    "Total number of entries stored in the DL
	    membership cache."
    ::= { ex2InformationStore 53 }

ex2ISDLMembershipCacheHits OBJECT-TYPE
    SYNTAX     Gauge32
    MAX-ACCESS read-only
    STATUS     current
    DESCRIPTION
	    "Total number of hits for the DL membership
	    cache."
    ::= { ex2InformationStore 54 }

ex2ISDLMembershipCacheMisses OBJECT-TYPE
    SYNTAX     Gauge32
    MAX-ACCESS read-only
    STATUS     current
    DESCRIPTION
	    "Total number of misses for the DL membership
	    cache."
    ::= { ex2InformationStore 55 }

ex2ISDLMembershipCacheSize OBJECT-TYPE
    SYNTAX     Gauge32
    MAX-ACCESS read-only
    STATUS     current
    DESCRIPTION
	    "Total number of memory bytes consumed by the
	    DL membership cache."
    ::= { ex2InformationStore 56 }

ex2ISExchmemCurrentByteAllocated OBJECT-TYPE
    SYNTAX     Gauge32
    MAX-ACCESS read-only
    STATUS     current
    DESCRIPTION
	    "The current bytes allocated through Exchmem
	    (excluding virtual allocations)."
    ::= { ex2InformationStore 57 }

ex2ISExchmemCurrNumbOfVirtAlloca OBJECT-TYPE
    SYNTAX     Gauge32
    MAX-ACCESS read-only
    STATUS     current
    DESCRIPTION
	    "The current number of Exchmem allocations that
	    were directly allocated from virtual Mem."
    ::= { ex2InformationStore 58 }

ex2ISExchmemCurrVirtByteAllocate OBJECT-TYPE
    SYNTAX     Gauge32
    MAX-ACCESS read-only
    STATUS     current
    DESCRIPTION
	    "The current bytes virtually allocated through
	    Exchmem."
    ::= { ex2InformationStore 59 }

ex2ISExchmemMaximumByteAllocated OBJECT-TYPE
    SYNTAX     Gauge32
    MAX-ACCESS read-only
    STATUS     current
    DESCRIPTION
	    "The maximum concurrent bytes allocated through
	    Exchmem (excluding virtual allocations)."
    ::= { ex2InformationStore 60 }

ex2ISExchmemMaxVirtualBytAllocat OBJECT-TYPE
    SYNTAX     Gauge32
    MAX-ACCESS read-only
    STATUS     current
    DESCRIPTION
	    "The maximum concurrent bytes virtually
	    allocated through Exchmem."
    ::= { ex2InformationStore 61 }

ex2ISExchmemNumAdditionalHeaps OBJECT-TYPE
    SYNTAX     Gauge32
    MAX-ACCESS read-only
    STATUS     current
    DESCRIPTION
	    "The number of Exchmem heaps created by
	    MSExchangeIS after startup."
    ::= { ex2InformationStore 62 }

ex2ISExchmemNumberOfHeaps OBJECT-TYPE
    SYNTAX     Gauge32
    MAX-ACCESS read-only
    STATUS     current
    DESCRIPTION
	    "The total number of Exchmem heaps in use by
	    MSExchangeIS."
    ::= { ex2InformationStore 63 }

ex2ISExchmemNumHeapsMemErrors OBJECT-TYPE
    SYNTAX     Gauge32
    MAX-ACCESS read-only
    STATUS     current
    DESCRIPTION
	    "The total number of Exchmem heaps that failed
	    allocations due to insufficient available Mem."
    ::= { ex2InformationStore 64 }

ex2ISExchmemNumberOfMemoryErrors OBJECT-TYPE
    SYNTAX     Gauge32
    MAX-ACCESS read-only
    STATUS     current
    DESCRIPTION
	    "The total number of Exchmem allocations that
	    could not be satisfied by available memory."
    ::= { ex2InformationStore 65 }

ex2ISExchmemTotalNumVirtAllocate OBJECT-TYPE
    SYNTAX     Gauge32
    MAX-ACCESS read-only
    STATUS     current
    DESCRIPTION
	    "The total number of Exchmem allocations that
	    were directly allocated from virtual Mem."
    ::= { ex2InformationStore 66 }

ex2ISFBPublishCount OBJECT-TYPE
    SYNTAX     Gauge32
    MAX-ACCESS read-only
    STATUS     current
    DESCRIPTION
	    "Number of free-busy publishes"
    ::= { ex2InformationStore 67 }

ex2ISFBPublishRate OBJECT-TYPE
    SYNTAX     Gauge32
    MAX-ACCESS read-only
    STATUS     current
    DESCRIPTION
	    "Number of free-busy publishes/sec"
    ::= { ex2InformationStore 68 }

ex2ISMaximumAnonymousUsers OBJECT-TYPE
    SYNTAX     Gauge32
    MAX-ACCESS read-only
    STATUS     current
    DESCRIPTION
	    "The maximum number of anonymous users since
	    startup."
    ::= { ex2InformationStore 69 }

ex2ISMaximumConnections OBJECT-TYPE
    SYNTAX     Gauge32
    MAX-ACCESS read-only
    STATUS     current
    DESCRIPTION
	    "The maximum number of concurrent connections
	    since startup."
    ::= { ex2InformationStore 70 }

ex2ISMaximumUsers OBJECT-TYPE
    SYNTAX     Gauge32
    MAX-ACCESS read-only
    STATUS     current
    DESCRIPTION
	    "Maximum Users is the maximum number of
	    concurrent users since startup."
    ::= { ex2InformationStore 71 }

ex2ISOABDifferentialDnldAttempts OBJECT-TYPE
    SYNTAX     Gauge32
    MAX-ACCESS read-only
    STATUS     current
    DESCRIPTION
	    "Total number of attempts by clients to
	    download changes to the Offline Address Book."
    ::= { ex2InformationStore 72 }

ex2ISOABDifferentialDnldBytes OBJECT-TYPE
    SYNTAX     Gauge32
    MAX-ACCESS read-only
    STATUS     current
    DESCRIPTION
	    "Total number of bytes sent to clients
	    performing a differential download of the
	    Offline Address Book."
    ::= { ex2InformationStore 73 }

ex2ISOABDifferentialDnldBytesSec OBJECT-TYPE
    SYNTAX     Gauge32
    MAX-ACCESS read-only
    STATUS     current
    DESCRIPTION
	    "Rate at which bytes are being sent to clients
	    performing a differential download of the
	    Offline Address Book."
    ::= { ex2InformationStore 74 }

ex2ISOABFullDownloadAttempts OBJECT-TYPE
    SYNTAX     Gauge32
    MAX-ACCESS read-only
    STATUS     current
    DESCRIPTION
	    "Total number of attempts by clients to
	    download the full Offline Address Book."
    ::= { ex2InformationStore 75 }

ex2ISOABFullDnldAttemptsBlocked OBJECT-TYPE
    SYNTAX     Gauge32
    MAX-ACCESS read-only
    STATUS     current
    DESCRIPTION
	    "Total number of attempts by clients to
	    download the full Offline Address Book blocked
	    due to bandwidth throttling."
    ::= { ex2InformationStore 76 }

ex2ISOABFullDownloadBytes OBJECT-TYPE
    SYNTAX     Gauge32
    MAX-ACCESS read-only
    STATUS     current
    DESCRIPTION
	    "Total number of bytes sent to clients
	    performing a full download of the Offline
	    Address Book."
    ::= { ex2InformationStore 77 }

ex2ISOABFullDownloadBytesPerSec OBJECT-TYPE
    SYNTAX     Gauge32
    MAX-ACCESS read-only
    STATUS     current
    DESCRIPTION
	    "Rate at which bytes are being sent to clients
	    performing a full download of the Offline
	    Address Book."
    ::= { ex2InformationStore 78 }

ex2ISPeakAsyncNotificaCacheSize OBJECT-TYPE
    SYNTAX     Gauge32
    MAX-ACCESS read-only
    STATUS     current
    DESCRIPTION
	    "The maximum size of the Async Notifications
	    Cache."
    ::= { ex2InformationStore 79 }

ex2ISPeakPushNotificatCacheSize OBJECT-TYPE
    SYNTAX     Gauge32
    MAX-ACCESS read-only
    STATUS     current
    DESCRIPTION
	    "The maximum size of the Push Notifications
	    Cache."
    ::= { ex2InformationStore 80 }

ex2ISPushNotificationsCacheSize OBJECT-TYPE
    SYNTAX     Gauge32
    MAX-ACCESS read-only
    STATUS     current
    DESCRIPTION
	    "The current size of the Push Notifications
	    Cache."
    ::= { ex2InformationStore 81 }

ex2ISPushNotificatGeneratePerSec OBJECT-TYPE
    SYNTAX     Gauge32
    MAX-ACCESS read-only
    STATUS     current
    DESCRIPTION
	    "Push Notifications Generated/sec is the rate
	    at which notifications are being sent to
	    clients that have registered for notifications
	    of changes to tables in the information store."
    ::= { ex2InformationStore 82 }

ex2ISPushNotificationsSkipPerSec OBJECT-TYPE
    SYNTAX     Gauge32
    MAX-ACCESS read-only
    STATUS     current
    DESCRIPTION
	    "Push Notifications Skipped/sec is the number
	    of push notifications that have been skipped by
	    caching at the server."
    ::= { ex2InformationStore 83 }

ex2ISRPCAveragedLatency OBJECT-TYPE
    SYNTAX     Gauge32
    MAX-ACCESS read-only
    STATUS     current
    DESCRIPTION
	    "RPC latency in milliseconds averaged for the
	    past 1024 packets."
    ::= { ex2InformationStore 84 }

ex2ISRPCClientBackoffPerSec OBJECT-TYPE
    SYNTAX     Gauge32
    MAX-ACCESS read-only
    STATUS     current
    DESCRIPTION
	    "RPC Client Backoff/sec is the rate that server
	    notifies a client to back off."
    ::= { ex2InformationStore 85 }

ex2ISRPCClientsBytesRead OBJECT-TYPE
    SYNTAX     Gauge32
    MAX-ACCESS read-only
    STATUS     current
    DESCRIPTION
	    "RPC Clients Bytes Read is the total number of
	    bytes read from RPC clients."
    ::= { ex2InformationStore 86 }

ex2ISRPCClientsBytesWritten OBJECT-TYPE
    SYNTAX     Gauge32
    MAX-ACCESS read-only
    STATUS     current
    DESCRIPTION
	    "RPC Clients Bytes Written is the total number
	    of bytes written to RPC clients."
    ::= { ex2InformationStore 87 }

ex2ISRPCClientsUncomprsdByteRead OBJECT-TYPE
    SYNTAX     Gauge32
    MAX-ACCESS read-only
    STATUS     current
    DESCRIPTION
	    "RPC Clients Uncompressed Bytes Read is the
	    total number of bytes read from RPC clients
	    after decompression."
    ::= { ex2InformationStore 88 }

ex2ISRPCClientUncomprsdByteWrite OBJECT-TYPE
    SYNTAX     Gauge32
    MAX-ACCESS read-only
    STATUS     current
    DESCRIPTION
	    "RPC Clients Uncompressed Bytes Written is the
	    total number of bytes written to RPC clients
	    before compression."
    ::= { ex2InformationStore 89 }

ex2ISRPCNumOfSlowPackets OBJECT-TYPE
    SYNTAX     Gauge32
    MAX-ACCESS read-only
    STATUS     current
    DESCRIPTION
	    "Number of RPC packets in the past 1024 that
	    have latencies longer than 2 seconds."
    ::= { ex2InformationStore 90 }

ex2ISRPCOperationsPerSec OBJECT-TYPE
    SYNTAX     Gauge32
    MAX-ACCESS read-only
    STATUS     current
    DESCRIPTION
	    "RPC Operations/sec is the rate that RPC
	    operations occur."
    ::= { ex2InformationStore 91 }

ex2ISRPCPacketsPerSec OBJECT-TYPE
    SYNTAX     Gauge32
    MAX-ACCESS read-only
    STATUS     current
    DESCRIPTION
	    "RPC Packets/sec is the rate that RPC packets
	    are processed."
    ::= { ex2InformationStore 92 }

ex2ISRPCRequests OBJECT-TYPE
    SYNTAX     Gauge32
    MAX-ACCESS read-only
    STATUS     current
    DESCRIPTION
	    "RPC Requests is the number of client requests
	    that are currently being processed by the
	    information store."
    ::= { ex2InformationStore 93 }

ex2ISRPCRequestsPeak OBJECT-TYPE
    SYNTAX     Gauge32
    MAX-ACCESS read-only
    STATUS     current
    DESCRIPTION
	    "RPC Requests Peak is the maximum number of
	    client requests that were processed
	    simultaneously by the information store since
	    it was started."
    ::= { ex2InformationStore 94 }

ex2ISReadBytesRPCClientsPerSec OBJECT-TYPE
    SYNTAX     Gauge32
    MAX-ACCESS read-only
    STATUS     current
    DESCRIPTION
	    "Read Bytes RPC Clients/sec is the rate that
	    bytes are read from RPC clients."
    ::= { ex2InformationStore 95 }

ex2ISRecurringApptmtDeletionRate OBJECT-TYPE
    SYNTAX     Gauge32
    MAX-ACCESS read-only
    STATUS     current
    DESCRIPTION
	    "Number of recurring appoinments deleted/sec"
    ::= { ex2InformationStore 96 }

ex2ISRecurApptmtModificationRate OBJECT-TYPE
    SYNTAX     Gauge32
    MAX-ACCESS read-only
    STATUS     current
    DESCRIPTION
	    "Number of recurring appointments modified/sec"
    ::= { ex2InformationStore 97 }

ex2ISRecurringApptmtsCreated OBJECT-TYPE
    SYNTAX     Gauge32
    MAX-ACCESS read-only
    STATUS     current
    DESCRIPTION
	    "Number of recurring appointments created"
    ::= { ex2InformationStore 98 }

ex2ISRecurringApptmtsDeleted OBJECT-TYPE
    SYNTAX     Gauge32
    MAX-ACCESS read-only
    STATUS     current
    DESCRIPTION
	    "Number of recurring appointments deleted"
    ::= { ex2InformationStore 99 }

ex2ISRecurringApptmtsModified OBJECT-TYPE
    SYNTAX     Gauge32
    MAX-ACCESS read-only
    STATUS     current
    DESCRIPTION
	    "Number of recurring appointments modified"
    ::= { ex2InformationStore 100 }

ex2ISRecurringApptmtCreationRate OBJECT-TYPE
    SYNTAX     Gauge32
    MAX-ACCESS read-only
    STATUS     current
    DESCRIPTION
	    "Number of recurring appointments created/sec"
    ::= { ex2InformationStore 101 }

ex2ISRecurringMstrApptmtExpanded OBJECT-TYPE
    SYNTAX     Gauge32
    MAX-ACCESS read-only
    STATUS     current
    DESCRIPTION
	    "Number of recurring master appointments
	    expanded"
    ::= { ex2InformationStore 102 }

ex2ISRecurringMasterExpansionRat OBJECT-TYPE
    SYNTAX     Gauge32
    MAX-ACCESS read-only
    STATUS     current
    DESCRIPTION
	    "Number of recurring master appointments
	    expanded/sec"
    ::= { ex2InformationStore 103 }

ex2ISSingleApptmtCreationRate OBJECT-TYPE
    SYNTAX     Gauge32
    MAX-ACCESS read-only
    STATUS     current
    DESCRIPTION
	    "Number of single instance appointments
	    created/sec"
    ::= { ex2InformationStore 104 }

ex2ISSingleApptmtDeletionRate OBJECT-TYPE
    SYNTAX     Gauge32
    MAX-ACCESS read-only
    STATUS     current
    DESCRIPTION
	    "Number of single instance appointments
	    deleted/sec"
    ::= { ex2InformationStore 105 }

ex2ISSingleApptmtModificationRat OBJECT-TYPE
    SYNTAX     Gauge32
    MAX-ACCESS read-only
    STATUS     current
    DESCRIPTION
	    "Number of single instance appointments
	    modified/sec"
    ::= { ex2InformationStore 106 }

ex2ISSingleAppointmentsCreated OBJECT-TYPE
    SYNTAX     Gauge32
    MAX-ACCESS read-only
    STATUS     current
    DESCRIPTION
	    "Number of single instance appointments
	    created"
    ::= { ex2InformationStore 107 }

ex2ISSingleAppointmentsDeleted OBJECT-TYPE
    SYNTAX     Gauge32
    MAX-ACCESS read-only
    STATUS     current
    DESCRIPTION
	    "Number of single instance appointments
	    deleted"
    ::= { ex2InformationStore 108 }

ex2ISSingleAppointmentsModified OBJECT-TYPE
    SYNTAX     Gauge32
    MAX-ACCESS read-only
    STATUS     current
    DESCRIPTION
	    "Number of single instance appointments
	    modified"
    ::= { ex2InformationStore 109 }

ex2ISSlowQPThreads OBJECT-TYPE
    SYNTAX     Gauge32
    MAX-ACCESS read-only
    STATUS     current
    DESCRIPTION
	    "Number of Query Processor threads currently
	    running unoptimized queries."
    ::= { ex2InformationStore 110 }

ex2ISSlowSearchThreads OBJECT-TYPE
    SYNTAX     Gauge32
    MAX-ACCESS read-only
    STATUS     current
    DESCRIPTION
	    "Number of Search threads currently running
	    unoptimized queries."
    ::= { ex2InformationStore 111 }

ex2ISTotalParkedAsyncNotifiCalls OBJECT-TYPE
    SYNTAX     Gauge32
    MAX-ACCESS read-only
    STATUS     current
    DESCRIPTION
	    "Total number of parked async notification
	    calls pending in the Information Store."
    ::= { ex2InformationStore 112 }

ex2ISUserCount OBJECT-TYPE
    SYNTAX     Gauge32
    MAX-ACCESS read-only
    STATUS     current
    DESCRIPTION
	    "User Count is the number of users connected to
	    the information store."
    ::= { ex2InformationStore 113 }

ex2ISVMLargestBlockSize OBJECT-TYPE
    SYNTAX     Gauge32
    MAX-ACCESS read-only
    STATUS     current
    DESCRIPTION
	    "Size of the largest free virtual memory
	    block."
    ::= { ex2InformationStore 114 }

ex2ISVMTotal16MBFreeBlocks OBJECT-TYPE
    SYNTAX     Gauge32
    MAX-ACCESS read-only
    STATUS     current
    DESCRIPTION
	    "Total number of free Virtual Memory blocks
	    larger than or equal to 16MB."
    ::= { ex2InformationStore 115 }

ex2ISVMTotalFreeBlocks OBJECT-TYPE
    SYNTAX     Gauge32
    MAX-ACCESS read-only
    STATUS     current
    DESCRIPTION
	    "Total number of free Virtual Memory blocks."
    ::= { ex2InformationStore 116 }

ex2ISVMTotalLargeFreeBlockBytes OBJECT-TYPE
    SYNTAX     Gauge32
    MAX-ACCESS read-only
    STATUS     current
    DESCRIPTION
	    "Total number of bytes in free Virtual Memory
	    blocks larger than or equal to 16MB."
    ::= { ex2InformationStore 117 }

ex2ISVirusScanBytesScanned OBJECT-TYPE
    SYNTAX     Gauge32
    MAX-ACCESS read-only
    STATUS     current
    DESCRIPTION
	    "Total number of bytes in all files processed
	    by virus scanner."
    ::= { ex2InformationStore 118 }

ex2ISVirusScanFilesCleaned OBJECT-TYPE
    SYNTAX     Gauge32
    MAX-ACCESS read-only
    STATUS     current
    DESCRIPTION
	    "Total number of separate files cleaned by
	    virus scanner."
    ::= { ex2InformationStore 119 }

ex2ISVirusScanFilesCleanedPerSec OBJECT-TYPE
    SYNTAX     Gauge32
    MAX-ACCESS read-only
    STATUS     current
    DESCRIPTION
	    "The rate at which separate files are cleaned
	    by virus scanner."
    ::= { ex2InformationStore 120 }

ex2ISVirusScanFilesQuarantined OBJECT-TYPE
    SYNTAX     Gauge32
    MAX-ACCESS read-only
    STATUS     current
    DESCRIPTION
	    "Total number of separate files put into
	    quarantine by virus scanner."
    ::= { ex2InformationStore 121 }

ex2ISVirusScanFileQuarantinePSec OBJECT-TYPE
    SYNTAX     Gauge32
    MAX-ACCESS read-only
    STATUS     current
    DESCRIPTION
	    "The rate at which separate files are put into
	    quarantine by virus scanner."
    ::= { ex2InformationStore 122 }

ex2ISVirusScanFilesScanned OBJECT-TYPE
    SYNTAX     Gauge32
    MAX-ACCESS read-only
    STATUS     current
    DESCRIPTION
	    "Total number of separate files processed by
	    virus scanner."
    ::= { ex2InformationStore 123 }

ex2ISVirusScanFilesScannedPerSec OBJECT-TYPE
    SYNTAX     Gauge32
    MAX-ACCESS read-only
    STATUS     current
    DESCRIPTION
	    "The rate at which separate files are processed
	    by virus scanner."
    ::= { ex2InformationStore 124 }

ex2ISVirusScanFoldersScannedInBg OBJECT-TYPE
    SYNTAX     Gauge32
    MAX-ACCESS read-only
    STATUS     current
    DESCRIPTION
	    "Total number of folders processed by
	    background scanning."
    ::= { ex2InformationStore 125 }

ex2ISVirusScanMessagesCleaned OBJECT-TYPE
    SYNTAX     Gauge32
    MAX-ACCESS read-only
    STATUS     current
    DESCRIPTION
	    "Total number of top-level messages cleaned by
	    virus scanner."
    ::= { ex2InformationStore 126 }

ex2ISVirusScanMsgsCleanedPerSec OBJECT-TYPE
    SYNTAX     Gauge32
    MAX-ACCESS read-only
    STATUS     current
    DESCRIPTION
	    "The rate at which top-level messages are
	    cleaned by virus scanner."
    ::= { ex2InformationStore 127 }

ex2ISVirusScanMessagesDeleted OBJECT-TYPE
    SYNTAX     Gauge32
    MAX-ACCESS read-only
    STATUS     current
    DESCRIPTION
	    "Total number of top-level messages that were
	    deleted upon request of the virus scanner."
    ::= { ex2InformationStore 128 }

ex2ISVirusScanMsgsDeletedPerSec OBJECT-TYPE
    SYNTAX     Gauge32
    MAX-ACCESS read-only
    STATUS     current
    DESCRIPTION
	    "The rate at which top-level messages are being
	    deleted upon request of the virus scanner."
    ::= { ex2InformationStore 129 }

ex2ISVirusScanMessagesProcessed OBJECT-TYPE
    SYNTAX     Gauge32
    MAX-ACCESS read-only
    STATUS     current
    DESCRIPTION
	    "Total number of top-level messages processed
	    by virus scanner."
    ::= { ex2InformationStore 130 }

ex2ISVirusScanMsgProcessedPerSec OBJECT-TYPE
    SYNTAX     Gauge32
    MAX-ACCESS read-only
    STATUS     current
    DESCRIPTION
	    "The rate at which top-level messages are
	    processed by virus scanner."
    ::= { ex2InformationStore 131 }

ex2ISVirusScanMsgsQuarantined OBJECT-TYPE
    SYNTAX     Gauge32
    MAX-ACCESS read-only
    STATUS     current
    DESCRIPTION
	    "Total number of top-level messages put into
	    quarantine by virus scanner."
    ::= { ex2InformationStore 132 }

ex2ISVirusScanMsgQuarantinPerSec OBJECT-TYPE
    SYNTAX     Gauge32
    MAX-ACCESS read-only
    STATUS     current
    DESCRIPTION
	    "The rate at which top-level messages are put
	    into quarantine by virus scanner."
    ::= { ex2InformationStore 133 }

ex2ISVirusScanMsgsScanBackground OBJECT-TYPE
    SYNTAX     Gauge32
    MAX-ACCESS read-only
    STATUS     current
    DESCRIPTION
	    "Total number of messages processed by
	    background scanning."
    ::= { ex2InformationStore 134 }

ex2ISVirusScanQueueLength OBJECT-TYPE
    SYNTAX     Gauge32
    MAX-ACCESS read-only
    STATUS     current
    DESCRIPTION
	    "Current number of outstanding requests that
	    are queued for virus scanning."
    ::= { ex2InformationStore 135 }

ex2ISWriteBytesRPCClientsPerSec OBJECT-TYPE
    SYNTAX     Gauge32
    MAX-ACCESS read-only
    STATUS     current
    DESCRIPTION
	    "Write Bytes RPC Clients/sec is the rate that
	    bytes are written to RPC clients."
    ::= { ex2InformationStore 136 }

ex2ISClientTable OBJECT-TYPE
    SYNTAX     SEQUENCE OF Ex2ISClientEntry
    MAX-ACCESS not-accessible
    STATUS     current
    DESCRIPTION
	    "A table containing performance information for
	    instances of 'MSExchangeIS Client' objects."
    ::= { exchangeV2 46 }

ex2ISClientEntry OBJECT-TYPE
    SYNTAX     Ex2ISClientEntry
    MAX-ACCESS not-accessible
    STATUS     current
    DESCRIPTION
	    "Performance information for one particular
	    instance of 'MSExchangeIS Client' object."
    INDEX      { ex2ISCInstance }
    ::= { ex2ISClientTable 1 }

Ex2ISClientEntry ::= SEQUENCE {
    ex2ISCInstance InstanceName,
    ex2ISCDirAccCacheEntryAddPerSec Gauge32,
    ex2ISCDirAccCacheEntryExpiredSec Gauge32,
    ex2ISCDirAccCacheHitsPercent Gauge32,
    ex2ISCDirAccLDAPReadsPerSec Gauge32,
    ex2ISCDirAccLDAPSearchesPerSec Gauge32,
    ex2ISCJETLogRecordBytesPerSec Gauge32,
    ex2ISCJETLogRecordsPerSec Gauge32,
    ex2ISCJETPagesModifiedPerSec Gauge32,
    ex2ISCJETPagesPrereadPerSec Gauge32,
    ex2ISCJETPagesReadPerSec Gauge32,
    ex2ISCJETPagesReferencedPerSec Gauge32,
    ex2ISCJETPagesRemodifiedPerSec Gauge32,
    ex2ISCRPCAverageLatency Gauge32,
    ex2ISCRPCBytesReceivedPerSec Gauge32,
    ex2ISCRPCBytesSentPerSec Gauge32,
    ex2ISCRPCOperationsPerSec Gauge32,
    ex2ISCRPCPacketsPerSec Gauge32
}

ex2ISCInstance OBJECT-TYPE
    SYNTAX     InstanceName
    MAX-ACCESS read-only
    STATUS     current
    DESCRIPTION
	    "Instance name."
    ::= { ex2ISClientEntry 1 }

ex2ISCDirAccCacheEntryAddPerSec OBJECT-TYPE
    SYNTAX     Gauge32
    MAX-ACCESS read-only
    STATUS     current
    DESCRIPTION
	    "Directory Access: Cache Entries Added/sec is
	    the rate new entries are added to the cache
	    while processing requests for the client."
    ::= { ex2ISClientEntry 2 }

ex2ISCDirAccCacheEntryExpiredSec OBJECT-TYPE
    SYNTAX     Gauge32
    MAX-ACCESS read-only
    STATUS     current
    DESCRIPTION
	    "Directory Access: Cache Entries Expired/sec is
	    the rate entries are expired from the cache
	    while processing requests for the client."
    ::= { ex2ISClientEntry 3 }

ex2ISCDirAccCacheHitsPercent OBJECT-TYPE
    SYNTAX     Gauge32
    MAX-ACCESS read-only
    STATUS     current
    DESCRIPTION
	    "Directory Access: Cache Hits Percent is the
	    percent rate of the LDAP requests which are
	    read from the cache while processing requests
	    for the client."
    ::= { ex2ISClientEntry 4 }

ex2ISCDirAccLDAPReadsPerSec OBJECT-TYPE
    SYNTAX     Gauge32
    MAX-ACCESS read-only
    STATUS     current
    DESCRIPTION
	    "Directory Access: LDAP Reads/sec is the rate
	    LDAP reads occur while processing requests for
	    the client."
    ::= { ex2ISClientEntry 5 }

ex2ISCDirAccLDAPSearchesPerSec OBJECT-TYPE
    SYNTAX     Gauge32
    MAX-ACCESS read-only
    STATUS     current
    DESCRIPTION
	    "Directory Access: LDAP Searches/sec is the
	    rate LDAP searches occur while processing
	    requests for the client."
    ::= { ex2ISClientEntry 6 }

ex2ISCJETLogRecordBytesPerSec OBJECT-TYPE
    SYNTAX     Gauge32
    MAX-ACCESS read-only
    STATUS     current
    DESCRIPTION
	    "JET Log Record Bytes/sec is the rate that
	    database log record bytes are generated while
	    processing requests for the client."
    ::= { ex2ISClientEntry 7 }

ex2ISCJETLogRecordsPerSec OBJECT-TYPE
    SYNTAX     Gauge32
    MAX-ACCESS read-only
    STATUS     current
    DESCRIPTION
	    "JET Log Records/sec is the rate that database
	    log records are generated while processing
	    requests for the client."
    ::= { ex2ISClientEntry 8 }

ex2ISCJETPagesModifiedPerSec OBJECT-TYPE
    SYNTAX     Gauge32
    MAX-ACCESS read-only
    STATUS     current
    DESCRIPTION
	    "JET Pages Modified/sec is the rate that
	    database pages are modified while processing
	    requests for the client."
    ::= { ex2ISClientEntry 9 }

ex2ISCJETPagesPrereadPerSec OBJECT-TYPE
    SYNTAX     Gauge32
    MAX-ACCESS read-only
    STATUS     current
    DESCRIPTION
	    "JET Pages Preread/sec is the rate that
	    database pages are preread from disk while
	    processing requests for the client."
    ::= { ex2ISClientEntry 10 }

ex2ISCJETPagesReadPerSec OBJECT-TYPE
    SYNTAX     Gauge32
    MAX-ACCESS read-only
    STATUS     current
    DESCRIPTION
	    "JET Pages Read/sec is the rate that database
	    pages are read from disk while processing
	    requests for the client."
    ::= { ex2ISClientEntry 11 }

ex2ISCJETPagesReferencedPerSec OBJECT-TYPE
    SYNTAX     Gauge32
    MAX-ACCESS read-only
    STATUS     current
    DESCRIPTION
	    "JET Pages Referenced/sec is the rate that
	    database pages are referenced while processing
	    requests for the client."
    ::= { ex2ISClientEntry 12 }

ex2ISCJETPagesRemodifiedPerSec OBJECT-TYPE
    SYNTAX     Gauge32
    MAX-ACCESS read-only
    STATUS     current
    DESCRIPTION
	    "JET Pages Remodified/sec is the rate that
	    database pages are remodified while processing
	    requests for the client."
    ::= { ex2ISClientEntry 13 }

ex2ISCRPCAverageLatency OBJECT-TYPE
    SYNTAX     Gauge32
    MAX-ACCESS read-only
    STATUS     current
    DESCRIPTION
	    "RPC Average Latency is a server RPC latency in
	    milliseconds averaged for the past 1024
	    packets."
    ::= { ex2ISClientEntry 14 }

ex2ISCRPCBytesReceivedPerSec OBJECT-TYPE
    SYNTAX     Gauge32
    MAX-ACCESS read-only
    STATUS     current
    DESCRIPTION
	    "RPC Bytes Received/sec is the rate that bytes
	    are received from RPC clients."
    ::= { ex2ISClientEntry 15 }

ex2ISCRPCBytesSentPerSec OBJECT-TYPE
    SYNTAX     Gauge32
    MAX-ACCESS read-only
    STATUS     current
    DESCRIPTION
	    "RPC Bytes Sent/sec is the rate that bytes are
	    sent to RPC clients."
    ::= { ex2ISClientEntry 16 }

ex2ISCRPCOperationsPerSec OBJECT-TYPE
    SYNTAX     Gauge32
    MAX-ACCESS read-only
    STATUS     current
    DESCRIPTION
	    "RPC Operations/sec is the rate that RPC
	    operations occur."
    ::= { ex2ISClientEntry 17 }

ex2ISCRPCPacketsPerSec OBJECT-TYPE
    SYNTAX     Gauge32
    MAX-ACCESS read-only
    STATUS     current
    DESCRIPTION
	    "RPC Packets/sec is the rate that RPC packets
	    are processed."
    ::= { ex2ISClientEntry 18 }

ex2ISMailboxTable OBJECT-TYPE
    SYNTAX     SEQUENCE OF Ex2ISMailboxEntry
    MAX-ACCESS not-accessible
    STATUS     current
    DESCRIPTION
	    "A table containing performance information for
	    instances of 'MSExchangeIS Mailbox' objects."
    ::= { exchangeV2 47 }

ex2ISMailboxEntry OBJECT-TYPE
    SYNTAX     Ex2ISMailboxEntry
    MAX-ACCESS not-accessible
    STATUS     current
    DESCRIPTION
	    "Performance information for one particular
	    instance of 'MSExchangeIS Mailbox' object."
    INDEX      { ex2mbInstance }
    ::= { ex2ISMailboxTable 1 }

Ex2ISMailboxEntry ::= SEQUENCE {
    ex2mbInstance InstanceName,
    ex2mbActiveClientLogons Gauge32,
    ex2mbAverageDeliveryTime Gauge32,
    ex2mbCategorizationCount Gauge32,
    ex2mbClientLogons Gauge32,
    ex2mbEventHistoryDeletes Gauge32,
    ex2mbEventHistoryDeletesPerSec Gauge32,
    ex2mbEventHistEventCacheHitsPerc Gauge32,
    ex2mbEventHistoryEventsCount Gauge32,
    ex2mbEventHistEventEmptyConClass Gauge32,
    ex2mbEventHistEventEmptyMsgClass Gauge32,
    ex2mbEventHistEventsTrunConClass Gauge32,
    ex2mbEventHistEventsTrunMsgClass Gauge32,
    ex2mbEventHistoryReads Gauge32,
    ex2mbEventHistoryReadsPerSec Gauge32,
    ex2mbEventHistUncommitTransCount Gauge32,
    ex2mbEventHistoryWatermarksCount Gauge32,
    ex2mbEventHistWatermarksDeletes Gauge32,
    ex2mbEventHistWatermarkDelPerSec Gauge32,
    ex2mbEventHistoryWatermarksReads Gauge32,
    ex2mbEventHistWatermarkReadPrSec Gauge32,
    ex2mbEventHistWatermarksWrites Gauge32,
    ex2mbEventHistWatermarkWritPrSec Gauge32,
    ex2mbEventHistoryWrites Gauge32,
    ex2mbEventHistoryWritesPerSec Gauge32,
    ex2mbFolderOpensPerSec Gauge32,
    ex2mbHTTPPerDAVCurrentPendNotif Gauge32,
    ex2mbHTTPPerDAVCurrentSubscript Gauge32,
    ex2mbHTTPPerDAVCurrentTransLocks Gauge32,
    ex2mbHTTPPerDAVNotifyRequestPSec Gauge32,
    ex2mbHTTPPerDAVTotalLocksCreated Gauge32,
    ex2mbHTTPPerDAVTotalNotifyRequst Gauge32,
    ex2mbHTTPPerDAVTotalSubscCreated Gauge32,
    ex2mbHTTPPerDAVTotalSubscExpired Gauge32,
    ex2mbLocalDeliveries Gauge32,
    ex2mbLocalDeliveryRate Gauge32,
    ex2mbLogonOperationsPerSec Gauge32,
    ex2mbMessageOpensPerSec Gauge32,
    ex2mbMessageRecipientsDelivered Gauge32,
    ex2mbMessageRecipientDelivPerSec Gauge32,
    ex2mbMessagesDelivered Gauge32,
    ex2mbMessagesDeliveredPerSec Gauge32,
    ex2mbMessagesQueuedForSubmission Gauge32,
    ex2mbMessagesSent Gauge32,
    ex2mbMessagesSentPerSec Gauge32,
    ex2mbMessagesSubmitted Gauge32,
    ex2mbMessagesSubmittedPerSec Gauge32,
    ex2mbPeakClientLogons Gauge32,
    ex2mbReceiveQueueSize Gauge32,
    ex2mbReplIDCount Gauge32,
    ex2mbRestrictedViewCacheHitRate Gauge32,
    ex2mbRestrictedViewCacheMissRate Gauge32,
    ex2mbSearchTaskRate Gauge32,
    ex2mbSingleInstanceRatio Gauge32,
    ex2mbSlowFindRowRate Gauge32,
    ex2mbTotalCountOfRecoverableItem Gauge32,
    ex2mbTotalSizeOfRecoverableItems Gauge32,
    ex2mbVirusScanBackgrndScanThread Gauge32,
    ex2mbVirusScanBackgrndMsgScanned Gauge32,
    ex2mbVirusScanBackgrndMsgSkipped Gauge32,
    ex2mbVirusScanBackgrndMsgUpDate Gauge32,
    ex2mbVirusScanExtRsltsAccepted Gauge32,
    ex2mbVirusScanExtRsltNotAccepted Gauge32,
    ex2mbVirusScanExtRsltsNotPresent Gauge32
}

ex2mbInstance OBJECT-TYPE
    SYNTAX     InstanceName
    MAX-ACCESS read-only
    STATUS     current
    DESCRIPTION
	    "Instance name."
    ::= { ex2ISMailboxEntry 1 }

ex2mbActiveClientLogons OBJECT-TYPE
    SYNTAX     Gauge32
    MAX-ACCESS read-only
    STATUS     current
    DESCRIPTION
	    "Active Client Logons is the number of clients
	    that performed any action within the last ten
	    minute time interval."
    ::= { ex2ISMailboxEntry 2 }

ex2mbAverageDeliveryTime OBJECT-TYPE
    SYNTAX     Gauge32
    MAX-ACCESS read-only
    STATUS     current
    DESCRIPTION
	    "Average Delivery Time is the average time in
	    miliseconds between the submission of a message
	    to the mailbox store and the delivery to all
	    local recipients (recipients on the same
	    server) for the last 10 messages."
    ::= { ex2ISMailboxEntry 3 }

ex2mbCategorizationCount OBJECT-TYPE
    SYNTAX     Gauge32
    MAX-ACCESS read-only
    STATUS     current
    DESCRIPTION
	    "Categorization Count is the number of
	    categorizations that exist in the mailbox
	    store. Categorizations are created when a user
	    creates a filtered view or performs a search.
	    When the information store must maintain an
	    excessive number of categorizations,
	    performance can be affected."
    ::= { ex2ISMailboxEntry 4 }

ex2mbClientLogons OBJECT-TYPE
    SYNTAX     Gauge32
    MAX-ACCESS read-only
    STATUS     current
    DESCRIPTION
	    "Client Logons is the number of clients
	    (including system processes) currently logged
	    on."
    ::= { ex2ISMailboxEntry 5 }

ex2mbEventHistoryDeletes OBJECT-TYPE
    SYNTAX     Gauge32
    MAX-ACCESS read-only
    STATUS     current
    DESCRIPTION
	    "Event History: Deletes is the number of events
	    deleted from the event history of the mailbox
	    store since it was started."
    ::= { ex2ISMailboxEntry 6 }

ex2mbEventHistoryDeletesPerSec OBJECT-TYPE
    SYNTAX     Gauge32
    MAX-ACCESS read-only
    STATUS     current
    DESCRIPTION
	    "Event History: Deletes/sec is rate the events
	    are deleted from the event history of the
	    mailbox store."
    ::= { ex2ISMailboxEntry 7 }

ex2mbEventHistEventCacheHitsPerc OBJECT-TYPE
    SYNTAX     Gauge32
    MAX-ACCESS read-only
    STATUS     current
    DESCRIPTION
	    "Event History: Event Cache Hits Percent is the
	    percent rate of the events read from the events
	    history cache in the mailbox store."
    ::= { ex2ISMailboxEntry 8 }

ex2mbEventHistoryEventsCount OBJECT-TYPE
    SYNTAX     Gauge32
    MAX-ACCESS read-only
    STATUS     current
    DESCRIPTION
	    "Event History: Events Count is the approximate
	    number of events stored in the event history of
	    the mailbox store."
    ::= { ex2ISMailboxEntry 9 }

ex2mbEventHistEventEmptyConClass OBJECT-TYPE
    SYNTAX     Gauge32
    MAX-ACCESS read-only
    STATUS     current
    DESCRIPTION
	    "Event History: Events With Empty Container
	    Class is the number of events with no container
	    class generated in the mailbox store since it
	    was started."
    ::= { ex2ISMailboxEntry 10 }

ex2mbEventHistEventEmptyMsgClass OBJECT-TYPE
    SYNTAX     Gauge32
    MAX-ACCESS read-only
    STATUS     current
    DESCRIPTION
	    "Event History: Events With Empty Message Class
	    is the number of events with no message class
	    generated in the mailbox store since it was
	    started."
    ::= { ex2ISMailboxEntry 11 }

ex2mbEventHistEventsTrunConClass OBJECT-TYPE
    SYNTAX     Gauge32
    MAX-ACCESS read-only
    STATUS     current
    DESCRIPTION
	    "Event History: Events With Truncated Container
	    Class is the number of events with truncated
	    container class generated in the mailbox store
	    since it was started."
    ::= { ex2ISMailboxEntry 12 }

ex2mbEventHistEventsTrunMsgClass OBJECT-TYPE
    SYNTAX     Gauge32
    MAX-ACCESS read-only
    STATUS     current
    DESCRIPTION
	    "Event History: Events With Truncated Message
	    Class is the number of events with truncated
	    message class generated in the mailbox store
	    since it was started."
    ::= { ex2ISMailboxEntry 13 }

ex2mbEventHistoryReads OBJECT-TYPE
    SYNTAX     Gauge32
    MAX-ACCESS read-only
    STATUS     current
    DESCRIPTION
	    "Event History: Reads is the number of events
	    read from the event history of the mailbox
	    store since it was started."
    ::= { ex2ISMailboxEntry 14 }

ex2mbEventHistoryReadsPerSec OBJECT-TYPE
    SYNTAX     Gauge32
    MAX-ACCESS read-only
    STATUS     current
    DESCRIPTION
	    "Event History: Reads/sec is rate the events
	    are read from the event history of the mailbox
	    store."
    ::= { ex2ISMailboxEntry 15 }

ex2mbEventHistUncommitTransCount OBJECT-TYPE
    SYNTAX     Gauge32
    MAX-ACCESS read-only
    STATUS     current
    DESCRIPTION
	    "Event History: Uncommitted Transactions Count
	    is the number of uncommmitted transactions in
	    the mailbox store in their top level commit
	    phase and containing at least one event."
    ::= { ex2ISMailboxEntry 16 }

ex2mbEventHistoryWatermarksCount OBJECT-TYPE
    SYNTAX     Gauge32
    MAX-ACCESS read-only
    STATUS     current
    DESCRIPTION
	    "Event History: Watermarks Count is the
	    approximate number of event watermarks stored
	    in the event history of the mailbox store."
    ::= { ex2ISMailboxEntry 17 }

ex2mbEventHistWatermarksDeletes OBJECT-TYPE
    SYNTAX     Gauge32
    MAX-ACCESS read-only
    STATUS     current
    DESCRIPTION
	    "Event History: Watermarks Deletes is the
	    number of event watermarks deleted from the
	    event history of the mailbox store since it was
	    started."
    ::= { ex2ISMailboxEntry 18 }

ex2mbEventHistWatermarkDelPerSec OBJECT-TYPE
    SYNTAX     Gauge32
    MAX-ACCESS read-only
    STATUS     current
    DESCRIPTION
	    "Event History: Watermarks Deletes/sec is rate
	    the event watermarks are deleted from the event
	    history of the mailbox store."
    ::= { ex2ISMailboxEntry 19 }

ex2mbEventHistoryWatermarksReads OBJECT-TYPE
    SYNTAX     Gauge32
    MAX-ACCESS read-only
    STATUS     current
    DESCRIPTION
	    "Event History: Watermarks Reads is the number
	    of event watermarks read from the event history
	    of the mailbox store since it was started."
    ::= { ex2ISMailboxEntry 20 }

ex2mbEventHistWatermarkReadPrSec OBJECT-TYPE
    SYNTAX     Gauge32
    MAX-ACCESS read-only
    STATUS     current
    DESCRIPTION
	    "Event History: Watermarks Reads/sec is rate
	    the event watermarks are read from the event
	    history of the mailbox store."
    ::= { ex2ISMailboxEntry 21 }

ex2mbEventHistWatermarksWrites OBJECT-TYPE
    SYNTAX     Gauge32
    MAX-ACCESS read-only
    STATUS     current
    DESCRIPTION
	    "Event History: Watermarks Writes is the number
	    of event watermarks written to the event
	    history of the mailbox store since it was
	    started."
    ::= { ex2ISMailboxEntry 22 }

ex2mbEventHistWatermarkWritPrSec OBJECT-TYPE
    SYNTAX     Gauge32
    MAX-ACCESS read-only
    STATUS     current
    DESCRIPTION
	    "Event History: Watermarks Writes/sec is rate
	    the event watermarks are written to the event
	    history of the mailbox store."
    ::= { ex2ISMailboxEntry 23 }

ex2mbEventHistoryWrites OBJECT-TYPE
    SYNTAX     Gauge32
    MAX-ACCESS read-only
    STATUS     current
    DESCRIPTION
	    "Event History: Writes is the number of events
	    written to the event history of the mailbox
	    store since it was started."
    ::= { ex2ISMailboxEntry 24 }

ex2mbEventHistoryWritesPerSec OBJECT-TYPE
    SYNTAX     Gauge32
    MAX-ACCESS read-only
    STATUS     current
    DESCRIPTION
	    "Event History: Writes/sec is rate the events
	    are written to the event history of the mailbox
	    store."
    ::= { ex2ISMailboxEntry 25 }

ex2mbFolderOpensPerSec OBJECT-TYPE
    SYNTAX     Gauge32
    MAX-ACCESS read-only
    STATUS     current
    DESCRIPTION
	    "Folder opens/sec is the rate that requests to
	    open folders are submitted to the information
	    store."
    ::= { ex2ISMailboxEntry 26 }

ex2mbHTTPPerDAVCurrentPendNotif OBJECT-TYPE
    SYNTAX     Gauge32
    MAX-ACCESS read-only
    STATUS     current
    DESCRIPTION
	    "Number of notifications happened that are
	    pending (i.e. to be polled)."
    ::= { ex2ISMailboxEntry 27 }

ex2mbHTTPPerDAVCurrentSubscript OBJECT-TYPE
    SYNTAX     Gauge32
    MAX-ACCESS read-only
    STATUS     current
    DESCRIPTION
	    "The number of subscriptions currently active
	    in response to HTTP SUBSCRIBE requests."
    ::= { ex2ISMailboxEntry 28 }

ex2mbHTTPPerDAVCurrentTransLocks OBJECT-TYPE
    SYNTAX     Gauge32
    MAX-ACCESS read-only
    STATUS     current
    DESCRIPTION
	    "The number of DAV transaction locks currently
	    active."
    ::= { ex2ISMailboxEntry 29 }

ex2mbHTTPPerDAVNotifyRequestPSec OBJECT-TYPE
    SYNTAX     Gauge32
    MAX-ACCESS read-only
    STATUS     current
    DESCRIPTION
	    "The rate at which the server sends HTTP NOTIFY
	    requests."
    ::= { ex2ISMailboxEntry 30 }

ex2mbHTTPPerDAVTotalLocksCreated OBJECT-TYPE
    SYNTAX     Gauge32
    MAX-ACCESS read-only
    STATUS     current
    DESCRIPTION
	    "The number locks granted by the server in
	    response to HTTP LOCK requests since service
	    startup."
    ::= { ex2ISMailboxEntry 31 }

ex2mbHTTPPerDAVTotalNotifyRequst OBJECT-TYPE
    SYNTAX     Gauge32
    MAX-ACCESS read-only
    STATUS     current
    DESCRIPTION
	    "The number of HTTP NOTIFY requests sent by the
	    server since service startup."
    ::= { ex2ISMailboxEntry 32 }

ex2mbHTTPPerDAVTotalSubscCreated OBJECT-TYPE
    SYNTAX     Gauge32
    MAX-ACCESS read-only
    STATUS     current
    DESCRIPTION
	    "The number of subscriptions granted by the
	    server in response to HTTP SUBSCRIBE requests
	    since service startup."
    ::= { ex2ISMailboxEntry 33 }

ex2mbHTTPPerDAVTotalSubscExpired OBJECT-TYPE
    SYNTAX     Gauge32
    MAX-ACCESS read-only
    STATUS     current
    DESCRIPTION
	    "The number of subscriptions granted by the
	    server in response to HTTP SUBSCRIBE requests
	    that have expired since service startup."
    ::= { ex2ISMailboxEntry 34 }

ex2mbLocalDeliveries OBJECT-TYPE
    SYNTAX     Gauge32
    MAX-ACCESS read-only
    STATUS     current
    DESCRIPTION
	    "Total number of messages delivered locally"
    ::= { ex2ISMailboxEntry 35 }

ex2mbLocalDeliveryRate OBJECT-TYPE
    SYNTAX     Gauge32
    MAX-ACCESS read-only
    STATUS     current
    DESCRIPTION
	    "Rate at which messages are delivered locally"
    ::= { ex2ISMailboxEntry 36 }

ex2mbLogonOperationsPerSec OBJECT-TYPE
    SYNTAX     Gauge32
    MAX-ACCESS read-only
    STATUS     current
    DESCRIPTION
	    "Logon Operations/sec is the rate of Logon
	    requests in the mailbox store."
    ::= { ex2ISMailboxEntry 37 }

ex2mbMessageOpensPerSec OBJECT-TYPE
    SYNTAX     Gauge32
    MAX-ACCESS read-only
    STATUS     current
    DESCRIPTION
	    "Message Opens/sec is the rate that requests to
	    open messages are submitted to the information
	    store."
    ::= { ex2ISMailboxEntry 38 }

ex2mbMessageRecipientsDelivered OBJECT-TYPE
    SYNTAX     Gauge32
    MAX-ACCESS read-only
    STATUS     current
    DESCRIPTION
	    "Message Recipients Delivered is the total
	    number of recipients that have received a
	    message since startup."
    ::= { ex2ISMailboxEntry 39 }

ex2mbMessageRecipientDelivPerSec OBJECT-TYPE
    SYNTAX     Gauge32
    MAX-ACCESS read-only
    STATUS     current
    DESCRIPTION
	    "Message Recipients Delivered/sec is the rate
	    that recipients receive messages."
    ::= { ex2ISMailboxEntry 40 }

ex2mbMessagesDelivered OBJECT-TYPE
    SYNTAX     Gauge32
    MAX-ACCESS read-only
    STATUS     current
    DESCRIPTION
	    "Messages Delivered is the total number of
	    messages delivered to all recipients since
	    startup."
    ::= { ex2ISMailboxEntry 41 }

ex2mbMessagesDeliveredPerSec OBJECT-TYPE
    SYNTAX     Gauge32
    MAX-ACCESS read-only
    STATUS     current
    DESCRIPTION
	    "Messages Delivered/sec is the rate that
	    messages are delivered to all recipients."
    ::= { ex2ISMailboxEntry 42 }

ex2mbMessagesQueuedForSubmission OBJECT-TYPE
    SYNTAX     Gauge32
    MAX-ACCESS read-only
    STATUS     current
    DESCRIPTION
	    "Messages Queued For Submission is the current
	    number of submitted messages which are not yet
	    processed by transport."
    ::= { ex2ISMailboxEntry 43 }

ex2mbMessagesSent OBJECT-TYPE
    SYNTAX     Gauge32
    MAX-ACCESS read-only
    STATUS     current
    DESCRIPTION
	    "Messages Sent is the total number of messages
	    sent to the transport since startup."
    ::= { ex2ISMailboxEntry 44 }

ex2mbMessagesSentPerSec OBJECT-TYPE
    SYNTAX     Gauge32
    MAX-ACCESS read-only
    STATUS     current
    DESCRIPTION
	    "Messages Sent/sec is the rate that messages
	    are sent to the transport."
    ::= { ex2ISMailboxEntry 45 }

ex2mbMessagesSubmitted OBJECT-TYPE
    SYNTAX     Gauge32
    MAX-ACCESS read-only
    STATUS     current
    DESCRIPTION
	    "Messages Submitted is the total number of
	    messages submitted by clients since service
	    startup."
    ::= { ex2ISMailboxEntry 46 }

ex2mbMessagesSubmittedPerSec OBJECT-TYPE
    SYNTAX     Gauge32
    MAX-ACCESS read-only
    STATUS     current
    DESCRIPTION
	    "Messages Submitted/sec is the rate that
	    messages are submitted by clients."
    ::= { ex2ISMailboxEntry 47 }

ex2mbPeakClientLogons OBJECT-TYPE
    SYNTAX     Gauge32
    MAX-ACCESS read-only
    STATUS     current
    DESCRIPTION
	    "Peak Client Logons is the maximum number of
	    concurrent client logons since the service
	    started."
    ::= { ex2ISMailboxEntry 48 }

ex2mbReceiveQueueSize OBJECT-TYPE
    SYNTAX     Gauge32
    MAX-ACCESS read-only
    STATUS     current
    DESCRIPTION
	    "Receive Queue Size is the number of messages
	    in the mailbox store's receive queue."
    ::= { ex2ISMailboxEntry 49 }

ex2mbReplIDCount OBJECT-TYPE
    SYNTAX     Gauge32
    MAX-ACCESS read-only
    STATUS     current
    DESCRIPTION
	    "ReplID Count (replication ID count) is the
	    number of ReplID-to-GUID mappings in the
	    mailbox database or public folder database."
    ::= { ex2ISMailboxEntry 50 }

ex2mbRestrictedViewCacheHitRate OBJECT-TYPE
    SYNTAX     Gauge32
    MAX-ACCESS read-only
    STATUS     current
    DESCRIPTION
	    "Restricted View Cache Hit Rate is the rate at
	    which restricted views are reused in the
	    mailbox store."
    ::= { ex2ISMailboxEntry 51 }

ex2mbRestrictedViewCacheMissRate OBJECT-TYPE
    SYNTAX     Gauge32
    MAX-ACCESS read-only
    STATUS     current
    DESCRIPTION
	    "Restricted View Cache Miss Rate is the rate at
	    which restricted views are created in the
	    mailbox store."
    ::= { ex2ISMailboxEntry 52 }

ex2mbSearchTaskRate OBJECT-TYPE
    SYNTAX     Gauge32
    MAX-ACCESS read-only
    STATUS     current
    DESCRIPTION
	    "Number of search tasks created per second."
    ::= { ex2ISMailboxEntry 53 }

ex2mbSingleInstanceRatio OBJECT-TYPE
    SYNTAX     Gauge32
    MAX-ACCESS read-only
    STATUS     current
    DESCRIPTION
	    "Single Instance Ratio is the average number of
	    references to each message in the mailbox
	    store."
    ::= { ex2ISMailboxEntry 54 }

ex2mbSlowFindRowRate OBJECT-TYPE
    SYNTAX     Gauge32
    MAX-ACCESS read-only
    STATUS     current
    DESCRIPTION
	    "Slow FindRow Rate is the rate at which the
	    slower FindRow needs to be used in the mailbox
	    store."
    ::= { ex2ISMailboxEntry 55 }

ex2mbTotalCountOfRecoverableItem OBJECT-TYPE
    SYNTAX     Gauge32
    MAX-ACCESS read-only
    STATUS     current
    DESCRIPTION
	    "Total Count of Recoverable Items is the total
	    number of items retained for Item Recovery"
    ::= { ex2ISMailboxEntry 56 }

ex2mbTotalSizeOfRecoverableItems OBJECT-TYPE
    SYNTAX     Gauge32
    MAX-ACCESS read-only
    STATUS     current
    DESCRIPTION
	    "Total Size of Recoverable Items is the total
	    size in kilobytes of items retained for Item
	    Recovery"
    ::= { ex2ISMailboxEntry 57 }

ex2mbVirusScanBackgrndScanThread OBJECT-TYPE
    SYNTAX     Gauge32
    MAX-ACCESS read-only
    STATUS     current
    DESCRIPTION
	    "Number of threads currently running background
	    scanning."
    ::= { ex2ISMailboxEntry 58 }

ex2mbVirusScanBackgrndMsgScanned OBJECT-TYPE
    SYNTAX     Gauge32
    MAX-ACCESS read-only
    STATUS     current
    DESCRIPTION
	    "Total number of messages scanned during
	    background scanning."
    ::= { ex2ISMailboxEntry 59 }

ex2mbVirusScanBackgrndMsgSkipped OBJECT-TYPE
    SYNTAX     Gauge32
    MAX-ACCESS read-only
    STATUS     current
    DESCRIPTION
	    "Total number of messages skipped during
	    background scanning."
    ::= { ex2ISMailboxEntry 60 }

ex2mbVirusScanBackgrndMsgUpDate OBJECT-TYPE
    SYNTAX     Gauge32
    MAX-ACCESS read-only
    STATUS     current
    DESCRIPTION
	    "Total number of messages with up-to-date virus
	    results during background scanning."
    ::= { ex2ISMailboxEntry 61 }

ex2mbVirusScanExtRsltsAccepted OBJECT-TYPE
    SYNTAX     Gauge32
    MAX-ACCESS read-only
    STATUS     current
    DESCRIPTION
	    "Number of messages delivered with external
	    virus scanning results that can be preserved."
    ::= { ex2ISMailboxEntry 62 }

ex2mbVirusScanExtRsltNotAccepted OBJECT-TYPE
    SYNTAX     Gauge32
    MAX-ACCESS read-only
    STATUS     current
    DESCRIPTION
	    "Number of messages delivered with external
	    virus scanning results that cannot be
	    preserved."
    ::= { ex2ISMailboxEntry 63 }

ex2mbVirusScanExtRsltsNotPresent OBJECT-TYPE
    SYNTAX     Gauge32
    MAX-ACCESS read-only
    STATUS     current
    DESCRIPTION
	    "Number of messages delivered without external
	    virus scanning results."
    ::= { ex2ISMailboxEntry 64 }

ex2ISPublicTable OBJECT-TYPE
    SYNTAX     SEQUENCE OF Ex2ISPublicEntry
    MAX-ACCESS not-accessible
    STATUS     current
    DESCRIPTION
	    "A table containing performance information for
	    instances of 'MSExchangeIS Public' objects."
    ::= { exchangeV2 48 }

ex2ISPublicEntry OBJECT-TYPE
    SYNTAX     Ex2ISPublicEntry
    MAX-ACCESS not-accessible
    STATUS     current
    DESCRIPTION
	    "Performance information for one particular
	    instance of 'MSExchangeIS Public' object."
    INDEX      { ex2ispInstance }
    ::= { ex2ISPublicTable 1 }

Ex2ISPublicEntry ::= SEQUENCE {
    ex2ispInstance InstanceName,
    ex2ispActiveClientLogons Gauge32,
    ex2ispAverageDeliveryTime Gauge32,
    ex2ispCategorizationCount Gauge32,
    ex2ispClientLogons Gauge32,
    ex2ispEventHistoryDeletes Gauge32,
    ex2ispEventHistoryDeletesPerSec Gauge32,
    ex2ispEventHistEventCacheHitPerc Gauge32,
    ex2ispEventHistoryEventsCount Gauge32,
    ex2ispEventHistEvntEmptyCntClass Gauge32,
    ex2ispEventHisEventEmptyMsgClass Gauge32,
    ex2ispEventHistEventTrunConClass Gauge32,
    ex2ispEventHistEventTrunMsgClass Gauge32,
    ex2ispEventHistoryReads Gauge32,
    ex2ispEventHistoryReadsPerSec Gauge32,
    ex2ispEventHistUncommitTranCount Gauge32,
    ex2ispEventHistWatermarksCount Gauge32,
    ex2ispEventHistWatermarksDeletes Gauge32,
    ex2ispEventHistWatermarkDelPrSec Gauge32,
    ex2ispEventHistWatermarksReads Gauge32,
    ex2ispEventHistWatermarkRdPerSec Gauge32,
    ex2ispEventHistWatermarksWrites Gauge32,
    ex2ispEventHistWatermarkWriteSec Gauge32,
    ex2ispEventHistoryWrites Gauge32,
    ex2ispEventHistoryWritesPerSec Gauge32,
    ex2ispFolderOpensPerSec Gauge32,
    ex2ispHTTPPerDAVCurrentPendNotif Gauge32,
    ex2ispHTTPPerDAVCurrentSubscript Gauge32,
    ex2ispHTTPPerDAVCurrentTransLock Gauge32,
    ex2ispHTTPPerDAVNotifyReqPerSec Gauge32,
    ex2ispHTTPPerDAVTotalLockCreated Gauge32,
    ex2ispHTTPPerDAVTotalNotifyReqst Gauge32,
    ex2ispHTTPPerDAVTotalSubsCreated Gauge32,
    ex2ispHTTPPerDAVTotalSubsExpired Gauge32,
    ex2ispLogonOperationsPerSec Gauge32,
    ex2ispMessageOpensPerSec Gauge32,
    ex2ispMessageRecipientsDelivered Gauge32,
    ex2ispMsgRecipientsDeliverPerSec Gauge32,
    ex2ispMessagesDelivered Gauge32,
    ex2ispMessagesDeliveredPerSec Gauge32,
    ex2ispMsgsQueuedForSubmission Gauge32,
    ex2ispMessagesSent Gauge32,
    ex2ispMessagesSentPerSec Gauge32,
    ex2ispMessagesSubmitted Gauge32,
    ex2ispMessagesSubmittedPerSec Gauge32,
    ex2ispNumMsgsExpireFrmPublicFold Gauge32,
    ex2ispPeakClientLogons Gauge32,
    ex2ispReceiveQueueSize Gauge32,
    ex2ispReplIDCount Gauge32,
    ex2ispReplicBackfillDataMsgsRecv Gauge32,
    ex2ispReplicBackfillDataMsgsSent Gauge32,
    ex2ispReplicBackfillRequestRecvd Gauge32,
    ex2ispReplicBackfillRequestsSent Gauge32,
    ex2ispReplicFolderChangeReceived Gauge32,
    ex2ispReplicFolderChangesSent Gauge32,
    ex2ispReplicFolderDataMsgReceive Gauge32,
    ex2ispReplicFolderDataMsgsSent Gauge32,
    ex2ispReplicFolderTreeMsgReceive Gauge32,
    ex2ispReplicFolderTreeMsgsSent Gauge32,
    ex2ispReplicMessageChangeReceive Gauge32,
    ex2ispReplicMessageChangesSent Gauge32,
    ex2ispReplicMsgsReceived Gauge32,
    ex2ispReplicationMessagesSent Gauge32,
    ex2ispReplicReceiveQueueSize Gauge32,
    ex2ispReplicStatusMsgsReceived Gauge32,
    ex2ispReplicStatusMsgsSent Gauge32,
    ex2ispRestrictedViewCacheHitRate Gauge32,
    ex2ispRestricteViewCacheMissRate Gauge32,
    ex2ispSearchTaskRate Gauge32,
    ex2ispSingleInstanceRatio Gauge32,
    ex2ispSlowFindRowRate Gauge32,
    ex2ispTotalCountRecoverableItems Gauge32,
    ex2ispTotalSizeOfRecoverableItem Gauge32,
    ex2ispVirusScanBackgrndScnThread Gauge32,
    ex2ispVirusScanBackgrndMsgsScan Gauge32,
    ex2ispVirusScanBackgrndMsgSkippd Gauge32,
    ex2ispVirusScanBackgrndMsgUpDate Gauge32,
    ex2ispVirusScanExtResultAccepted Gauge32,
    ex2ispVirusScanExtResultNotAccpt Gauge32,
    ex2ispVirusScanExtResultsNotPres Gauge32
}

ex2ispInstance OBJECT-TYPE
    SYNTAX     InstanceName
    MAX-ACCESS read-only
    STATUS     current
    DESCRIPTION
	    "Instance name."
    ::= { ex2ISPublicEntry 1 }

ex2ispActiveClientLogons OBJECT-TYPE
    SYNTAX     Gauge32
    MAX-ACCESS read-only
    STATUS     current
    DESCRIPTION
	    "Active Client Logons is the number of clients
	    that performed any action within the last ten
	    minute time interval."
    ::= { ex2ISPublicEntry 2 }

ex2ispAverageDeliveryTime OBJECT-TYPE
    SYNTAX     Gauge32
    MAX-ACCESS read-only
    STATUS     current
    DESCRIPTION
	    "Average Delivery Time is the average time in
	    miliseconds between the submission of a message
	    to the public store and the delivery to all
	    local recipients (recipients on the same
	    server) for the last 10 messages."
    ::= { ex2ISPublicEntry 3 }

ex2ispCategorizationCount OBJECT-TYPE
    SYNTAX     Gauge32
    MAX-ACCESS read-only
    STATUS     current
    DESCRIPTION
	    "Categorization Count is the number of
	    categorizations that exist in the public store.
	    Categorizations are created when a user creates
	    a filtered view or performs a search. When the
	    information store must maintain an excessive
	    number of categorizations, performance can be
	    affected."
    ::= { ex2ISPublicEntry 4 }

ex2ispClientLogons OBJECT-TYPE
    SYNTAX     Gauge32
    MAX-ACCESS read-only
    STATUS     current
    DESCRIPTION
	    "Client Logons is the number of clients
	    (including system processes) currently logged
	    on."
    ::= { ex2ISPublicEntry 5 }

ex2ispEventHistoryDeletes OBJECT-TYPE
    SYNTAX     Gauge32
    MAX-ACCESS read-only
    STATUS     current
    DESCRIPTION
	    "Event History: Deletes is the number of events
	    deleted from the event history of the public
	    store since it was started."
    ::= { ex2ISPublicEntry 6 }

ex2ispEventHistoryDeletesPerSec OBJECT-TYPE
    SYNTAX     Gauge32
    MAX-ACCESS read-only
    STATUS     current
    DESCRIPTION
	    "Event History: Deletes/sec is rate the events
	    are deleted from the event history of the
	    public store."
    ::= { ex2ISPublicEntry 7 }

ex2ispEventHistEventCacheHitPerc OBJECT-TYPE
    SYNTAX     Gauge32
    MAX-ACCESS read-only
    STATUS     current
    DESCRIPTION
	    "Event History: Event Cache Hits Percent is the
	    percent rate of the events read from the events
	    history cache in the public store."
    ::= { ex2ISPublicEntry 8 }

ex2ispEventHistoryEventsCount OBJECT-TYPE
    SYNTAX     Gauge32
    MAX-ACCESS read-only
    STATUS     current
    DESCRIPTION
	    "Event History: Events Count is the approximate
	    number of events stored in the event history of
	    the public store."
    ::= { ex2ISPublicEntry 9 }

ex2ispEventHistEvntEmptyCntClass OBJECT-TYPE
    SYNTAX     Gauge32
    MAX-ACCESS read-only
    STATUS     current
    DESCRIPTION
	    "Event History: Events With Empty Container
	    Class is the number of events with no container
	    class generated in the public store since it
	    was started."
    ::= { ex2ISPublicEntry 10 }

ex2ispEventHisEventEmptyMsgClass OBJECT-TYPE
    SYNTAX     Gauge32
    MAX-ACCESS read-only
    STATUS     current
    DESCRIPTION
	    "Event History: Events With Empty Message Class
	    is the number of events with no message class
	    generated in the public store since it was
	    started."
    ::= { ex2ISPublicEntry 11 }

ex2ispEventHistEventTrunConClass OBJECT-TYPE
    SYNTAX     Gauge32
    MAX-ACCESS read-only
    STATUS     current
    DESCRIPTION
	    "Event History: Events With Truncated Container
	    Class is the number of events with truncated
	    container class generated in the public store
	    since it was started."
    ::= { ex2ISPublicEntry 12 }

ex2ispEventHistEventTrunMsgClass OBJECT-TYPE
    SYNTAX     Gauge32
    MAX-ACCESS read-only
    STATUS     current
    DESCRIPTION
	    "Event History: Events With Truncated Message
	    Class is the number of events with truncated
	    message class generated in the public store
	    since it was started."
    ::= { ex2ISPublicEntry 13 }

ex2ispEventHistoryReads OBJECT-TYPE
    SYNTAX     Gauge32
    MAX-ACCESS read-only
    STATUS     current
    DESCRIPTION
	    "Event History: Reads is the number of events
	    read from the event history of the public store
	    since it was started."
    ::= { ex2ISPublicEntry 14 }

ex2ispEventHistoryReadsPerSec OBJECT-TYPE
    SYNTAX     Gauge32
    MAX-ACCESS read-only
    STATUS     current
    DESCRIPTION
	    "Event History: Reads/sec is rate the events
	    are read from the event history of the public
	    store."
    ::= { ex2ISPublicEntry 15 }

ex2ispEventHistUncommitTranCount OBJECT-TYPE
    SYNTAX     Gauge32
    MAX-ACCESS read-only
    STATUS     current
    DESCRIPTION
	    "Event History: Uncommitted Transactions Count
	    is the number of uncommmitted transactions in
	    the public store in their top level commit
	    phase and containing at least one event."
    ::= { ex2ISPublicEntry 16 }

ex2ispEventHistWatermarksCount OBJECT-TYPE
    SYNTAX     Gauge32
    MAX-ACCESS read-only
    STATUS     current
    DESCRIPTION
	    "Event History: Watermarks Count is the
	    approximate number of event watermarks stored
	    in the event history of the public store."
    ::= { ex2ISPublicEntry 17 }

ex2ispEventHistWatermarksDeletes OBJECT-TYPE
    SYNTAX     Gauge32
    MAX-ACCESS read-only
    STATUS     current
    DESCRIPTION
	    "Event History: Watermarks Deletes is the
	    number of event watermarks deleted from the
	    event history of the public store since it was
	    started."
    ::= { ex2ISPublicEntry 18 }

ex2ispEventHistWatermarkDelPrSec OBJECT-TYPE
    SYNTAX     Gauge32
    MAX-ACCESS read-only
    STATUS     current
    DESCRIPTION
	    "Event History: Watermarks Deletes/sec is rate
	    the event watermarks are deleted from the event
	    history of the public store."
    ::= { ex2ISPublicEntry 19 }

ex2ispEventHistWatermarksReads OBJECT-TYPE
    SYNTAX     Gauge32
    MAX-ACCESS read-only
    STATUS     current
    DESCRIPTION
	    "Event History: Watermarks Reads is the number
	    of event watermarks read from the event history
	    of the public store since it was started."
    ::= { ex2ISPublicEntry 20 }

ex2ispEventHistWatermarkRdPerSec OBJECT-TYPE
    SYNTAX     Gauge32
    MAX-ACCESS read-only
    STATUS     current
    DESCRIPTION
	    "Event History: Watermarks Reads/sec is rate
	    the event watermarks are read from the event
	    history of the public store."
    ::= { ex2ISPublicEntry 21 }

ex2ispEventHistWatermarksWrites OBJECT-TYPE
    SYNTAX     Gauge32
    MAX-ACCESS read-only
    STATUS     current
    DESCRIPTION
	    "Event History: Watermarks Writes is the number
	    of event watermarks written to the event
	    history of the public store since it was
	    started."
    ::= { ex2ISPublicEntry 22 }

ex2ispEventHistWatermarkWriteSec OBJECT-TYPE
    SYNTAX     Gauge32
    MAX-ACCESS read-only
    STATUS     current
    DESCRIPTION
	    "Event History: Watermarks Writes/sec is rate
	    the event watermarks are written to the event
	    history of the public store."
    ::= { ex2ISPublicEntry 23 }

ex2ispEventHistoryWrites OBJECT-TYPE
    SYNTAX     Gauge32
    MAX-ACCESS read-only
    STATUS     current
    DESCRIPTION
	    "Event History: Writes is the number of events
	    written to the event history of the public
	    store since it was started."
    ::= { ex2ISPublicEntry 24 }

ex2ispEventHistoryWritesPerSec OBJECT-TYPE
    SYNTAX     Gauge32
    MAX-ACCESS read-only
    STATUS     current
    DESCRIPTION
	    "Event History: Writes/sec is rate the events
	    are written to the event history of the public
	    store."
    ::= { ex2ISPublicEntry 25 }

ex2ispFolderOpensPerSec OBJECT-TYPE
    SYNTAX     Gauge32
    MAX-ACCESS read-only
    STATUS     current
    DESCRIPTION
	    "Folder opens/sec is the rate that requests to
	    open folders are submitted to the information
	    store."
    ::= { ex2ISPublicEntry 26 }

ex2ispHTTPPerDAVCurrentPendNotif OBJECT-TYPE
    SYNTAX     Gauge32
    MAX-ACCESS read-only
    STATUS     current
    DESCRIPTION
	    "Number of notifications happened that are
	    pending (i.e. to be polled)."
    ::= { ex2ISPublicEntry 27 }

ex2ispHTTPPerDAVCurrentSubscript OBJECT-TYPE
    SYNTAX     Gauge32
    MAX-ACCESS read-only
    STATUS     current
    DESCRIPTION
	    "The number of subscriptions currently active
	    in response to HTTP SUBSCRIBE requests."
    ::= { ex2ISPublicEntry 28 }

ex2ispHTTPPerDAVCurrentTransLock OBJECT-TYPE
    SYNTAX     Gauge32
    MAX-ACCESS read-only
    STATUS     current
    DESCRIPTION
	    "The number of DAV transaction locks currently
	    active."
    ::= { ex2ISPublicEntry 29 }

ex2ispHTTPPerDAVNotifyReqPerSec OBJECT-TYPE
    SYNTAX     Gauge32
    MAX-ACCESS read-only
    STATUS     current
    DESCRIPTION
	    "The rate at which the server sends HTTP NOTIFY
	    requests."
    ::= { ex2ISPublicEntry 30 }

ex2ispHTTPPerDAVTotalLockCreated OBJECT-TYPE
    SYNTAX     Gauge32
    MAX-ACCESS read-only
    STATUS     current
    DESCRIPTION
	    "The number locks granted by the server in
	    response to HTTP LOCK requests since service
	    startup."
    ::= { ex2ISPublicEntry 31 }

ex2ispHTTPPerDAVTotalNotifyReqst OBJECT-TYPE
    SYNTAX     Gauge32
    MAX-ACCESS read-only
    STATUS     current
    DESCRIPTION
	    "The number of HTTP NOTIFY requests sent by the
	    server since service startup."
    ::= { ex2ISPublicEntry 32 }

ex2ispHTTPPerDAVTotalSubsCreated OBJECT-TYPE
    SYNTAX     Gauge32
    MAX-ACCESS read-only
    STATUS     current
    DESCRIPTION
	    "The number of subscriptions granted by the
	    server in response to HTTP SUBSCRIBE requests
	    since service startup."
    ::= { ex2ISPublicEntry 33 }

ex2ispHTTPPerDAVTotalSubsExpired OBJECT-TYPE
    SYNTAX     Gauge32
    MAX-ACCESS read-only
    STATUS     current
    DESCRIPTION
	    "The number of subscriptions granted by the
	    server in response to HTTP SUBSCRIBE requests
	    that have expired since service startup."
    ::= { ex2ISPublicEntry 34 }

ex2ispLogonOperationsPerSec OBJECT-TYPE
    SYNTAX     Gauge32
    MAX-ACCESS read-only
    STATUS     current
    DESCRIPTION
	    "Logon Operations/sec is the rate of Logon
	    requests in the public store."
    ::= { ex2ISPublicEntry 35 }

ex2ispMessageOpensPerSec OBJECT-TYPE
    SYNTAX     Gauge32
    MAX-ACCESS read-only
    STATUS     current
    DESCRIPTION
	    "Message Opens/sec is the rate that requests to
	    open messages are submitted to the information
	    store."
    ::= { ex2ISPublicEntry 36 }

ex2ispMessageRecipientsDelivered OBJECT-TYPE
    SYNTAX     Gauge32
    MAX-ACCESS read-only
    STATUS     current
    DESCRIPTION
	    "Message Recipients Delivered is the total
	    number of recipients that have received a
	    message since startup."
    ::= { ex2ISPublicEntry 37 }

ex2ispMsgRecipientsDeliverPerSec OBJECT-TYPE
    SYNTAX     Gauge32
    MAX-ACCESS read-only
    STATUS     current
    DESCRIPTION
	    "Message Recipients Delivered/sec is the rate
	    that recipients receive messages."
    ::= { ex2ISPublicEntry 38 }

ex2ispMessagesDelivered OBJECT-TYPE
    SYNTAX     Gauge32
    MAX-ACCESS read-only
    STATUS     current
    DESCRIPTION
	    "Messages Delivered is the total number of
	    messages delivered to all recipients since
	    startup."
    ::= { ex2ISPublicEntry 39 }

ex2ispMessagesDeliveredPerSec OBJECT-TYPE
    SYNTAX     Gauge32
    MAX-ACCESS read-only
    STATUS     current
    DESCRIPTION
	    "Messages Delivered/sec is the rate that
	    messages are delivered to all recipients."
    ::= { ex2ISPublicEntry 40 }

ex2ispMsgsQueuedForSubmission OBJECT-TYPE
    SYNTAX     Gauge32
    MAX-ACCESS read-only
    STATUS     current
    DESCRIPTION
	    "Messages Queued For Submission is the current
	    number of submitted messages which are not yet
	    processed by transport."
    ::= { ex2ISPublicEntry 41 }

ex2ispMessagesSent OBJECT-TYPE
    SYNTAX     Gauge32
    MAX-ACCESS read-only
    STATUS     current
    DESCRIPTION
	    "Messages Sent is the total number of messages
	    sent to the transport since startup."
    ::= { ex2ISPublicEntry 42 }

ex2ispMessagesSentPerSec OBJECT-TYPE
    SYNTAX     Gauge32
    MAX-ACCESS read-only
    STATUS     current
    DESCRIPTION
	    "Messages Sent/sec is the rate that messages
	    are sent to the transport."
    ::= { ex2ISPublicEntry 43 }

ex2ispMessagesSubmitted OBJECT-TYPE
    SYNTAX     Gauge32
    MAX-ACCESS read-only
    STATUS     current
    DESCRIPTION
	    "Messages Submitted is the total number of
	    messages submitted by clients since service
	    startup."
    ::= { ex2ISPublicEntry 44 }

ex2ispMessagesSubmittedPerSec OBJECT-TYPE
    SYNTAX     Gauge32
    MAX-ACCESS read-only
    STATUS     current
    DESCRIPTION
	    "Messages Submitted/sec is the rate that
	    messages are submitted by clients."
    ::= { ex2ISPublicEntry 45 }

ex2ispNumMsgsExpireFrmPublicFold OBJECT-TYPE
    SYNTAX     Gauge32
    MAX-ACCESS read-only
    STATUS     current
    DESCRIPTION
	    "Number of messages expired from public
	    folders"
    ::= { ex2ISPublicEntry 46 }

ex2ispPeakClientLogons OBJECT-TYPE
    SYNTAX     Gauge32
    MAX-ACCESS read-only
    STATUS     current
    DESCRIPTION
	    "Peak Client Logons is the maximum number of
	    concurrent client logons since the service
	    started."
    ::= { ex2ISPublicEntry 47 }

ex2ispReceiveQueueSize OBJECT-TYPE
    SYNTAX     Gauge32
    MAX-ACCESS read-only
    STATUS     current
    DESCRIPTION
	    "Receive Queue Size is the number of messages
	    in the public store's receive queue."
    ::= { ex2ISPublicEntry 48 }

ex2ispReplIDCount OBJECT-TYPE
    SYNTAX     Gauge32
    MAX-ACCESS read-only
    STATUS     current
    DESCRIPTION
	    "ReplID Count (replication ID count) is the
	    number of ReplID-to-GUID mappings in the
	    mailbox database or public folder database."
    ::= { ex2ISPublicEntry 49 }

ex2ispReplicBackfillDataMsgsRecv OBJECT-TYPE
    SYNTAX     Gauge32
    MAX-ACCESS read-only
    STATUS     current
    DESCRIPTION
	    "Replication Backfill Data Messages Received is
	    the number of replication messages received
	    from other servers in response to backfill
	    requests since service startup."
    ::= { ex2ISPublicEntry 50 }

ex2ispReplicBackfillDataMsgsSent OBJECT-TYPE
    SYNTAX     Gauge32
    MAX-ACCESS read-only
    STATUS     current
    DESCRIPTION
	    "Replication Backfill Data Messages Sent is the
	    number of replication messages sent in response
	    to backfill requests from other servers since
	    service startup."
    ::= { ex2ISPublicEntry 51 }

ex2ispReplicBackfillRequestRecvd OBJECT-TYPE
    SYNTAX     Gauge32
    MAX-ACCESS read-only
    STATUS     current
    DESCRIPTION
	    "Replication Backfill Requests Received is the
	    number of backfill request replication messages
	    that have been received from other servers
	    since service startup."
    ::= { ex2ISPublicEntry 52 }

ex2ispReplicBackfillRequestsSent OBJECT-TYPE
    SYNTAX     Gauge32
    MAX-ACCESS read-only
    STATUS     current
    DESCRIPTION
	    "Replication Backfill Requests Sent is the
	    number of backfill request replication messages
	    that have been sent to other servers since
	    service startup."
    ::= { ex2ISPublicEntry 53 }

ex2ispReplicFolderChangeReceived OBJECT-TYPE
    SYNTAX     Gauge32
    MAX-ACCESS read-only
    STATUS     current
    DESCRIPTION
	    "Replication Folder Changes Received is the
	    number of folder changes that have been
	    replicated from other servers since service
	    startup."
    ::= { ex2ISPublicEntry 54 }

ex2ispReplicFolderChangesSent OBJECT-TYPE
    SYNTAX     Gauge32
    MAX-ACCESS read-only
    STATUS     current
    DESCRIPTION
	    "Replication Folder Tree Messages Sent is the
	    number of replication messages due to public
	    folder hierarchy changes that have been sent to
	    other servers since service startup."
    ::= { ex2ISPublicEntry 55 }

ex2ispReplicFolderDataMsgReceive OBJECT-TYPE
    SYNTAX     Gauge32
    MAX-ACCESS read-only
    STATUS     current
    DESCRIPTION
	    "Replication Folder Data Messages Received is
	    the number of replication messages due to
	    changes to items in public folders that have
	    been received from other service since service
	    startup."
    ::= { ex2ISPublicEntry 56 }

ex2ispReplicFolderDataMsgsSent OBJECT-TYPE
    SYNTAX     Gauge32
    MAX-ACCESS read-only
    STATUS     current
    DESCRIPTION
	    "Replication Folder Data Message Messages sent
	    is the number of replication messages due to
	    changes to items in public folders that have
	    been sent to other servers since service
	    startup."
    ::= { ex2ISPublicEntry 57 }

ex2ispReplicFolderTreeMsgReceive OBJECT-TYPE
    SYNTAX     Gauge32
    MAX-ACCESS read-only
    STATUS     current
    DESCRIPTION
	    "Replication Folder Tree Messages Received is
	    the number of replication messages due to
	    public folder hierarchy changes that have been
	    received from other servers since service
	    startup."
    ::= { ex2ISPublicEntry 58 }

ex2ispReplicFolderTreeMsgsSent OBJECT-TYPE
    SYNTAX     Gauge32
    MAX-ACCESS read-only
    STATUS     current
    DESCRIPTION
	    "Replication Folder Tree Messages Sent is the
	    number of replication messages due to public
	    folder hierarchy changes that have been sent to
	    other servers since service startup."
    ::= { ex2ISPublicEntry 59 }

ex2ispReplicMessageChangeReceive OBJECT-TYPE
    SYNTAX     Gauge32
    MAX-ACCESS read-only
    STATUS     current
    DESCRIPTION
	    "Replication Message Changes Received is the
	    number of changes to items in public folders
	    that have been received from other servers
	    since service startup."
    ::= { ex2ISPublicEntry 60 }

ex2ispReplicMessageChangesSent OBJECT-TYPE
    SYNTAX     Gauge32
    MAX-ACCESS read-only
    STATUS     current
    DESCRIPTION
	    "Replication Message Changes Sent is the number
	    of changes to items in public folders that have
	    been replicated to other servers since service
	    startup."
    ::= { ex2ISPublicEntry 61 }

ex2ispReplicMsgsReceived OBJECT-TYPE
    SYNTAX     Gauge32
    MAX-ACCESS read-only
    STATUS     current
    DESCRIPTION
	    "Replication Messages Received is the total
	    number of replication messages received from
	    other servers since service startup."
    ::= { ex2ISPublicEntry 62 }

ex2ispReplicationMessagesSent OBJECT-TYPE
    SYNTAX     Gauge32
    MAX-ACCESS read-only
    STATUS     current
    DESCRIPTION
	    "Replication Messages Sent is the total number
	    of replication messages that have been sent to
	    other servers since service startup."
    ::= { ex2ISPublicEntry 63 }

ex2ispReplicReceiveQueueSize OBJECT-TYPE
    SYNTAX     Gauge32
    MAX-ACCESS read-only
    STATUS     current
    DESCRIPTION
	    "Replication Receive Queue Size is the number
	    of replication messages waiting to be
	    processed."
    ::= { ex2ISPublicEntry 64 }

ex2ispReplicStatusMsgsReceived OBJECT-TYPE
    SYNTAX     Gauge32
    MAX-ACCESS read-only
    STATUS     current
    DESCRIPTION
	    "Status Messages Received is the number of
	    replication status request or response messages
	    that have been received from other servers
	    since service startup."
    ::= { ex2ISPublicEntry 65 }

ex2ispReplicStatusMsgsSent OBJECT-TYPE
    SYNTAX     Gauge32
    MAX-ACCESS read-only
    STATUS     current
    DESCRIPTION
	    "Replication Status Messages Sent is the number
	    of replication status request or response
	    messages that have been sent to other servers
	    since service startup."
    ::= { ex2ISPublicEntry 66 }

ex2ispRestrictedViewCacheHitRate OBJECT-TYPE
    SYNTAX     Gauge32
    MAX-ACCESS read-only
    STATUS     current
    DESCRIPTION
	    "Restricted View Cache Hit Rate is the rate at
	    which restricted views are reused in the public
	    store."
    ::= { ex2ISPublicEntry 67 }

ex2ispRestricteViewCacheMissRate OBJECT-TYPE
    SYNTAX     Gauge32
    MAX-ACCESS read-only
    STATUS     current
    DESCRIPTION
	    "Restricted View Cache Miss Rate is the rate at
	    which restricted views are created in the
	    public store."
    ::= { ex2ISPublicEntry 68 }

ex2ispSearchTaskRate OBJECT-TYPE
    SYNTAX     Gauge32
    MAX-ACCESS read-only
    STATUS     current
    DESCRIPTION
	    "Number of search tasks created per second."
    ::= { ex2ISPublicEntry 69 }

ex2ispSingleInstanceRatio OBJECT-TYPE
    SYNTAX     Gauge32
    MAX-ACCESS read-only
    STATUS     current
    DESCRIPTION
	    "Single Instance Ratio is the average number of
	    references to each message in the public
	    store."
    ::= { ex2ISPublicEntry 70 }

ex2ispSlowFindRowRate OBJECT-TYPE
    SYNTAX     Gauge32
    MAX-ACCESS read-only
    STATUS     current
    DESCRIPTION
	    "Slow FindRow Rate is the rate at which the
	    slower FindRow needs to be used in the public
	    store."
    ::= { ex2ISPublicEntry 71 }

ex2ispTotalCountRecoverableItems OBJECT-TYPE
    SYNTAX     Gauge32
    MAX-ACCESS read-only
    STATUS     current
    DESCRIPTION
	    "Total Count of Recoverable Items is the total
	    number of items retained for Item Recovery"
    ::= { ex2ISPublicEntry 72 }

ex2ispTotalSizeOfRecoverableItem OBJECT-TYPE
    SYNTAX     Gauge32
    MAX-ACCESS read-only
    STATUS     current
    DESCRIPTION
	    "Total Size of Recoverable Items is the total
	    size in kilobytes of items retained for Item
	    Recovery"
    ::= { ex2ISPublicEntry 73 }

ex2ispVirusScanBackgrndScnThread OBJECT-TYPE
    SYNTAX     Gauge32
    MAX-ACCESS read-only
    STATUS     current
    DESCRIPTION
	    "Number of threads currently running background
	    scanning."
    ::= { ex2ISPublicEntry 74 }

ex2ispVirusScanBackgrndMsgsScan OBJECT-TYPE
    SYNTAX     Gauge32
    MAX-ACCESS read-only
    STATUS     current
    DESCRIPTION
	    "Total number of messages scanned during
	    background scanning."
    ::= { ex2ISPublicEntry 75 }

ex2ispVirusScanBackgrndMsgSkippd OBJECT-TYPE
    SYNTAX     Gauge32
    MAX-ACCESS read-only
    STATUS     current
    DESCRIPTION
	    "Total number of messages skipped during
	    background scanning."
    ::= { ex2ISPublicEntry 76 }

ex2ispVirusScanBackgrndMsgUpDate OBJECT-TYPE
    SYNTAX     Gauge32
    MAX-ACCESS read-only
    STATUS     current
    DESCRIPTION
	    "Total number of messages with up-to-date virus
	    results during background scanning."
    ::= { ex2ISPublicEntry 77 }

ex2ispVirusScanExtResultAccepted OBJECT-TYPE
    SYNTAX     Gauge32
    MAX-ACCESS read-only
    STATUS     current
    DESCRIPTION
	    "Number of messages delivered with external
	    virus scanning results that can be preserved."
    ::= { ex2ISPublicEntry 78 }

ex2ispVirusScanExtResultNotAccpt OBJECT-TYPE
    SYNTAX     Gauge32
    MAX-ACCESS read-only
    STATUS     current
    DESCRIPTION
	    "Number of messages delivered with external
	    virus scanning results that cannot be
	    preserved."
    ::= { ex2ISPublicEntry 79 }

ex2ispVirusScanExtResultsNotPres OBJECT-TYPE
    SYNTAX     Gauge32
    MAX-ACCESS read-only
    STATUS     current
    DESCRIPTION
	    "Number of messages delivered without external
	    virus scanning results."
    ::= { ex2ISPublicEntry 80 }

ex2Imap4Table OBJECT-TYPE
    SYNTAX     SEQUENCE OF Ex2Imap4Entry
    MAX-ACCESS not-accessible
    STATUS     current
    DESCRIPTION
	    "A table containing performance information for
	    instances of 'MSExchangeImap4' objects."
    ::= { exchangeV2 49 }

ex2Imap4Entry OBJECT-TYPE
    SYNTAX     Ex2Imap4Entry
    MAX-ACCESS not-accessible
    STATUS     current
    DESCRIPTION
	    "Performance information for one particular
	    instance of 'MSExchangeImap4' object."
    INDEX      { ex2im4Instance }
    ::= { ex2Imap4Table 1 }

Ex2Imap4Entry ::= SEQUENCE {
    ex2im4Instance InstanceName,
    ex2im4ActiveSSLConnections Gauge32,
    ex2im4AppendFailures Gauge32,
    ex2im4AppendRate Gauge32,
    ex2im4AppendTotal Gauge32,
    ex2im4AuthenticateFailures Gauge32,
    ex2im4AuthenticateRate Gauge32,
    ex2im4AuthenticateTotal Gauge32,
    ex2im4AvgCommProcessTimeMillisec Gauge32,
    ex2im4CapabilityFailures Gauge32,
    ex2im4CapabilityRate Gauge32,
    ex2im4CapabilityTotal Gauge32,
    ex2im4CheckFailures Gauge32,
    ex2im4CheckRate Gauge32,
    ex2im4CheckTotal Gauge32,
    ex2im4CloseFailures Gauge32,
    ex2im4CloseRate Gauge32,
    ex2im4CloseTotal Gauge32,
    ex2im4ConnectionsFailed Gauge32,
    ex2im4ConnectionsRejected Gauge32,
    ex2im4CopyFailures Gauge32,
    ex2im4CopyRate Gauge32,
    ex2im4CopyTotal Gauge32,
    ex2im4CreateFailures Gauge32,
    ex2im4CreateRate Gauge32,
    ex2im4CreateTotal Gauge32,
    ex2im4CurrentConnections Gauge32,
    ex2im4DeleteFailures Gauge32,
    ex2im4DeleteRate Gauge32,
    ex2im4DeleteTotal Gauge32,
    ex2im4ExamineFailures Gauge32,
    ex2im4ExamineRate Gauge32,
    ex2im4ExamineTotal Gauge32,
    ex2im4ExpungeFailures Gauge32,
    ex2im4ExpungeRate Gauge32,
    ex2im4ExpungeTotal Gauge32,
    ex2im4FetchFailures Gauge32,
    ex2im4FetchRate Gauge32,
    ex2im4FetchTotal Gauge32,
    ex2im4IdleFailures Gauge32,
    ex2im4IdleRate Gauge32,
    ex2im4IdleTotal Gauge32,
    ex2im4InvalidCommands Gauge32,
    ex2im4InvalidCommandsRate Gauge32,
    ex2im4LSUBFailures Gauge32,
    ex2im4LSUBRate Gauge32,
    ex2im4LSUBTotal Gauge32,
    ex2im4ListFailures Gauge32,
    ex2im4ListRate Gauge32,
    ex2im4ListTotal Gauge32,
    ex2im4LoginFailures Gauge32,
    ex2im4LoginRate Gauge32,
    ex2im4LoginTotal Gauge32,
    ex2im4LogoutFailures Gauge32,
    ex2im4LogoutRate Gauge32,
    ex2im4LogoutTotal Gauge32,
    ex2im4NOOPFailures Gauge32,
    ex2im4NOOPRate Gauge32,
    ex2im4NOOPTotal Gauge32,
    ex2im4NamespaceFailures Gauge32,
    ex2im4NamespaceRate Gauge32,
    ex2im4NamespaceTotal Gauge32,
    ex2im4RenameFailures Gauge32,
    ex2im4RenameRate Gauge32,
    ex2im4RenameTotal Gauge32,
    ex2im4SSLConnections Gauge32,
    ex2im4STARTTLSFailures Gauge32,
    ex2im4STARTTLSRate Gauge32,
    ex2im4STARTTLSTotal Gauge32,
    ex2im4SearchFailures Gauge32,
    ex2im4SearchRate Gauge32,
    ex2im4SearchTotal Gauge32,
    ex2im4SelectFailures Gauge32,
    ex2im4SelectRate Gauge32,
    ex2im4SelectTotal Gauge32,
    ex2im4StatusFailures Gauge32,
    ex2im4StatusRate Gauge32,
    ex2im4StatusTotal Gauge32,
    ex2im4StoreFailures Gauge32,
    ex2im4StoreRate Gauge32,
    ex2im4StoreTotal Gauge32,
    ex2im4SubscribeFailures Gauge32,
    ex2im4SubscribeRate Gauge32,
    ex2im4SubscribeTotal Gauge32,
    ex2im4TotalConnections Gauge32,
    ex2im4UnsubscribeFailures Gauge32,
    ex2im4UnsubscribeRate Gauge32,
    ex2im4UnsubscribeTotal Gauge32
}

ex2im4Instance OBJECT-TYPE
    SYNTAX     InstanceName
    MAX-ACCESS read-only
    STATUS     current
    DESCRIPTION
	    "Instance name."
    ::= { ex2Imap4Entry 1 }

ex2im4ActiveSSLConnections OBJECT-TYPE
    SYNTAX     Gauge32
    MAX-ACCESS read-only
    STATUS     current
    DESCRIPTION
	    "Active SSL Connections is the number of SSL or
	    TLS connections that are currently open on the
	    IMAP service."
    ::= { ex2Imap4Entry 2 }

ex2im4AppendFailures OBJECT-TYPE
    SYNTAX     Gauge32
    MAX-ACCESS read-only
    STATUS     current
    DESCRIPTION
	    "Append Failures is the number of APPEND
	    commands that have failed since the IMAP
	    service was started."
    ::= { ex2Imap4Entry 3 }

ex2im4AppendRate OBJECT-TYPE
    SYNTAX     Gauge32
    MAX-ACCESS read-only
    STATUS     current
    DESCRIPTION
	    "Append Rate is the number of APPEND commands
	    per second."
    ::= { ex2Imap4Entry 4 }

ex2im4AppendTotal OBJECT-TYPE
    SYNTAX     Gauge32
    MAX-ACCESS read-only
    STATUS     current
    DESCRIPTION
	    "Append Total is the total number of APPEND
	    commands that have been received since the IMAP
	    service started."
    ::= { ex2Imap4Entry 5 }

ex2im4AuthenticateFailures OBJECT-TYPE
    SYNTAX     Gauge32
    MAX-ACCESS read-only
    STATUS     current
    DESCRIPTION
	    "Authenticate Failures is the number of
	    AUTHENTICATE commands that have failed since
	    the IMAP service was started."
    ::= { ex2Imap4Entry 6 }

ex2im4AuthenticateRate OBJECT-TYPE
    SYNTAX     Gauge32
    MAX-ACCESS read-only
    STATUS     current
    DESCRIPTION
	    "Authenticate Rate is the number of
	    AUTHENTICATE commands per second."
    ::= { ex2Imap4Entry 7 }

ex2im4AuthenticateTotal OBJECT-TYPE
    SYNTAX     Gauge32
    MAX-ACCESS read-only
    STATUS     current
    DESCRIPTION
	    "Authenticate Total is the total number of
	    AUTHENTICATE commands that have been received
	    since the IMAP service was started."
    ::= { ex2Imap4Entry 8 }

ex2im4AvgCommProcessTimeMillisec OBJECT-TYPE
    SYNTAX     Gauge32
    MAX-ACCESS read-only
    STATUS     current
    DESCRIPTION
	    "Average Command Processing Time is the average
	    processing time, in milliseconds, for the last
	    1024 commands received from clients."
    ::= { ex2Imap4Entry 9 }

ex2im4CapabilityFailures OBJECT-TYPE
    SYNTAX     Gauge32
    MAX-ACCESS read-only
    STATUS     current
    DESCRIPTION
	    "Capability Failures is the number of
	    CAPABILITY commands that have failed since the
	    IMAP service was started."
    ::= { ex2Imap4Entry 10 }

ex2im4CapabilityRate OBJECT-TYPE
    SYNTAX     Gauge32
    MAX-ACCESS read-only
    STATUS     current
    DESCRIPTION
	    "Capability Rate is the number of CAPABILITY
	    commands per second."
    ::= { ex2Imap4Entry 11 }

ex2im4CapabilityTotal OBJECT-TYPE
    SYNTAX     Gauge32
    MAX-ACCESS read-only
    STATUS     current
    DESCRIPTION
	    "Capability Total is the total number of
	    CAPABILITY commands that have been received
	    since the IMAP service was started."
    ::= { ex2Imap4Entry 12 }

ex2im4CheckFailures OBJECT-TYPE
    SYNTAX     Gauge32
    MAX-ACCESS read-only
    STATUS     current
    DESCRIPTION
	    "Check Failures is the number of CHECK commands
	    that have failed since the IMAP service was
	    started."
    ::= { ex2Imap4Entry 13 }

ex2im4CheckRate OBJECT-TYPE
    SYNTAX     Gauge32
    MAX-ACCESS read-only
    STATUS     current
    DESCRIPTION
	    "Check Rate is the number of CHECK commands per
	    second."
    ::= { ex2Imap4Entry 14 }

ex2im4CheckTotal OBJECT-TYPE
    SYNTAX     Gauge32
    MAX-ACCESS read-only
    STATUS     current
    DESCRIPTION
	    "Check Total is the total number of CHECK
	    commands that have been received since the IMAP
	    service was started."
    ::= { ex2Imap4Entry 15 }

ex2im4CloseFailures OBJECT-TYPE
    SYNTAX     Gauge32
    MAX-ACCESS read-only
    STATUS     current
    DESCRIPTION
	    "Close Failures is the number of CLOSE commands
	    that have failed since the IMAP service was
	    started."
    ::= { ex2Imap4Entry 16 }

ex2im4CloseRate OBJECT-TYPE
    SYNTAX     Gauge32
    MAX-ACCESS read-only
    STATUS     current
    DESCRIPTION
	    "Close Rate is the number of CLOSE commands per
	    second."
    ::= { ex2Imap4Entry 17 }

ex2im4CloseTotal OBJECT-TYPE
    SYNTAX     Gauge32
    MAX-ACCESS read-only
    STATUS     current
    DESCRIPTION
	    "Close Total is the total number of CLOSE
	    commands that have been received since the IMAP
	    service was started."
    ::= { ex2Imap4Entry 18 }

ex2im4ConnectionsFailed OBJECT-TYPE
    SYNTAX     Gauge32
    MAX-ACCESS read-only
    STATUS     current
    DESCRIPTION
	    "Connections Failed is the number of
	    connections that have failed since the IMAP
	    service was started."
    ::= { ex2Imap4Entry 19 }

ex2im4ConnectionsRejected OBJECT-TYPE
    SYNTAX     Gauge32
    MAX-ACCESS read-only
    STATUS     current
    DESCRIPTION
	    "Connections Rejected is the number of
	    connections that have been rejected since the
	    IMAP service was started."
    ::= { ex2Imap4Entry 20 }

ex2im4CopyFailures OBJECT-TYPE
    SYNTAX     Gauge32
    MAX-ACCESS read-only
    STATUS     current
    DESCRIPTION
	    "Copy Failures is the number of COPY commands
	    that have failed since the IMAP service was
	    started."
    ::= { ex2Imap4Entry 21 }

ex2im4CopyRate OBJECT-TYPE
    SYNTAX     Gauge32
    MAX-ACCESS read-only
    STATUS     current
    DESCRIPTION
	    "Copy Rate is the number of COPY commands per
	    second."
    ::= { ex2Imap4Entry 22 }

ex2im4CopyTotal OBJECT-TYPE
    SYNTAX     Gauge32
    MAX-ACCESS read-only
    STATUS     current
    DESCRIPTION
	    "Copy Total is the total number of COPY
	    commands that have been received since the IMAP
	    service was started."
    ::= { ex2Imap4Entry 23 }

ex2im4CreateFailures OBJECT-TYPE
    SYNTAX     Gauge32
    MAX-ACCESS read-only
    STATUS     current
    DESCRIPTION
	    "Create Failures is the number of CREATE
	    commands that have failed since the IMAP
	    service was started."
    ::= { ex2Imap4Entry 24 }

ex2im4CreateRate OBJECT-TYPE
    SYNTAX     Gauge32
    MAX-ACCESS read-only
    STATUS     current
    DESCRIPTION
	    "Create Rate is the number of CREATE commands
	    per second."
    ::= { ex2Imap4Entry 25 }

ex2im4CreateTotal OBJECT-TYPE
    SYNTAX     Gauge32
    MAX-ACCESS read-only
    STATUS     current
    DESCRIPTION
	    "Create Total is the total number of CREATE
	    commands that have been received since the IMAP
	    service was started."
    ::= { ex2Imap4Entry 26 }

ex2im4CurrentConnections OBJECT-TYPE
    SYNTAX     Gauge32
    MAX-ACCESS read-only
    STATUS     current
    DESCRIPTION
	    "Current Connections is the number of
	    connections that are currently open on the IMAP
	    service."
    ::= { ex2Imap4Entry 27 }

ex2im4DeleteFailures OBJECT-TYPE
    SYNTAX     Gauge32
    MAX-ACCESS read-only
    STATUS     current
    DESCRIPTION
	    "Delete Failures is the number of DELETE
	    commands that have failed since the IMAP
	    service was started."
    ::= { ex2Imap4Entry 28 }

ex2im4DeleteRate OBJECT-TYPE
    SYNTAX     Gauge32
    MAX-ACCESS read-only
    STATUS     current
    DESCRIPTION
	    "Delete Rate is the number of DELETE commands
	    per second."
    ::= { ex2Imap4Entry 29 }

ex2im4DeleteTotal OBJECT-TYPE
    SYNTAX     Gauge32
    MAX-ACCESS read-only
    STATUS     current
    DESCRIPTION
	    "Delete Total is the total number of DELETE
	    commands that have been received since the IMAP
	    service was started."
    ::= { ex2Imap4Entry 30 }

ex2im4ExamineFailures OBJECT-TYPE
    SYNTAX     Gauge32
    MAX-ACCESS read-only
    STATUS     current
    DESCRIPTION
	    "Examine Failures is the number of EXAMINE
	    commands that have failed since the IMAP
	    service was started."
    ::= { ex2Imap4Entry 31 }

ex2im4ExamineRate OBJECT-TYPE
    SYNTAX     Gauge32
    MAX-ACCESS read-only
    STATUS     current
    DESCRIPTION
	    "Examine Rate is the number of EXAMINE commands
	    per second."
    ::= { ex2Imap4Entry 32 }

ex2im4ExamineTotal OBJECT-TYPE
    SYNTAX     Gauge32
    MAX-ACCESS read-only
    STATUS     current
    DESCRIPTION
	    "Examine Total is the total number of EXAMINE
	    commands that have been received since the IMAP
	    service was started."
    ::= { ex2Imap4Entry 33 }

ex2im4ExpungeFailures OBJECT-TYPE
    SYNTAX     Gauge32
    MAX-ACCESS read-only
    STATUS     current
    DESCRIPTION
	    "Expunge Failures is the number of EXPUNGE
	    commands that have failed since the IMAP
	    service was started."
    ::= { ex2Imap4Entry 34 }

ex2im4ExpungeRate OBJECT-TYPE
    SYNTAX     Gauge32
    MAX-ACCESS read-only
    STATUS     current
    DESCRIPTION
	    "Expunge Rate is the number of EXPUNGE commands
	    per second."
    ::= { ex2Imap4Entry 35 }

ex2im4ExpungeTotal OBJECT-TYPE
    SYNTAX     Gauge32
    MAX-ACCESS read-only
    STATUS     current
    DESCRIPTION
	    "Expunge Total is the total number of EXPUNGE
	    commands that have been received since the IMAP
	    service was started."
    ::= { ex2Imap4Entry 36 }

ex2im4FetchFailures OBJECT-TYPE
    SYNTAX     Gauge32
    MAX-ACCESS read-only
    STATUS     current
    DESCRIPTION
	    "Fetch Failures is the number of FETCH commands
	    that have failed since the IMAP service was
	    started."
    ::= { ex2Imap4Entry 37 }

ex2im4FetchRate OBJECT-TYPE
    SYNTAX     Gauge32
    MAX-ACCESS read-only
    STATUS     current
    DESCRIPTION
	    "Fetch Rate is the number of FETCH commands per
	    second."
    ::= { ex2Imap4Entry 38 }

ex2im4FetchTotal OBJECT-TYPE
    SYNTAX     Gauge32
    MAX-ACCESS read-only
    STATUS     current
    DESCRIPTION
	    "Fetch Total is the total number of FETCH
	    commands that have been received since the IMAP
	    service was started."
    ::= { ex2Imap4Entry 39 }

ex2im4IdleFailures OBJECT-TYPE
    SYNTAX     Gauge32
    MAX-ACCESS read-only
    STATUS     current
    DESCRIPTION
	    "Idle Failures is the number of IDLE commands
	    that have failed since the IMAP service was
	    started."
    ::= { ex2Imap4Entry 40 }

ex2im4IdleRate OBJECT-TYPE
    SYNTAX     Gauge32
    MAX-ACCESS read-only
    STATUS     current
    DESCRIPTION
	    "Idle Rate is the number of IDLE commands per
	    second."
    ::= { ex2Imap4Entry 41 }

ex2im4IdleTotal OBJECT-TYPE
    SYNTAX     Gauge32
    MAX-ACCESS read-only
    STATUS     current
    DESCRIPTION
	    "Idle Total is the total number of IDLE
	    commands that have been received since the IMAP
	    service was started."
    ::= { ex2Imap4Entry 42 }

ex2im4InvalidCommands OBJECT-TYPE
    SYNTAX     Gauge32
    MAX-ACCESS read-only
    STATUS     current
    DESCRIPTION
	    "Invalid Commands is the number of commands
	    that failed since the IMAP service was started
	    because the command was not valid for the state
	    of the connection."
    ::= { ex2Imap4Entry 43 }

ex2im4InvalidCommandsRate OBJECT-TYPE
    SYNTAX     Gauge32
    MAX-ACCESS read-only
    STATUS     current
    DESCRIPTION
	    "Invalid Commands Rate is the number of invalid
	    commands per second."
    ::= { ex2Imap4Entry 44 }

ex2im4LSUBFailures OBJECT-TYPE
    SYNTAX     Gauge32
    MAX-ACCESS read-only
    STATUS     current
    DESCRIPTION
	    "LSUB Failures is the number of LSUB commands
	    that have failed since the IMAP service was
	    started."
    ::= { ex2Imap4Entry 45 }

ex2im4LSUBRate OBJECT-TYPE
    SYNTAX     Gauge32
    MAX-ACCESS read-only
    STATUS     current
    DESCRIPTION
	    "LSUB Rate is the number of LSUB commands per
	    second."
    ::= { ex2Imap4Entry 46 }

ex2im4LSUBTotal OBJECT-TYPE
    SYNTAX     Gauge32
    MAX-ACCESS read-only
    STATUS     current
    DESCRIPTION
	    "LSUB Total is the total number of LSUB
	    commands that have been received since the IMAP
	    service was started."
    ::= { ex2Imap4Entry 47 }

ex2im4ListFailures OBJECT-TYPE
    SYNTAX     Gauge32
    MAX-ACCESS read-only
    STATUS     current
    DESCRIPTION
	    "List Failures is the number of LIST commands
	    that have failed since the IMAP service was
	    started."
    ::= { ex2Imap4Entry 48 }

ex2im4ListRate OBJECT-TYPE
    SYNTAX     Gauge32
    MAX-ACCESS read-only
    STATUS     current
    DESCRIPTION
	    "List Rate is the number of LIST commands per
	    second."
    ::= { ex2Imap4Entry 49 }

ex2im4ListTotal OBJECT-TYPE
    SYNTAX     Gauge32
    MAX-ACCESS read-only
    STATUS     current
    DESCRIPTION
	    "List Total is the total number of LIST
	    commands that have been received since the IMAP
	    service was started."
    ::= { ex2Imap4Entry 50 }

ex2im4LoginFailures OBJECT-TYPE
    SYNTAX     Gauge32
    MAX-ACCESS read-only
    STATUS     current
    DESCRIPTION
	    "Login Failures is the number of LOGIN commands
	    that have failed since the IMAP service was
	    started."
    ::= { ex2Imap4Entry 51 }

ex2im4LoginRate OBJECT-TYPE
    SYNTAX     Gauge32
    MAX-ACCESS read-only
    STATUS     current
    DESCRIPTION
	    "Login Rate is the number of LOGIN commands per
	    second."
    ::= { ex2Imap4Entry 52 }

ex2im4LoginTotal OBJECT-TYPE
    SYNTAX     Gauge32
    MAX-ACCESS read-only
    STATUS     current
    DESCRIPTION
	    "Login Total is the total number of LOGIN
	    commands that have been received since the IMAP
	    service was started."
    ::= { ex2Imap4Entry 53 }

ex2im4LogoutFailures OBJECT-TYPE
    SYNTAX     Gauge32
    MAX-ACCESS read-only
    STATUS     current
    DESCRIPTION
	    "Logout Failures is the number of LOGOUT
	    commands that have failed since the IMAP
	    service was started."
    ::= { ex2Imap4Entry 54 }

ex2im4LogoutRate OBJECT-TYPE
    SYNTAX     Gauge32
    MAX-ACCESS read-only
    STATUS     current
    DESCRIPTION
	    "Logout Rate is the number of LOGOUT commands
	    per second."
    ::= { ex2Imap4Entry 55 }

ex2im4LogoutTotal OBJECT-TYPE
    SYNTAX     Gauge32
    MAX-ACCESS read-only
    STATUS     current
    DESCRIPTION
	    "Logout Total is the total number of LOGOUT
	    commands that have been received since the IMAP
	    service was started."
    ::= { ex2Imap4Entry 56 }

ex2im4NOOPFailures OBJECT-TYPE
    SYNTAX     Gauge32
    MAX-ACCESS read-only
    STATUS     current
    DESCRIPTION
	    "NOOP Failures is the number of NOOP commands
	    that have failed since the IMAP service was
	    started."
    ::= { ex2Imap4Entry 57 }

ex2im4NOOPRate OBJECT-TYPE
    SYNTAX     Gauge32
    MAX-ACCESS read-only
    STATUS     current
    DESCRIPTION
	    "NOOP Rate is the number of NOOP commands per
	    second."
    ::= { ex2Imap4Entry 58 }

ex2im4NOOPTotal OBJECT-TYPE
    SYNTAX     Gauge32
    MAX-ACCESS read-only
    STATUS     current
    DESCRIPTION
	    "NOOP Total is the total number of NOOP
	    commands that have been received since the IMAP
	    service was started."
    ::= { ex2Imap4Entry 59 }

ex2im4NamespaceFailures OBJECT-TYPE
    SYNTAX     Gauge32
    MAX-ACCESS read-only
    STATUS     current
    DESCRIPTION
	    "Namespace Failures is the number of NAMESPACE
	    commands that have failed since the IMAP
	    service was started."
    ::= { ex2Imap4Entry 60 }

ex2im4NamespaceRate OBJECT-TYPE
    SYNTAX     Gauge32
    MAX-ACCESS read-only
    STATUS     current
    DESCRIPTION
	    "Namespace Rate is the number of NAMESPACE
	    commands per second."
    ::= { ex2Imap4Entry 61 }

ex2im4NamespaceTotal OBJECT-TYPE
    SYNTAX     Gauge32
    MAX-ACCESS read-only
    STATUS     current
    DESCRIPTION
	    "Namespace Total is the total number of
	    NAMESPACE commands that have been received
	    since the IMAP service was started."
    ::= { ex2Imap4Entry 62 }

ex2im4RenameFailures OBJECT-TYPE
    SYNTAX     Gauge32
    MAX-ACCESS read-only
    STATUS     current
    DESCRIPTION
	    "Rename Failures is the number of RENAME
	    commands that have failed since the IMAP
	    service was started."
    ::= { ex2Imap4Entry 63 }

ex2im4RenameRate OBJECT-TYPE
    SYNTAX     Gauge32
    MAX-ACCESS read-only
    STATUS     current
    DESCRIPTION
	    "Rename Rate is the number of RENAME commands
	    per second."
    ::= { ex2Imap4Entry 64 }

ex2im4RenameTotal OBJECT-TYPE
    SYNTAX     Gauge32
    MAX-ACCESS read-only
    STATUS     current
    DESCRIPTION
	    "Rename Total is the total number of RENAME
	    commands that have been received since the IMAP
	    service was started."
    ::= { ex2Imap4Entry 65 }

ex2im4SSLConnections OBJECT-TYPE
    SYNTAX     Gauge32
    MAX-ACCESS read-only
    STATUS     current
    DESCRIPTION
	    "SSL Connections is the total number of SSL or
	    TLS connections that have been opened since the
	    IMAP service was started."
    ::= { ex2Imap4Entry 66 }

ex2im4STARTTLSFailures OBJECT-TYPE
    SYNTAX     Gauge32
    MAX-ACCESS read-only
    STATUS     current
    DESCRIPTION
	    "STARTTLS Failures is the number of STARTTLS
	    commands that have failed since the IMAP
	    service was started."
    ::= { ex2Imap4Entry 67 }

ex2im4STARTTLSRate OBJECT-TYPE
    SYNTAX     Gauge32
    MAX-ACCESS read-only
    STATUS     current
    DESCRIPTION
	    "STARTTLS Rate is the number of STARTTLS
	    commands per second."
    ::= { ex2Imap4Entry 68 }

ex2im4STARTTLSTotal OBJECT-TYPE
    SYNTAX     Gauge32
    MAX-ACCESS read-only
    STATUS     current
    DESCRIPTION
	    "STARTTLS Total is the total number of STARTTLS
	    commands that have been received since the IMAP
	    service was started."
    ::= { ex2Imap4Entry 69 }

ex2im4SearchFailures OBJECT-TYPE
    SYNTAX     Gauge32
    MAX-ACCESS read-only
    STATUS     current
    DESCRIPTION
	    "Search Failures is the number of SEARCH
	    commands that have failed since the IMAP
	    service was started."
    ::= { ex2Imap4Entry 70 }

ex2im4SearchRate OBJECT-TYPE
    SYNTAX     Gauge32
    MAX-ACCESS read-only
    STATUS     current
    DESCRIPTION
	    "Search Rate is the number of SEARCH commands
	    per second."
    ::= { ex2Imap4Entry 71 }

ex2im4SearchTotal OBJECT-TYPE
    SYNTAX     Gauge32
    MAX-ACCESS read-only
    STATUS     current
    DESCRIPTION
	    "Search Total is the total number of SEARCH
	    commands that have been received since the IMAP
	    service was started."
    ::= { ex2Imap4Entry 72 }

ex2im4SelectFailures OBJECT-TYPE
    SYNTAX     Gauge32
    MAX-ACCESS read-only
    STATUS     current
    DESCRIPTION
	    "Select Failures is the number of SELECT
	    commands that have failed since the IMAP
	    service was started."
    ::= { ex2Imap4Entry 73 }

ex2im4SelectRate OBJECT-TYPE
    SYNTAX     Gauge32
    MAX-ACCESS read-only
    STATUS     current
    DESCRIPTION
	    "Select Rate is the number of SELECT commands
	    per second."
    ::= { ex2Imap4Entry 74 }

ex2im4SelectTotal OBJECT-TYPE
    SYNTAX     Gauge32
    MAX-ACCESS read-only
    STATUS     current
    DESCRIPTION
	    "Select Total is the total number of SELECT
	    commands that have been received since the IMAP
	    service was started."
    ::= { ex2Imap4Entry 75 }

ex2im4StatusFailures OBJECT-TYPE
    SYNTAX     Gauge32
    MAX-ACCESS read-only
    STATUS     current
    DESCRIPTION
	    "Status Failures is the number of STATUS
	    commands that have failed since the IMAP
	    service was started."
    ::= { ex2Imap4Entry 76 }

ex2im4StatusRate OBJECT-TYPE
    SYNTAX     Gauge32
    MAX-ACCESS read-only
    STATUS     current
    DESCRIPTION
	    "Status Rate is the number of STATUS commands
	    per second."
    ::= { ex2Imap4Entry 77 }

ex2im4StatusTotal OBJECT-TYPE
    SYNTAX     Gauge32
    MAX-ACCESS read-only
    STATUS     current
    DESCRIPTION
	    "Status Total is the total number of STATUS
	    commands that have been received since the IMAP
	    service was started."
    ::= { ex2Imap4Entry 78 }

ex2im4StoreFailures OBJECT-TYPE
    SYNTAX     Gauge32
    MAX-ACCESS read-only
    STATUS     current
    DESCRIPTION
	    "Store Failures is the number of STORE commands
	    that have failed since the IMAP service was
	    started."
    ::= { ex2Imap4Entry 79 }

ex2im4StoreRate OBJECT-TYPE
    SYNTAX     Gauge32
    MAX-ACCESS read-only
    STATUS     current
    DESCRIPTION
	    "Store Rate is the number of STORE commands per
	    second."
    ::= { ex2Imap4Entry 80 }

ex2im4StoreTotal OBJECT-TYPE
    SYNTAX     Gauge32
    MAX-ACCESS read-only
    STATUS     current
    DESCRIPTION
	    "Store Total is the total number of STORE
	    commands that have been received since the IMAP
	    service was started."
    ::= { ex2Imap4Entry 81 }

ex2im4SubscribeFailures OBJECT-TYPE
    SYNTAX     Gauge32
    MAX-ACCESS read-only
    STATUS     current
    DESCRIPTION
	    "Subscribe Failures is the number of SUBSCRIBE
	    commands that have failed since the IMAP
	    service was started."
    ::= { ex2Imap4Entry 82 }

ex2im4SubscribeRate OBJECT-TYPE
    SYNTAX     Gauge32
    MAX-ACCESS read-only
    STATUS     current
    DESCRIPTION
	    "Subscribe Rate is the number of SUBSCRIBE
	    commands per second."
    ::= { ex2Imap4Entry 83 }

ex2im4SubscribeTotal OBJECT-TYPE
    SYNTAX     Gauge32
    MAX-ACCESS read-only
    STATUS     current
    DESCRIPTION
	    "Subscribe Total is the total number of
	    SUBSCRIBE commands that have been received
	    since the IMAP service was started."
    ::= { ex2Imap4Entry 84 }

ex2im4TotalConnections OBJECT-TYPE
    SYNTAX     Gauge32
    MAX-ACCESS read-only
    STATUS     current
    DESCRIPTION
	    "Connections Total is the total number of
	    connections that have been opened since the
	    IMAP service was started."
    ::= { ex2Imap4Entry 85 }

ex2im4UnsubscribeFailures OBJECT-TYPE
    SYNTAX     Gauge32
    MAX-ACCESS read-only
    STATUS     current
    DESCRIPTION
	    "Unsubscribe Failures is the number of
	    UNSUBCRIBE commands that have failed since the
	    IMAP service was started."
    ::= { ex2Imap4Entry 86 }

ex2im4UnsubscribeRate OBJECT-TYPE
    SYNTAX     Gauge32
    MAX-ACCESS read-only
    STATUS     current
    DESCRIPTION
	    "Unsubscribe Rate is the number of UNSUBSCRIBE
	    commands per second."
    ::= { ex2Imap4Entry 87 }

ex2im4UnsubscribeTotal OBJECT-TYPE
    SYNTAX     Gauge32
    MAX-ACCESS read-only
    STATUS     current
    DESCRIPTION
	    "Unsubscribe Total is the total number of
	    UNSUBSCRIBE commands that have been received
	    since the IMAP service was started."
    ::= { ex2Imap4Entry 88 }

ex2MailSubmissionTable OBJECT-TYPE
    SYNTAX     SEQUENCE OF Ex2MailSubmissionEntry
    MAX-ACCESS not-accessible
    STATUS     current
    DESCRIPTION
	    "A table containing performance information for
	    instances of 'MSExchangeMailSubmission'
	    objects."
    ::= { exchangeV2 50 }

ex2MailSubmissionEntry OBJECT-TYPE
    SYNTAX     Ex2MailSubmissionEntry
    MAX-ACCESS not-accessible
    STATUS     current
    DESCRIPTION
	    "Performance information for one particular
	    instance of 'MSExchangeMailSubmission' object."
    INDEX      { ex2msInstance }
    ::= { ex2MailSubmissionTable 1 }

Ex2MailSubmissionEntry ::= SEQUENCE {
    ex2msInstance InstanceName,
    ex2msFailedSubmissions Gauge32,
    ex2msFailedSubmissionsPerSecond Gauge32,
    ex2msHubServers Gauge32,
    ex2msHubServersInRetry Gauge32,
    ex2msSuccessfulSubmissions Gauge32,
    ex2msSuccessfulSubmsPerSecond Gauge32,
    ex2msTemporarySubmissionFailures Gauge32,
    ex2msTemporarySubmFailuresPerSec Gauge32
}

ex2msInstance OBJECT-TYPE
    SYNTAX     InstanceName
    MAX-ACCESS read-only
    STATUS     current
    DESCRIPTION
	    "Instance name."
    ::= { ex2MailSubmissionEntry 1 }

ex2msFailedSubmissions OBJECT-TYPE
    SYNTAX     Gauge32
    MAX-ACCESS read-only
    STATUS     current
    DESCRIPTION
	    "Failed Submissions is the number of failed
	    submissions."
    ::= { ex2MailSubmissionEntry 2 }

ex2msFailedSubmissionsPerSecond OBJECT-TYPE
    SYNTAX     Gauge32
    MAX-ACCESS read-only
    STATUS     current
    DESCRIPTION
	    "Failed Submissions Per Second"
    ::= { ex2MailSubmissionEntry 3 }

ex2msHubServers OBJECT-TYPE
    SYNTAX     Gauge32
    MAX-ACCESS read-only
    STATUS     current
    DESCRIPTION
	    "Hub Servers is the total number of hub servers
	    in the same ADSite."
    ::= { ex2MailSubmissionEntry 4 }

ex2msHubServersInRetry OBJECT-TYPE
    SYNTAX     Gauge32
    MAX-ACCESS read-only
    STATUS     current
    DESCRIPTION
	    "Hub Servers In Retry is the number of hub
	    servers in retry."
    ::= { ex2MailSubmissionEntry 5 }

ex2msSuccessfulSubmissions OBJECT-TYPE
    SYNTAX     Gauge32
    MAX-ACCESS read-only
    STATUS     current
    DESCRIPTION
	    "Successful Submissions is the number of
	    successful submissions."
    ::= { ex2MailSubmissionEntry 6 }

ex2msSuccessfulSubmsPerSecond OBJECT-TYPE
    SYNTAX     Gauge32
    MAX-ACCESS read-only
    STATUS     current
    DESCRIPTION
	    "Successful Submissions Per Second"
    ::= { ex2MailSubmissionEntry 7 }

ex2msTemporarySubmissionFailures OBJECT-TYPE
    SYNTAX     Gauge32
    MAX-ACCESS read-only
    STATUS     current
    DESCRIPTION
	    "Temporary Submission Failures is the number of
	    temporary submission failures."
    ::= { ex2MailSubmissionEntry 8 }

ex2msTemporarySubmFailuresPerSec OBJECT-TYPE
    SYNTAX     Gauge32
    MAX-ACCESS read-only
    STATUS     current
    DESCRIPTION
	    "Temporary Submission Failures per second is
	    the number of temporary submission failures per
	    second."
    ::= { ex2MailSubmissionEntry 9 }

ex2Pop3Table OBJECT-TYPE
    SYNTAX     SEQUENCE OF Ex2Pop3Entry
    MAX-ACCESS not-accessible
    STATUS     current
    DESCRIPTION
	    "A table containing performance information for
	    instances of 'MSExchangePop3' objects."
    ::= { exchangeV2 51 }

ex2Pop3Entry OBJECT-TYPE
    SYNTAX     Ex2Pop3Entry
    MAX-ACCESS not-accessible
    STATUS     current
    DESCRIPTION
	    "Performance information for one particular
	    instance of 'MSExchangePop3' object."
    INDEX      { ex2p3Instance }
    ::= { ex2Pop3Table 1 }

Ex2Pop3Entry ::= SEQUENCE {
    ex2p3Instance InstanceName,
    ex2p3AUTHFailures Gauge32,
    ex2p3AUTHRate Gauge32,
    ex2p3AUTHTotal Gauge32,
    ex2p3ActiveSSLConnections Gauge32,
    ex2p3AvgComndProcessTimeMillisec Gauge32,
    ex2p3CAPAFailures Gauge32,
    ex2p3CAPARate Gauge32,
    ex2p3CAPATotal Gauge32,
    ex2p3ConnectionsCurrent Gauge32,
    ex2p3ConnectionsFailed Gauge32,
    ex2p3ConnectionsRejected Gauge32,
    ex2p3ConnectionsTotal Gauge32,
    ex2p3DELEFailures Gauge32,
    ex2p3DELERate Gauge32,
    ex2p3DELETotal Gauge32,
    ex2p3InvalidCommands Gauge32,
    ex2p3InvalidCommandsRate Gauge32,
    ex2p3LISTFailures Gauge32,
    ex2p3LISTRate Gauge32,
    ex2p3LISTTotal Gauge32,
    ex2p3NOOPFailures Gauge32,
    ex2p3NOOPRate Gauge32,
    ex2p3NOOPTotal Gauge32,
    ex2p3PASSFailures Gauge32,
    ex2p3PASSRate Gauge32,
    ex2p3PASSTotal Gauge32,
    ex2p3QUITFailures Gauge32,
    ex2p3QUITRate Gauge32,
    ex2p3QUITTotal Gauge32,
    ex2p3RETRFailures Gauge32,
    ex2p3RETRRate Gauge32,
    ex2p3RETRTotal Gauge32,
    ex2p3RSETFailures Gauge32,
    ex2p3RSETRate Gauge32,
    ex2p3RSETTotal Gauge32,
    ex2p3SSLConnections Gauge32,
    ex2p3STATFailures Gauge32,
    ex2p3STATRate Gauge32,
    ex2p3STATTotal Gauge32,
    ex2p3STLSFailures Gauge32,
    ex2p3STLSRate Gauge32,
    ex2p3STLSTotal Gauge32,
    ex2p3TOPFailures Gauge32,
    ex2p3TOPRate Gauge32,
    ex2p3TOPTotal Gauge32,
    ex2p3UIDLFailures Gauge32,
    ex2p3UIDLRate Gauge32,
    ex2p3UIDLTotal Gauge32,
    ex2p3USERFailures Gauge32,
    ex2p3USERRate Gauge32,
    ex2p3USERTotal Gauge32
}

ex2p3Instance OBJECT-TYPE
    SYNTAX     InstanceName
    MAX-ACCESS read-only
    STATUS     current
    DESCRIPTION
	    "Instance name."
    ::= { ex2Pop3Entry 1 }

ex2p3AUTHFailures OBJECT-TYPE
    SYNTAX     Gauge32
    MAX-ACCESS read-only
    STATUS     current
    DESCRIPTION
	    "AUTH Failures is the number of AUTH commands
	    that have failed since the POP service was
	    started."
    ::= { ex2Pop3Entry 2 }

ex2p3AUTHRate OBJECT-TYPE
    SYNTAX     Gauge32
    MAX-ACCESS read-only
    STATUS     current
    DESCRIPTION
	    "AUTH Rate is the number of AUTH commands per
	    second."
    ::= { ex2Pop3Entry 3 }

ex2p3AUTHTotal OBJECT-TYPE
    SYNTAX     Gauge32
    MAX-ACCESS read-only
    STATUS     current
    DESCRIPTION
	    "AUTH Total is the total number of AUTH
	    commands that have been received since the POP
	    service was started."
    ::= { ex2Pop3Entry 4 }

ex2p3ActiveSSLConnections OBJECT-TYPE
    SYNTAX     Gauge32
    MAX-ACCESS read-only
    STATUS     current
    DESCRIPTION
	    "Active SSL Connections is the number of SSL or
	    TLS connections that are currently open on the
	    POP service."
    ::= { ex2Pop3Entry 5 }

ex2p3AvgComndProcessTimeMillisec OBJECT-TYPE
    SYNTAX     Gauge32
    MAX-ACCESS read-only
    STATUS     current
    DESCRIPTION
	    "Average Command Processing Time is the average
	    processing time, in milliseconds, for the last
	    1024 commands received from clients."
    ::= { ex2Pop3Entry 6 }

ex2p3CAPAFailures OBJECT-TYPE
    SYNTAX     Gauge32
    MAX-ACCESS read-only
    STATUS     current
    DESCRIPTION
	    "CAPA Failures is the number of CAPA commands
	    that have failed since the POP service was
	    started."
    ::= { ex2Pop3Entry 7 }

ex2p3CAPARate OBJECT-TYPE
    SYNTAX     Gauge32
    MAX-ACCESS read-only
    STATUS     current
    DESCRIPTION
	    "CAPA Rate is the number of CAPA commands per
	    second."
    ::= { ex2Pop3Entry 8 }

ex2p3CAPATotal OBJECT-TYPE
    SYNTAX     Gauge32
    MAX-ACCESS read-only
    STATUS     current
    DESCRIPTION
	    "CAPA Total is the total number of CAPA
	    commands that have been received since the POP
	    service was started."
    ::= { ex2Pop3Entry 9 }

ex2p3ConnectionsCurrent OBJECT-TYPE
    SYNTAX     Gauge32
    MAX-ACCESS read-only
    STATUS     current
    DESCRIPTION
	    "Current Connections is the number of
	    connections that are currently open on the POP
	    service."
    ::= { ex2Pop3Entry 10 }

ex2p3ConnectionsFailed OBJECT-TYPE
    SYNTAX     Gauge32
    MAX-ACCESS read-only
    STATUS     current
    DESCRIPTION
	    "Connections Failed is the number of
	    connections that have failed since the POP
	    service was started."
    ::= { ex2Pop3Entry 11 }

ex2p3ConnectionsRejected OBJECT-TYPE
    SYNTAX     Gauge32
    MAX-ACCESS read-only
    STATUS     current
    DESCRIPTION
	    "Connections Rejected is the number of
	    connections that have been rejected since the
	    POP service was started."
    ::= { ex2Pop3Entry 12 }

ex2p3ConnectionsTotal OBJECT-TYPE
    SYNTAX     Gauge32
    MAX-ACCESS read-only
    STATUS     current
    DESCRIPTION
	    "Connections Total is the total number of
	    connections that have been opened since the POP
	    service was started."
    ::= { ex2Pop3Entry 13 }

ex2p3DELEFailures OBJECT-TYPE
    SYNTAX     Gauge32
    MAX-ACCESS read-only
    STATUS     current
    DESCRIPTION
	    "DELE Failures is the number of DELE commands
	    that have failed since the POP service was
	    started."
    ::= { ex2Pop3Entry 14 }

ex2p3DELERate OBJECT-TYPE
    SYNTAX     Gauge32
    MAX-ACCESS read-only
    STATUS     current
    DESCRIPTION
	    "DELE Rate is the number of DELE commands per
	    second."
    ::= { ex2Pop3Entry 15 }

ex2p3DELETotal OBJECT-TYPE
    SYNTAX     Gauge32
    MAX-ACCESS read-only
    STATUS     current
    DESCRIPTION
	    "DELE Total is the total number of DELE
	    commands that have been received since the POP
	    service was started."
    ::= { ex2Pop3Entry 16 }

ex2p3InvalidCommands OBJECT-TYPE
    SYNTAX     Gauge32
    MAX-ACCESS read-only
    STATUS     current
    DESCRIPTION
	    "Invalid Commands is the number of commands
	    that failed since the POP service was started
	    because the command was not valid for the state
	    of the connection."
    ::= { ex2Pop3Entry 17 }

ex2p3InvalidCommandsRate OBJECT-TYPE
    SYNTAX     Gauge32
    MAX-ACCESS read-only
    STATUS     current
    DESCRIPTION
	    "Invalid Commands Rate is the number of invalid
	    commands per second."
    ::= { ex2Pop3Entry 18 }

ex2p3LISTFailures OBJECT-TYPE
    SYNTAX     Gauge32
    MAX-ACCESS read-only
    STATUS     current
    DESCRIPTION
	    "LIST Failures is the number of LIST commands
	    that have failed since the POP service was
	    started."
    ::= { ex2Pop3Entry 19 }

ex2p3LISTRate OBJECT-TYPE
    SYNTAX     Gauge32
    MAX-ACCESS read-only
    STATUS     current
    DESCRIPTION
	    "LIST Rate is the number of LIST commands per
	    second."
    ::= { ex2Pop3Entry 20 }

ex2p3LISTTotal OBJECT-TYPE
    SYNTAX     Gauge32
    MAX-ACCESS read-only
    STATUS     current
    DESCRIPTION
	    "LIST Total is the total number of LIST
	    commands that have been received since the POP
	    service was started."
    ::= { ex2Pop3Entry 21 }

ex2p3NOOPFailures OBJECT-TYPE
    SYNTAX     Gauge32
    MAX-ACCESS read-only
    STATUS     current
    DESCRIPTION
	    "NOOP Failures is the number of NOOP commands
	    that have failed since the POP service was
	    started."
    ::= { ex2Pop3Entry 22 }

ex2p3NOOPRate OBJECT-TYPE
    SYNTAX     Gauge32
    MAX-ACCESS read-only
    STATUS     current
    DESCRIPTION
	    "NOOP Rate is the number of NOOP commands per
	    second."
    ::= { ex2Pop3Entry 23 }

ex2p3NOOPTotal OBJECT-TYPE
    SYNTAX     Gauge32
    MAX-ACCESS read-only
    STATUS     current
    DESCRIPTION
	    "NOOP Total is the total number of NOOP
	    commands that have been received since the POP
	    service was started."
    ::= { ex2Pop3Entry 24 }

ex2p3PASSFailures OBJECT-TYPE
    SYNTAX     Gauge32
    MAX-ACCESS read-only
    STATUS     current
    DESCRIPTION
	    "PASS Failures is the number of PASS commands
	    that have failed since the POP service was
	    started."
    ::= { ex2Pop3Entry 25 }

ex2p3PASSRate OBJECT-TYPE
    SYNTAX     Gauge32
    MAX-ACCESS read-only
    STATUS     current
    DESCRIPTION
	    "PASS Rate is the number of NOOP commands per
	    second."
    ::= { ex2Pop3Entry 26 }

ex2p3PASSTotal OBJECT-TYPE
    SYNTAX     Gauge32
    MAX-ACCESS read-only
    STATUS     current
    DESCRIPTION
	    "PASS Total is the total number of PASS
	    commands that have been received since the POP
	    service was started."
    ::= { ex2Pop3Entry 27 }

ex2p3QUITFailures OBJECT-TYPE
    SYNTAX     Gauge32
    MAX-ACCESS read-only
    STATUS     current
    DESCRIPTION
	    "QUIT Failures is the number of QUIT commands
	    that have failed since the POP service was
	    started."
    ::= { ex2Pop3Entry 28 }

ex2p3QUITRate OBJECT-TYPE
    SYNTAX     Gauge32
    MAX-ACCESS read-only
    STATUS     current
    DESCRIPTION
	    "QUIT Rate is the number of QUIT commands per
	    second."
    ::= { ex2Pop3Entry 29 }

ex2p3QUITTotal OBJECT-TYPE
    SYNTAX     Gauge32
    MAX-ACCESS read-only
    STATUS     current
    DESCRIPTION
	    "QUIT Total is the total number of QUIT
	    commands that have been received since the POP
	    service was started."
    ::= { ex2Pop3Entry 30 }

ex2p3RETRFailures OBJECT-TYPE
    SYNTAX     Gauge32
    MAX-ACCESS read-only
    STATUS     current
    DESCRIPTION
	    "RETR Failures is the number of RETR commands
	    that have failed since the POP service was
	    started."
    ::= { ex2Pop3Entry 31 }

ex2p3RETRRate OBJECT-TYPE
    SYNTAX     Gauge32
    MAX-ACCESS read-only
    STATUS     current
    DESCRIPTION
	    "RETR Rate is the number of RETR commands per
	    second."
    ::= { ex2Pop3Entry 32 }

ex2p3RETRTotal OBJECT-TYPE
    SYNTAX     Gauge32
    MAX-ACCESS read-only
    STATUS     current
    DESCRIPTION
	    "RETR Total is the total number of RETR
	    commands that have been received since the POP
	    service was started."
    ::= { ex2Pop3Entry 33 }

ex2p3RSETFailures OBJECT-TYPE
    SYNTAX     Gauge32
    MAX-ACCESS read-only
    STATUS     current
    DESCRIPTION
	    "RSET Failures is the number of RSET commands
	    that have failed since the POP service was
	    started."
    ::= { ex2Pop3Entry 34 }

ex2p3RSETRate OBJECT-TYPE
    SYNTAX     Gauge32
    MAX-ACCESS read-only
    STATUS     current
    DESCRIPTION
	    "RSET Rate is the number of RSET commands per
	    second."
    ::= { ex2Pop3Entry 35 }

ex2p3RSETTotal OBJECT-TYPE
    SYNTAX     Gauge32
    MAX-ACCESS read-only
    STATUS     current
    DESCRIPTION
	    "RSET Total is the total number of RSET
	    commands that have been received since the POP
	    service was started."
    ::= { ex2Pop3Entry 36 }

ex2p3SSLConnections OBJECT-TYPE
    SYNTAX     Gauge32
    MAX-ACCESS read-only
    STATUS     current
    DESCRIPTION
	    "SSL Connections is the total number of SSL or
	    TLS connections that have been opened since the
	    POP service was started."
    ::= { ex2Pop3Entry 37 }

ex2p3STATFailures OBJECT-TYPE
    SYNTAX     Gauge32
    MAX-ACCESS read-only
    STATUS     current
    DESCRIPTION
	    "STAT Failures is the number of STAT commands
	    that have failed since the POP service was
	    started."
    ::= { ex2Pop3Entry 38 }

ex2p3STATRate OBJECT-TYPE
    SYNTAX     Gauge32
    MAX-ACCESS read-only
    STATUS     current
    DESCRIPTION
	    "STAT Rate is the number of STAT commands per
	    second."
    ::= { ex2Pop3Entry 39 }

ex2p3STATTotal OBJECT-TYPE
    SYNTAX     Gauge32
    MAX-ACCESS read-only
    STATUS     current
    DESCRIPTION
	    "STAT Total is the total number of STAT
	    commands that have been received since the POP
	    service was started."
    ::= { ex2Pop3Entry 40 }

ex2p3STLSFailures OBJECT-TYPE
    SYNTAX     Gauge32
    MAX-ACCESS read-only
    STATUS     current
    DESCRIPTION
	    "STLS Failures is the number of STLS commands
	    that have failed since the POP service was
	    started."
    ::= { ex2Pop3Entry 41 }

ex2p3STLSRate OBJECT-TYPE
    SYNTAX     Gauge32
    MAX-ACCESS read-only
    STATUS     current
    DESCRIPTION
	    "STLS Rate is the number of STLS commands per
	    second."
    ::= { ex2Pop3Entry 42 }

ex2p3STLSTotal OBJECT-TYPE
    SYNTAX     Gauge32
    MAX-ACCESS read-only
    STATUS     current
    DESCRIPTION
	    "STLS Total is the total number of STLS
	    commands that have been received since the POP
	    service was started."
    ::= { ex2Pop3Entry 43 }

ex2p3TOPFailures OBJECT-TYPE
    SYNTAX     Gauge32
    MAX-ACCESS read-only
    STATUS     current
    DESCRIPTION
	    "TOP Failures is the number of TOP commands
	    that have failed since the POP service was
	    started."
    ::= { ex2Pop3Entry 44 }

ex2p3TOPRate OBJECT-TYPE
    SYNTAX     Gauge32
    MAX-ACCESS read-only
    STATUS     current
    DESCRIPTION
	    "TOP Rate is the number of TOP commands per
	    second."
    ::= { ex2Pop3Entry 45 }

ex2p3TOPTotal OBJECT-TYPE
    SYNTAX     Gauge32
    MAX-ACCESS read-only
    STATUS     current
    DESCRIPTION
	    "TOP Total is the total number of TOP commands
	    that have been received since the POP service
	    was started."
    ::= { ex2Pop3Entry 46 }

ex2p3UIDLFailures OBJECT-TYPE
    SYNTAX     Gauge32
    MAX-ACCESS read-only
    STATUS     current
    DESCRIPTION
	    "UIDL Failures is the number of UIDL commands
	    that have failed since the POP service was
	    started."
    ::= { ex2Pop3Entry 47 }

ex2p3UIDLRate OBJECT-TYPE
    SYNTAX     Gauge32
    MAX-ACCESS read-only
    STATUS     current
    DESCRIPTION
	    "UIDL Rate is the number of UIDL commands per
	    second."
    ::= { ex2Pop3Entry 48 }

ex2p3UIDLTotal OBJECT-TYPE
    SYNTAX     Gauge32
    MAX-ACCESS read-only
    STATUS     current
    DESCRIPTION
	    "UIDL Total is the total number of UIDL
	    commands that have been received since the POP
	    service was started."
    ::= { ex2Pop3Entry 49 }

ex2p3USERFailures OBJECT-TYPE
    SYNTAX     Gauge32
    MAX-ACCESS read-only
    STATUS     current
    DESCRIPTION
	    "USER Failures is the number of USER commands
	    that have failed since the POP service was
	    restarted."
    ::= { ex2Pop3Entry 50 }

ex2p3USERRate OBJECT-TYPE
    SYNTAX     Gauge32
    MAX-ACCESS read-only
    STATUS     current
    DESCRIPTION
	    "USER Rate is the number of USER commands per
	    second."
    ::= { ex2Pop3Entry 51 }

ex2p3USERTotal OBJECT-TYPE
    SYNTAX     Gauge32
    MAX-ACCESS read-only
    STATUS     current
    DESCRIPTION
	    "USER Total is the total number of USER
	    commands that have been received since the POP
	    service was started."
    ::= { ex2Pop3Entry 52 }

ex2SANSPIProxy OBJECT IDENTIFIER
    ::= { exchangeV2 52 }

ex2SANSPIPBytesTransmittedPerSec OBJECT-TYPE
    SYNTAX     Gauge32
    MAX-ACCESS read-only
    STATUS     current
    DESCRIPTION
	    "Bytes Transmitted/sec is the rate at which
	    data bytes are sent to the Domain Controller
	    and clients by the NSPI Proxy."
    ::= { ex2SANSPIProxy 1 }

ex2SANSPIPClientConnectionCount OBJECT-TYPE
    SYNTAX     Gauge32
    MAX-ACCESS read-only
    STATUS     current
    DESCRIPTION
	    "Client Connect Count is the number of clients
	    that are presently connected to the NSPI
	    Proxy."
    ::= { ex2SANSPIProxy 2 }

ex2SANSPIPClientConnectionPerSec OBJECT-TYPE
    SYNTAX     Gauge32
    MAX-ACCESS read-only
    STATUS     current
    DESCRIPTION
	    "Client Connection/sec is the rate at which new
	    client are connecting to the NSPI Proxy."
    ::= { ex2SANSPIProxy 3 }

ex2SANSPIPClientDisconnectPerSec OBJECT-TYPE
    SYNTAX     Gauge32
    MAX-ACCESS read-only
    STATUS     current
    DESCRIPTION
	    "Rate that clients are disconnecting from the
	    NSPI Proxy.  This counts normal disconnects and
	    disconnects forced by the Proxy after a network
	    error."
    ::= { ex2SANSPIProxy 4 }

ex2SANSPIPClientReferrals OBJECT-TYPE
    SYNTAX     Gauge32
    MAX-ACCESS read-only
    STATUS     current
    DESCRIPTION
	    "How many MAPI client Referral requests have
	    been successfully satisfied, since the NSPI
	    Proxy service was started."
    ::= { ex2SANSPIProxy 5 }

ex2SANSPIPClientReferralsPerSec OBJECT-TYPE
    SYNTAX     Gauge32
    MAX-ACCESS read-only
    STATUS     current
    DESCRIPTION
	    "Rate that MAPI client Referral requests are
	    satisfied."
    ::= { ex2SANSPIProxy 6 }

ex2SANSPIPCumulatClientConnCount OBJECT-TYPE
    SYNTAX     Gauge32
    MAX-ACCESS read-only
    STATUS     current
    DESCRIPTION
	    "Total client connections made with NSPI Proxy
	    for the life of the process."
    ::= { ex2SANSPIProxy 7 }

ex2SANSPIPFailedClientConnPerSec OBJECT-TYPE
    SYNTAX     Gauge32
    MAX-ACCESS read-only
    STATUS     current
    DESCRIPTION
	    "Failed Client Connections/sec is the rate at
	    which connect operations from clients have
	    failed."
    ::= { ex2SANSPIProxy 8 }

ex2SANSPIPFailedReadsPerSec OBJECT-TYPE
    SYNTAX     Gauge32
    MAX-ACCESS read-only
    STATUS     current
    DESCRIPTION
	    "Failed Reads/sec is the rate at which read
	    operations from the Domain Controller and
	    clients have failed."
    ::= { ex2SANSPIProxy 9 }

ex2SANSPIPFailedServerConnPerSec OBJECT-TYPE
    SYNTAX     Gauge32
    MAX-ACCESS read-only
    STATUS     current
    DESCRIPTION
	    "Failed Server Connections/sec is the rate at
	    which connect operations to the Domain
	    Controller have failed."
    ::= { ex2SANSPIProxy 10 }

ex2SANSPIPFailedWritesPerSec OBJECT-TYPE
    SYNTAX     Gauge32
    MAX-ACCESS read-only
    STATUS     current
    DESCRIPTION
	    "Failed Writes/sec is the rate at which write
	    operationss to the Domain Controller and
	    clients have failed."
    ::= { ex2SANSPIProxy 11 }

ex2SANSPIPPacketsTransmittPerSec OBJECT-TYPE
    SYNTAX     Gauge32
    MAX-ACCESS read-only
    STATUS     current
    DESCRIPTION
	    "Packets Transmitted/sec is the rate at which
	    data packets are sent to the Domain Controller
	    and clients by the NSPI Proxy."
    ::= { ex2SANSPIProxy 12 }

ex2SANSPIPPeakClientConnections OBJECT-TYPE
    SYNTAX     Gauge32
    MAX-ACCESS read-only
    STATUS     current
    DESCRIPTION
	    "Peak Client Connections is the maximum number
	    of clients that have been connected to the NSPI
	    Proxy at any one point, since the proxy was
	    started."
    ::= { ex2SANSPIProxy 13 }

ex2SANSPIPPeakWorkerThreads OBJECT-TYPE
    SYNTAX     Gauge32
    MAX-ACCESS read-only
    STATUS     current
    DESCRIPTION
	    "Peak Worker Threads is the maximum number of
	    worker threads the NSPI Proxy has had since it
	    was started."
    ::= { ex2SANSPIProxy 14 }

ex2SANSPIPTotalFailedClientConns OBJECT-TYPE
    SYNTAX     Gauge32
    MAX-ACCESS read-only
    STATUS     current
    DESCRIPTION
	    "Total Failed Client Connections is the number
	    of failed connect operations from clients. 
	    This is an accumulator counting all failures
	    since the NSPI Proxy was started."
    ::= { ex2SANSPIProxy 15 }

ex2SANSPIPTotalFailedReads OBJECT-TYPE
    SYNTAX     Gauge32
    MAX-ACCESS read-only
    STATUS     current
    DESCRIPTION
	    "Total Failed Reads is the number of failed
	    read operations from the Domain Controller and
	    clients.  This is an accumulator counting all
	    failures since the NSPI Proxy was started."
    ::= { ex2SANSPIProxy 16 }

ex2SANSPIPTotalFailedServerConns OBJECT-TYPE
    SYNTAX     Gauge32
    MAX-ACCESS read-only
    STATUS     current
    DESCRIPTION
	    "Total Failed Server Connections is the number
	    of failed connect operations to the Domain
	    Controller.  This is an accumulator counting
	    all failures since the NSPI Proxy was started."
    ::= { ex2SANSPIProxy 17 }

ex2SANSPIPTotalFailedWrites OBJECT-TYPE
    SYNTAX     Gauge32
    MAX-ACCESS read-only
    STATUS     current
    DESCRIPTION
	    "Total Failed Writes is the number of failed
	    write operations to the Domain Controller and
	    clients.  This is an accumulator counting all
	    failures since the NSPI Proxy was started."
    ::= { ex2SANSPIProxy 18 }

ex2SANSPIPWorkerThreadsInUse OBJECT-TYPE
    SYNTAX     Gauge32
    MAX-ACCESS read-only
    STATUS     current
    DESCRIPTION
	    "Worker Threads in Use is the number of worker
	    threads currently active in the NSPI Proxy.  A
	    worker thread handles receiving and re-sending
	    data between the Domain Controller and
	    connected clients.	More worker threads are
	    necessary to handle large numbers of clients."
    ::= { ex2SANSPIProxy 19 }

ex2TransportBatchPointTable OBJECT-TYPE
    SYNTAX     SEQUENCE OF Ex2TransportBatchPointEntry
    MAX-ACCESS not-accessible
    STATUS     current
    DESCRIPTION
	    "A table containing performance information for
	    instances of 'MSExchangeTransport Batch Point'
	    objects."
    ::= { exchangeV2 53 }

ex2TransportBatchPointEntry OBJECT-TYPE
    SYNTAX     Ex2TransportBatchPointEntry
    MAX-ACCESS not-accessible
    STATUS     current
    DESCRIPTION
	    "Performance information for one particular
	    instance of 'MSExchangeTransport Batch Point'
	    object."
    INDEX      { ex2tbpInstance }
    ::= { ex2TransportBatchPointTable 1 }

Ex2TransportBatchPointEntry ::= SEQUENCE {
    ex2tbpInstance InstanceName,
    ex2tbpBatchSizeExecutedTotal Gauge32,
    ex2tbpBatchSizeExecutedPerSec Gauge32,
    ex2tbpBatchesExecBackgroundTotal Gauge32,
    ex2tbpBatchesExecBackgroundPrSec Gauge32,
    ex2tbpBatchesExecutedNormalTotal Gauge32,
    ex2tbpBatcheExecutedNormalPerSec Gauge32,
    ex2tbpBatchesExecutedTotal Gauge32,
    ex2tbpBatchesExecutedPerSec Gauge32,
    ex2tbpBatchesPendingTotal Gauge32,
    ex2tbpBatchesPendingPerSec Gauge32,
    ex2tbpBatchesTimedOutTotal Gauge32,
    ex2tbpBatchesTimedOutPerSec Gauge32,
    ex2tbpBatchesWaitingCurrent Gauge32,
    ex2tbpBatchesWaitingTotal Gauge32,
    ex2tbpBatchesWaitingPerSec Gauge32,
    ex2tbpCursorsClosedTotal Gauge32,
    ex2tbpCursorsClosedPerSec Gauge32,
    ex2tbpCursorsOpenedTotal Gauge32,
    ex2tbpCursorsOpenedPerSec Gauge32,
    ex2tbpDatabaseConnectionsCurrent Gauge32,
    ex2tbpDatabaseConnsRejectedTotal Gauge32,
    ex2tbpDatabaseConnsRejectdPerSec Gauge32,
    ex2tbpTransactionsAbortedTotal Gauge32,
    ex2tbpTransactionsAbortedPerSec Gauge32,
    ex2tbpTransactionsCommittedTotal Gauge32,
    ex2tbpTransactionCommittedPerSec Gauge32
}

ex2tbpInstance OBJECT-TYPE
    SYNTAX     InstanceName
    MAX-ACCESS read-only
    STATUS     current
    DESCRIPTION
	    "Instance name."
    ::= { ex2TransportBatchPointEntry 1 }

ex2tbpBatchSizeExecutedTotal OBJECT-TYPE
    SYNTAX     Gauge32
    MAX-ACCESS read-only
    STATUS     current
    DESCRIPTION
	    "The Batch size executed total performance
	    counter should only be used if Microsoft
	    Product Support services requests this
	    information to troubleshoot a complex
	    ESE-related performance problem."
    ::= { ex2TransportBatchPointEntry 2 }

ex2tbpBatchSizeExecutedPerSec OBJECT-TYPE
    SYNTAX     Gauge32
    MAX-ACCESS read-only
    STATUS     current
    DESCRIPTION
	    "The Batch size executed/sec performance
	    counter should only be used if Microsoft
	    Product Support services requests this
	    information to troubleshoot a complex
	    ESE-related performance problem."
    ::= { ex2TransportBatchPointEntry 3 }

ex2tbpBatchesExecBackgroundTotal OBJECT-TYPE
    SYNTAX     Gauge32
    MAX-ACCESS read-only
    STATUS     current
    DESCRIPTION
	    "The Batches executed background total
	    performance counter should only be used if
	    Microsoft Product Support services requests
	    this information to troubleshoot a complex
	    ESE-related performance problem."
    ::= { ex2TransportBatchPointEntry 4 }

ex2tbpBatchesExecBackgroundPrSec OBJECT-TYPE
    SYNTAX     Gauge32
    MAX-ACCESS read-only
    STATUS     current
    DESCRIPTION
	    "The Batches executed background/sec
	    performance counter should only be used if
	    Microsoft Product Support services requests
	    this information to troubleshoot a complex
	    ESE-related performance problem."
    ::= { ex2TransportBatchPointEntry 5 }

ex2tbpBatchesExecutedNormalTotal OBJECT-TYPE
    SYNTAX     Gauge32
    MAX-ACCESS read-only
    STATUS     current
    DESCRIPTION
	    "The Batches executed normal total performance
	    counter should only be used if Microsoft
	    Product Support services requests this
	    information to troubleshoot a complex
	    ESE-related performance problem."
    ::= { ex2TransportBatchPointEntry 6 }

ex2tbpBatcheExecutedNormalPerSec OBJECT-TYPE
    SYNTAX     Gauge32
    MAX-ACCESS read-only
    STATUS     current
    DESCRIPTION
	    "The Batches executed normal/sec performance
	    counter should only be used if Microsoft
	    Product Support services requests this
	    information to troubleshoot a complex
	    ESE-related performance problem."
    ::= { ex2TransportBatchPointEntry 7 }

ex2tbpBatchesExecutedTotal OBJECT-TYPE
    SYNTAX     Gauge32
    MAX-ACCESS read-only
    STATUS     current
    DESCRIPTION
	    "The Batches executed total performance counter
	    should only be used if Microsoft Product
	    Support services requests this information to
	    troubleshoot a complex ESE-related performance
	    problem."
    ::= { ex2TransportBatchPointEntry 8 }

ex2tbpBatchesExecutedPerSec OBJECT-TYPE
    SYNTAX     Gauge32
    MAX-ACCESS read-only
    STATUS     current
    DESCRIPTION
	    "The Batches executed/sec performance counter
	    should only be used if Microsoft Product
	    Support services requests this information to
	    troubleshoot a complex ESE-related performance
	    problem."
    ::= { ex2TransportBatchPointEntry 9 }

ex2tbpBatchesPendingTotal OBJECT-TYPE
    SYNTAX     Gauge32
    MAX-ACCESS read-only
    STATUS     current
    DESCRIPTION
	    "The Batches pending total performance counter
	    should only be used if Microsoft Product
	    Support services requests this information to
	    troubleshoot a complex ESE-related performance
	    problem."
    ::= { ex2TransportBatchPointEntry 10 }

ex2tbpBatchesPendingPerSec OBJECT-TYPE
    SYNTAX     Gauge32
    MAX-ACCESS read-only
    STATUS     current
    DESCRIPTION
	    "The Batches pending/sec performance counter
	    should only be used if Microsoft Product
	    Support services requests this information to
	    troubleshoot a complex ESE-related performance
	    problem."
    ::= { ex2TransportBatchPointEntry 11 }

ex2tbpBatchesTimedOutTotal OBJECT-TYPE
    SYNTAX     Gauge32
    MAX-ACCESS read-only
    STATUS     current
    DESCRIPTION
	    "The Batches timed out total performance
	    counter should only be used if Microsoft
	    Product Support services requests this
	    information to troubleshoot a complex
	    ESE-related performance problem."
    ::= { ex2TransportBatchPointEntry 12 }

ex2tbpBatchesTimedOutPerSec OBJECT-TYPE
    SYNTAX     Gauge32
    MAX-ACCESS read-only
    STATUS     current
    DESCRIPTION
	    "The Batches timed out/sec performance counter
	    should only be used if Microsoft Product
	    Support services requests this information to
	    troubleshoot a complex ESE-related performance
	    problem."
    ::= { ex2TransportBatchPointEntry 13 }

ex2tbpBatchesWaitingCurrent OBJECT-TYPE
    SYNTAX     Gauge32
    MAX-ACCESS read-only
    STATUS     current
    DESCRIPTION
	    "The Batches waiting current performance
	    counter should only be used if Microsoft
	    Product Support services requests this
	    information to troubleshoot a complex
	    ESE-related performance problem."
    ::= { ex2TransportBatchPointEntry 14 }

ex2tbpBatchesWaitingTotal OBJECT-TYPE
    SYNTAX     Gauge32
    MAX-ACCESS read-only
    STATUS     current
    DESCRIPTION
	    "The Batches waiting total performance counter
	    should only be used if Microsoft Product
	    Support services requests this information to
	    troubleshoot a complex ESE-related performance
	    problem."
    ::= { ex2TransportBatchPointEntry 15 }

ex2tbpBatchesWaitingPerSec OBJECT-TYPE
    SYNTAX     Gauge32
    MAX-ACCESS read-only
    STATUS     current
    DESCRIPTION
	    "The Batches waiting/sec performance counter
	    should only be used if Microsoft Product
	    Support services requests this information to
	    troubleshoot a complex ESE-related performance
	    problem."
    ::= { ex2TransportBatchPointEntry 16 }

ex2tbpCursorsClosedTotal OBJECT-TYPE
    SYNTAX     Gauge32
    MAX-ACCESS read-only
    STATUS     current
    DESCRIPTION
	    "The Cursors closed total performance counter
	    should only be used if Microsoft Product
	    Support services requests this information to
	    troubleshoot a complex ESE-related performance
	    problem."
    ::= { ex2TransportBatchPointEntry 17 }

ex2tbpCursorsClosedPerSec OBJECT-TYPE
    SYNTAX     Gauge32
    MAX-ACCESS read-only
    STATUS     current
    DESCRIPTION
	    "The Cursors closed/sec performance counter
	    should only be used if Microsoft Product
	    Support services requests this information to
	    troubleshoot a complex ESE-related performance
	    problem."
    ::= { ex2TransportBatchPointEntry 18 }

ex2tbpCursorsOpenedTotal OBJECT-TYPE
    SYNTAX     Gauge32
    MAX-ACCESS read-only
    STATUS     current
    DESCRIPTION
	    "The Cursors opened total performance counter
	    should only be used if Microsoft Product
	    Support services requests this information to
	    troubleshoot a complex ESE-related performance
	    problem."
    ::= { ex2TransportBatchPointEntry 19 }

ex2tbpCursorsOpenedPerSec OBJECT-TYPE
    SYNTAX     Gauge32
    MAX-ACCESS read-only
    STATUS     current
    DESCRIPTION
	    "The Cursors opened/sec performance counter
	    should only be used if Microsoft Product
	    Support services requests this information to
	    troubleshoot a complex ESE-related performance
	    problem."
    ::= { ex2TransportBatchPointEntry 20 }

ex2tbpDatabaseConnectionsCurrent OBJECT-TYPE
    SYNTAX     Gauge32
    MAX-ACCESS read-only
    STATUS     current
    DESCRIPTION
	    "The Database connections current performance
	    counter should only be used if Microsoft
	    Product Support services requests this
	    information to troubleshoot a complex
	    ESE-related performance problem."
    ::= { ex2TransportBatchPointEntry 21 }

ex2tbpDatabaseConnsRejectedTotal OBJECT-TYPE
    SYNTAX     Gauge32
    MAX-ACCESS read-only
    STATUS     current
    DESCRIPTION
	    "The Database connections rejected total
	    performance counter should only be used if
	    Microsoft Product Support services requests
	    this information to troubleshoot a complex
	    ESE-related performance problem."
    ::= { ex2TransportBatchPointEntry 22 }

ex2tbpDatabaseConnsRejectdPerSec OBJECT-TYPE
    SYNTAX     Gauge32
    MAX-ACCESS read-only
    STATUS     current
    DESCRIPTION
	    "The Database connections rejected/sec
	    performance counter should only be used if
	    Microsoft Product Support services requests
	    this information to troubleshoot a complex
	    ESE-related performance problem."
    ::= { ex2TransportBatchPointEntry 23 }

ex2tbpTransactionsAbortedTotal OBJECT-TYPE
    SYNTAX     Gauge32
    MAX-ACCESS read-only
    STATUS     current
    DESCRIPTION
	    "This counter should only be used if Microsoft
	    Product Support services advises that they need
	    this information to troubleshoot a complex
	    ESE-related performance issue."
    ::= { ex2TransportBatchPointEntry 24 }

ex2tbpTransactionsAbortedPerSec OBJECT-TYPE
    SYNTAX     Gauge32
    MAX-ACCESS read-only
    STATUS     current
    DESCRIPTION
	    "The Transactions aborted/sec performance
	    counter should only be used if Microsoft
	    Product Support services requests this
	    information to troubleshoot a complex
	    ESE-related performance problem."
    ::= { ex2TransportBatchPointEntry 25 }

ex2tbpTransactionsCommittedTotal OBJECT-TYPE
    SYNTAX     Gauge32
    MAX-ACCESS read-only
    STATUS     current
    DESCRIPTION
	    "This counter should only be used if Microsoft
	    Product Support services advises that they need
	    this information to troubleshoot a complex
	    ESE-related performance issue."
    ::= { ex2TransportBatchPointEntry 26 }

ex2tbpTransactionCommittedPerSec OBJECT-TYPE
    SYNTAX     Gauge32
    MAX-ACCESS read-only
    STATUS     current
    DESCRIPTION
	    "The Transactions committed/sec performance
	    counter should only be used if Microsoft
	    Product Support services requests this
	    information to troubleshoot a complex
	    ESE-related performance problem."
    ::= { ex2TransportBatchPointEntry 27 }

ex2TransportDSNTable OBJECT-TYPE
    SYNTAX     SEQUENCE OF Ex2TransportDSNEntry
    MAX-ACCESS not-accessible
    STATUS     current
    DESCRIPTION
	    "A table containing performance information for
	    instances of 'MSExchangeTransport DSN'
	    objects."
    ::= { exchangeV2 54 }

ex2TransportDSNEntry OBJECT-TYPE
    SYNTAX     Ex2TransportDSNEntry
    MAX-ACCESS not-accessible
    STATUS     current
    DESCRIPTION
	    "Performance information for one particular
	    instance of 'MSExchangeTransport DSN' object."
    INDEX      { ex2tdsnInstance }
    ::= { ex2TransportDSNTable 1 }

Ex2TransportDSNEntry ::= SEQUENCE {
    ex2tdsnInstance InstanceName,
    ex2tdsnDelayDSNs Gauge32,
    ex2tdsnDeliveredDSNs Gauge32,
    ex2tdsnExpandedDSNs Gauge32,
    ex2tdsnFailureDSNsTotal Gauge32,
    ex2tdsnRelayDSNs Gauge32
}

ex2tdsnInstance OBJECT-TYPE
    SYNTAX     InstanceName
    MAX-ACCESS read-only
    STATUS     current
    DESCRIPTION
	    "Instance name."
    ::= { ex2TransportDSNEntry 1 }

ex2tdsnDelayDSNs OBJECT-TYPE
    SYNTAX     Gauge32
    MAX-ACCESS read-only
    STATUS     current
    DESCRIPTION
	    "Delay DSNs is the number of delivery status
	    notifications (DSNs) that have been generated."
    ::= { ex2TransportDSNEntry 2 }

ex2tdsnDeliveredDSNs OBJECT-TYPE
    SYNTAX     Gauge32
    MAX-ACCESS read-only
    STATUS     current
    DESCRIPTION
	    "Delivered DSNs is the number of delivered
	    delivery status notifications (DSNs)
	    generated."
    ::= { ex2TransportDSNEntry 3 }

ex2tdsnExpandedDSNs OBJECT-TYPE
    SYNTAX     Gauge32
    MAX-ACCESS read-only
    STATUS     current
    DESCRIPTION
	    "Expanded DSNs is the number of expanded
	    delivery status notifications (DSNs)
	    generated."
    ::= { ex2TransportDSNEntry 4 }

ex2tdsnFailureDSNsTotal OBJECT-TYPE
    SYNTAX     Gauge32
    MAX-ACCESS read-only
    STATUS     current
    DESCRIPTION
	    "Failure DSNs is the number of failure delivery
	    status notifications (DSNs) that have been
	    generated."
    ::= { ex2TransportDSNEntry 5 }

ex2tdsnRelayDSNs OBJECT-TYPE
    SYNTAX     Gauge32
    MAX-ACCESS read-only
    STATUS     current
    DESCRIPTION
	    "Relay DSNs is the number of relayed DSNs that
	    were generated."
    ::= { ex2TransportDSNEntry 6 }

ex2TransportDatabaseTable OBJECT-TYPE
    SYNTAX     SEQUENCE OF Ex2TransportDatabaseEntry
    MAX-ACCESS not-accessible
    STATUS     current
    DESCRIPTION
	    "A table containing performance information for
	    instances of 'MSExchangeTransport Database'
	    objects."
    ::= { exchangeV2 55 }

ex2TransportDatabaseEntry OBJECT-TYPE
    SYNTAX     Ex2TransportDatabaseEntry
    MAX-ACCESS not-accessible
    STATUS     current
    DESCRIPTION
	    "Performance information for one particular
	    instance of 'MSExchangeTransport Database'
	    object."
    INDEX      { ex2tbInstance }
    ::= { ex2TransportDatabaseTable 1 }

Ex2TransportDatabaseEntry ::= SEQUENCE {
    ex2tbInstance InstanceName,
    ex2tbColumCacheLoadTotal Gauge32,
    ex2tbColumCacheLoadPerSec Gauge32,
    ex2tbColumCacheSaveTotal Gauge32,
    ex2tbColumCacheSavePerSec Gauge32,
    ex2tbColumnCacheLoadedBytesTotal Gauge32,
    ex2tbColumnCachLoadedBytesPerSec Gauge32,
    ex2tbColumnCacheLoadColumnsTotal Gauge32,
    ex2tbColumnCacheLoadedColumnsSec Gauge32,
    ex2tbColumnCacheSavedBytesTotal Gauge32,
    ex2tbColumnCacheSavedBytesPerSec Gauge32,
    ex2tbColumnCacheSavedColumnTotal Gauge32,
    ex2tbColumnCacheSaveColumnPerSec Gauge32,
    ex2tbDataRowClonesTotal Gauge32,
    ex2tbDataRowClonesPerSec Gauge32,
    ex2tbDataRowDeletesTotal Gauge32,
    ex2tbDataRowDeletesPerSec Gauge32,
    ex2tbDataRowLoadsTotal Gauge32,
    ex2tbDataRowLoadsPerSec Gauge32,
    ex2tbDataRowMinimizeMemoryTotal Gauge32,
    ex2tbDataRowMinimizeMemoryPerSec Gauge32,
    ex2tbDataRowMovesTotal Gauge32,
    ex2tbDataRowMovesPerSec Gauge32,
    ex2tbDataRowNewInsertsTotal Gauge32,
    ex2tbDataRowNewInsertsPerSec Gauge32,
    ex2tbDataRowSeeksPrefixTotal Gauge32,
    ex2tbDataRowSeeksPrefixPerSec Gauge32,
    ex2tbDataRowSeeksTotal Gauge32,
    ex2tbDataRowSeeksPerSec Gauge32,
    ex2tbDataRowUpdatesTotal Gauge32,
    ex2tbDataRowUpdatesPerSec Gauge32,
    ex2tbExtendPropertyByteReadTotal Gauge32,
    ex2tbExtendPropertyBytReadPerSec Gauge32,
    ex2tbExtenePropertyByteWritTotal Gauge32,
    ex2tbExtenPropertyByteWritPerSec Gauge32,
    ex2tbExtenedPropertyReadsTotal Gauge32,
    ex2tbExtenedPropertyReadsPerSec Gauge32,
    ex2tbExtenedPropertyWritesTotal Gauge32,
    ex2tbExtenedPropertyWritesPerSec Gauge32,
    ex2tbLazyBytesLoadPerformedTotal Gauge32,
    ex2tbLazyByteLoadPerformedPerSec Gauge32,
    ex2tbLazyBytesLoadRequestedTotal Gauge32,
    ex2tbLazyByteLoadRequestedPerSec Gauge32,
    ex2tbMailItemBeginCommitTotal Gauge32,
    ex2tbMailItemBeginCommitPerSec Gauge32,
    ex2tbMailItemCloneCreateTotal Gauge32,
    ex2tbMailItemCloneCreatePerSec Gauge32,
    ex2tbMailItemCommitImmediatTotal Gauge32,
    ex2tbMailItemCommitImmediaPerSec Gauge32,
    ex2tbMailItemCommitLazyTotal Gauge32,
    ex2tbMailItemCommitLazyPerSec Gauge32,
    ex2tbMailItemDehydrateTotal Gauge32,
    ex2tbMailItemDehydratePerSec Gauge32,
    ex2tbMailItemDeleteLazyTotal Gauge32,
    ex2tbMailItemDeleteLazyPerSec Gauge32,
    ex2tbMailItemLoadTotal Gauge32,
    ex2tbMailItemLoadPerSec Gauge32,
    ex2tbMailItemMaterialize Gauge32,
    ex2tbMailItemMaterializePerSec Gauge32,
    ex2tbMailItemNewTotal Gauge32,
    ex2tbMailItemNewPerSec Gauge32,
    ex2tbMailItemWriteMimeToTotal Gauge32,
    ex2tbMailItemWriteMimeToPerSec Gauge32,
    ex2tbStreamBytesReadTotal Gauge32,
    ex2tbStreamBytesReadPerSec Gauge32,
    ex2tbStreamBytesWrittenTotal Gauge32,
    ex2tbStreamBytesWrittenPerSec Gauge32,
    ex2tbStreamReadTotal Gauge32,
    ex2tbStreamReadPerSec Gauge32,
    ex2tbStreamSetLengthCount Gauge32,
    ex2tbStreamSetLengthPerSec Gauge32,
    ex2tbStreamWritesTotal Gauge32,
    ex2tbStreamWritesPerSec Gauge32
}

ex2tbInstance OBJECT-TYPE
    SYNTAX     InstanceName
    MAX-ACCESS read-only
    STATUS     current
    DESCRIPTION
	    "Instance name."
    ::= { ex2TransportDatabaseEntry 1 }

ex2tbColumCacheLoadTotal OBJECT-TYPE
    SYNTAX     Gauge32
    MAX-ACCESS read-only
    STATUS     current
    DESCRIPTION
	    "The Column cache load total performance
	    counter should only be used if Microsoft
	    Product Support services request this
	    information to troubleshoot a complex
	    ESE-related performance problem."
    ::= { ex2TransportDatabaseEntry 2 }

ex2tbColumCacheLoadPerSec OBJECT-TYPE
    SYNTAX     Gauge32
    MAX-ACCESS read-only
    STATUS     current
    DESCRIPTION
	    "The Column cache load/sec performance counter
	    should only be used if Microsoft Product
	    Support services requests this information to
	    troubleshoot a complex ESE-related performance
	    problem."
    ::= { ex2TransportDatabaseEntry 3 }

ex2tbColumCacheSaveTotal OBJECT-TYPE
    SYNTAX     Gauge32
    MAX-ACCESS read-only
    STATUS     current
    DESCRIPTION
	    "The Column cache save total performance
	    counter should only be used if Microsoft
	    Product Support services request this
	    information to troubleshoot a complex
	    ESE-related performance problem."
    ::= { ex2TransportDatabaseEntry 4 }

ex2tbColumCacheSavePerSec OBJECT-TYPE
    SYNTAX     Gauge32
    MAX-ACCESS read-only
    STATUS     current
    DESCRIPTION
	    "The Column cache save/sec performance counter
	    should only be used if Microsoft Product
	    Support services requests this information to
	    troubleshoot a complex ESE-related performance
	    problem."
    ::= { ex2TransportDatabaseEntry 5 }

ex2tbColumnCacheLoadedBytesTotal OBJECT-TYPE
    SYNTAX     Gauge32
    MAX-ACCESS read-only
    STATUS     current
    DESCRIPTION
	    "The Column cache loaded bytes total
	    performance counter should only be used if
	    Microsoft Product Support services request this
	    information to troubleshoot a complex
	    ESE-related performance problem."
    ::= { ex2TransportDatabaseEntry 6 }

ex2tbColumnCachLoadedBytesPerSec OBJECT-TYPE
    SYNTAX     Gauge32
    MAX-ACCESS read-only
    STATUS     current
    DESCRIPTION
	    "The Column cache loaded bytes/sec performance
	    counter should only be used if Microsoft
	    Product Support services requests this
	    information to troubleshoot a complex
	    ESE-related performance problem."
    ::= { ex2TransportDatabaseEntry 7 }

ex2tbColumnCacheLoadColumnsTotal OBJECT-TYPE
    SYNTAX     Gauge32
    MAX-ACCESS read-only
    STATUS     current
    DESCRIPTION
	    "The Column cache loaded columns total
	    performance counter should only be used if
	    Microsoft Product Support services request this
	    information to troubleshoot a complex
	    ESE-related performance problem."
    ::= { ex2TransportDatabaseEntry 8 }

ex2tbColumnCacheLoadedColumnsSec OBJECT-TYPE
    SYNTAX     Gauge32
    MAX-ACCESS read-only
    STATUS     current
    DESCRIPTION
	    "The Column cache loaded columns/sec
	    performance counter should only be used if
	    Microsoft Product Support services requests
	    this information to troubleshoot a complex
	    ESE-related performance problem."
    ::= { ex2TransportDatabaseEntry 9 }

ex2tbColumnCacheSavedBytesTotal OBJECT-TYPE
    SYNTAX     Gauge32
    MAX-ACCESS read-only
    STATUS     current
    DESCRIPTION
	    "The Column cache saved bytes total performance
	    counter should only be used if Microsoft
	    Product Support services request this
	    information to troubleshoot a complex
	    ESE-related performance problem."
    ::= { ex2TransportDatabaseEntry 10 }

ex2tbColumnCacheSavedBytesPerSec OBJECT-TYPE
    SYNTAX     Gauge32
    MAX-ACCESS read-only
    STATUS     current
    DESCRIPTION
	    "The Column cache saved bytes/sec performance
	    counter should only be used if Microsoft
	    Product Support services requests this
	    information to troubleshoot a complex
	    ESE-related performance problem."
    ::= { ex2TransportDatabaseEntry 11 }

ex2tbColumnCacheSavedColumnTotal OBJECT-TYPE
    SYNTAX     Gauge32
    MAX-ACCESS read-only
    STATUS     current
    DESCRIPTION
	    "The Column cache saved columns total
	    performance counter should only be used if
	    Microsoft Product Support services request this
	    information to troubleshoot a complex
	    ESE-related performance problem."
    ::= { ex2TransportDatabaseEntry 12 }

ex2tbColumnCacheSaveColumnPerSec OBJECT-TYPE
    SYNTAX     Gauge32
    MAX-ACCESS read-only
    STATUS     current
    DESCRIPTION
	    "The Column cache saved columns/sec performance
	    counter should only be used if Microsoft
	    Product Support services requests this
	    information to troubleshoot a complex
	    ESE-related performance problem."
    ::= { ex2TransportDatabaseEntry 13 }

ex2tbDataRowClonesTotal OBJECT-TYPE
    SYNTAX     Gauge32
    MAX-ACCESS read-only
    STATUS     current
    DESCRIPTION
	    "The DataRow clones total performance counter
	    should only be used if Microsoft Product
	    Support services requests this information to
	    troubleshoot a complex ESE-related performance
	    problem."
    ::= { ex2TransportDatabaseEntry 14 }

ex2tbDataRowClonesPerSec OBJECT-TYPE
    SYNTAX     Gauge32
    MAX-ACCESS read-only
    STATUS     current
    DESCRIPTION
	    "The DataRow clones/sec performance counter
	    should only be used if Microsoft Product
	    Support services requests this information to
	    troubleshoot a complex ESE-related performance
	    problem."
    ::= { ex2TransportDatabaseEntry 15 }

ex2tbDataRowDeletesTotal OBJECT-TYPE
    SYNTAX     Gauge32
    MAX-ACCESS read-only
    STATUS     current
    DESCRIPTION
	    "The DataRow deletes total performance counter
	    should only be used if Microsoft Product
	    Support services requests this information to
	    troubleshoot a complex ESE-related performance
	    problem."
    ::= { ex2TransportDatabaseEntry 16 }

ex2tbDataRowDeletesPerSec OBJECT-TYPE
    SYNTAX     Gauge32
    MAX-ACCESS read-only
    STATUS     current
    DESCRIPTION
	    "The DataRow deletes/sec performance counter
	    should only be used if Microsoft Product
	    Support services requests this information to
	    troubleshoot a complex ESE-related performance
	    problem."
    ::= { ex2TransportDatabaseEntry 17 }

ex2tbDataRowLoadsTotal OBJECT-TYPE
    SYNTAX     Gauge32
    MAX-ACCESS read-only
    STATUS     current
    DESCRIPTION
	    "The DataRow loads total performance counter
	    should only be used if Microsoft Product
	    Support services requests this information to
	    troubleshoot a complex ESE-related performance
	    problem."
    ::= { ex2TransportDatabaseEntry 18 }

ex2tbDataRowLoadsPerSec OBJECT-TYPE
    SYNTAX     Gauge32
    MAX-ACCESS read-only
    STATUS     current
    DESCRIPTION
	    "The DataRow loads/sec performance counter
	    should only be used if Microsoft Product
	    Support services requests this information to
	    troubleshoot a complex ESE-related performance
	    problem."
    ::= { ex2TransportDatabaseEntry 19 }

ex2tbDataRowMinimizeMemoryTotal OBJECT-TYPE
    SYNTAX     Gauge32
    MAX-ACCESS read-only
    STATUS     current
    DESCRIPTION
	    "The DataRow minimize memory total performance
	    counter should only be used if Microsoft
	    Product Support services requests this
	    information to troubleshoot a complex
	    ESE-related performance problem."
    ::= { ex2TransportDatabaseEntry 20 }

ex2tbDataRowMinimizeMemoryPerSec OBJECT-TYPE
    SYNTAX     Gauge32
    MAX-ACCESS read-only
    STATUS     current
    DESCRIPTION
	    "The DataRow minimize memory/sec performance
	    counter should only be used if Microsoft
	    Product Support services requests this
	    information to troubleshoot a complex
	    ESE-related performance problem."
    ::= { ex2TransportDatabaseEntry 21 }

ex2tbDataRowMovesTotal OBJECT-TYPE
    SYNTAX     Gauge32
    MAX-ACCESS read-only
    STATUS     current
    DESCRIPTION
	    "The DataRow moves total performance counter
	    should only be used if Microsoft Product
	    Support services requests this information to
	    troubleshoot a complex ESE-related performance
	    problem."
    ::= { ex2TransportDatabaseEntry 22 }

ex2tbDataRowMovesPerSec OBJECT-TYPE
    SYNTAX     Gauge32
    MAX-ACCESS read-only
    STATUS     current
    DESCRIPTION
	    "The DataRow moves/sec performance counter
	    should only be used if Microsoft Product
	    Support services requests this information to
	    troubleshoot a complex ESE-related performance
	    problem."
    ::= { ex2TransportDatabaseEntry 23 }

ex2tbDataRowNewInsertsTotal OBJECT-TYPE
    SYNTAX     Gauge32
    MAX-ACCESS read-only
    STATUS     current
    DESCRIPTION
	    "The DataRow new inserts total performance
	    counter should only be used if Microsoft
	    Product Support services requests this
	    information to troubleshoot a complex
	    ESE-related performance problem."
    ::= { ex2TransportDatabaseEntry 24 }

ex2tbDataRowNewInsertsPerSec OBJECT-TYPE
    SYNTAX     Gauge32
    MAX-ACCESS read-only
    STATUS     current
    DESCRIPTION
	    "The DataRow new inserts/sec performance
	    counter should only be used if Microsoft
	    Product Support services requests this
	    information to troubleshoot a complex
	    ESE-related performance problem."
    ::= { ex2TransportDatabaseEntry 25 }

ex2tbDataRowSeeksPrefixTotal OBJECT-TYPE
    SYNTAX     Gauge32
    MAX-ACCESS read-only
    STATUS     current
    DESCRIPTION
	    "The DataRow seeks prefix total performance
	    counter should only be used if Microsoft
	    Product Support services requests this
	    information to troubleshoot a complex
	    ESE-related performance problem."
    ::= { ex2TransportDatabaseEntry 26 }

ex2tbDataRowSeeksPrefixPerSec OBJECT-TYPE
    SYNTAX     Gauge32
    MAX-ACCESS read-only
    STATUS     current
    DESCRIPTION
	    "The DataRow seeks prefix/sec performance
	    counter should only be used if Microsoft
	    Product Support services requests this
	    information to troubleshoot a complex
	    ESE-related performance problem."
    ::= { ex2TransportDatabaseEntry 27 }

ex2tbDataRowSeeksTotal OBJECT-TYPE
    SYNTAX     Gauge32
    MAX-ACCESS read-only
    STATUS     current
    DESCRIPTION
	    "The DataRow seeks total performance counter
	    should only be used if Microsoft Product
	    Support services requests this information to
	    troubleshoot a complex ESE-related performance
	    problem."
    ::= { ex2TransportDatabaseEntry 28 }

ex2tbDataRowSeeksPerSec OBJECT-TYPE
    SYNTAX     Gauge32
    MAX-ACCESS read-only
    STATUS     current
    DESCRIPTION
	    "The DataRow seeks/sec performance counter
	    should only be used if Microsoft Product
	    Support services requests this information to
	    troubleshoot a complex ESE-related performance
	    problem."
    ::= { ex2TransportDatabaseEntry 29 }

ex2tbDataRowUpdatesTotal OBJECT-TYPE
    SYNTAX     Gauge32
    MAX-ACCESS read-only
    STATUS     current
    DESCRIPTION
	    "The DataRow updates total performance counter
	    should only be used if Microsoft Product
	    Support services requests this information to
	    troubleshoot a complex ESE-related performance
	    problem."
    ::= { ex2TransportDatabaseEntry 30 }

ex2tbDataRowUpdatesPerSec OBJECT-TYPE
    SYNTAX     Gauge32
    MAX-ACCESS read-only
    STATUS     current
    DESCRIPTION
	    "The DataRow updates/sec performance counter
	    should only be used if Microsoft Product
	    Support services requests this information to
	    troubleshoot a complex ESE-related performance
	    problem."
    ::= { ex2TransportDatabaseEntry 31 }

ex2tbExtendPropertyByteReadTotal OBJECT-TYPE
    SYNTAX     Gauge32
    MAX-ACCESS read-only
    STATUS     current
    DESCRIPTION
	    "The Extended property bytes read total
	    performance counter should only be used if
	    Microsoft Product Support services requests
	    this information to troubleshoot a complex
	    ESE-related performance problem."
    ::= { ex2TransportDatabaseEntry 32 }

ex2tbExtendPropertyBytReadPerSec OBJECT-TYPE
    SYNTAX     Gauge32
    MAX-ACCESS read-only
    STATUS     current
    DESCRIPTION
	    "The Extended property bytes read/sec
	    performance counter should only be used if
	    Microsoft Product Support services requests
	    this information to troubleshoot a complex
	    ESE-related performance problem."
    ::= { ex2TransportDatabaseEntry 33 }

ex2tbExtenePropertyByteWritTotal OBJECT-TYPE
    SYNTAX     Gauge32
    MAX-ACCESS read-only
    STATUS     current
    DESCRIPTION
	    "The Extended property bytes written total
	    performance counter should only be used if
	    Microsoft Product Support services requests
	    this information to troubleshoot a complex
	    ESE-related performance problem."
    ::= { ex2TransportDatabaseEntry 34 }

ex2tbExtenPropertyByteWritPerSec OBJECT-TYPE
    SYNTAX     Gauge32
    MAX-ACCESS read-only
    STATUS     current
    DESCRIPTION
	    "The Extended property bytes written/sec
	    performance counter should only be used if
	    Microsoft Product Support services requests
	    this information to troubleshoot a complex
	    ESE-related performance problem."
    ::= { ex2TransportDatabaseEntry 35 }

ex2tbExtenedPropertyReadsTotal OBJECT-TYPE
    SYNTAX     Gauge32
    MAX-ACCESS read-only
    STATUS     current
    DESCRIPTION
	    "The Extended property reads total performance
	    counter should only be used if Microsoft
	    Product Support services requests this
	    information to troubleshoot a complex
	    ESE-related performance problem."
    ::= { ex2TransportDatabaseEntry 36 }

ex2tbExtenedPropertyReadsPerSec OBJECT-TYPE
    SYNTAX     Gauge32
    MAX-ACCESS read-only
    STATUS     current
    DESCRIPTION
	    "The Extended property reads/sec performance
	    counter should only be used if Microsoft
	    Product Support services requests this
	    information to troubleshoot a complex
	    ESE-related performance problem."
    ::= { ex2TransportDatabaseEntry 37 }

ex2tbExtenedPropertyWritesTotal OBJECT-TYPE
    SYNTAX     Gauge32
    MAX-ACCESS read-only
    STATUS     current
    DESCRIPTION
	    "The Extended property writes total performance
	    counter should only be used if Microsoft
	    Product Support services requests this
	    information to troubleshoot a complex
	    ESE-related performance problem."
    ::= { ex2TransportDatabaseEntry 38 }

ex2tbExtenedPropertyWritesPerSec OBJECT-TYPE
    SYNTAX     Gauge32
    MAX-ACCESS read-only
    STATUS     current
    DESCRIPTION
	    "The Extended property writes/sec performance
	    counter should only be used if Microsoft
	    Product Support services requests this
	    information to troubleshoot a complex
	    ESE-related performance problem."
    ::= { ex2TransportDatabaseEntry 39 }

ex2tbLazyBytesLoadPerformedTotal OBJECT-TYPE
    SYNTAX     Gauge32
    MAX-ACCESS read-only
    STATUS     current
    DESCRIPTION
	    "The Lazy bytes load performed total
	    performance counter should only be used if
	    Microsoft Product Support services requests
	    this information to troubleshoot a complex
	    ESE-related performance problem."
    ::= { ex2TransportDatabaseEntry 40 }

ex2tbLazyByteLoadPerformedPerSec OBJECT-TYPE
    SYNTAX     Gauge32
    MAX-ACCESS read-only
    STATUS     current
    DESCRIPTION
	    "The Lazy bytes load performed/sec performance
	    counter should only be used if Microsoft
	    Product Support services requests this
	    information to troubleshoot a complex
	    ESE-related performance problem."
    ::= { ex2TransportDatabaseEntry 41 }

ex2tbLazyBytesLoadRequestedTotal OBJECT-TYPE
    SYNTAX     Gauge32
    MAX-ACCESS read-only
    STATUS     current
    DESCRIPTION
	    "The Lazy bytes load requested total
	    performance counter should only be used if
	    Microsoft Product Support services requests
	    this information to troubleshoot a complex
	    ESE-related performance problem."
    ::= { ex2TransportDatabaseEntry 42 }

ex2tbLazyByteLoadRequestedPerSec OBJECT-TYPE
    SYNTAX     Gauge32
    MAX-ACCESS read-only
    STATUS     current
    DESCRIPTION
	    "The Lazy bytes load requested/sec performance
	    counter should only be used if Microsoft
	    Product Support services requests this
	    information to troubleshoot a complex
	    ESE-related performance problem."
    ::= { ex2TransportDatabaseEntry 43 }

ex2tbMailItemBeginCommitTotal OBJECT-TYPE
    SYNTAX     Gauge32
    MAX-ACCESS read-only
    STATUS     current
    DESCRIPTION
	    "The MailItem begin commit total performance
	    counter should only be used if Microsoft
	    Product Support services requests this
	    information to troubleshoot a complex
	    ESE-related performance problem."
    ::= { ex2TransportDatabaseEntry 44 }

ex2tbMailItemBeginCommitPerSec OBJECT-TYPE
    SYNTAX     Gauge32
    MAX-ACCESS read-only
    STATUS     current
    DESCRIPTION
	    "The MailItem begin commit/sec performance
	    counter should only be used if Microsoft
	    Product Support services requests this
	    information to troubleshoot a complex
	    ESE-related performance problem."
    ::= { ex2TransportDatabaseEntry 45 }

ex2tbMailItemCloneCreateTotal OBJECT-TYPE
    SYNTAX     Gauge32
    MAX-ACCESS read-only
    STATUS     current
    DESCRIPTION
	    "The MailItem clone create total performance
	    counter should only be used if Microsoft
	    Product Support services requests this
	    information to troubleshoot a complex
	    ESE-related performance problem."
    ::= { ex2TransportDatabaseEntry 46 }

ex2tbMailItemCloneCreatePerSec OBJECT-TYPE
    SYNTAX     Gauge32
    MAX-ACCESS read-only
    STATUS     current
    DESCRIPTION
	    "The MailItem clone create/sec performance
	    counter should only be used if Microsoft
	    Product Support services requests this
	    information to troubleshoot a complex
	    ESE-related performance problem."
    ::= { ex2TransportDatabaseEntry 47 }

ex2tbMailItemCommitImmediatTotal OBJECT-TYPE
    SYNTAX     Gauge32
    MAX-ACCESS read-only
    STATUS     current
    DESCRIPTION
	    "The MailItem commit immediate total
	    performance counter should only be used if
	    Microsoft Product Support services request this
	    information to troubleshoot a complex
	    ESE-related performance problem."
    ::= { ex2TransportDatabaseEntry 48 }

ex2tbMailItemCommitImmediaPerSec OBJECT-TYPE
    SYNTAX     Gauge32
    MAX-ACCESS read-only
    STATUS     current
    DESCRIPTION
	    "The MailItem commit immediate/sec performance
	    counter should only be used if Microsoft
	    Product Support services requests this
	    information to troubleshoot a complex
	    ESE-related performance problem."
    ::= { ex2TransportDatabaseEntry 49 }

ex2tbMailItemCommitLazyTotal OBJECT-TYPE
    SYNTAX     Gauge32
    MAX-ACCESS read-only
    STATUS     current
    DESCRIPTION
	    "The MailItem commit lazy total performance
	    counter should only be used if Microsoft
	    Product Support services request this
	    information to troubleshoot a complex
	    ESE-related performance problem."
    ::= { ex2TransportDatabaseEntry 50 }

ex2tbMailItemCommitLazyPerSec OBJECT-TYPE
    SYNTAX     Gauge32
    MAX-ACCESS read-only
    STATUS     current
    DESCRIPTION
	    "The MailItem commit lazy/sec performance
	    counter should only be used if Microsoft
	    Product Support services requests this
	    information to troubleshoot a complex
	    ESE-related performance problem."
    ::= { ex2TransportDatabaseEntry 51 }

ex2tbMailItemDehydrateTotal OBJECT-TYPE
    SYNTAX     Gauge32
    MAX-ACCESS read-only
    STATUS     current
    DESCRIPTION
	    "The MailItem dehydrate total performance
	    counter should only be used if Microsoft
	    Product Support services requests this
	    information to troubleshoot a complex
	    ESE-related performance problem."
    ::= { ex2TransportDatabaseEntry 52 }

ex2tbMailItemDehydratePerSec OBJECT-TYPE
    SYNTAX     Gauge32
    MAX-ACCESS read-only
    STATUS     current
    DESCRIPTION
	    "The MailItem dehydrate/sec performance counter
	    should only be used if Microsoft Product
	    Support services requests this information to
	    troubleshoot a complex ESE-related performance
	    problem."
    ::= { ex2TransportDatabaseEntry 53 }

ex2tbMailItemDeleteLazyTotal OBJECT-TYPE
    SYNTAX     Gauge32
    MAX-ACCESS read-only
    STATUS     current
    DESCRIPTION
	    "The MailItem delete lazy total performance
	    counter should only be used if Microsoft
	    Product Support services requests this
	    information to troubleshoot a complex
	    ESE-related performance problem."
    ::= { ex2TransportDatabaseEntry 54 }

ex2tbMailItemDeleteLazyPerSec OBJECT-TYPE
    SYNTAX     Gauge32
    MAX-ACCESS read-only
    STATUS     current
    DESCRIPTION
	    "The MailItem delete lazy/sec performance
	    counter should only be used if Microsoft
	    Product Support services requests this
	    information to troubleshoot a complex
	    ESE-related performance problem."
    ::= { ex2TransportDatabaseEntry 55 }

ex2tbMailItemLoadTotal OBJECT-TYPE
    SYNTAX     Gauge32
    MAX-ACCESS read-only
    STATUS     current
    DESCRIPTION
	    "The MailItem load total performance counter
	    should only be used if Microsoft Product
	    Support services requests this information to
	    troubleshoot a complex ESE-related performance
	    problem."
    ::= { ex2TransportDatabaseEntry 56 }

ex2tbMailItemLoadPerSec OBJECT-TYPE
    SYNTAX     Gauge32
    MAX-ACCESS read-only
    STATUS     current
    DESCRIPTION
	    "The MailItem load/sec performance counter
	    should only be used if Microsoft Product
	    Support services requests this information to
	    troubleshoot a complex ESE-related performance
	    problem."
    ::= { ex2TransportDatabaseEntry 57 }

ex2tbMailItemMaterialize OBJECT-TYPE
    SYNTAX     Gauge32
    MAX-ACCESS read-only
    STATUS     current
    DESCRIPTION
	    "The MailItem materialize performance counter
	    should only be used if Microsoft Product
	    Support services requests this information to
	    troubleshoot a complex ESE-related performance
	    problem."
    ::= { ex2TransportDatabaseEntry 58 }

ex2tbMailItemMaterializePerSec OBJECT-TYPE
    SYNTAX     Gauge32
    MAX-ACCESS read-only
    STATUS     current
    DESCRIPTION
	    "The MailItem materialize/sec performance
	    counter should only be used if Microsoft
	    Product Support services requests this
	    information to troubleshoot a complex
	    ESE-related performance problem."
    ::= { ex2TransportDatabaseEntry 59 }

ex2tbMailItemNewTotal OBJECT-TYPE
    SYNTAX     Gauge32
    MAX-ACCESS read-only
    STATUS     current
    DESCRIPTION
	    "The MailItem new total performance counter
	    should only be used if Microsoft Product
	    Support services requests this information to
	    troubleshoot a complex ESE-related performance
	    problem."
    ::= { ex2TransportDatabaseEntry 60 }

ex2tbMailItemNewPerSec OBJECT-TYPE
    SYNTAX     Gauge32
    MAX-ACCESS read-only
    STATUS     current
    DESCRIPTION
	    "The MailItem new/sec performance counter
	    should only be used if Microsoft Product
	    Support services requests this information to
	    troubleshoot a complex ESE-related performance
	    problem."
    ::= { ex2TransportDatabaseEntry 61 }

ex2tbMailItemWriteMimeToTotal OBJECT-TYPE
    SYNTAX     Gauge32
    MAX-ACCESS read-only
    STATUS     current
    DESCRIPTION
	    "The MailItem writeMimeTo total performance
	    counter should only be used if Microsoft
	    Product Support services requests this
	    information to troubleshoot a complex
	    ESE-related performance problem."
    ::= { ex2TransportDatabaseEntry 62 }

ex2tbMailItemWriteMimeToPerSec OBJECT-TYPE
    SYNTAX     Gauge32
    MAX-ACCESS read-only
    STATUS     current
    DESCRIPTION
	    "The MailItem writeMimeTo/sec performance
	    counter should only be used if Microsoft
	    Product Support services requests this
	    information to troubleshoot a complex
	    ESE-related performance problem."
    ::= { ex2TransportDatabaseEntry 63 }

ex2tbStreamBytesReadTotal OBJECT-TYPE
    SYNTAX     Gauge32
    MAX-ACCESS read-only
    STATUS     current
    DESCRIPTION
	    "The Stream bytes read total performance
	    counter should only be used if Microsoft
	    Product Support services requests this
	    information to troubleshoot a complex
	    ESE-related performance problem."
    ::= { ex2TransportDatabaseEntry 64 }

ex2tbStreamBytesReadPerSec OBJECT-TYPE
    SYNTAX     Gauge32
    MAX-ACCESS read-only
    STATUS     current
    DESCRIPTION
	    "The Stream bytes read/sec performance counter
	    should only be used if Microsoft Product
	    Support services requests this information to
	    troubleshoot a complex ESE-related performance
	    problem."
    ::= { ex2TransportDatabaseEntry 65 }

ex2tbStreamBytesWrittenTotal OBJECT-TYPE
    SYNTAX     Gauge32
    MAX-ACCESS read-only
    STATUS     current
    DESCRIPTION
	    "The Stream bytes written total performance
	    counter should only be used if Microsoft
	    Product Support services requests this
	    information to troubleshoot a complex
	    ESE-related performance problem."
    ::= { ex2TransportDatabaseEntry 66 }

ex2tbStreamBytesWrittenPerSec OBJECT-TYPE
    SYNTAX     Gauge32
    MAX-ACCESS read-only
    STATUS     current
    DESCRIPTION
	    "The Stream bytes written/sec performance
	    counter should only be used if Microsoft
	    Product Support services requests this
	    information to troubleshoot a complex
	    ESE-related performance problem."
    ::= { ex2TransportDatabaseEntry 67 }

ex2tbStreamReadTotal OBJECT-TYPE
    SYNTAX     Gauge32
    MAX-ACCESS read-only
    STATUS     current
    DESCRIPTION
	    "The Stream read total performance counter
	    should only be used if Microsoft Product
	    Support services requests this information to
	    troubleshoot a complex ESE-related performance
	    problem."
    ::= { ex2TransportDatabaseEntry 68 }

ex2tbStreamReadPerSec OBJECT-TYPE
    SYNTAX     Gauge32
    MAX-ACCESS read-only
    STATUS     current
    DESCRIPTION
	    "The Stream read/sec performance counter should
	    only be used if Microsoft Product Support
	    services requests this information to
	    troubleshoot a complex ESE-related performance
	    problem."
    ::= { ex2TransportDatabaseEntry 69 }

ex2tbStreamSetLengthCount OBJECT-TYPE
    SYNTAX     Gauge32
    MAX-ACCESS read-only
    STATUS     current
    DESCRIPTION
	    "The Stream set length count performance
	    counter should only be used if Microsoft
	    Product Support services requests this
	    information to troubleshoot a complex
	    ESE-related performance problem."
    ::= { ex2TransportDatabaseEntry 70 }

ex2tbStreamSetLengthPerSec OBJECT-TYPE
    SYNTAX     Gauge32
    MAX-ACCESS read-only
    STATUS     current
    DESCRIPTION
	    "The Stream set length/sec performance counter
	    should only be used if Microsoft Product
	    Support services requests this information to
	    troubleshoot a complex ESE-related performance
	    problem."
    ::= { ex2TransportDatabaseEntry 71 }

ex2tbStreamWritesTotal OBJECT-TYPE
    SYNTAX     Gauge32
    MAX-ACCESS read-only
    STATUS     current
    DESCRIPTION
	    "The Stream writes total performance counter
	    should only be used if Microsoft Product
	    Support services requests this information to
	    troubleshoot a complex ESE-related performance
	    problem."
    ::= { ex2TransportDatabaseEntry 72 }

ex2tbStreamWritesPerSec OBJECT-TYPE
    SYNTAX     Gauge32
    MAX-ACCESS read-only
    STATUS     current
    DESCRIPTION
	    "The Stream writes/sec performance counter
	    should only be used if Microsoft Product
	    Support services requests this information to
	    troubleshoot a complex ESE-related performance
	    problem."
    ::= { ex2TransportDatabaseEntry 73 }

ex2TransportDumpster OBJECT IDENTIFIER
    ::= { exchangeV2 56 }

ex2tdDumpsterDeletesPerSec OBJECT-TYPE
    SYNTAX     Gauge32
    MAX-ACCESS read-only
    STATUS     current
    DESCRIPTION
	    "Delete Rate is the rate at which items are
	    deleted from the Transport Dumpster on this
	    server."
    ::= { ex2TransportDumpster 1 }

ex2tdDumpsterInsertsPerSec OBJECT-TYPE
    SYNTAX     Gauge32
    MAX-ACCESS read-only
    STATUS     current
    DESCRIPTION
	    "Insert Rate is the rate at which items are
	    inserted into the Transport Dumpster on this
	    server."
    ::= { ex2TransportDumpster 2 }

ex2tdDumpsterItemCount OBJECT-TYPE
    SYNTAX     Gauge32
    MAX-ACCESS read-only
    STATUS     current
    DESCRIPTION
	    "Item Count is the total number of mail  items
	    that are currently in the Transport Dumpster on
	    this server."
    ::= { ex2TransportDumpster 3 }

ex2tdDumpsterSize OBJECT-TYPE
    SYNTAX     Gauge32
    MAX-ACCESS read-only
    STATUS     current
    DESCRIPTION
	    "Item Size is the total size  (in bytes) of
	    mail items that are currently in the Transport
	    Dumpster on this server."
    ::= { ex2TransportDumpster 4 }

ex2tdRedeliveryCount OBJECT-TYPE
    SYNTAX     Gauge32
    MAX-ACCESS read-only
    STATUS     current
    DESCRIPTION
	    "Redelivery Count is the number of mail items
	    that were re-delivered from the Transport
	    Dumpster on this server."
    ::= { ex2TransportDumpster 5 }

ex2TransportPickupTable OBJECT-TYPE
    SYNTAX     SEQUENCE OF Ex2TransportPickupEntry
    MAX-ACCESS not-accessible
    STATUS     current
    DESCRIPTION
	    "A table containing performance information for
	    instances of 'MSExchangeTransport Pickup'
	    objects."
    ::= { exchangeV2 57 }

ex2TransportPickupEntry OBJECT-TYPE
    SYNTAX     Ex2TransportPickupEntry
    MAX-ACCESS not-accessible
    STATUS     current
    DESCRIPTION
	    "Performance information for one particular
	    instance of 'MSExchangeTransport Pickup'
	    object."
    INDEX      { ex2tpInstance }
    ::= { ex2TransportPickupTable 1 }

Ex2TransportPickupEntry ::= SEQUENCE {
    ex2tpkInstance InstanceName,
    ex2tpkMessagesBadmailed Gauge32,
    ex2tpkMessagesNDRed Gauge32,
    ex2tpkMessagesSubmitted Gauge32
}

ex2tpkInstance OBJECT-TYPE
    SYNTAX     InstanceName
    MAX-ACCESS read-only
    STATUS     current
    DESCRIPTION
	    "Instance name."
    ::= { ex2TransportPickupEntry 1 }

ex2tpkMessagesBadmailed OBJECT-TYPE
    SYNTAX     Gauge32
    MAX-ACCESS read-only
    STATUS     current
    DESCRIPTION
	    "Messages Badmailed is the number of messages
	    that were submitted to the Pickup directory but
	    were classified as badmail and not delivered."
    ::= { ex2TransportPickupEntry 2 }

ex2tpkMessagesNDRed OBJECT-TYPE
    SYNTAX     Gauge32
    MAX-ACCESS read-only
    STATUS     current
    DESCRIPTION
	    "Messages NDRed is the number of messages
	    processed by the Pickup directory that causes
	    NDRs to be created."
    ::= { ex2TransportPickupEntry 3 }

ex2tpkMessagesSubmitted OBJECT-TYPE
    SYNTAX     Gauge32
    MAX-ACCESS read-only
    STATUS     current
    DESCRIPTION
	    "Messages Submitted is the number of messages
	    that were successfully submitted by the Pickup
	    directory."
    ::= { ex2TransportPickupEntry 4 }

ex2TransportQueuesTable OBJECT-TYPE
    SYNTAX     SEQUENCE OF Ex2TransportQueuesEntry
    MAX-ACCESS not-accessible
    STATUS     current
    DESCRIPTION
	    "A table containing performance information for
	    instances of 'MSExchangeTransport Queues'
	    objects."
    ::= { exchangeV2 58 }

ex2TransportQueuesEntry OBJECT-TYPE
    SYNTAX     Ex2TransportQueuesEntry
    MAX-ACCESS not-accessible
    STATUS     current
    DESCRIPTION
	    "Performance information for one particular
	    instance of 'MSExchangeTransport Queues'
	    object."
    INDEX      { ex2tqInstance }
    ::= { ex2TransportQueuesTable 1 }

Ex2TransportQueuesEntry ::= SEQUENCE {
    ex2tqInstance InstanceName,
    ex2tqActiveMailboxDelivQueLength Gauge32,
    ex2tqActiveNonSmtpDelivQueLength Gauge32,
    ex2tqActiveRemoteDelivQueLength Gauge32,
    ex2tqAggregDelivQueLengthAllQues Gauge32,
    ex2tqItemCompletedDelivPerSecond Gauge32,
    ex2tqItemsCompletedDeliveryTotal Gauge32,
    ex2tqItemsDeletedByAdminTotal Gauge32,
    ex2tqItemQuedForDelivExpireTotal Gauge32,
    ex2tqItemsQueuedForDeliveryTotal Gauge32,
    ex2tqItemsQuedForDelivPerSecond Gauge32,
    ex2tqItemsResubmittedTotal Gauge32,
    ex2tqLargestDeliveryQueueLength Gauge32,
    ex2tqMsgsCompletedDelivPerSecond Gauge32,
    ex2tqMsgsCompletedDelivTotal Gauge32,
    ex2tqMessagesQueuedForDelivery Gauge32,
    ex2tqMsgsQuedForDelivTotal Gauge32,
    ex2tqMsgsQuedForDelivPerSecond Gauge32,
    ex2tqMessagesSubmittedPerSecond Gauge32,
    ex2tqMessagesSubmittedTotal Gauge32,
    ex2tqPoisonQueueLength Gauge32,
    ex2tqRetryMailboxDelivQueLength Gauge32,
    ex2tqRetryNonSmtpDelivQueLength Gauge32,
    ex2tqRetryRemoteDelivQueLength Gauge32,
    ex2tqSubmissQueueItemExpireTotal Gauge32,
    ex2tqSubmissionQueueLength Gauge32,
    ex2tqUnreachableQueueLength Gauge32
}

ex2tqInstance OBJECT-TYPE
    SYNTAX     InstanceName
    MAX-ACCESS read-only
    STATUS     current
    DESCRIPTION
	    "Instance name."
    ::= { ex2TransportQueuesEntry 1 }

ex2tqActiveMailboxDelivQueLength OBJECT-TYPE
    SYNTAX     Gauge32
    MAX-ACCESS read-only
    STATUS     current
    DESCRIPTION
	    "Active Mailbox Delivery Queue Length is the
	    number of messages in the active mailbox
	    queues."
    ::= { ex2TransportQueuesEntry 2 }

ex2tqActiveNonSmtpDelivQueLength OBJECT-TYPE
    SYNTAX     Gauge32
    MAX-ACCESS read-only
    STATUS     current
    DESCRIPTION
	    "Active Non-SMTP Delivery Queue Length is the
	    number of messages in the Drop directory that
	    is used by a Foreign connector."
    ::= { ex2TransportQueuesEntry 3 }

ex2tqActiveRemoteDelivQueLength OBJECT-TYPE
    SYNTAX     Gauge32
    MAX-ACCESS read-only
    STATUS     current
    DESCRIPTION
	    "Active Remote Delivery Queue Length is the
	    number of messages in the active remote
	    delivery queues."
    ::= { ex2TransportQueuesEntry 4 }

ex2tqAggregDelivQueLengthAllQues OBJECT-TYPE
    SYNTAX     Gauge32
    MAX-ACCESS read-only
    STATUS     current
    DESCRIPTION
	    "Aggregate Delivery Queue Length (All Queues)
	    is the number of messages queued for delivery
	    in all queues."
    ::= { ex2TransportQueuesEntry 5 }

ex2tqItemCompletedDelivPerSecond OBJECT-TYPE
    SYNTAX     Gauge32
    MAX-ACCESS read-only
    STATUS     current
    DESCRIPTION
	    "Items Completed Delivery Per Second is the
	    number of items processed to completion. All
	    recipients either succeeded or failed."
    ::= { ex2TransportQueuesEntry 6 }

ex2tqItemsCompletedDeliveryTotal OBJECT-TYPE
    SYNTAX     Gauge32
    MAX-ACCESS read-only
    STATUS     current
    DESCRIPTION
	    "Items Completed Delivery Total is the total
	    number of items processed to completion. All
	    recipients either succeeded or failed."
    ::= { ex2TransportQueuesEntry 7 }

ex2tqItemsDeletedByAdminTotal OBJECT-TYPE
    SYNTAX     Gauge32
    MAX-ACCESS read-only
    STATUS     current
    DESCRIPTION
	    "Items Deleted By Admin Total is the total
	    number of queued items deleted by the
	    administrator."
    ::= { ex2TransportQueuesEntry 8 }

ex2tqItemQuedForDelivExpireTotal OBJECT-TYPE
    SYNTAX     Gauge32
    MAX-ACCESS read-only
    STATUS     current
    DESCRIPTION
	    "Items Queued For Delivery Expired Total is the
	    total number of items queued for delivery that
	    have expired."
    ::= { ex2TransportQueuesEntry 9 }

ex2tqItemsQueuedForDeliveryTotal OBJECT-TYPE
    SYNTAX     Gauge32
    MAX-ACCESS read-only
    STATUS     current
    DESCRIPTION
	    "Items Queued For Delivery Total is the total
	    number of items queued for delivery."
    ::= { ex2TransportQueuesEntry 10 }

ex2tqItemsQuedForDelivPerSecond OBJECT-TYPE
    SYNTAX     Gauge32
    MAX-ACCESS read-only
    STATUS     current
    DESCRIPTION
	    "Items Queued for Delivery Per Second is the
	    number of items queued for delivery per
	    second."
    ::= { ex2TransportQueuesEntry 11 }

ex2tqItemsResubmittedTotal OBJECT-TYPE
    SYNTAX     Gauge32
    MAX-ACCESS read-only
    STATUS     current
    DESCRIPTION
	    "Items Resubmitted Total is the total number of
	    items that were resubmitted to the
	    categorizer."
    ::= { ex2TransportQueuesEntry 12 }

ex2tqLargestDeliveryQueueLength OBJECT-TYPE
    SYNTAX     Gauge32
    MAX-ACCESS read-only
    STATUS     current
    DESCRIPTION
	    "Largest Delivery Queue Length is the number of
	    messages in the largest delivery queue."
    ::= { ex2TransportQueuesEntry 13 }

ex2tqMsgsCompletedDelivPerSecond OBJECT-TYPE
    SYNTAX     Gauge32
    MAX-ACCESS read-only
    STATUS     current
    DESCRIPTION
	    "Messages Completed Delivery Per Second is the
	    number of messages that are delivered per
	    second."
    ::= { ex2TransportQueuesEntry 14 }

ex2tqMsgsCompletedDelivTotal OBJECT-TYPE
    SYNTAX     Gauge32
    MAX-ACCESS read-only
    STATUS     current
    DESCRIPTION
	    "Messages Completed Delivery Total is the
	    number of messages that have completed
	    delivery. All recipients either succeeded or
	    failed."
    ::= { ex2TransportQueuesEntry 15 }

ex2tqMessagesQueuedForDelivery OBJECT-TYPE
    SYNTAX     Gauge32
    MAX-ACCESS read-only
    STATUS     current
    DESCRIPTION
	    "Messages Queued For Delivery is the number of
	    messages currently queued for delivery in one
	    or more queues."
    ::= { ex2TransportQueuesEntry 16 }

ex2tqMsgsQuedForDelivTotal OBJECT-TYPE
    SYNTAX     Gauge32
    MAX-ACCESS read-only
    STATUS     current
    DESCRIPTION
	    "Messages Queued For Delivery Total is the
	    total  number of messages that have been queued
	    for delivery in one or more queues."
    ::= { ex2TransportQueuesEntry 17 }

ex2tqMsgsQuedForDelivPerSecond OBJECT-TYPE
    SYNTAX     Gauge32
    MAX-ACCESS read-only
    STATUS     current
    DESCRIPTION
	    "Messages Queued for Delivery Per Second is the
	    number of messages that have been queued for
	    delivery per second."
    ::= { ex2TransportQueuesEntry 18 }

ex2tqMessagesSubmittedPerSecond OBJECT-TYPE
    SYNTAX     Gauge32
    MAX-ACCESS read-only
    STATUS     current
    DESCRIPTION
	    "Messages Submitted Per Second is the number of
	    messages that have been queued in the
	    Submission queue per second."
    ::= { ex2TransportQueuesEntry 19 }

ex2tqMessagesSubmittedTotal OBJECT-TYPE
    SYNTAX     Gauge32
    MAX-ACCESS read-only
    STATUS     current
    DESCRIPTION
	    "Messages Submitted Total is the total number
	    of messages that have been queued in the
	    Submission queue."
    ::= { ex2TransportQueuesEntry 20 }

ex2tqPoisonQueueLength OBJECT-TYPE
    SYNTAX     Gauge32
    MAX-ACCESS read-only
    STATUS     current
    DESCRIPTION
	    "Poison Message Queue Length is the number of
	    messages in the poison message queue."
    ::= { ex2TransportQueuesEntry 21 }

ex2tqRetryMailboxDelivQueLength OBJECT-TYPE
    SYNTAX     Gauge32
    MAX-ACCESS read-only
    STATUS     current
    DESCRIPTION
	    "Retry Mailbox Delivery Queue Length is the
	    number of messages in retry."
    ::= { ex2TransportQueuesEntry 22 }

ex2tqRetryNonSmtpDelivQueLength OBJECT-TYPE
    SYNTAX     Gauge32
    MAX-ACCESS read-only
    STATUS     current
    DESCRIPTION
	    "Retry Non-SMTP Delivery Queue Length is the
	    number of messages in retry in the non-SMTP
	    gateway delivery queues."
    ::= { ex2TransportQueuesEntry 23 }

ex2tqRetryRemoteDelivQueLength OBJECT-TYPE
    SYNTAX     Gauge32
    MAX-ACCESS read-only
    STATUS     current
    DESCRIPTION
	    "Retry Remote Delivery Queue Length is the
	    number of messages in retry in the remote
	    delivery queues."
    ::= { ex2TransportQueuesEntry 24 }

ex2tqSubmissQueueItemExpireTotal OBJECT-TYPE
    SYNTAX     Gauge32
    MAX-ACCESS read-only
    STATUS     current
    DESCRIPTION
	    "Submission Queue Items Expired Total is the
	    number of expired messages in the Submission
	    queue."
    ::= { ex2TransportQueuesEntry 25 }

ex2tqSubmissionQueueLength OBJECT-TYPE
    SYNTAX     Gauge32
    MAX-ACCESS read-only
    STATUS     current
    DESCRIPTION
	    "Submission Queue Length is the number of
	    messages in the Submission queue."
    ::= { ex2TransportQueuesEntry 26 }

ex2tqUnreachableQueueLength OBJECT-TYPE
    SYNTAX     Gauge32
    MAX-ACCESS read-only
    STATUS     current
    DESCRIPTION
	    "Unreachable Queue Length is the number of
	    messages in the Unreachable queue."
    ::= { ex2TransportQueuesEntry 27 }

ex2TransportResolverTable OBJECT-TYPE
    SYNTAX     SEQUENCE OF Ex2TransportResolverEntry
    MAX-ACCESS not-accessible
    STATUS     current
    DESCRIPTION
	    "A table containing performance information for
	    instances of 'MSExchangeTransport Resolver'
	    objects."
    ::= { exchangeV2 59 }

ex2TransportResolverEntry OBJECT-TYPE
    SYNTAX     Ex2TransportResolverEntry
    MAX-ACCESS not-accessible
    STATUS     current
    DESCRIPTION
	    "Performance information for one particular
	    instance of 'MSExchangeTransport Resolver'
	    object."
    INDEX      { ex2treInstance }
    ::= { ex2TransportResolverTable 1 }

Ex2TransportResolverEntry ::= SEQUENCE {
    ex2treInstance InstanceName,
    ex2treAmbiguousRecipients Gauge32,
    ex2treAmbiguousSenders Gauge32,
    ex2treFailedRecipients Gauge32,
    ex2treLoopRecipients Gauge32,
    ex2treMessagesChipped Gauge32,
    ex2treMessagesCreated Gauge32,
    ex2treMessagesRetried Gauge32,
    ex2treUnresolvedOrgRecipients Gauge32,
    ex2treUnresolvedOrgSenders Gauge32
}

ex2treInstance OBJECT-TYPE
    SYNTAX     InstanceName
    MAX-ACCESS read-only
    STATUS     current
    DESCRIPTION
	    "Instance name."
    ::= { ex2TransportResolverEntry 1 }

ex2treAmbiguousRecipients OBJECT-TYPE
    SYNTAX     Gauge32
    MAX-ACCESS read-only
    STATUS     current
    DESCRIPTION
	    "Ambiguous Recipients is the total number of
	    ambiguous recipients."
    ::= { ex2TransportResolverEntry 2 }

ex2treAmbiguousSenders OBJECT-TYPE
    SYNTAX     Gauge32
    MAX-ACCESS read-only
    STATUS     current
    DESCRIPTION
	    "Ambiguous Senders is the total number of
	    ambiguous senders."
    ::= { ex2TransportResolverEntry 3 }

ex2treFailedRecipients OBJECT-TYPE
    SYNTAX     Gauge32
    MAX-ACCESS read-only
    STATUS     current
    DESCRIPTION
	    "Failed Recipients is the number of failed
	    recipients that were detected during recipient
	    resolution."
    ::= { ex2TransportResolverEntry 4 }

ex2treLoopRecipients OBJECT-TYPE
    SYNTAX     Gauge32
    MAX-ACCESS read-only
    STATUS     current
    DESCRIPTION
	    "Loop Recipients is the number of recipients
	    that failed recipient resolution because of
	    recipient loops."
    ::= { ex2TransportResolverEntry 5 }

ex2treMessagesChipped OBJECT-TYPE
    SYNTAX     Gauge32
    MAX-ACCESS read-only
    STATUS     current
    DESCRIPTION
	    "Messages Chipped is the total number of copies
	    of the same message that were created during
	    recipient resolution to control the number of
	    envelope recipients in a single message."
    ::= { ex2TransportResolverEntry 6 }

ex2treMessagesCreated OBJECT-TYPE
    SYNTAX     Gauge32
    MAX-ACCESS read-only
    STATUS     current
    DESCRIPTION
	    "Messages Created is the number of messages
	    that were created during recipient resolution."
    ::= { ex2TransportResolverEntry 7 }

ex2treMessagesRetried OBJECT-TYPE
    SYNTAX     Gauge32
    MAX-ACCESS read-only
    STATUS     current
    DESCRIPTION
	    "Messages Retried is the number of messages
	    that were scheduled for retry during recipient
	    resolution."
    ::= { ex2TransportResolverEntry 8 }

ex2treUnresolvedOrgRecipients OBJECT-TYPE
    SYNTAX     Gauge32
    MAX-ACCESS read-only
    STATUS     current
    DESCRIPTION
	    "Unresolved Org Recipients is the number of
	    unresolved recipients from an authoritative
	    domain that were detected during recipient
	    resolution."
    ::= { ex2TransportResolverEntry 9 }

ex2treUnresolvedOrgSenders OBJECT-TYPE
    SYNTAX     Gauge32
    MAX-ACCESS read-only
    STATUS     current
    DESCRIPTION
	    "Unresolved Org Senders is the number of
	    unresolved senders from an authoritative domain
	    that were detected during recipient
	    resolution."
    ::= { ex2TransportResolverEntry 10 }

ex2TransportRoutingTable OBJECT-TYPE
    SYNTAX     SEQUENCE OF Ex2TransportRoutingEntry
    MAX-ACCESS not-accessible
    STATUS     current
    DESCRIPTION
	    "A table containing performance information for
	    instances of 'MSExchangeTransport Routing'
	    objects."
    ::= { exchangeV2 60 }

ex2TransportRoutingEntry OBJECT-TYPE
    SYNTAX     Ex2TransportRoutingEntry
    MAX-ACCESS not-accessible
    STATUS     current
    DESCRIPTION
	    "Performance information for one particular
	    instance of 'MSExchangeTransport Routing'
	    object."
    INDEX      { ex2troInstance }
    ::= { ex2TransportRoutingTable 1 }

Ex2TransportRoutingEntry ::= SEQUENCE {
    ex2troInstance InstanceName,
    ex2troRoutingNDRsTotal Gauge32,
    ex2troRoutingTableCalculateTotal Gauge32,
    ex2troRoutingTablesChangedTotal Gauge32
}

ex2troInstance OBJECT-TYPE
    SYNTAX     InstanceName
    MAX-ACCESS read-only
    STATUS     current
    DESCRIPTION
	    "Instance name."
    ::= { ex2TransportRoutingEntry 1 }

ex2troRoutingNDRsTotal OBJECT-TYPE
    SYNTAX     Gauge32
    MAX-ACCESS read-only
    STATUS     current
    DESCRIPTION
	    "Routing NDRs Total is the number of recipients
	    NDRed by routing."
    ::= { ex2TransportRoutingEntry 2 }

ex2troRoutingTableCalculateTotal OBJECT-TYPE
    SYNTAX     Gauge32
    MAX-ACCESS read-only
    STATUS     current
    DESCRIPTION
	    "Routing Tables Calculated Total is the number
	    of times that routing tables have been
	    calculated."
    ::= { ex2TransportRoutingEntry 3 }

ex2troRoutingTablesChangedTotal OBJECT-TYPE
    SYNTAX     Gauge32
    MAX-ACCESS read-only
    STATUS     current
    DESCRIPTION
	    "Routing Tables Changed Total is the number of
	    times routing tables have changed."
    ::= { ex2TransportRoutingEntry 4 }

ex2TransportSmtpReceiveTable OBJECT-TYPE
    SYNTAX     SEQUENCE OF Ex2TransportSmtpReceiveEntry
    MAX-ACCESS not-accessible
    STATUS     current
    DESCRIPTION
	    "A table containing performance information for
	    instances of 'MSExchangeTransport SmtpReceive'
	    objects."
    ::= { exchangeV2 61 }

ex2TransportSmtpReceiveEntry OBJECT-TYPE
    SYNTAX     Ex2TransportSmtpReceiveEntry
    MAX-ACCESS not-accessible
    STATUS     current
    DESCRIPTION
	    "Performance information for one particular
	    instance of 'MSExchangeTransport SmtpReceive'
	    object."
    INDEX      { ex2tsrInstance }
    ::= { ex2TransportSmtpReceiveTable 1 }

Ex2TransportSmtpReceiveEntry ::= SEQUENCE {
    ex2tsrInstance InstanceName,
    ex2tsrAverageBytesPerConnection Gauge32,
    ex2tsrAverageBytesPerMessage Gauge32,
    ex2tsrAverageMessagePerConnectin Gauge32,
    ex2tsrAverageRecipientPerMessage Gauge32,
    ex2tsrBytesReceivedTotal Gauge32,
    ex2tsrBytesReceivedPerSec Gauge32,
    ex2tsrConnectionsCreatedPerSec Gauge32,
    ex2tsrConnectionsCurrent Gauge32,
    ex2tsrConnectionsTotal Gauge32,
    ex2tsrDisconnectionsByAgents Gauge32,
    ex2tsrDisconnectByAgentPerSecond Gauge32,
    ex2tsrMessageBytesReceivedTotal Gauge32,
    ex2tsrMessageBytesReceivedPerSec Gauge32,
    ex2tsrMessagesReceivedTotal Gauge32,
    ex2tsrMessagesReceivedPerSec Gauge32,
    ex2tsrMessagesRefusedForSize Gauge32,
    ex2tsrRecipientsAcceptedTotal Gauge32,
    ex2tsrTarpittingDelaysAnonymous Gauge32,
    ex2tsrTarpittngDelayAuthenticate Gauge32
}

ex2tsrInstance OBJECT-TYPE
    SYNTAX     InstanceName
    MAX-ACCESS read-only
    STATUS     current
    DESCRIPTION
	    "Instance name."
    ::= { ex2TransportSmtpReceiveEntry 1 }

ex2tsrAverageBytesPerConnection OBJECT-TYPE
    SYNTAX     Gauge32
    MAX-ACCESS read-only
    STATUS     current
    DESCRIPTION
	    "Average Bytes/Connection is the average number
	    of bytes received per connection."
    ::= { ex2TransportSmtpReceiveEntry 2 }

ex2tsrAverageBytesPerMessage OBJECT-TYPE
    SYNTAX     Gauge32
    MAX-ACCESS read-only
    STATUS     current
    DESCRIPTION
	    "Average Bytes/Message is the average number of
	    message bytes per inbound message received."
    ::= { ex2TransportSmtpReceiveEntry 3 }

ex2tsrAverageMessagePerConnectin OBJECT-TYPE
    SYNTAX     Gauge32
    MAX-ACCESS read-only
    STATUS     current
    DESCRIPTION
	    "Average Messages/Connection is the average
	    number of messages received per connection."
    ::= { ex2TransportSmtpReceiveEntry 4 }

ex2tsrAverageRecipientPerMessage OBJECT-TYPE
    SYNTAX     Gauge32
    MAX-ACCESS read-only
    STATUS     current
    DESCRIPTION
	    "Average Recipients/Message is the average
	    number of recipients per inbound message
	    received."
    ::= { ex2TransportSmtpReceiveEntry 5 }

ex2tsrBytesReceivedTotal OBJECT-TYPE
    SYNTAX     Gauge32
    MAX-ACCESS read-only
    STATUS     current
    DESCRIPTION
	    "Bytes Received Total is the total number of
	    bytes received."
    ::= { ex2TransportSmtpReceiveEntry 6 }

ex2tsrBytesReceivedPerSec OBJECT-TYPE
    SYNTAX     Gauge32
    MAX-ACCESS read-only
    STATUS     current
    DESCRIPTION
	    "Bytes Received/sec is the number of bytes
	    received per second."
    ::= { ex2TransportSmtpReceiveEntry 7 }

ex2tsrConnectionsCreatedPerSec OBJECT-TYPE
    SYNTAX     Gauge32
    MAX-ACCESS read-only
    STATUS     current
    DESCRIPTION
	    "Connections Created/sec is the number of new
	    connections to the SMTP server that are
	    established each second."
    ::= { ex2TransportSmtpReceiveEntry 8 }

ex2tsrConnectionsCurrent OBJECT-TYPE
    SYNTAX     Gauge32
    MAX-ACCESS read-only
    STATUS     current
    DESCRIPTION
	    "Connections Current is the number of inbound
	    connections to the SMTP server."
    ::= { ex2TransportSmtpReceiveEntry 9 }

ex2tsrConnectionsTotal OBJECT-TYPE
    SYNTAX     Gauge32
    MAX-ACCESS read-only
    STATUS     current
    DESCRIPTION
	    "Connections Total is the total number of
	    connections ever made to the SMTP server."
    ::= { ex2TransportSmtpReceiveEntry 10 }

ex2tsrDisconnectionsByAgents OBJECT-TYPE
    SYNTAX     Gauge32
    MAX-ACCESS read-only
    STATUS     current
    DESCRIPTION
	    "Disconnections By Agents is the number of
	    inbound connections that are dropped by Agent
	    actions."
    ::= { ex2TransportSmtpReceiveEntry 11 }

ex2tsrDisconnectByAgentPerSecond OBJECT-TYPE
    SYNTAX     Gauge32
    MAX-ACCESS read-only
    STATUS     current
    DESCRIPTION
	    "Disconnections by Agents/second is the number
	    of inbound connections that are dropped by
	    Agent actions per second."
    ::= { ex2TransportSmtpReceiveEntry 12 }

ex2tsrMessageBytesReceivedTotal OBJECT-TYPE
    SYNTAX     Gauge32
    MAX-ACCESS read-only
    STATUS     current
    DESCRIPTION
	    "Message Bytes Received Total is the total
	    number of bytes in messages received and
	    committed to database. This includes the
	    headers that are inserted by the SMTP server
	    and is the actual number of bytes that are
	    written to database."
    ::= { ex2TransportSmtpReceiveEntry 13 }

ex2tsrMessageBytesReceivedPerSec OBJECT-TYPE
    SYNTAX     Gauge32
    MAX-ACCESS read-only
    STATUS     current
    DESCRIPTION
	    "Message Bytes Received/sec is the number of
	    bytes received in messages each second."
    ::= { ex2TransportSmtpReceiveEntry 14 }

ex2tsrMessagesReceivedTotal OBJECT-TYPE
    SYNTAX     Gauge32
    MAX-ACCESS read-only
    STATUS     current
    DESCRIPTION
	    "Messages Received Total is the number of
	    messages received by the SMTP server."
    ::= { ex2TransportSmtpReceiveEntry 15 }

ex2tsrMessagesReceivedPerSec OBJECT-TYPE
    SYNTAX     Gauge32
    MAX-ACCESS read-only
    STATUS     current
    DESCRIPTION
	    "Messages Received/sec is the number of
	    messages received by the SMTP server each
	    second."
    ::= { ex2TransportSmtpReceiveEntry 16 }

ex2tsrMessagesRefusedForSize OBJECT-TYPE
    SYNTAX     Gauge32
    MAX-ACCESS read-only
    STATUS     current
    DESCRIPTION
	    "Messages Refused for Size is the number of
	    messages that were rejected because they were
	    too big."
    ::= { ex2TransportSmtpReceiveEntry 17 }

ex2tsrRecipientsAcceptedTotal OBJECT-TYPE
    SYNTAX     Gauge32
    MAX-ACCESS read-only
    STATUS     current
    DESCRIPTION
	    "Recipients Accepted Total is the number of
	    recipients accepted."
    ::= { ex2TransportSmtpReceiveEntry 18 }

ex2tsrTarpittingDelaysAnonymous OBJECT-TYPE
    SYNTAX     Gauge32
    MAX-ACCESS read-only
    STATUS     current
    DESCRIPTION
	    "Tarpitting Delays Anonymous is the total
	    number of tarpitting delays on anonymous
	    sessions."
    ::= { ex2TransportSmtpReceiveEntry 19 }

ex2tsrTarpittngDelayAuthenticate OBJECT-TYPE
    SYNTAX     Gauge32
    MAX-ACCESS read-only
    STATUS     current
    DESCRIPTION
	    "Tarpitting Delays Authenticated is the total
	    number of tarpitting delays on authenticated
	    sessions."
    ::= { ex2TransportSmtpReceiveEntry 20 }

ex2TransportSmtpSendTable OBJECT-TYPE
    SYNTAX     SEQUENCE OF Ex2TransportSmtpSendEntry
    MAX-ACCESS not-accessible
    STATUS     current
    DESCRIPTION
	    "A table containing performance information for
	    instances of 'MSExchangeTransport SmtpSend'
	    objects."
    ::= { exchangeV2 62 }

ex2TransportSmtpSendEntry OBJECT-TYPE
    SYNTAX     Ex2TransportSmtpSendEntry
    MAX-ACCESS not-accessible
    STATUS     current
    DESCRIPTION
	    "Performance information for one particular
	    instance of 'MSExchangeTransport SmtpSend'
	    object."
    INDEX      { ex2tssInstance }
    ::= { ex2TransportSmtpSendTable 1 }

Ex2TransportSmtpSendEntry ::= SEQUENCE {
    ex2tssInstance InstanceName,
    ex2tssAverageBytesPerConnection Gauge32,
    ex2tssAvgMessageBytesPerMessage Gauge32,
    ex2tssAvgMessagesPerConnection Gauge32,
    ex2tssAvgRecipientsPerMessage Gauge32,
    ex2tssBytesSentTotal Gauge32,
    ex2tssBytesSentPerSec Gauge32,
    ex2tssConnectionsCreatedPerSec Gauge32,
    ex2tssConnectionsCurrent Gauge32,
    ex2tssConnectionsTotal Gauge32,
    ex2tssMessageBytesSentTotal Gauge32,
    ex2tssMessageBytesSentPerSec Gauge32,
    ex2tssMessagesSentTotal Gauge32,
    ex2tssMessagesSentPerSec Gauge32,
    ex2tssRecipientsSent Gauge32
}

ex2tssInstance OBJECT-TYPE
    SYNTAX     InstanceName
    MAX-ACCESS read-only
    STATUS     current
    DESCRIPTION
	    "Instance name."
    ::= { ex2TransportSmtpSendEntry 1 }

ex2tssAverageBytesPerConnection OBJECT-TYPE
    SYNTAX     Gauge32
    MAX-ACCESS read-only
    STATUS     current
    DESCRIPTION
	    "Average Bytes/Connection is the average number
	    of bytes per connection sent by this SMTP Send
	    connector."
    ::= { ex2TransportSmtpSendEntry 2 }

ex2tssAvgMessageBytesPerMessage OBJECT-TYPE
    SYNTAX     Gauge32
    MAX-ACCESS read-only
    STATUS     current
    DESCRIPTION
	    "Average Message Bytes/Message is the average
	    number of bytes per message sent by this SMTP
	    Send connector."
    ::= { ex2TransportSmtpSendEntry 3 }

ex2tssAvgMessagesPerConnection OBJECT-TYPE
    SYNTAX     Gauge32
    MAX-ACCESS read-only
    STATUS     current
    DESCRIPTION
	    "Average Messages/Connection is the average
	    number of messages per connection sent by this
	    SMTP Send connector."
    ::= { ex2TransportSmtpSendEntry 4 }

ex2tssAvgRecipientsPerMessage OBJECT-TYPE
    SYNTAX     Gauge32
    MAX-ACCESS read-only
    STATUS     current
    DESCRIPTION
	    "Average Recipients/Message is the average
	    recipients per message handled by this SMTP
	    Send connector."
    ::= { ex2TransportSmtpSendEntry 5 }

ex2tssBytesSentTotal OBJECT-TYPE
    SYNTAX     Gauge32
    MAX-ACCESS read-only
    STATUS     current
    DESCRIPTION
	    "Bytes Sent Total is the total number of bytes
	    sent."
    ::= { ex2TransportSmtpSendEntry 6 }

ex2tssBytesSentPerSec OBJECT-TYPE
    SYNTAX     Gauge32
    MAX-ACCESS read-only
    STATUS     current
    DESCRIPTION
	    "Bytes Sent/sec is the number of bytes sent per
	    second."
    ::= { ex2TransportSmtpSendEntry 7 }

ex2tssConnectionsCreatedPerSec OBJECT-TYPE
    SYNTAX     Gauge32
    MAX-ACCESS read-only
    STATUS     current
    DESCRIPTION
	    "Connections Created/sec is the number of
	    outbound connections established each second
	    from the SMTP Send connector."
    ::= { ex2TransportSmtpSendEntry 8 }

ex2tssConnectionsCurrent OBJECT-TYPE
    SYNTAX     Gauge32
    MAX-ACCESS read-only
    STATUS     current
    DESCRIPTION
	    "Connections Current is the number of outbound
	    connections from the SMTP Send connector."
    ::= { ex2TransportSmtpSendEntry 9 }

ex2tssConnectionsTotal OBJECT-TYPE
    SYNTAX     Gauge32
    MAX-ACCESS read-only
    STATUS     current
    DESCRIPTION
	    "Connections Total is the number of connections
	    ever made from the SMTP Send connector."
    ::= { ex2TransportSmtpSendEntry 10 }

ex2tssMessageBytesSentTotal OBJECT-TYPE
    SYNTAX     Gauge32
    MAX-ACCESS read-only
    STATUS     current
    DESCRIPTION
	    "Message Bytes Sent Total is the total number
	    of bytes sent. This number includes only those
	    messages that were successfully sent."
    ::= { ex2TransportSmtpSendEntry 11 }

ex2tssMessageBytesSentPerSec OBJECT-TYPE
    SYNTAX     Gauge32
    MAX-ACCESS read-only
    STATUS     current
    DESCRIPTION
	    "Message Bytes Sent/sec is the number of bytes
	    sent per second."
    ::= { ex2TransportSmtpSendEntry 12 }

ex2tssMessagesSentTotal OBJECT-TYPE
    SYNTAX     Gauge32
    MAX-ACCESS read-only
    STATUS     current
    DESCRIPTION
	    "Messages Sent Total is the number of messages
	    sent by the SMTP Send connector."
    ::= { ex2TransportSmtpSendEntry 13 }

ex2tssMessagesSentPerSec OBJECT-TYPE
    SYNTAX     Gauge32
    MAX-ACCESS read-only
    STATUS     current
    DESCRIPTION
	    "Messages Sent/sec is the number of messages
	    sent by the SMTP Send connector each second."
    ::= { ex2TransportSmtpSendEntry 14 }

ex2tssRecipientsSent OBJECT-TYPE
    SYNTAX     Gauge32
    MAX-ACCESS read-only
    STATUS     current
    DESCRIPTION
	    "Recipients sent is the number of recipients
	    sent by the SMTPSend Connector."
    ::= { ex2TransportSmtpSendEntry 15 }

ex2UMAutoAttendantTable OBJECT-TYPE
    SYNTAX     SEQUENCE OF Ex2UMAutoAttendantEntry
    MAX-ACCESS not-accessible
    STATUS     current
    DESCRIPTION
	    "A table containing performance information for
	    instances of 'MSExchangeUMAutoAttendant'
	    objects."
    ::= { exchangeV2 63 }

ex2UMAutoAttendantEntry OBJECT-TYPE
    SYNTAX     Ex2UMAutoAttendantEntry
    MAX-ACCESS not-accessible
    STATUS     current
    DESCRIPTION
	    "Performance information for one particular
	    instance of 'MSExchangeUMAutoAttendant'
	    object."
    INDEX      { ex2umaaInstance }
    ::= { ex2UMAutoAttendantTable 1 }

Ex2UMAutoAttendantEntry ::= SEQUENCE {
    ex2umaaInstance InstanceName,
    ex2umaaPercentSuccessfulCalls Gauge32,
    ex2umaaAmbiguousNameTransfers Gauge32,
    ex2umaaAverageCallTime Gauge32,
    ex2umaaAverageRecentCallTime Gauge32,
    ex2umaaBusinessHoursCalls Gauge32,
    ex2umaaCallsDisconUMIrreExtError Gauge32,
    ex2umaaCallsWithDTMFFallback Gauge32,
    ex2umaaCallsWithSentMessage Gauge32,
    ex2umaaCallsWithSpeechInput Gauge32,
    ex2umaaCallsWithSpokenName Gauge32,
    ex2umaaCustomMenuOptions Gauge32,
    ex2umaaDirectoryAccessed Gauge32,
    ex2umaaDirAccsdSuccByDialByName Gauge32,
    ex2umaaDirAccsdSuccBySpokenName Gauge32,
    ex2umaaDirAccsdByDialByName Gauge32,
    ex2umaaDirAccsdByExtension Gauge32,
    ex2umaaDirAccsdBySpokenName Gauge32,
    ex2umaaDisallowedTransfers Gauge32,
    ex2umaaDisconnectedWithoutInput Gauge32,
    ex2umaaMenuOption1Used Gauge32,
    ex2umaaMenuOption2Used Gauge32,
    ex2umaaMenuOption3Used Gauge32,
    ex2umaaMenuOption4Used Gauge32,
    ex2umaaMenuOption5Used Gauge32,
    ex2umaaMenuOption6Used Gauge32,
    ex2umaaMenuOption7Used Gauge32,
    ex2umaaMenuOption8Used Gauge32,
    ex2umaaMenuOption9Used Gauge32,
    ex2umaaMenuOptionTimedOut Gauge32,
    ex2umaaOperatorTransfers Gauge32,
    ex2umaaOperTransReqByUser Gauge32,
    ex2umaaOperTransReqByUseOpenMenu Gauge32,
    ex2umaaOutOfHoursCalls Gauge32,
    ex2umaaSentToAutoAttendant Gauge32,
    ex2umaaTotalCalls Gauge32,
    ex2umaaTransferredCount Gauge32
}

ex2umaaInstance OBJECT-TYPE
    SYNTAX     InstanceName
    MAX-ACCESS read-only
    STATUS     current
    DESCRIPTION
	    "Instance name."
    ::= { ex2UMAutoAttendantEntry 1 }

ex2umaaPercentSuccessfulCalls OBJECT-TYPE
    SYNTAX     Gauge32
    MAX-ACCESS read-only
    STATUS     current
    DESCRIPTION
	    "This counter calculates the success rate of
	    the auto attendant."
    ::= { ex2UMAutoAttendantEntry 2 }

ex2umaaAmbiguousNameTransfers OBJECT-TYPE
    SYNTAX     Gauge32
    MAX-ACCESS read-only
    STATUS     current
    DESCRIPTION
	    "Ambiguous Name Transfers is the number of
	    times that a caller was transferred to the
	    operator because the name that they spelled or
	    spoke was too common in the search results."
    ::= { ex2UMAutoAttendantEntry 3 }

ex2umaaAverageCallTime OBJECT-TYPE
    SYNTAX     Gauge32
    MAX-ACCESS read-only
    STATUS     current
    DESCRIPTION
	    "Average Call Time is the average length of
	    time that callers interacted with the auto
	    attendant."
    ::= { ex2UMAutoAttendantEntry 4 }

ex2umaaAverageRecentCallTime OBJECT-TYPE
    SYNTAX     Gauge32
    MAX-ACCESS read-only
    STATUS     current
    DESCRIPTION
	    "Average Recent Call Time is the average length
	    of time, in seconds, of the last 50 auto
	    attendant calls."
    ::= { ex2UMAutoAttendantEntry 5 }

ex2umaaBusinessHoursCalls OBJECT-TYPE
    SYNTAX     Gauge32
    MAX-ACCESS read-only
    STATUS     current
    DESCRIPTION
	    "Business Hours Calls is the number of calls
	    processed by this auto attendant during
	    business hours."
    ::= { ex2UMAutoAttendantEntry 6 }

ex2umaaCallsDisconUMIrreExtError OBJECT-TYPE
    SYNTAX     Gauge32
    MAX-ACCESS read-only
    STATUS     current
    DESCRIPTION
	    "Calls Disconnected by UM on Irrecoverable
	    External Error is the total number of calls
	    that were disconnected after an irrecoverable
	    external error occurred."
    ::= { ex2UMAutoAttendantEntry 7 }

ex2umaaCallsWithDTMFFallback OBJECT-TYPE
    SYNTAX     Gauge32
    MAX-ACCESS read-only
    STATUS     current
    DESCRIPTION
	    "Calls with DTMF fallback is the number of
	    calls to this auto attendant during which a
	    caller has been passed to the DTMF fallback
	    auto attendant. This only happens for
	    speech-enabled auto attendants."
    ::= { ex2UMAutoAttendantEntry 8 }

ex2umaaCallsWithSentMessage OBJECT-TYPE
    SYNTAX     Gauge32
    MAX-ACCESS read-only
    STATUS     current
    DESCRIPTION
	    "Calls with Sent Message is the number of calls
	    to this auto attendant in which a caller has
	    sent a voice message."
    ::= { ex2UMAutoAttendantEntry 9 }

ex2umaaCallsWithSpeechInput OBJECT-TYPE
    SYNTAX     Gauge32
    MAX-ACCESS read-only
    STATUS     current
    DESCRIPTION
	    "Calls with Speech Input is the total number of
	    calls during which the caller is determined to
	    have spoken at least once."
    ::= { ex2UMAutoAttendantEntry 10 }

ex2umaaCallsWithSpokenName OBJECT-TYPE
    SYNTAX     Gauge32
    MAX-ACCESS read-only
    STATUS     current
    DESCRIPTION
	    "Calls with Spoken Name is the number of calls
	    to this auto attendant in which a caller has
	    spoken a name at least once."
    ::= { ex2UMAutoAttendantEntry 11 }

ex2umaaCustomMenuOptions OBJECT-TYPE
    SYNTAX     Gauge32
    MAX-ACCESS read-only
    STATUS     current
    DESCRIPTION
	    "Custom Menu Options is the number of times
	    that callers have selected custom menu
	    options."
    ::= { ex2UMAutoAttendantEntry 12 }

ex2umaaDirectoryAccessed OBJECT-TYPE
    SYNTAX     Gauge32
    MAX-ACCESS read-only
    STATUS     current
    DESCRIPTION
	    "Directory Accessed is the number of directory
	    access operations performed by this auto
	    attendant."
    ::= { ex2UMAutoAttendantEntry 13 }

ex2umaaDirAccsdSuccByDialByName OBJECT-TYPE
    SYNTAX     Gauge32
    MAX-ACCESS read-only
    STATUS     current
    DESCRIPTION
	    "Directory Accessed Successfully by Dial by
	    Name is the number of successful directory
	    access operations in which the caller used the
	    Dial by Name feature."
    ::= { ex2UMAutoAttendantEntry 14 }

ex2umaaDirAccsdSuccBySpokenName OBJECT-TYPE
    SYNTAX     Gauge32
    MAX-ACCESS read-only
    STATUS     current
    DESCRIPTION
	    "Directory Accessed Successfully by Spoken Name
	    is the number of successful directory access
	    operations in which the caller used the Dial by
	    Name feature."
    ::= { ex2UMAutoAttendantEntry 15 }

ex2umaaDirAccsdByDialByName OBJECT-TYPE
    SYNTAX     Gauge32
    MAX-ACCESS read-only
    STATUS     current
    DESCRIPTION
	    "Directory Accessed by Dial by Name is the
	    number of directory access operations in which
	    the subscriber used the Dial by Name feature."
    ::= { ex2UMAutoAttendantEntry 16 }

ex2umaaDirAccsdByExtension OBJECT-TYPE
    SYNTAX     Gauge32
    MAX-ACCESS read-only
    STATUS     current
    DESCRIPTION
	    "Directory Accessed by Extension is the number
	    of directory access operations in which the
	    user supplied the extension number."
    ::= { ex2UMAutoAttendantEntry 17 }

ex2umaaDirAccsdBySpokenName OBJECT-TYPE
    SYNTAX     Gauge32
    MAX-ACCESS read-only
    STATUS     current
    DESCRIPTION
	    "Directory Accessed by Spoken Name is the
	    number of directory access operations in which
	    the subscriber spoke a recipient name."
    ::= { ex2UMAutoAttendantEntry 18 }

ex2umaaDisallowedTransfers OBJECT-TYPE
    SYNTAX     Gauge32
    MAX-ACCESS read-only
    STATUS     current
    DESCRIPTION
	    "Disallowed Transfers is the number of times a
	    caller was transferred to the operator because
	    the user they identified was configured to
	    accept calls only from users who are logged
	    on."
    ::= { ex2UMAutoAttendantEntry 19 }

ex2umaaDisconnectedWithoutInput OBJECT-TYPE
    SYNTAX     Gauge32
    MAX-ACCESS read-only
    STATUS     current
    DESCRIPTION
	    "Disconnected Without Input is the number of
	    calls that were dropped without any input being
	    offered in response to the auto attendant
	    prompts."
    ::= { ex2UMAutoAttendantEntry 20 }

ex2umaaMenuOption1Used OBJECT-TYPE
    SYNTAX     Gauge32
    MAX-ACCESS read-only
    STATUS     current
    DESCRIPTION
	    "Menu Option 1 Used is the number of times that
	    a caller has chosen option 1 from the custom
	    menu."
    ::= { ex2UMAutoAttendantEntry 21 }

ex2umaaMenuOption2Used OBJECT-TYPE
    SYNTAX     Gauge32
    MAX-ACCESS read-only
    STATUS     current
    DESCRIPTION
	    "Menu Option 2 Used is the number of times that
	    a caller has chosen option 2 from the custom
	    menu."
    ::= { ex2UMAutoAttendantEntry 22 }

ex2umaaMenuOption3Used OBJECT-TYPE
    SYNTAX     Gauge32
    MAX-ACCESS read-only
    STATUS     current
    DESCRIPTION
	    "Menu Option 3 Used is the number of times that
	    a caller has chosen option 3 from the custom
	    menu."
    ::= { ex2UMAutoAttendantEntry 23 }

ex2umaaMenuOption4Used OBJECT-TYPE
    SYNTAX     Gauge32
    MAX-ACCESS read-only
    STATUS     current
    DESCRIPTION
	    "Menu Option 4 Used is the number of times that
	    a caller has chosen option 4 from the custom
	    menu."
    ::= { ex2UMAutoAttendantEntry 24 }

ex2umaaMenuOption5Used OBJECT-TYPE
    SYNTAX     Gauge32
    MAX-ACCESS read-only
    STATUS     current
    DESCRIPTION
	    "Menu Option 5 Used is the number of times that
	    a caller has chosen option 5 from the custom
	    menu."
    ::= { ex2UMAutoAttendantEntry 25 }

ex2umaaMenuOption6Used OBJECT-TYPE
    SYNTAX     Gauge32
    MAX-ACCESS read-only
    STATUS     current
    DESCRIPTION
	    "Menu Option 6 Used is the number of times that
	    a caller has chosen option 6 from the custom
	    menu."
    ::= { ex2UMAutoAttendantEntry 26 }

ex2umaaMenuOption7Used OBJECT-TYPE
    SYNTAX     Gauge32
    MAX-ACCESS read-only
    STATUS     current
    DESCRIPTION
	    "Menu Option 7 Used is the number of times that
	    a caller has chosen option 7 from the custom
	    menu."
    ::= { ex2UMAutoAttendantEntry 27 }

ex2umaaMenuOption8Used OBJECT-TYPE
    SYNTAX     Gauge32
    MAX-ACCESS read-only
    STATUS     current
    DESCRIPTION
	    "Menu Option 8 Used is the number of times that
	    a caller has chosen option 8 from the custom
	    menu."
    ::= { ex2UMAutoAttendantEntry 28 }

ex2umaaMenuOption9Used OBJECT-TYPE
    SYNTAX     Gauge32
    MAX-ACCESS read-only
    STATUS     current
    DESCRIPTION
	    "Menu Option 9 Used is the number of times that
	    a caller has chosen option 9 from the custom
	    menu."
    ::= { ex2UMAutoAttendantEntry 29 }

ex2umaaMenuOptionTimedOut OBJECT-TYPE
    SYNTAX     Gauge32
    MAX-ACCESS read-only
    STATUS     current
    DESCRIPTION
	    "Menu Option Timed Out is the number of times
	    that the system has timed out while waiting for
	    a caller to select an option from the custom
	    menu."
    ::= { ex2UMAutoAttendantEntry 30 }

ex2umaaOperatorTransfers OBJECT-TYPE
    SYNTAX     Gauge32
    MAX-ACCESS read-only
    STATUS     current
    DESCRIPTION
	    "Operator Transfers is the number of calls that
	    have been transferred to the operator."
    ::= { ex2UMAutoAttendantEntry 31 }

ex2umaaOperTransReqByUser OBJECT-TYPE
    SYNTAX     Gauge32
    MAX-ACCESS read-only
    STATUS     current
    DESCRIPTION
	    "Operator Transfers Requested by User is the
	    number of times that a caller to this auto
	    attendant has asked to be transferred to an
	    operator."
    ::= { ex2UMAutoAttendantEntry 32 }

ex2umaaOperTransReqByUseOpenMenu OBJECT-TYPE
    SYNTAX     Gauge32
    MAX-ACCESS read-only
    STATUS     current
    DESCRIPTION
	    "Operator Transfers Requested by User from
	    Opening Menu is the number of times that a
	    caller to this auto attendant has asked to be
	    transferred to an operator while at the opening
	    menu."
    ::= { ex2UMAutoAttendantEntry 33 }

ex2umaaOutOfHoursCalls OBJECT-TYPE
    SYNTAX     Gauge32
    MAX-ACCESS read-only
    STATUS     current
    DESCRIPTION
	    "Out of Hours Calls is the number of calls that
	    have been processed by this auto attendant
	    outside of business hours."
    ::= { ex2UMAutoAttendantEntry 34 }

ex2umaaSentToAutoAttendant OBJECT-TYPE
    SYNTAX     Gauge32
    MAX-ACCESS read-only
    STATUS     current
    DESCRIPTION
	    "Sent to Auto Attendant is the number of times
	    that a caller to this auto attendant has used
	    the custom menu to go to an auto attendant."
    ::= { ex2UMAutoAttendantEntry 35 }

ex2umaaTotalCalls OBJECT-TYPE
    SYNTAX     Gauge32
    MAX-ACCESS read-only
    STATUS     current
    DESCRIPTION
	    "Total Calls is the number of calls that have
	    been processed by this auto attendant."
    ::= { ex2UMAutoAttendantEntry 36 }

ex2umaaTransferredCount OBJECT-TYPE
    SYNTAX     Gauge32
    MAX-ACCESS read-only
    STATUS     current
    DESCRIPTION
	    "Transferred Count is the number of calls that
	    were transferred by this auto attendant. This
	    number does not include calls that were
	    transferred by the operator."
    ::= { ex2UMAutoAttendantEntry 37 }

ex2UMAvailability OBJECT IDENTIFIER
    ::= { exchangeV2 64 }

ex2umaCallAnswerQueuedMessages OBJECT-TYPE
    SYNTAX     Gauge32
    MAX-ACCESS read-only
    STATUS     current
    DESCRIPTION
	    "Call Answer Queued Messages is the number of
	    messages created and not yet submitted for
	    delivery."
    ::= { ex2UMAvailability 1 }

ex2umaCalDisconUMIrrecovExtError OBJECT-TYPE
    SYNTAX     Gauge32
    MAX-ACCESS read-only
    STATUS     current
    DESCRIPTION
	    "Calls Disconnected by UM on Irrecoverable
	    External Error is the total number of calls
	    disconnected after an irrecoverable external
	    error occurred."
    ::= { ex2UMAvailability 2 }

ex2umaCalDiscnUMIrrecovExtErrSec OBJECT-TYPE
    SYNTAX     Gauge32
    MAX-ACCESS read-only
    STATUS     current
    DESCRIPTION
	    "Calls Disconnected by UM on Irrecoverable
	    External Error per second is the number of
	    calls disconnected after an irrecoverable
	    external error occurred in the last second."
    ::= { ex2UMAvailability 3 }

ex2umaCalDiscnIrrecovInternalErr OBJECT-TYPE
    SYNTAX     Gauge32
    MAX-ACCESS read-only
    STATUS     current
    DESCRIPTION
	    "Calls Disconnected on Irrecoverable Internal
	    Error is the number of calls disconnected after
	    an internal system error occurred."
    ::= { ex2UMAvailability 4 }

ex2umaDirectoryAccessFailures OBJECT-TYPE
    SYNTAX     Gauge32
    MAX-ACCESS read-only
    STATUS     current
    DESCRIPTION
	    "Directory Access Failures is the number of
	    times that attempts to access Active Directory
	    failed."
    ::= { ex2UMAvailability 5 }

ex2umaFailedToRedirectCall OBJECT-TYPE
    SYNTAX     Gauge32
    MAX-ACCESS read-only
    STATUS     current
    DESCRIPTION
	    "Failed to Redirect Call is the number of times
	    the Microsoft Exchange Unified Messaging
	    service did not redirect calls to a UM worker
	    process."
    ::= { ex2UMAvailability 6 }

ex2umaHubTransportAccessComplete OBJECT-TYPE
    SYNTAX     Gauge32
    MAX-ACCESS read-only
    STATUS     current
    DESCRIPTION
	    "Hub Transport Access Completed is the number
	    of times that the Hub Transport server was
	    accessed successfully."
    ::= { ex2UMAvailability 7 }

ex2umaHubTransportAccessFailures OBJECT-TYPE
    SYNTAX     Gauge32
    MAX-ACCESS read-only
    STATUS     current
    DESCRIPTION
	    "Hub Transport Access Failures is the number of
	    times that attempts to access a Hub Transport
	    server failed. This number is only incremented
	    if all Hub Transport servers were unavailable."
    ::= { ex2UMAvailability 8 }

ex2umaIncompSignalingInformation OBJECT-TYPE
    SYNTAX     Gauge32
    MAX-ACCESS read-only
    STATUS     current
    DESCRIPTION
	    "Incomplete Signaling Information is the number
	    of calls for which the signaling information
	    was missing or incomplete."
    ::= { ex2UMAvailability 9 }

ex2umaMailboxServerAccessFailure OBJECT-TYPE
    SYNTAX     Gauge32
    MAX-ACCESS read-only
    STATUS     current
    DESCRIPTION
	    "Mailbox Server Access Failures is the number
	    of times the system did not access a Mailbox
	    server."
    ::= { ex2UMAvailability 10 }

ex2umaMaximumCallsAllowed OBJECT-TYPE
    SYNTAX     Gauge32
    MAX-ACCESS read-only
    STATUS     current
    DESCRIPTION
	    "Maximum Calls Allowed is the length of time,
	    in seconds, that the server  concurrently
	    processed the maximum number of calls allowed."
    ::= { ex2UMAvailability 11 }

ex2umaNameTTSed OBJECT-TYPE
    SYNTAX     Gauge32
    MAX-ACCESS read-only
    STATUS     current
    DESCRIPTION
	    "Name TTSed is the number of times the system
	    used Text-to-Speech (TTS) to create an audio
	    version of the display name of a subscriber."
    ::= { ex2UMAvailability 12 }

ex2umaQueuedOCSUserEventNotifica OBJECT-TYPE
    SYNTAX     Gauge32
    MAX-ACCESS read-only
    STATUS     current
    DESCRIPTION
	    "Queued OCS User Event Notifications is the
	    number of notifications that have been created
	    and not yet submitted for delivery."
    ::= { ex2UMAvailability 13 }

ex2umaSpokenNameAccessed OBJECT-TYPE
    SYNTAX     Gauge32
    MAX-ACCESS read-only
    STATUS     current
    DESCRIPTION
	    "Spoken Name Accessed is the number of times
	    the system retrieved the recorded name of a
	    user."
    ::= { ex2UMAvailability 14 }

ex2umaTotalWorkerProcesCallCount OBJECT-TYPE
    SYNTAX     Gauge32
    MAX-ACCESS read-only
    STATUS     current
    DESCRIPTION
	    "Total Worker Process Call Count is the total
	    number of calls handled by this UM worker
	    process."
    ::= { ex2UMAvailability 15 }

ex2umaUnhandledExceptionsPerSec OBJECT-TYPE
    SYNTAX     Gauge32
    MAX-ACCESS read-only
    STATUS     current
    DESCRIPTION
	    "Calls Disconnected on Irrecoverable Internal
	    Error Per Second is the number of calls that
	    were disconnected after an internal system
	    error occurred in the last second."
    ::= { ex2UMAvailability 16 }

ex2umaWorkerProcessRecycled OBJECT-TYPE
    SYNTAX     Gauge32
    MAX-ACCESS read-only
    STATUS     current
    DESCRIPTION
	    "Worker Process Recycled is the number of times
	    a new UM worker process has been started."
    ::= { ex2UMAvailability 17 }

ex2UMCallAnswer OBJECT IDENTIFIER
    ::= { exchangeV2 65 }

ex2UMCallAnsAvgGreetingSize OBJECT-TYPE
    SYNTAX     Gauge32
    MAX-ACCESS read-only
    STATUS     current
    DESCRIPTION
	    "Average Greeting Size is the average size, in
	    seconds, of recorded greetings that have been
	    retrieved by the UM server."
    ::= { ex2UMCallAnswer 1 }

ex2UMCallAnsAvgRecentVoiceMsgSiz OBJECT-TYPE
    SYNTAX     Gauge32
    MAX-ACCESS read-only
    STATUS     current
    DESCRIPTION
	    "Average Recent Voice Message Size is the
	    average size, in seconds, of the last 50 voice
	    messages that have been left for subscribers."
    ::= { ex2UMCallAnswer 2 }

ex2UMCallAnsAvgVoiceMsgSize OBJECT-TYPE
    SYNTAX     Gauge32
    MAX-ACCESS read-only
    STATUS     current
    DESCRIPTION
	    "Average Voice Message Size is the average
	    size, in seconds, of voice messages left for
	    subscribers."
    ::= { ex2UMCallAnswer 3 }

ex2UMCallAnsCallAnsingCalls OBJECT-TYPE
    SYNTAX     Gauge32
    MAX-ACCESS read-only
    STATUS     current
    DESCRIPTION
	    "Call Answering Calls is the number of diverted
	    calls that were answered on behalf of
	    subscribers."
    ::= { ex2UMCallAnswer 4 }

ex2UMCallAnsCallAnsingEscapes OBJECT-TYPE
    SYNTAX     Gauge32
    MAX-ACCESS read-only
    STATUS     current
    DESCRIPTION
	    "Call Answering Escapes is the number of times
	    a caller pressed the * key to connect to
	    another user rather than leaving a message."
    ::= { ex2UMCallAnswer 5 }

ex2UMCallAnsCallAnsingMissedCall OBJECT-TYPE
    SYNTAX     Gauge32
    MAX-ACCESS read-only
    STATUS     current
    DESCRIPTION
	    "Call Answering Missed Calls is the number of
	    times a diverted call was dropped without a
	    message being left."
    ::= { ex2UMCallAnswer 6 }

ex2UMCallAnsCallAnsingVoiceMsgs OBJECT-TYPE
    SYNTAX     Gauge32
    MAX-ACCESS read-only
    STATUS     current
    DESCRIPTION
	    "Call Answering Voice Messages is the total
	    number of messages that were submitted because
	    the calls were answered on behalf of
	    subscribers."
    ::= { ex2UMCallAnswer 7 }

ex2UMCallAnsCallAnsVoiceMsgPrSec OBJECT-TYPE
    SYNTAX     Gauge32
    MAX-ACCESS read-only
    STATUS     current
    DESCRIPTION
	    "Call Answering Voice Messages per Second is
	    the number of messages that were submitted
	    because the calls were answered on behalf of
	    subscribers."
    ::= { ex2UMCallAnswer 8 }

ex2UMCallAnsCallFailTransUnavail OBJECT-TYPE
    SYNTAX     Gauge32
    MAX-ACCESS read-only
    STATUS     current
    DESCRIPTION
	    "Call Failed Because Transport Unavailable is
	    the number of calls that failed because the
	    transport service is not available to submit
	    the message."
    ::= { ex2UMCallAnswer 9 }

ex2UMCalAnsCalDisCalUMAudioHrgls OBJECT-TYPE
    SYNTAX     Gauge32
    MAX-ACCESS read-only
    STATUS     current
    DESCRIPTION
	    "Calls Disconnected by Callers During UM Audio
	    Hourglass is the number of calls during which
	    the caller disconnected while Unified Messaging
	    was playing the audio hourglass tones."
    ::= { ex2UMCallAnswer 10 }

ex2UMCalAnsCalDisUMIrrecExtError OBJECT-TYPE
    SYNTAX     Gauge32
    MAX-ACCESS read-only
    STATUS     current
    DESCRIPTION
	    "Calls Disconnected by UM on Irrecoverable
	    External Error is the total number of calls
	    that have been disconnected after an
	    irrecoverable external error occurred."
    ::= { ex2UMCallAnswer 11 }

ex2UMCallAnsCallWithoutPersGreet OBJECT-TYPE
    SYNTAX     Gauge32
    MAX-ACCESS read-only
    STATUS     current
    DESCRIPTION
	    "Calls Without Personal Greetings is the number
	    of diverted calls received for subscribers that
	    did not have recorded greeting messages."
    ::= { ex2UMCallAnswer 12 }

ex2UMCallAnsDivertExtNotProvis OBJECT-TYPE
    SYNTAX     Gauge32
    MAX-ACCESS read-only
    STATUS     current
    DESCRIPTION
	    "Diverted Extension Not Provisioned is the
	    number of calls received for which the diverted
	    extension supplied with the call is not a UM
	    subscriber extension."
    ::= { ex2UMCallAnswer 13 }

ex2UMCallAnsFetchGreetingTimeOut OBJECT-TYPE
    SYNTAX     Gauge32
    MAX-ACCESS read-only
    STATUS     current
    DESCRIPTION
	    "Fetch Greeting Timed Out is the number of
	    diverted calls for which the subscriber's
	    personal greeting could not be retrieved within
	    the time allowed."
    ::= { ex2UMCallAnswer 14 }

ex2UMClientAccessTable OBJECT-TYPE
    SYNTAX     SEQUENCE OF Ex2UMClientAccessEntry
    MAX-ACCESS not-accessible
    STATUS     current
    DESCRIPTION
	    "A table containing performance information for
	    instances of 'MSExchangeUMClientAccess'
	    objects."
    ::= { exchangeV2 66 }

ex2UMClientAccessEntry OBJECT-TYPE
    SYNTAX     Ex2UMClientAccessEntry
    MAX-ACCESS not-accessible
    STATUS     current
    DESCRIPTION
	    "Performance information for one particular
	    instance of 'MSExchangeUMClientAccess' object."
    INDEX      { ex2umcacInstance }
    ::= { ex2UMClientAccessTable 1 }

Ex2UMClientAccessEntry ::= SEQUENCE {
    ex2umcacInstance InstanceName,
    ex2umcacPID Gauge32,
    ex2umcacTotalNumPINResetRequests Gauge32,
    ex2umcacTotalNumFailPINResetReq Gauge32,
    ex2umcacTotalNumFailPlayPhoneReq Gauge32,
    ex2umcacTotalNumPlayPhoneRequest Gauge32
}

ex2umcacInstance OBJECT-TYPE
    SYNTAX     InstanceName
    MAX-ACCESS read-only
    STATUS     current
    DESCRIPTION
	    "Instance name."
    ::= { ex2UMClientAccessEntry 1 }

ex2umcacPID OBJECT-TYPE
    SYNTAX     Gauge32
    MAX-ACCESS read-only
    STATUS     current
    DESCRIPTION
	    "Process ID that is hosting the UM client
	    access component"
    ::= { ex2UMClientAccessEntry 2 }

ex2umcacTotalNumPINResetRequests OBJECT-TYPE
    SYNTAX     Gauge32
    MAX-ACCESS read-only
    STATUS     current
    DESCRIPTION
	    "Total Number of PIN Reset Requests is the
	    number of PIN resets that have been requested
	    since the host process was restarted."
    ::= { ex2UMClientAccessEntry 3 }

ex2umcacTotalNumFailPINResetReq OBJECT-TYPE
    SYNTAX     Gauge32
    MAX-ACCESS read-only
    STATUS     current
    DESCRIPTION
	    "Total Number of Failed PIN Reset Requests is
	    the number of requested PIN resets that have
	    failed since the host process was restarted."
    ::= { ex2UMClientAccessEntry 4 }

ex2umcacTotalNumFailPlayPhoneReq OBJECT-TYPE
    SYNTAX     Gauge32
    MAX-ACCESS read-only
    STATUS     current
    DESCRIPTION
	    "Total number of failed play on phone requests
	    since the host process was restarted"
    ::= { ex2UMClientAccessEntry 5 }

ex2umcacTotalNumPlayPhoneRequest OBJECT-TYPE
    SYNTAX     Gauge32
    MAX-ACCESS read-only
    STATUS     current
    DESCRIPTION
	    "Total number of play on phone requests since
	    the host process was restarted"
    ::= { ex2UMClientAccessEntry 6 }

ex2UMFax OBJECT IDENTIFIER
    ::= { exchangeV2 67 }

ex2umfAverageFaxMessageSize OBJECT-TYPE
    SYNTAX     Gauge32
    MAX-ACCESS read-only
    STATUS     current
    DESCRIPTION
	    "Average Fax Message Size is the average size,
	    in kilobytes, of fax messages received."
    ::= { ex2UMFax 1 }

ex2umfAverageRecentFaxMessageSiz OBJECT-TYPE
    SYNTAX     Gauge32
    MAX-ACCESS read-only
    STATUS     current
    DESCRIPTION
	    "Average Recent Fax Message Size is the average
	    size, in kilobytes, of the last 20 fax
	    messages."
    ::= { ex2UMFax 2 }

ex2umfFaxCallDurationExceeded OBJECT-TYPE
    SYNTAX     Gauge32
    MAX-ACCESS read-only
    STATUS     current
    DESCRIPTION
	    "Fax Call Duration Exceeded is the number of
	    fax calls that were disconnected because they
	    exceeded the UM maximum call length."
    ::= { ex2UMFax 3 }

ex2umfFaxCallNonProvisionMailbox OBJECT-TYPE
    SYNTAX     Gauge32
    MAX-ACCESS read-only
    STATUS     current
    DESCRIPTION
	    "Fax Calls to Non Provisioned Mailboxes is the
	    number of calls to extensions that resolved to
	    mailboxes that are not enabled for fax."
    ::= { ex2UMFax 4 }

ex2umfFaxIncomplete OBJECT-TYPE
    SYNTAX     Gauge32
    MAX-ACCESS read-only
    STATUS     current
    DESCRIPTION
	    "Fax Incomplete is the number of fax calls that
	    were dropped before completion."
    ::= { ex2UMFax 5 }

ex2umfFaxMessages OBJECT-TYPE
    SYNTAX     Gauge32
    MAX-ACCESS read-only
    STATUS     current
    DESCRIPTION
	    "Fax Messages is the total number of fax
	    messages received."
    ::= { ex2UMFax 6 }

ex2UMGeneral OBJECT IDENTIFIER
    ::= { exchangeV2 68 }

ex2umgAverageCallDuration OBJECT-TYPE
    SYNTAX     Gauge32
    MAX-ACCESS read-only
    STATUS     current
    DESCRIPTION
	    "Average Call Duration is the average duration,
	    in seconds, of calls since the service was
	    started."
    ::= { ex2UMGeneral 1 }

ex2umgAverageRecentCallDuration OBJECT-TYPE
    SYNTAX     Gauge32
    MAX-ACCESS read-only
    STATUS     current
    DESCRIPTION
	    "Average Recent Call Duration is the average
	    duration, in seconds, of the last 50 calls."
    ::= { ex2UMGeneral 2 }

ex2umgCallDurationExceeded OBJECT-TYPE
    SYNTAX     Gauge32
    MAX-ACCESS read-only
    STATUS     current
    DESCRIPTION
	    "Call Duration Exceeded is the number of calls
	    that were disconnected because they exceeded
	    the UM maximum call length. This number
	    includes all types of calls, including fax
	    calls."
    ::= { ex2UMGeneral 3 }

ex2umgCallsDisconnectUserFailure OBJECT-TYPE
    SYNTAX     Gauge32
    MAX-ACCESS read-only
    STATUS     current
    DESCRIPTION
	    "Calls Disconnected by User Failure is the
	    total number of calls disconnected after too
	    many user entry failures."
    ::= { ex2UMGeneral 4 }

ex2umgCallsRejected OBJECT-TYPE
    SYNTAX     Gauge32
    MAX-ACCESS read-only
    STATUS     current
    DESCRIPTION
	    "Calls Rejected is the total number of new call
	    invitations that have been rejected."
    ::= { ex2UMGeneral 5 }

ex2umgCallsRejectedPerSecond OBJECT-TYPE
    SYNTAX     Gauge32
    MAX-ACCESS read-only
    STATUS     current
    DESCRIPTION
	    "Calls Rejected per Second is the number of new
	    call invitations that have been rejected in the
	    last second."
    ::= { ex2UMGeneral 6 }

ex2umgCurrentAutoAttendantCalls OBJECT-TYPE
    SYNTAX     Gauge32
    MAX-ACCESS read-only
    STATUS     current
    DESCRIPTION
	    "Current Auto Attendant Calls is the number of
	    auto attendant calls that are currently
	    connected to the UM server."
    ::= { ex2UMGeneral 7 }

ex2umgCurrentCASConnections OBJECT-TYPE
    SYNTAX     Gauge32
    MAX-ACCESS read-only
    STATUS     current
    DESCRIPTION
	    "Current CAS Connections is the number of
	    connections that are currently open between the
	    Unified Messaging server and Client Access
	    servers."
    ::= { ex2UMGeneral 8 }

ex2umgCurrentCalls OBJECT-TYPE
    SYNTAX     Gauge32
    MAX-ACCESS read-only
    STATUS     current
    DESCRIPTION
	    "Current Calls is the number of calls that are
	    currently connected to the UM server."
    ::= { ex2UMGeneral 9 }

ex2umgCurrentFaxCalls OBJECT-TYPE
    SYNTAX     Gauge32
    MAX-ACCESS read-only
    STATUS     current
    DESCRIPTION
	    "Current Fax Calls is the number of fax calls
	    that are currently connected to the UM server.
	    Voice calls become fax calls after a fax tone
	    is detected."
    ::= { ex2UMGeneral 10 }

ex2umgCurrentPlayOnPhoneCalls OBJECT-TYPE
    SYNTAX     Gauge32
    MAX-ACCESS read-only
    STATUS     current
    DESCRIPTION
	    "Current Play on Phone Calls is the number of
	    outbound calls that were initiated to play back
	    messages."
    ::= { ex2UMGeneral 11 }

ex2umgCurrentPromptEditingCalls OBJECT-TYPE
    SYNTAX     Gauge32
    MAX-ACCESS read-only
    STATUS     current
    DESCRIPTION
	    "Current Prompt Editing Calls is the number of
	    logged on users who are editing custom
	    prompts."
    ::= { ex2UMGeneral 12 }

ex2umgCurrentSubscriberAccesCall OBJECT-TYPE
    SYNTAX     Gauge32
    MAX-ACCESS read-only
    STATUS     current
    DESCRIPTION
	    "Current Subscriber Access Calls is the number
	    of logged on subscribers who are currently
	    connected to the UM server."
    ::= { ex2UMGeneral 13 }

ex2umgCurrUnauthentPilotNumCall OBJECT-TYPE
    SYNTAX     Gauge32
    MAX-ACCESS read-only
    STATUS     current
    DESCRIPTION
	    "Current Unauthenticated Pilot Number Calls is
	    the number of voice calls to the pilot number
	    that have not yet been authenticated."
    ::= { ex2UMGeneral 14 }

ex2umgCurrentVoiceCalls OBJECT-TYPE
    SYNTAX     Gauge32
    MAX-ACCESS read-only
    STATUS     current
    DESCRIPTION
	    "Current Voice Calls is the number of voice
	    calls that are currently connected to the UM
	    server."
    ::= { ex2UMGeneral 15 }

ex2umgDelayedCalls OBJECT-TYPE
    SYNTAX     Gauge32
    MAX-ACCESS read-only
    STATUS     current
    DESCRIPTION
	    "Delayed Calls is the number of calls that
	    experienced one or more delays longer than 2
	    seconds."
    ::= { ex2UMGeneral 16 }

ex2umgOCSUserEventNotifications OBJECT-TYPE
    SYNTAX     Gauge32
    MAX-ACCESS read-only
    STATUS     current
    DESCRIPTION
	    "OCS User Event Notifications is the total
	    number of OCS User Event notifications that
	    have occurred since the service was started."
    ::= { ex2UMGeneral 17 }

ex2umgTotalCalls OBJECT-TYPE
    SYNTAX     Gauge32
    MAX-ACCESS read-only
    STATUS     current
    DESCRIPTION
	    "Total Calls is the number of calls since the
	    service was started."
    ::= { ex2UMGeneral 18 }

ex2umgTotalCallsPerSecond OBJECT-TYPE
    SYNTAX     Gauge32
    MAX-ACCESS read-only
    STATUS     current
    DESCRIPTION
	    "Total Calls per Second is the number of new
	    calls that have arrived in the last second."
    ::= { ex2UMGeneral 19 }

ex2umgTotalPlayOnPhoneCalls OBJECT-TYPE
    SYNTAX     Gauge32
    MAX-ACCESS read-only
    STATUS     current
    DESCRIPTION
	    "Total Play on Phone Calls is the total number
	    of Play on Phone calls that have been initiated
	    since the service was started."
    ::= { ex2UMGeneral 20 }

ex2umgUserResponseLatency OBJECT-TYPE
    SYNTAX     Gauge32
    MAX-ACCESS read-only
    STATUS     current
    DESCRIPTION
	    "User Response Latency is the average response
	    time, in milliseconds, for the system to
	    respond to a user request. This average is
	    calculated over the last 25 calls. This counter
	    is limited to calls that require significant
	    processing."
    ::= { ex2UMGeneral 21 }

ex2UMPerformance OBJECT IDENTIFIER
    ::= { exchangeV2 69 }

ex2umpOperationsOverFiveSeconds OBJECT-TYPE
    SYNTAX     Gauge32
    MAX-ACCESS read-only
    STATUS     current
    DESCRIPTION
	    "Operations over Five Seconds is the number of
	    all UM operations that took between 5 and 6
	    seconds to complete. This is the time during
	    which a caller was waiting for UM to respond."
    ::= { ex2UMPerformance 1 }

ex2umpOperationsOverFourSeconds OBJECT-TYPE
    SYNTAX     Gauge32
    MAX-ACCESS read-only
    STATUS     current
    DESCRIPTION
	    "Operations over Four Seconds is the number of
	    all UM operations that took between 4 and 5
	    seconds to complete. This is the time during
	    which a caller was waiting for UM to respond."
    ::= { ex2UMPerformance 2 }

ex2umpOperationsOverSixSeconds OBJECT-TYPE
    SYNTAX     Gauge32
    MAX-ACCESS read-only
    STATUS     current
    DESCRIPTION
	    "Operations over Six Seconds is the number of
	    all UM operations that took more than 6 seconds
	    to complete. This is the time during which a
	    caller was waiting for UM to respond."
    ::= { ex2UMPerformance 3 }

ex2umpOperationsOverThreeSeconds OBJECT-TYPE
    SYNTAX     Gauge32
    MAX-ACCESS read-only
    STATUS     current
    DESCRIPTION
	    "Operations over Three Seconds is the number of
	    all UM operations that took between 3 and 4
	    seconds to complete. This is the time during
	    which a caller was waiting for UM to respond."
    ::= { ex2UMPerformance 4 }

ex2umpOperationsOverTwoSeconds OBJECT-TYPE
    SYNTAX     Gauge32
    MAX-ACCESS read-only
    STATUS     current
    DESCRIPTION
	    "Operations over Two Seconds is the number of
	    all UM operations that took between 2 and 3
	    seconds to complete. This is the time during
	    which a caller was waiting for UM to respond."
    ::= { ex2UMPerformance 5 }

ex2umpOperationsUnderTwoSeconds OBJECT-TYPE
    SYNTAX     Gauge32
    MAX-ACCESS read-only
    STATUS     current
    DESCRIPTION
	    "Operations under Two Seconds is the number of
	    all UM operations that took less than 2 seconds
	    to complete. This is the time during which a
	    caller was waiting for UM to respond."
    ::= { ex2UMPerformance 6 }

ex2UMSubscriberAccess OBJECT IDENTIFIER
    ::= { exchangeV2 70 }

ex2umsaAvgRecentSentVoiceMsgSize OBJECT-TYPE
    SYNTAX     Gauge32
    MAX-ACCESS read-only
    STATUS     current
    DESCRIPTION
	    "Average Recent Sent Voice Message Size is the
	    average size, in seconds, of the last 50 voice
	    messages that were sent."
    ::= { ex2UMSubscriberAccess 1 }

ex2umsaAvgRecentSubscribeCallDur OBJECT-TYPE
    SYNTAX     Gauge32
    MAX-ACCESS read-only
    STATUS     current
    DESCRIPTION
	    "Average Subscriber Recent Call Duration is the
	    average length of time, in seconds, that
	    subscribers spent logged on to the system for
	    the last 50 subscriber calls."
    ::= { ex2UMSubscriberAccess 2 }

ex2umsaAvgSentVoiceMessageSize OBJECT-TYPE
    SYNTAX     Gauge32
    MAX-ACCESS read-only
    STATUS     current
    DESCRIPTION
	    "Average Sent Voice Message Size is the average
	    size, in seconds, of voice messages that are
	    sent. This size does not include any attachment
	    data."
    ::= { ex2UMSubscriberAccess 3 }

ex2umsaAvgSubscriberCallDuration OBJECT-TYPE
    SYNTAX     Gauge32
    MAX-ACCESS read-only
    STATUS     current
    DESCRIPTION
	    "Average Subscriber Call Duration is the
	    average duration, in seconds, that subscribers
	    spent logged on to the system. This timer
	    starts when logon completes."
    ::= { ex2UMSubscriberAccess 4 }

ex2umsaCalendarAccessed OBJECT-TYPE
    SYNTAX     Gauge32
    MAX-ACCESS read-only
    STATUS     current
    DESCRIPTION
	    "Calendar Accessed is the number of times
	    subscribers accessed their calendars using the
	    telephone user interface."
    ::= { ex2UMSubscriberAccess 5 }

ex2umsaCalendarItemDetailRequest OBJECT-TYPE
    SYNTAX     Gauge32
    MAX-ACCESS read-only
    STATUS     current
    DESCRIPTION
	    "Calendar Items Details Requested is the number
	    of times a subscriber requested additional
	    details for a calendar item."
    ::= { ex2UMSubscriberAccess 6 }

ex2umsaCalendarItemsHeard OBJECT-TYPE
    SYNTAX     Gauge32
    MAX-ACCESS read-only
    STATUS     current
    DESCRIPTION
	    "Calendar Items Heard is the number of Calendar
	    items that have been heard by authenticated
	    subscribers."
    ::= { ex2UMSubscriberAccess 7 }

ex2umsaCalendarLateAttendance OBJECT-TYPE
    SYNTAX     Gauge32
    MAX-ACCESS read-only
    STATUS     current
    DESCRIPTION
	    "Calendar Late Attendance is the number of
	    messages that have been sent to inform the
	    organizer of a meeting that the subscriber will
	    be late."
    ::= { ex2UMSubscriberAccess 8 }

ex2umsaCalledMeetingOrganizer OBJECT-TYPE
    SYNTAX     Gauge32
    MAX-ACCESS read-only
    STATUS     current
    DESCRIPTION
	    "Called Meeting Organizer is the number of
	    times subscribers called the meeting
	    organizer."
    ::= { ex2UMSubscriberAccess 9 }

ex2umsaCalDiscCalDurUMAudioHrgls OBJECT-TYPE
    SYNTAX     Gauge32
    MAX-ACCESS read-only
    STATUS     current
    DESCRIPTION
	    "Calls Disconnected by Callers During UM Audio
	    Hourglass is the number of calls in which the
	    caller disconnected while UM was playing the
	    audio hourglass tones."
    ::= { ex2UMSubscriberAccess 10 }

ex2umsaCallDisUMOnIrrecvExtError OBJECT-TYPE
    SYNTAX     Gauge32
    MAX-ACCESS read-only
    STATUS     current
    DESCRIPTION
	    "Calls Disconnected by UM on Irrecoverable
	    External Error is the total number of calls
	    that have been disconnected after an
	    irrecoverable external error occurred."
    ::= { ex2UMSubscriberAccess 11 }

ex2umsaContactItemsHeard OBJECT-TYPE
    SYNTAX     Gauge32
    MAX-ACCESS read-only
    STATUS     current
    DESCRIPTION
	    "Contact Items Heard is the number of times
	    authenticated subscribers listened to directory
	    details."
    ::= { ex2UMSubscriberAccess 12 }

ex2umsaContactsAccessed OBJECT-TYPE
    SYNTAX     Gauge32
    MAX-ACCESS read-only
    STATUS     current
    DESCRIPTION
	    "Contacts Accessed is the number of times
	    subscribers accessed the Main Menu Contacts
	    option using the telephone user interface."
    ::= { ex2UMSubscriberAccess 13 }

ex2umsaDirectoryAccessed OBJECT-TYPE
    SYNTAX     Gauge32
    MAX-ACCESS read-only
    STATUS     current
    DESCRIPTION
	    "Directory Accessed is the number of times
	    subscribers accessed the Main Menu Directory
	    option by using the telephone user interface."
    ::= { ex2UMSubscriberAccess 14 }

ex2umsaDirAccsdSuccessDialName OBJECT-TYPE
    SYNTAX     Gauge32
    MAX-ACCESS read-only
    STATUS     current
    DESCRIPTION
	    "Directory Accessed Successfully by Dial by
	    Name is the number of Dial by Name directory
	    access operations that completed successfully
	    on behalf of subscribers."
    ::= { ex2UMSubscriberAccess 15 }

ex2umsaDirAccsdSuccessSpokenName OBJECT-TYPE
    SYNTAX     Gauge32
    MAX-ACCESS read-only
    STATUS     current
    DESCRIPTION
	    "Directory Accessed Successfully by Spoken Name
	    is the number of speech recognition directory
	    access operations that completed successfully
	    on behalf of subscribers."
    ::= { ex2UMSubscriberAccess 16 }

ex2umsaDirAccsdByDialByName OBJECT-TYPE
    SYNTAX     Gauge32
    MAX-ACCESS read-only
    STATUS     current
    DESCRIPTION
	    "Directory Accessed by Dial by Name is the
	    number of directory access operations where the
	    subscriber used the Dial by Name feature."
    ::= { ex2UMSubscriberAccess 17 }

ex2umsaDirAccsdByExtension OBJECT-TYPE
    SYNTAX     Gauge32
    MAX-ACCESS read-only
    STATUS     current
    DESCRIPTION
	    "Directory Accessed by Extension is the number
	    of directory access operations in which the
	    user supplied the extension number."
    ::= { ex2UMSubscriberAccess 18 }

ex2umsaDirAccsdBySpokenName OBJECT-TYPE
    SYNTAX     Gauge32
    MAX-ACCESS read-only
    STATUS     current
    DESCRIPTION
	    "Directory Accessed by Spoken Name is the
	    number of directory access operations in which
	    the subscriber spoke a recipient name."
    ::= { ex2UMSubscriberAccess 19 }

ex2umsaEmailMessageQueueAccessed OBJECT-TYPE
    SYNTAX     Gauge32
    MAX-ACCESS read-only
    STATUS     current
    DESCRIPTION
	    "Email Message Queue Accessed is the number of
	    times subscribers accessed their e-mail message
	    queue by using the telephone user interface."
    ::= { ex2UMSubscriberAccess 20 }

ex2umsaEmailMessagesDeleted OBJECT-TYPE
    SYNTAX     Gauge32
    MAX-ACCESS read-only
    STATUS     current
    DESCRIPTION
	    "Email Messages Deleted is the number of e-mail
	    messages that were deleted by authenticated
	    subscribers."
    ::= { ex2UMSubscriberAccess 21 }

ex2umsaEmailMessagesHeard OBJECT-TYPE
    SYNTAX     Gauge32
    MAX-ACCESS read-only
    STATUS     current
    DESCRIPTION
	    "Email Messages Heard is the number of e-mail
	    messages that have been heard by authenticated
	    subscribers."
    ::= { ex2UMSubscriberAccess 22 }

ex2umsaForwardMessagesSent OBJECT-TYPE
    SYNTAX     Gauge32
    MAX-ACCESS read-only
    STATUS     current
    DESCRIPTION
	    "Forward Messages Sent is the number of
	    messages that have been forwarded by
	    authenticated subscribers."
    ::= { ex2UMSubscriberAccess 23 }

ex2umsaLaunchedCalls OBJECT-TYPE
    SYNTAX     Gauge32
    MAX-ACCESS read-only
    STATUS     current
    DESCRIPTION
	    "Launched Calls is the number of subscriber
	    calls that resulted in an outbound call being
	    placed."
    ::= { ex2UMSubscriberAccess 24 }

ex2umsaMeetingsAccepted OBJECT-TYPE
    SYNTAX     Gauge32
    MAX-ACCESS read-only
    STATUS     current
    DESCRIPTION
	    "Meetings Accepted is the number of Meeting
	    Accepted messages send by subscribers."
    ::= { ex2UMSubscriberAccess 25 }

ex2umsaMeetingsDeclined OBJECT-TYPE
    SYNTAX     Gauge32
    MAX-ACCESS read-only
    STATUS     current
    DESCRIPTION
	    "Meetings Declined is the number of Meeting
	    Declined messages sent by subscribers."
    ::= { ex2UMSubscriberAccess 26 }

ex2umsaRepliedToOrganizer OBJECT-TYPE
    SYNTAX     Gauge32
    MAX-ACCESS read-only
    STATUS     current
    DESCRIPTION
	    "Replied to Organizer is the number of times
	    subscribers sent reply messages to meeting
	    organizers."
    ::= { ex2UMSubscriberAccess 27 }

ex2umsaReplyMessagesSent OBJECT-TYPE
    SYNTAX     Gauge32
    MAX-ACCESS read-only
    STATUS     current
    DESCRIPTION
	    "Reply Messages Sent is the number of replies
	    sent by authenticated subscribers."
    ::= { ex2UMSubscriberAccess 28 }

ex2umsaSubscriberAuthentFailure OBJECT-TYPE
    SYNTAX     Gauge32
    MAX-ACCESS read-only
    STATUS     current
    DESCRIPTION
	    "Subscriber Authentication Failures is the
	    number of authentication failures that have
	    occurred since the service was started. This
	    number is incremented once for every failed
	    authentication. It is possible that a single
	    phone call could generate several
	    authentication failures."
    ::= { ex2UMSubscriberAccess 29 }

ex2umsaSubscriberLogonFailures OBJECT-TYPE
    SYNTAX     Gauge32
    MAX-ACCESS read-only
    STATUS     current
    DESCRIPTION
	    "Subscriber Logon Failures is the number of
	    logon failures since the service was started.
	    This number is incremented at most once per
	    phone call."
    ::= { ex2UMSubscriberAccess 30 }

ex2umsaSubscriberLogons OBJECT-TYPE
    SYNTAX     Gauge32
    MAX-ACCESS read-only
    STATUS     current
    DESCRIPTION
	    "Subscriber Logons is the number of successful
	    authentications by UM subscribers since the
	    service was started."
    ::= { ex2UMSubscriberAccess 31 }

ex2umsaVoiceMessageQueueAccessed OBJECT-TYPE
    SYNTAX     Gauge32
    MAX-ACCESS read-only
    STATUS     current
    DESCRIPTION
	    "Voice Message Queue Accessed is the number of
	    times subscribers accessed their voice message
	    queues by using the telephone user interface."
    ::= { ex2UMSubscriberAccess 32 }

ex2umsaVoiceMessagesDeleted OBJECT-TYPE
    SYNTAX     Gauge32
    MAX-ACCESS read-only
    STATUS     current
    DESCRIPTION
	    "Voice Messages Deleted is the number of voice
	    messages that were deleted by authenticated
	    subscribers."
    ::= { ex2UMSubscriberAccess 33 }

ex2umsaVoiceMessagesHeard OBJECT-TYPE
    SYNTAX     Gauge32
    MAX-ACCESS read-only
    STATUS     current
    DESCRIPTION
	    "Voice Messages Heard is the number of voice
	    messages played to subscribers. This count is
	    incremented as soon as playback starts. The
	    subscriber does not need to listen to the
	    entire message."
    ::= { ex2UMSubscriberAccess 34 }

ex2umsaVoiceMessagesSent OBJECT-TYPE
    SYNTAX     Gauge32
    MAX-ACCESS read-only
    STATUS     current
    DESCRIPTION
	    "Voice Messages Sent is the number of voice
	    messages that have been sent by authenticated
	    UM subscribers."
    ::= { ex2UMSubscriberAccess 35 }

ex2WS OBJECT IDENTIFIER
    ::= { exchangeV2 71 }

ex2WSActiveSubscriptions OBJECT-TYPE
    SYNTAX     Gauge32
    MAX-ACCESS read-only
    STATUS     current
    DESCRIPTION
	    "Active Subscriptions is the number of active
	    subscriptions."
    ::= { ex2WS 1 }

ex2WSAddDelegateRequests OBJECT-TYPE
    SYNTAX     Gauge32
    MAX-ACCESS read-only
    STATUS     current
    DESCRIPTION
	    "AddDelegate Requests is the total number of
	    requests for the AddDelegate Web method."
    ::= { ex2WS 2 }

ex2WSAddDelegateRequestsPerSec OBJECT-TYPE
    SYNTAX     Gauge32
    MAX-ACCESS read-only
    STATUS     current
    DESCRIPTION
	    "AddDelegate Requests per second is the number
	    of AddDelegate requests processed each second."
    ::= { ex2WS 3 }

ex2WSConvertIdRequests OBJECT-TYPE
    SYNTAX     Gauge32
    MAX-ACCESS read-only
    STATUS     current
    DESCRIPTION
	    "ConvertId Requests is the total number of
	    requests for the ConvertId web method."
    ::= { ex2WS 4 }

ex2WSConvertIdRequestsPerSec OBJECT-TYPE
    SYNTAX     Gauge32
    MAX-ACCESS read-only
    STATUS     current
    DESCRIPTION
	    "ConvertId Requests per second is the number of
	    ConvertId requests processed each second."
    ::= { ex2WS 5 }

ex2WSCopyFolderRequests OBJECT-TYPE
    SYNTAX     Gauge32
    MAX-ACCESS read-only
    STATUS     current
    DESCRIPTION
	    "CopyFolder Requests is the total number of
	    requests for the CopyFolder Web method."
    ::= { ex2WS 6 }

ex2WSCopyFolderRequestsPerSec OBJECT-TYPE
    SYNTAX     Gauge32
    MAX-ACCESS read-only
    STATUS     current
    DESCRIPTION
	    "CopyFolder Requests  per second is the number
	    of CopyFolder requests processed each second."
    ::= { ex2WS 7 }

ex2WSCopyItemRequests OBJECT-TYPE
    SYNTAX     Gauge32
    MAX-ACCESS read-only
    STATUS     current
    DESCRIPTION
	    "CopyItem Requests is the total number of
	    requests for the CopyItem Web method."
    ::= { ex2WS 8 }

ex2WSCopyItemRequestsPerSec OBJECT-TYPE
    SYNTAX     Gauge32
    MAX-ACCESS read-only
    STATUS     current
    DESCRIPTION
	    "CopyItem Requests per second is the number of
	    CopyItem requests processed each second."
    ::= { ex2WS 9 }

ex2WSCreateAttachmentRequests OBJECT-TYPE
    SYNTAX     Gauge32
    MAX-ACCESS read-only
    STATUS     current
    DESCRIPTION
	    "CreateAttachment Requests is the total number
	    of requests for the CreateAttachment Web
	    method."
    ::= { ex2WS 10 }

ex2WSCreateAttachRequestsPerSec OBJECT-TYPE
    SYNTAX     Gauge32
    MAX-ACCESS read-only
    STATUS     current
    DESCRIPTION
	    "CreateAttachment Requests per second is the
	    number of CreateAttachment requests processed
	    each second."
    ::= { ex2WS 11 }

ex2WSCreateFolderRequests OBJECT-TYPE
    SYNTAX     Gauge32
    MAX-ACCESS read-only
    STATUS     current
    DESCRIPTION
	    "CreateFolder Requests is the total number of
	    requests for the CreateFolder Web method."
    ::= { ex2WS 12 }

ex2WSCreateFolderRequestsPerSec OBJECT-TYPE
    SYNTAX     Gauge32
    MAX-ACCESS read-only
    STATUS     current
    DESCRIPTION
	    "CreateFolder Requests per second is the number
	    of CreateFolder requests processed each
	    second."
    ::= { ex2WS 13 }

ex2WSCreateItemRequests OBJECT-TYPE
    SYNTAX     Gauge32
    MAX-ACCESS read-only
    STATUS     current
    DESCRIPTION
	    "CreateItem Requests is the total number of
	    requests for the CreateItem Web method."
    ::= { ex2WS 14 }

ex2WSCreateItemRequestsPerSec OBJECT-TYPE
    SYNTAX     Gauge32
    MAX-ACCESS read-only
    STATUS     current
    DESCRIPTION
	    "CreateItem Requests per second is the number
	    of CreateItem requests processed each second."
    ::= { ex2WS 15 }

ex2WSCreateManagedFolderRequests OBJECT-TYPE
    SYNTAX     Gauge32
    MAX-ACCESS read-only
    STATUS     current
    DESCRIPTION
	    "CreateManagedFolder Requests is the total
	    number of requests for the CreateManagedFolder
	    Web method."
    ::= { ex2WS 16 }

ex2WSCreateManageFoldReqstPerSec OBJECT-TYPE
    SYNTAX     Gauge32
    MAX-ACCESS read-only
    STATUS     current
    DESCRIPTION
	    "CreateManagedFolder Requests per second is the
	    number of CreateManagedFolder requests
	    processed each second."
    ::= { ex2WS 17 }

ex2WSDeleteAttachmentRequests OBJECT-TYPE
    SYNTAX     Gauge32
    MAX-ACCESS read-only
    STATUS     current
    DESCRIPTION
	    "DeleteAttachment Requests is the total number
	    of requests for the DeleteAttachment Web
	    method."
    ::= { ex2WS 18 }

ex2WSDeleteAttachmentReqstPerSec OBJECT-TYPE
    SYNTAX     Gauge32
    MAX-ACCESS read-only
    STATUS     current
    DESCRIPTION
	    "DeleteAttachment Requests per second is the
	    number of DeleteAttachment requests processed
	    each second."
    ::= { ex2WS 19 }

ex2WSDeleteFolderRequests OBJECT-TYPE
    SYNTAX     Gauge32
    MAX-ACCESS read-only
    STATUS     current
    DESCRIPTION
	    "DeleteFolder Requests is the total number of
	    requests for the DeleteFolder Web method."
    ::= { ex2WS 20 }

ex2WSDeleteFolderRequestsPerSec OBJECT-TYPE
    SYNTAX     Gauge32
    MAX-ACCESS read-only
    STATUS     current
    DESCRIPTION
	    "DeleteFolder Requests per second is the number
	    of DeleteFolder requests processed each
	    second."
    ::= { ex2WS 21 }

ex2WSDeleteItemRequests OBJECT-TYPE
    SYNTAX     Gauge32
    MAX-ACCESS read-only
    STATUS     current
    DESCRIPTION
	    "DeleteItem Requests is the total number of
	    requests for the DeleteItem Web method."
    ::= { ex2WS 22 }

ex2WSDeleteItemRequestsPerSec OBJECT-TYPE
    SYNTAX     Gauge32
    MAX-ACCESS read-only
    STATUS     current
    DESCRIPTION
	    "DeleteItem Requests per second is the number
	    of DeleteItem requests processed each second."
    ::= { ex2WS 23 }

ex2WSExpandDLRequests OBJECT-TYPE
    SYNTAX     Gauge32
    MAX-ACCESS read-only
    STATUS     current
    DESCRIPTION
	    "ExpandDL Requests is the total number of
	    requests for the ExpandDL Web method."
    ::= { ex2WS 24 }

ex2WSExpandDLRequestsPerSec OBJECT-TYPE
    SYNTAX     Gauge32
    MAX-ACCESS read-only
    STATUS     current
    DESCRIPTION
	    "ExpandDL Requests per second is the number of
	    ExpandDL requests processed each second."
    ::= { ex2WS 25 }

ex2WSFindFolderRequests OBJECT-TYPE
    SYNTAX     Gauge32
    MAX-ACCESS read-only
    STATUS     current
    DESCRIPTION
	    "FindFolder Requests is the total number of
	    requests for the FindFolder Web method."
    ::= { ex2WS 26 }

ex2WSFindFolderRequestsPerSec OBJECT-TYPE
    SYNTAX     Gauge32
    MAX-ACCESS read-only
    STATUS     current
    DESCRIPTION
	    "FindFolder Requests per second is the number
	    of FindFolder requests processed each second."
    ::= { ex2WS 27 }

ex2WSFindItemRequests OBJECT-TYPE
    SYNTAX     Gauge32
    MAX-ACCESS read-only
    STATUS     current
    DESCRIPTION
	    "FindItem Requests is the total  number of
	    requests for the FindItem Web method."
    ::= { ex2WS 28 }

ex2WSFindItemRequestsPerSec OBJECT-TYPE
    SYNTAX     Gauge32
    MAX-ACCESS read-only
    STATUS     current
    DESCRIPTION
	    "FindItem Requests per second is the number of
	    FindItem requests processed each second."
    ::= { ex2WS 29 }

ex2WSFoldersCopied OBJECT-TYPE
    SYNTAX     Gauge32
    MAX-ACCESS read-only
    STATUS     current
    DESCRIPTION
	    "Folders Copied is the total number of folders
	    copied."
    ::= { ex2WS 30 }

ex2WSFoldersCopiedPerSec OBJECT-TYPE
    SYNTAX     Gauge32
    MAX-ACCESS read-only
    STATUS     current
    DESCRIPTION
	    "Folders Copied per second is the number of
	    folders copied each second."
    ::= { ex2WS 31 }

ex2WSFoldersCreated OBJECT-TYPE
    SYNTAX     Gauge32
    MAX-ACCESS read-only
    STATUS     current
    DESCRIPTION
	    "Folders Created is the total number of folders
	    created."
    ::= { ex2WS 32 }

ex2WSFoldersCreatedPerSec OBJECT-TYPE
    SYNTAX     Gauge32
    MAX-ACCESS read-only
    STATUS     current
    DESCRIPTION
	    "Folders Created per second is the number of
	    folders created each second."
    ::= { ex2WS 33 }

ex2WSFoldersDeleted OBJECT-TYPE
    SYNTAX     Gauge32
    MAX-ACCESS read-only
    STATUS     current
    DESCRIPTION
	    "Folders Deleted is the total number of folders
	    deleted."
    ::= { ex2WS 34 }

ex2WSFoldersDeletedPerSec OBJECT-TYPE
    SYNTAX     Gauge32
    MAX-ACCESS read-only
    STATUS     current
    DESCRIPTION
	    "Folders Deleted per second is the number of
	    folders deleted each second."
    ::= { ex2WS 35 }

ex2WSFoldersMoved OBJECT-TYPE
    SYNTAX     Gauge32
    MAX-ACCESS read-only
    STATUS     current
    DESCRIPTION
	    "Folders Moved is the total number of folders
	    moved."
    ::= { ex2WS 36 }

ex2WSFoldersMovedPerSec OBJECT-TYPE
    SYNTAX     Gauge32
    MAX-ACCESS read-only
    STATUS     current
    DESCRIPTION
	    "Folders Moved per second is the number of
	    folders moved each second."
    ::= { ex2WS 37 }

ex2WSFoldersRead OBJECT-TYPE
    SYNTAX     Gauge32
    MAX-ACCESS read-only
    STATUS     current
    DESCRIPTION
	    "Folders Read is the total number of folders
	    read."
    ::= { ex2WS 38 }

ex2WSFoldersSentPerSec OBJECT-TYPE
    SYNTAX     Gauge32
    MAX-ACCESS read-only
    STATUS     current
    DESCRIPTION
	    "Folders Sent per second is the number of
	    folders read each second."
    ::= { ex2WS 39 }

ex2WSFoldersSyncedPerSec OBJECT-TYPE
    SYNTAX     Gauge32
    MAX-ACCESS read-only
    STATUS     current
    DESCRIPTION
	    "Folders Synced per second is the number of
	    folders synchronized each second."
    ::= { ex2WS 40 }

ex2WSFoldersSynchronized OBJECT-TYPE
    SYNTAX     Gauge32
    MAX-ACCESS read-only
    STATUS     current
    DESCRIPTION
	    "Folders Synchronized is the total number of
	    folders synchronized."
    ::= { ex2WS 41 }

ex2WSFoldersUpdated OBJECT-TYPE
    SYNTAX     Gauge32
    MAX-ACCESS read-only
    STATUS     current
    DESCRIPTION
	    "Folders Updated is the total number of folders
	    updated."
    ::= { ex2WS 42 }

ex2WSFoldersUpdatedPerSec OBJECT-TYPE
    SYNTAX     Gauge32
    MAX-ACCESS read-only
    STATUS     current
    DESCRIPTION
	    "Folders Updated per second is the number of
	    folders updated each second."
    ::= { ex2WS 43 }

ex2WSGetAttachmentRequests OBJECT-TYPE
    SYNTAX     Gauge32
    MAX-ACCESS read-only
    STATUS     current
    DESCRIPTION
	    "GetAttachment Requests is the total number of
	    requests for the GetAttachment Web method."
    ::= { ex2WS 44 }

ex2WSGetAttachmentRequestsPerSec OBJECT-TYPE
    SYNTAX     Gauge32
    MAX-ACCESS read-only
    STATUS     current
    DESCRIPTION
	    "GetAttachment Requests per second is the
	    number of GetAttachment requests processed each
	    second."
    ::= { ex2WS 45 }

ex2WSGetDelegateRequests OBJECT-TYPE
    SYNTAX     Gauge32
    MAX-ACCESS read-only
    STATUS     current
    DESCRIPTION
	    "GetDelegate Requests is the total number of
	    requests for the GetDelegate Web method."
    ::= { ex2WS 46 }

ex2WSGetDelegateRequestsPerSec OBJECT-TYPE
    SYNTAX     Gauge32
    MAX-ACCESS read-only
    STATUS     current
    DESCRIPTION
	    "GetDelegate Requests per second is the number
	    of GetDelegate requests processed each second."
    ::= { ex2WS 47 }

ex2WSGetEventsRequests OBJECT-TYPE
    SYNTAX     Gauge32
    MAX-ACCESS read-only
    STATUS     current
    DESCRIPTION
	    "GetEvents Requests is the total number of
	    requests for the GetEvents Web method."
    ::= { ex2WS 48 }

ex2WSGetEventsRequestsPerSec OBJECT-TYPE
    SYNTAX     Gauge32
    MAX-ACCESS read-only
    STATUS     current
    DESCRIPTION
	    "GetEvents Requests per second is the number of
	    GetEvents requests processed each second."
    ::= { ex2WS 49 }

ex2WSGetFolderRequests OBJECT-TYPE
    SYNTAX     Gauge32
    MAX-ACCESS read-only
    STATUS     current
    DESCRIPTION
	    "GetFolder Requests is the total number of
	    requests for the GetFolder Web method."
    ::= { ex2WS 50 }

ex2WSGetFolderRequestsPerSec OBJECT-TYPE
    SYNTAX     Gauge32
    MAX-ACCESS read-only
    STATUS     current
    DESCRIPTION
	    "GetFolder Requests per second is the number of
	    GetFolder requests processed each second."
    ::= { ex2WS 51 }

ex2WSGetItemRequests OBJECT-TYPE
    SYNTAX     Gauge32
    MAX-ACCESS read-only
    STATUS     current
    DESCRIPTION
	    "GetItem Requests is the total  number of
	    requests for the GetItem web method."
    ::= { ex2WS 52 }

ex2WSGetItemRequestsPerSec OBJECT-TYPE
    SYNTAX     Gauge32
    MAX-ACCESS read-only
    STATUS     current
    DESCRIPTION
	    "GetItem Requests per second is the number of
	    GetItem requests processed each second."
    ::= { ex2WS 53 }

ex2WSIdsConvertedPerSec OBJECT-TYPE
    SYNTAX     Gauge32
    MAX-ACCESS read-only
    STATUS     current
    DESCRIPTION
	    "Ids converted per second is the number of ids
	    converted each second."
    ::= { ex2WS 54 }

ex2WSItemsCopied OBJECT-TYPE
    SYNTAX     Gauge32
    MAX-ACCESS read-only
    STATUS     current
    DESCRIPTION
	    "Items Copied is the total number of items
	    copied."
    ::= { ex2WS 55 }

ex2WSItemsCopiedPerSec OBJECT-TYPE
    SYNTAX     Gauge32
    MAX-ACCESS read-only
    STATUS     current
    DESCRIPTION
	    "Items Copied per second is the number of items
	    copied each second."
    ::= { ex2WS 56 }

ex2WSItemsCreated OBJECT-TYPE
    SYNTAX     Gauge32
    MAX-ACCESS read-only
    STATUS     current
    DESCRIPTION
	    "Items Created is the total number of items
	    created."
    ::= { ex2WS 57 }

ex2WSItemsCreatedPerSec OBJECT-TYPE
    SYNTAX     Gauge32
    MAX-ACCESS read-only
    STATUS     current
    DESCRIPTION
	    "Items Created per second is the number of
	    items created each second."
    ::= { ex2WS 58 }

ex2WSItemsDeleted OBJECT-TYPE
    SYNTAX     Gauge32
    MAX-ACCESS read-only
    STATUS     current
    DESCRIPTION
	    "Items Deleted is the total number of items
	    deleted."
    ::= { ex2WS 59 }

ex2WSItemsDeletedPerSec OBJECT-TYPE
    SYNTAX     Gauge32
    MAX-ACCESS read-only
    STATUS     current
    DESCRIPTION
	    "Items Deleted per second is the number of
	    items deleted each second."
    ::= { ex2WS 60 }

ex2WSItemsMoved OBJECT-TYPE
    SYNTAX     Gauge32
    MAX-ACCESS read-only
    STATUS     current
    DESCRIPTION
	    "Items Moved is the total number of items
	    moved."
    ::= { ex2WS 61 }

ex2WSItemsMovedPerSec OBJECT-TYPE
    SYNTAX     Gauge32
    MAX-ACCESS read-only
    STATUS     current
    DESCRIPTION
	    "Items Moved per second is the number of items
	    moved each second."
    ::= { ex2WS 62 }

ex2WSItemsRead OBJECT-TYPE
    SYNTAX     Gauge32
    MAX-ACCESS read-only
    STATUS     current
    DESCRIPTION
	    "Items Read is the total number of items read."
    ::= { ex2WS 63 }

ex2WSItemsReadPerSec OBJECT-TYPE
    SYNTAX     Gauge32
    MAX-ACCESS read-only
    STATUS     current
    DESCRIPTION
	    "Items Read per second is the number of items
	    read each second."
    ::= { ex2WS 64 }

ex2WSItemsSent OBJECT-TYPE
    SYNTAX     Gauge32
    MAX-ACCESS read-only
    STATUS     current
    DESCRIPTION
	    "Items Sent is the total number of items sent."
    ::= { ex2WS 65 }

ex2WSItemsSentPerSec OBJECT-TYPE
    SYNTAX     Gauge32
    MAX-ACCESS read-only
    STATUS     current
    DESCRIPTION
	    "Items Sent per second is the number of items
	    sent each second."
    ::= { ex2WS 66 }

ex2WSItemsSyncedPerSec OBJECT-TYPE
    SYNTAX     Gauge32
    MAX-ACCESS read-only
    STATUS     current
    DESCRIPTION
	    "Items Synced per second is the number of items
	    synchronized each second."
    ::= { ex2WS 67 }

ex2WSItemsSynchronized OBJECT-TYPE
    SYNTAX     Gauge32
    MAX-ACCESS read-only
    STATUS     current
    DESCRIPTION
	    "Items Synchronized is the total number of
	    items synchronized."
    ::= { ex2WS 68 }

ex2WSItemsUpdated OBJECT-TYPE
    SYNTAX     Gauge32
    MAX-ACCESS read-only
    STATUS     current
    DESCRIPTION
	    "Items Updated is the total number of items
	    updated."
    ::= { ex2WS 69 }

ex2WSItemsUpdatedPerSec OBJECT-TYPE
    SYNTAX     Gauge32
    MAX-ACCESS read-only
    STATUS     current
    DESCRIPTION
	    "Items Updated per second is the number of
	    items updated each second."
    ::= { ex2WS 70 }

ex2WSMoveFolderRequests OBJECT-TYPE
    SYNTAX     Gauge32
    MAX-ACCESS read-only
    STATUS     current
    DESCRIPTION
	    "MoveFolder Requests is the total number of
	    requests for the MoveFolder web method."
    ::= { ex2WS 71 }

ex2WSMoveFolderRequestsPerSec OBJECT-TYPE
    SYNTAX     Gauge32
    MAX-ACCESS read-only
    STATUS     current
    DESCRIPTION
	    "MoveFolder Requests per second is the number
	    of MoveFolder requests processed each second."
    ::= { ex2WS 72 }

ex2WSMoveItemRequests OBJECT-TYPE
    SYNTAX     Gauge32
    MAX-ACCESS read-only
    STATUS     current
    DESCRIPTION
	    "MoveItem Requests	is the total number of
	    requests for the MoveItem Web method."
    ::= { ex2WS 73 }

ex2WSMoveItemRequestsPerSec OBJECT-TYPE
    SYNTAX     Gauge32
    MAX-ACCESS read-only
    STATUS     current
    DESCRIPTION
	    "MoveItem Requests per second is the number of
	    MoveItem requests processed each second."
    ::= { ex2WS 74 }

ex2WSNumberOfCurrentProxyCalls OBJECT-TYPE
    SYNTAX     Gauge32
    MAX-ACCESS read-only
    STATUS     current
    DESCRIPTION
	    "The number of outstanding requests that are
	    being proxied to other CAS servers from this
	    server."
    ::= { ex2WS 75 }

ex2WSNumberOfProxyReqstPerSecond OBJECT-TYPE
    SYNTAX     Gauge32
    MAX-ACCESS read-only
    STATUS     current
    DESCRIPTION
	    "Average number of proxy requests per second"
    ::= { ex2WS 76 }

ex2WSNumbrProxyFailoverPerSecond OBJECT-TYPE
    SYNTAX     Gauge32
    MAX-ACCESS read-only
    STATUS     current
    DESCRIPTION
	    "Average number of proxy failovers per second"
    ::= { ex2WS 77 }

ex2WSProcessID OBJECT-TYPE
    SYNTAX     Gauge32
    MAX-ACCESS read-only
    STATUS     current
    DESCRIPTION
	    "Process ID that hosts WebServices."
    ::= { ex2WS 78 }

ex2WSProxyAverageResponseTime OBJECT-TYPE
    SYNTAX     Gauge32
    MAX-ACCESS read-only
    STATUS     current
    DESCRIPTION
	    "Average elapsed time (in milliseconds) between
	    the beginning and end of a proxied request."
    ::= { ex2WS 79 }

ex2WSProxyAverageResponseTimNum1 OBJECT-TYPE
    SYNTAX     Gauge32
    MAX-ACCESS read-only
    STATUS     current
    DESCRIPTION
	    "No description available"
    ::= { ex2WS 80 }

ex2WSPushNotificationsFailed OBJECT-TYPE
    SYNTAX     Gauge32
    MAX-ACCESS read-only
    STATUS     current
    DESCRIPTION
	    "Push Notifications Failed is the total number
	    of failed push notifications."
    ::= { ex2WS 81 }

ex2WSPushNotificationsSucceeded OBJECT-TYPE
    SYNTAX     Gauge32
    MAX-ACCESS read-only
    STATUS     current
    DESCRIPTION
	    "Push Notifications Succeeded is the total
	    number of successful push notifications."
    ::= { ex2WS 82 }

ex2WSRemoveDelegateRequests OBJECT-TYPE
    SYNTAX     Gauge32
    MAX-ACCESS read-only
    STATUS     current
    DESCRIPTION
	    "RemoveDelegate Requests is the total number of
	    requests for the RemoveDelegate Web method."
    ::= { ex2WS 83 }

ex2WSRemoveDelegateRequestPerSec OBJECT-TYPE
    SYNTAX     Gauge32
    MAX-ACCESS read-only
    STATUS     current
    DESCRIPTION
	    "RemoveDelegate Requests per second is the
	    number of RemoveDelegate requests processed
	    each second."
    ::= { ex2WS 84 }

ex2WSRequestsPerSec OBJECT-TYPE
    SYNTAX     Gauge32
    MAX-ACCESS read-only
    STATUS     current
    DESCRIPTION
	    "Requests per second is the number of requests
	    processed each second."
    ::= { ex2WS 85 }

ex2WSResolveNamesRequests OBJECT-TYPE
    SYNTAX     Gauge32
    MAX-ACCESS read-only
    STATUS     current
    DESCRIPTION
	    "ResolveNames Requests is the total number of
	    requests for the ResolveNames Web method."
    ::= { ex2WS 86 }

ex2WSResolveNamesRequestsPerSec OBJECT-TYPE
    SYNTAX     Gauge32
    MAX-ACCESS read-only
    STATUS     current
    DESCRIPTION
	    "ResolveNames Requests per second is the number
	    of ResolveNames requests processed each
	    second."
    ::= { ex2WS 87 }

ex2WSSendItemRequests OBJECT-TYPE
    SYNTAX     Gauge32
    MAX-ACCESS read-only
    STATUS     current
    DESCRIPTION
	    "SendItem Requests is the total number of
	    requests for the SendItem Web method."
    ::= { ex2WS 88 }

ex2WSSendItemRequestsPerSec OBJECT-TYPE
    SYNTAX     Gauge32
    MAX-ACCESS read-only
    STATUS     current
    DESCRIPTION
	    "SendItem Requests per second is the number of
	    SendItem requests processed each second."
    ::= { ex2WS 89 }

ex2WSSubscribeRequests OBJECT-TYPE
    SYNTAX     Gauge32
    MAX-ACCESS read-only
    STATUS     current
    DESCRIPTION
	    "Subscribe Requests is the total number of
	    requests for the Subscribe web method."
    ::= { ex2WS 90 }

ex2WSSubscribeRequestsPerSec OBJECT-TYPE
    SYNTAX     Gauge32
    MAX-ACCESS read-only
    STATUS     current
    DESCRIPTION
	    "Subscribe Requests per second is the number of
	    Subscribe requests processed each second."
    ::= { ex2WS 91 }

ex2WSSyncFolderHierarchyRequests OBJECT-TYPE
    SYNTAX     Gauge32
    MAX-ACCESS read-only
    STATUS     current
    DESCRIPTION
	    "SyncFolderHierarchy Requests is the total
	    number of requests for the SyncFolderHierarchy
	    Web method."
    ::= { ex2WS 92 }

ex2WSSynFoldHierarchyReqstPerSec OBJECT-TYPE
    SYNTAX     Gauge32
    MAX-ACCESS read-only
    STATUS     current
    DESCRIPTION
	    "SyncFolderHierarchy Requests per second is the
	    number of SyncFolderHierarchy requests
	    processed each second."
    ::= { ex2WS 93 }

ex2WSSyncFolderItemsRequests OBJECT-TYPE
    SYNTAX     Gauge32
    MAX-ACCESS read-only
    STATUS     current
    DESCRIPTION
	    "SyncFolderItems Requests is the total number
	    of requests for the SyncFolderItems Web
	    method."
    ::= { ex2WS 94 }

ex2WSSyncFolderItemsReqstPerSec OBJECT-TYPE
    SYNTAX     Gauge32
    MAX-ACCESS read-only
    STATUS     current
    DESCRIPTION
	    "SyncFolderItems Requests per second is the
	    number of SyncFolderItems requests processed
	    each second."
    ::= { ex2WS 95 }

ex2WSTotalNumberOfIdsConverted OBJECT-TYPE
    SYNTAX     Gauge32
    MAX-ACCESS read-only
    STATUS     current
    DESCRIPTION
	    "Ids Converted is the total number of Ids
	    converted."
    ::= { ex2WS 96 }

ex2WSTotalRequests OBJECT-TYPE
    SYNTAX     Gauge32
    MAX-ACCESS read-only
    STATUS     current
    DESCRIPTION
	    "Total Requests is the total number of requests
	    processed."
    ::= { ex2WS 97 }

ex2WSTotalNumberOfBytesProxied OBJECT-TYPE
    SYNTAX     Gauge32
    MAX-ACCESS read-only
    STATUS     current
    DESCRIPTION
	    "Total number of bytes proxied from this CAS
	    server to other CAS servers"
    ::= { ex2WS 98 }

ex2WSTotalNumberOfProxiedRequest OBJECT-TYPE
    SYNTAX     Gauge32
    MAX-ACCESS read-only
    STATUS     current
    DESCRIPTION
	    "Total number of proxied request since this
	    process started."
    ::= { ex2WS 99 }

ex2WSTotalNumberOfProxyFailover OBJECT-TYPE
    SYNTAX     Gauge32
    MAX-ACCESS read-only
    STATUS     current
    DESCRIPTION
	    "Number of times EWS has failed over to an
	    alternate CAS during proxy calls"
    ::= { ex2WS 100 }

ex2WSTotalNumberProxyResponsByte OBJECT-TYPE
    SYNTAX     Gauge32
    MAX-ACCESS read-only
    STATUS     current
    DESCRIPTION
	    "Total number of response bytes resulting from
	    proxy calls from this CAS server"
    ::= { ex2WS 101 }

ex2WSUnsubscribeRequests OBJECT-TYPE
    SYNTAX     Gauge32
    MAX-ACCESS read-only
    STATUS     current
    DESCRIPTION
	    "Unsubscribe Requests is the total number of
	    requests for the Unsubscribe web method."
    ::= { ex2WS 102 }

ex2WSUnsubscribeRequestsPerSec OBJECT-TYPE
    SYNTAX     Gauge32
    MAX-ACCESS read-only
    STATUS     current
    DESCRIPTION
	    "Unsubscribe Requests per second is the number
	    of Unsubscribe requests processed each second."
    ::= { ex2WS 103 }

ex2WSUpdateDelegateRequests OBJECT-TYPE
    SYNTAX     Gauge32
    MAX-ACCESS read-only
    STATUS     current
    DESCRIPTION
	    "UpdateDelegate Requests is the total number of
	    requests for the UpdateDelegate Web method."
    ::= { ex2WS 104 }

ex2WSUpdateDelegateRequestPerSec OBJECT-TYPE
    SYNTAX     Gauge32
    MAX-ACCESS read-only
    STATUS     current
    DESCRIPTION
	    "UpdateDelegate Requests per second is the
	    number of UpdateDelegate requests processed
	    each second."
    ::= { ex2WS 105 }

ex2WSUpdateFolderRequests OBJECT-TYPE
    SYNTAX     Gauge32
    MAX-ACCESS read-only
    STATUS     current
    DESCRIPTION
	    "UpdateFolder Requests is the total number of
	    requests for the UpdateFolder web method."
    ::= { ex2WS 106 }

ex2WSUpdateFolderRequestsPerSec OBJECT-TYPE
    SYNTAX     Gauge32
    MAX-ACCESS read-only
    STATUS     current
    DESCRIPTION
	    "UpdateFolder Requests per second is the number
	    of UpdateFolder requests processed each
	    second."
    ::= { ex2WS 107 }

ex2WSUpdateItemRequests OBJECT-TYPE
    SYNTAX     Gauge32
    MAX-ACCESS read-only
    STATUS     current
    DESCRIPTION
	    "UpdateItem Requests is the total number of
	    requests for the UpdateItem Web method."
    ::= { ex2WS 108 }

ex2WSUpdateItemRequestsPerSec OBJECT-TYPE
    SYNTAX     Gauge32
    MAX-ACCESS read-only
    STATUS     current
    DESCRIPTION
	    "UpdateItem Requests per second is the number
	    of UpdateItem requests processed each second."
    ::= { ex2WS 109 }

ex2CatalogsTable OBJECT-TYPE
    SYNTAX     SEQUENCE OF MSFTESQLExchangeCatalogsEntry
    MAX-ACCESS not-accessible
    STATUS     current
    DESCRIPTION
	    "A table containing performance information for
	    instances of 'MSFTESQL-Exchange:Catalogs'
	    objects."
    ::= { exchangeV2 72 }

ex2CatalogsEntry OBJECT-TYPE
    SYNTAX     MSFTESQLExchangeCatalogsEntry
    MAX-ACCESS not-accessible
    STATUS     current
    DESCRIPTION
	    "Performance information for one particular
	    instance of 'MSFTESQL-Exchange:Catalogs'
	    object."
    INDEX      { ex2catInstance }
    ::= { ex2CatalogsTable 1 }

MSFTESQLExchangeCatalogsEntry ::= SEQUENCE {
    ex2catInstance InstanceName,
    ex2catBatchesFPC Gauge32,
    ex2catBatchesAborted Gauge32,
    ex2catBatchesCompletedSuccess Gauge32,
    ex2catBatchesCompletedWPerErrors Gauge32,
    ex2catBatchesCompleteWPerWarning Gauge32,
    ex2catBatchesDone Gauge32,
    ex2catBatchesInProgress Gauge32,
    ex2catBatchesReceived Gauge32,
    ex2catPhaseComplete Gauge32,
    ex2catPhaseInHDFD Gauge32,
    ex2catPhaseInMTFD Gauge32,
    ex2catPhaseInSTFD Gauge32,
    ex2catPhaseInPipeline Gauge32,
    ex2catPhaseInReadyQueue Gauge32,
    ex2catPhaseOnHold Gauge32,
    ex2catPhasePendingCompletion Gauge32,
    ex2catPhaseRedundant Gauge32,
    ex2catRequestAbort Gauge32,
    ex2catRequestAsyncFlush Gauge32,
    ex2catRequestFlushPerDrain Gauge32,
    ex2catRequestForceMerge Gauge32,
    ex2catRequestPause Gauge32,
    ex2catRequestReset Gauge32,
    ex2catRequestResume Gauge32,
    ex2catState Gauge32,
    ex2catStateCallerComponent Gauge32,
    ex2catStateReasonCode Gauge32,
    ex2catStateResultCode Gauge32,
    ex2catTransDeletes Gauge32,
    ex2catTransDone Gauge32,
    ex2catTransErrored Gauge32,
    ex2catTransInProgress Gauge32,
    ex2catTransModifies Gauge32,
    ex2catTransRerouted Gauge32
}

ex2catInstance OBJECT-TYPE
    SYNTAX     InstanceName
    MAX-ACCESS read-only
    STATUS     current
    DESCRIPTION
	    "Instance name."
    ::= { ex2CatalogsEntry 1 }

ex2catBatchesFPC OBJECT-TYPE
    SYNTAX     Gauge32
    MAX-ACCESS read-only
    STATUS     current
    DESCRIPTION
	    "Number of current batches past filter phase
	    complete.  This counter is incremented after
	    all the transactions in the batch are filtered
	    by the filter daemon and given to the plugin(s)
	    for processing."
    ::= { ex2CatalogsEntry 2 }

ex2catBatchesAborted OBJECT-TYPE
    SYNTAX     Gauge32
    MAX-ACCESS read-only
    STATUS     current
    DESCRIPTION
	    "Number of batches aborted to date.  By
	    definition the state of an aborted batch, how
	    far some or all of its transactions got through
	    the indexing process is unknown.  These batches
	    are retried by SQL."
    ::= { ex2CatalogsEntry 3 }

ex2catBatchesCompletedSuccess OBJECT-TYPE
    SYNTAX     Gauge32
    MAX-ACCESS read-only
    STATUS     current
    DESCRIPTION
	    "Number of batches completed without warnings
	    or errors, to date."
    ::= { ex2CatalogsEntry 4 }

ex2catBatchesCompletedWPerErrors OBJECT-TYPE
    SYNTAX     Gauge32
    MAX-ACCESS read-only
    STATUS     current
    DESCRIPTION
	    "Number of batches completed with one or more
	    errors, to date."
    ::= { ex2CatalogsEntry 5 }

ex2catBatchesCompleteWPerWarning OBJECT-TYPE
    SYNTAX     Gauge32
    MAX-ACCESS read-only
    STATUS     current
    DESCRIPTION
	    "Number of batches completed with warnings but
	    no errors, to date."
    ::= { ex2CatalogsEntry 6 }

ex2catBatchesDone OBJECT-TYPE
    SYNTAX     Gauge32
    MAX-ACCESS read-only
    STATUS     current
    DESCRIPTION
	    "Number of all batches completed or aborted to
	    date.  This counter is incremented after the
	    completion status is sent to SQL."
    ::= { ex2CatalogsEntry 7 }

ex2catBatchesInProgress OBJECT-TYPE
    SYNTAX     Gauge32
    MAX-ACCESS read-only
    STATUS     current
    DESCRIPTION
	    "Number of batches currently being processed. 
	    This counter is incremented when a batch of
	    transactions is accepted by the
	    MSFTESQL-Exchange service and is decremented
	    after the completion is sent or attempted to be
	    sent back to the SQL process."
    ::= { ex2CatalogsEntry 8 }

ex2catBatchesReceived OBJECT-TYPE
    SYNTAX     Gauge32
    MAX-ACCESS read-only
    STATUS     current
    DESCRIPTION
	    "Number of batches received to date.  This
	    counter is incremented when a batch of
	    transactions is accepted by the
	    MSFTESQL-Exchange service."
    ::= { ex2CatalogsEntry 9 }

ex2catPhaseComplete OBJECT-TYPE
    SYNTAX     Gauge32
    MAX-ACCESS read-only
    STATUS     current
    DESCRIPTION
	    "Number of transactions currently in the
	    complete phase."
    ::= { ex2CatalogsEntry 10 }

ex2catPhaseInHDFD OBJECT-TYPE
    SYNTAX     Gauge32
    MAX-ACCESS read-only
    STATUS     current
    DESCRIPTION
	    "Number of transactions currently in the huge
	    document filter daemon phase."
    ::= { ex2CatalogsEntry 11 }

ex2catPhaseInMTFD OBJECT-TYPE
    SYNTAX     Gauge32
    MAX-ACCESS read-only
    STATUS     current
    DESCRIPTION
	    "Number of transactions currently in the
	    multi-threaded filter daemon phase."
    ::= { ex2CatalogsEntry 12 }

ex2catPhaseInSTFD OBJECT-TYPE
    SYNTAX     Gauge32
    MAX-ACCESS read-only
    STATUS     current
    DESCRIPTION
	    "Number of transactions currently in the
	    single-threaded filter daemon phase."
    ::= { ex2CatalogsEntry 13 }

ex2catPhaseInPipeline OBJECT-TYPE
    SYNTAX     Gauge32
    MAX-ACCESS read-only
    STATUS     current
    DESCRIPTION
	    "Number of transactions currently in the
	    pipeline phase."
    ::= { ex2CatalogsEntry 14 }

ex2catPhaseInReadyQueue OBJECT-TYPE
    SYNTAX     Gauge32
    MAX-ACCESS read-only
    STATUS     current
    DESCRIPTION
	    "Number of transactions currently in the ready
	    queue phase."
    ::= { ex2CatalogsEntry 15 }

ex2catPhaseOnHold OBJECT-TYPE
    SYNTAX     Gauge32
    MAX-ACCESS read-only
    STATUS     current
    DESCRIPTION
	    "Number of transactions currently in the
	    on-hold phase."
    ::= { ex2CatalogsEntry 16 }

ex2catPhasePendingCompletion OBJECT-TYPE
    SYNTAX     Gauge32
    MAX-ACCESS read-only
    STATUS     current
    DESCRIPTION
	    "Number of transactions currently in the
	    pending completion phase."
    ::= { ex2CatalogsEntry 17 }

ex2catPhaseRedundant OBJECT-TYPE
    SYNTAX     Gauge32
    MAX-ACCESS read-only
    STATUS     current
    DESCRIPTION
	    "Number of transactions currently in the
	    redundant phase."
    ::= { ex2CatalogsEntry 18 }

ex2catRequestAbort OBJECT-TYPE
    SYNTAX     Gauge32
    MAX-ACCESS read-only
    STATUS     current
    DESCRIPTION
	    "Number of abort status change requests to
	    date."
    ::= { ex2CatalogsEntry 19 }

ex2catRequestAsyncFlush OBJECT-TYPE
    SYNTAX     Gauge32
    MAX-ACCESS read-only
    STATUS     current
    DESCRIPTION
	    "Number of async flush hints to date."
    ::= { ex2CatalogsEntry 20 }

ex2catRequestFlushPerDrain OBJECT-TYPE
    SYNTAX     Gauge32
    MAX-ACCESS read-only
    STATUS     current
    DESCRIPTION
	    "Number of flush/drain status change request to
	    date."
    ::= { ex2CatalogsEntry 21 }

ex2catRequestForceMerge OBJECT-TYPE
    SYNTAX     Gauge32
    MAX-ACCESS read-only
    STATUS     current
    DESCRIPTION
	    "Number of force merge async status change
	    requests to date."
    ::= { ex2CatalogsEntry 22 }

ex2catRequestPause OBJECT-TYPE
    SYNTAX     Gauge32
    MAX-ACCESS read-only
    STATUS     current
    DESCRIPTION
	    "Number of pause status change requests to
	    date."
    ::= { ex2CatalogsEntry 23 }

ex2catRequestReset OBJECT-TYPE
    SYNTAX     Gauge32
    MAX-ACCESS read-only
    STATUS     current
    DESCRIPTION
	    "Number of reset status change requests to
	    date."
    ::= { ex2CatalogsEntry 24 }

ex2catRequestResume OBJECT-TYPE
    SYNTAX     Gauge32
    MAX-ACCESS read-only
    STATUS     current
    DESCRIPTION
	    "Number of resume status change requests to
	    date."
    ::= { ex2CatalogsEntry 25 }

ex2catState OBJECT-TYPE
    SYNTAX     Gauge32
    MAX-ACCESS read-only
    STATUS     current
    DESCRIPTION
	    "Current project state. 0=Not Initialized;
	    1=Available; 2=Available with input queue near
	    limit; 4=Shut down; 5=Paused from Status Change
	    i.e. for backup; 6=Forced paused; 7=Draining;
	    8=Pipeline flushing; 9=Prepare to pause;
	    10=Pipline pausing; 11=Prepare to resume;
	    12=Aborting queues; 13=Draining FDs;
	    14=Pipeline aborting; 15=Pipeline resetting"
    ::= { ex2CatalogsEntry 26 }

ex2catStateCallerComponent OBJECT-TYPE
    SYNTAX     Gauge32
    MAX-ACCESS read-only
    STATUS     current
    DESCRIPTION
	    "Caller Component type identifies the type of
	    component that has changed the project state.
	    0=n/a; 1=Ready queue; 2=Inprogress map;
	    3=Memory manager; 4=Plugin; 5=Self; 6=CB
	    Master; 7=Pipeline; 8=Request task; 9=Property
	    Id task; 10=FD manager; 11=Status change"
    ::= { ex2CatalogsEntry 27 }

ex2catStateReasonCode OBJECT-TYPE
    SYNTAX     Gauge32
    MAX-ACCESS read-only
    STATUS     current
    DESCRIPTION
	    "Reason code further defines the project state.
	    0=Clear; 1=Temporary from low resources;
	    2=Temporary connection problem; 3=Temporary
	    other such as ongoing status change, status
	    change failure, failure to start an FD, failure
	    during merge, see State Caller and State HR;
	    4=Fatal error; 5=Reset needed"
    ::= { ex2CatalogsEntry 28 }

ex2catStateResultCode OBJECT-TYPE
    SYNTAX     Gauge32
    MAX-ACCESS read-only
    STATUS     current
    DESCRIPTION
	    "Result code that led to a change in project
	    state."
    ::= { ex2CatalogsEntry 29 }

ex2catTransDeletes OBJECT-TYPE
    SYNTAX     Gauge32
    MAX-ACCESS read-only
    STATUS     current
    DESCRIPTION
	    "Number of delete transactions to date"
    ::= { ex2CatalogsEntry 30 }

ex2catTransDone OBJECT-TYPE
    SYNTAX     Gauge32
    MAX-ACCESS read-only
    STATUS     current
    DESCRIPTION
	    "Number of transactions finished to date,
	    includes success, warnings, errors, aborted."
    ::= { ex2CatalogsEntry 31 }

ex2catTransErrored OBJECT-TYPE
    SYNTAX     Gauge32
    MAX-ACCESS read-only
    STATUS     current
    DESCRIPTION
	    "Number of transactions completed in error to
	    date."
    ::= { ex2CatalogsEntry 32 }

ex2catTransInProgress OBJECT-TYPE
    SYNTAX     Gauge32
    MAX-ACCESS read-only
    STATUS     current
    DESCRIPTION
	    "Number of transactions currently in progress"
    ::= { ex2CatalogsEntry 33 }

ex2catTransModifies OBJECT-TYPE
    SYNTAX     Gauge32
    MAX-ACCESS read-only
    STATUS     current
    DESCRIPTION
	    "Number of modify transactions to date"
    ::= { ex2CatalogsEntry 34 }

ex2catTransRerouted OBJECT-TYPE
    SYNTAX     Gauge32
    MAX-ACCESS read-only
    STATUS     current
    DESCRIPTION
	    "Number of transactions rerouted from the
	    multi-threaded filter daemon to the
	    signle-threaded filter daemon to date."
    ::= { ex2CatalogsEntry 35 }

ex2FDTable OBJECT-TYPE
    SYNTAX     SEQUENCE OF MSFTESQLExchangeFDEntry
    MAX-ACCESS not-accessible
    STATUS     current
    DESCRIPTION
	    "A table containing performance information for
	    instances of 'MSFTESQL-Exchange:FD' objects."
    ::= { exchangeV2 73 }

ex2FDEntry OBJECT-TYPE
    SYNTAX     MSFTESQLExchangeFDEntry
    MAX-ACCESS not-accessible
    STATUS     current
    DESCRIPTION
	    "Performance information for one particular
	    instance of 'MSFTESQL-Exchange:FD' object."
    INDEX      { ex2FDInstance }
    ::= { ex2FDTable 1 }

MSFTESQLExchangeFDEntry ::= SEQUENCE {
    ex2FDInstance InstanceName,
    ex2FDBatchesCompleted Gauge32,
    ex2FDBatchesInProgress Gauge32,
    ex2FDBatchesReceived Gauge32,
    ex2FDBatchesRejected Gauge32,
    ex2FDFilters Gauge32,
    ex2FDNoiseWordLists Gauge32,
    ex2FDTransErrors Gauge32,
    ex2FDTransSuccess Gauge32,
    ex2FDTransactionsCompleted Gauge32,
    ex2FDTransactionsReceived Gauge32,
    ex2FDTransactionsStarted Gauge32,
    ex2FDWordBreakers Gauge32
}

ex2FDInstance OBJECT-TYPE
    SYNTAX     InstanceName
    MAX-ACCESS read-only
    STATUS     current
    DESCRIPTION
	    "Instance name."
    ::= { ex2FDEntry 1 }

ex2FDBatchesCompleted OBJECT-TYPE
    SYNTAX     Gauge32
    MAX-ACCESS read-only
    STATUS     current
    DESCRIPTION
	    "Batches completed to date"
    ::= { ex2FDEntry 2 }

ex2FDBatchesInProgress OBJECT-TYPE
    SYNTAX     Gauge32
    MAX-ACCESS read-only
    STATUS     current
    DESCRIPTION
	    "Batches currently in progress."
    ::= { ex2FDEntry 3 }

ex2FDBatchesReceived OBJECT-TYPE
    SYNTAX     Gauge32
    MAX-ACCESS read-only
    STATUS     current
    DESCRIPTION
	    "Batches received to date."
    ::= { ex2FDEntry 4 }

ex2FDBatchesRejected OBJECT-TYPE
    SYNTAX     Gauge32
    MAX-ACCESS read-only
    STATUS     current
    DESCRIPTION
	    "Batches rejected to date.	These batches could
	    not be processed due to low memory stress."
    ::= { ex2FDEntry 5 }

ex2FDFilters OBJECT-TYPE
    SYNTAX     Gauge32
    MAX-ACCESS read-only
    STATUS     current
    DESCRIPTION
	    "Number of Filters Loaded by filter daemon to
	    date"
    ::= { ex2FDEntry 6 }

ex2FDNoiseWordLists OBJECT-TYPE
    SYNTAX     Gauge32
    MAX-ACCESS read-only
    STATUS     current
    DESCRIPTION
	    "Number of Noise Word Files loaded by filter
	    daemon to date"
    ::= { ex2FDEntry 7 }

ex2FDTransErrors OBJECT-TYPE
    SYNTAX     Gauge32
    MAX-ACCESS read-only
    STATUS     current
    DESCRIPTION
	    "Transactions completed in error to date."
    ::= { ex2FDEntry 8 }

ex2FDTransSuccess OBJECT-TYPE
    SYNTAX     Gauge32
    MAX-ACCESS read-only
    STATUS     current
    DESCRIPTION
	    "Transactions completed successfully to date."
    ::= { ex2FDEntry 9 }

ex2FDTransactionsCompleted OBJECT-TYPE
    SYNTAX     Gauge32
    MAX-ACCESS read-only
    STATUS     current
    DESCRIPTION
	    "Transactions completed to date."
    ::= { ex2FDEntry 10 }

ex2FDTransactionsReceived OBJECT-TYPE
    SYNTAX     Gauge32
    MAX-ACCESS read-only
    STATUS     current
    DESCRIPTION
	    "Transactions received to date."
    ::= { ex2FDEntry 11 }

ex2FDTransactionsStarted OBJECT-TYPE
    SYNTAX     Gauge32
    MAX-ACCESS read-only
    STATUS     current
    DESCRIPTION
	    "Transactions started (given to a worker thread
	    to be filtered) to date."
    ::= { ex2FDEntry 12 }

ex2FDWordBreakers OBJECT-TYPE
    SYNTAX     Gauge32
    MAX-ACCESS read-only
    STATUS     current
    DESCRIPTION
	    "Number of Wordbreakers Loaded by filter daemon
	    to date"
    ::= { ex2FDEntry 13 }

ex2Service OBJECT IDENTIFIER
    ::= { exchangeV2 74 }

ex2svcBatchesFPC OBJECT-TYPE
    SYNTAX     Gauge32
    MAX-ACCESS read-only
    STATUS     current
    DESCRIPTION
	    "Number of current batches past filter phase
	    complete.  This counter is incremented after
	    all the transactions in the batch are filtered
	    by the filter daemon and given to the plugin(s)
	    for processing."
    ::= { ex2Service 1 }

ex2svcBatchesAborted OBJECT-TYPE
    SYNTAX     Gauge32
    MAX-ACCESS read-only
    STATUS     current
    DESCRIPTION
	    "Number of batches aborted to date.  By
	    definition the state of an aborted batch, how
	    far some or all of its transactions got through
	    the indexing process is unknown.  These batches
	    are retried by SQL."
    ::= { ex2Service 2 }

ex2svcBatchesCompletedWPerErrors OBJECT-TYPE
    SYNTAX     Gauge32
    MAX-ACCESS read-only
    STATUS     current
    DESCRIPTION
	    "Number of batches completed with one or more
	    errors, to date.  A batch is a group of one or
	    more transactions."
    ::= { ex2Service 3 }

ex2svcBatchesCompleteWPerWarning OBJECT-TYPE
    SYNTAX     Gauge32
    MAX-ACCESS read-only
    STATUS     current
    DESCRIPTION
	    "Number of batches completed with warnings but
	    no errors, to date.  A batch is a group of one
	    or more transactions."
    ::= { ex2Service 4 }

ex2svcBatcheCompletelySuccessful OBJECT-TYPE
    SYNTAX     Gauge32
    MAX-ACCESS read-only
    STATUS     current
    DESCRIPTION
	    "Number of batches completed without warnings
	    or errors, to date.  A batch is a group of one
	    or more transactions."
    ::= { ex2Service 5 }

ex2svcBatchesDone OBJECT-TYPE
    SYNTAX     Gauge32
    MAX-ACCESS read-only
    STATUS     current
    DESCRIPTION
	    "Number of all batches completed or aborted to
	    date.  This counter is incremented after the
	    completion status is sent to SQL."
    ::= { ex2Service 6 }

ex2svcBatchesInProgress OBJECT-TYPE
    SYNTAX     Gauge32
    MAX-ACCESS read-only
    STATUS     current
    DESCRIPTION
	    "Number of batches currently being processed. 
	    This counter is incremented when a batch of
	    transactions is accepted by the
	    MSFTESQL-Exchange service and is decremented
	    after the completion is sent or attempted to be
	    sent back to the SQL process."
    ::= { ex2Service 7 }

ex2svcBatchesInReadyQueue OBJECT-TYPE
    SYNTAX     Gauge32
    MAX-ACCESS read-only
    STATUS     current
    DESCRIPTION
	    "Number of batches in the ready queue.  This
	    queue buffers work that will be given to the
	    filter daemons."
    ::= { ex2Service 8 }

ex2svcBatchesReceived OBJECT-TYPE
    SYNTAX     Gauge32
    MAX-ACCESS read-only
    STATUS     current
    DESCRIPTION
	    "Number of batches received to date.  This
	    counter is incremented when a batch of
	    transactions is accepted by the
	    MSFTESQL-Exchange service."
    ::= { ex2Service 9 }

ex2svcCBSize OBJECT-TYPE
    SYNTAX     Gauge32
    MAX-ACCESS read-only
    STATUS     current
    DESCRIPTION
	    "Amount of memory (MB) currently being used by
	    chunk buffers.  Chunk buffers are blocks of
	    shared memory common to the msftesql-Exchange
	    service and the filter daemons."
    ::= { ex2Service 10 }

ex2svcCBsAcquired OBJECT-TYPE
    SYNTAX     Gauge32
    MAX-ACCESS read-only
    STATUS     current
    DESCRIPTION
	    "Number of chunk buffers that have been
	    returned from the FD.  Chunk buffers are blocks
	    of shared memory common to the
	    msftesql-Exchange service and the filter
	    daemons."
    ::= { ex2Service 11 }

ex2svcCBsDestroyed OBJECT-TYPE
    SYNTAX     Gauge32
    MAX-ACCESS read-only
    STATUS     current
    DESCRIPTION
	    "Number of chunk buffers destructed, returned
	    to the o/s, to date.  Chunk buffers are blocks
	    of shared memory common to the
	    msftesql-Exchange service and the filter
	    daemons."
    ::= { ex2Service 12 }

ex2svcCBsGarbageCollected OBJECT-TYPE
    SYNTAX     Gauge32
    MAX-ACCESS read-only
    STATUS     current
    DESCRIPTION
	    "Number of chunk buffers that have been garbage
	    collected from the filter daemons to date. 
	    Chunk buffers are blocks of shared memory
	    common to the msftesql-Exchange service and the
	    filter daemons."
    ::= { ex2Service 13 }

ex2svcCBsGiven OBJECT-TYPE
    SYNTAX     Gauge32
    MAX-ACCESS read-only
    STATUS     current
    DESCRIPTION
	    "Number of chunk buffers given to the filter
	    daemons to date.  Chunk buffers are blocks of
	    shared memory common to the msftesql-Exchange
	    service and the filter daemons."
    ::= { ex2Service 14 }

ex2svcCBsInUse OBJECT-TYPE
    SYNTAX     Gauge32
    MAX-ACCESS read-only
    STATUS     current
    DESCRIPTION
	    "Number of chunk buffers that are currently in
	    use.  Chunk buffers are blocks of shared memory
	    common to the msftesql-Exchange service and the
	    filter daemons."
    ::= { ex2Service 15 }

ex2svcCBsReleased OBJECT-TYPE
    SYNTAX     Gauge32
    MAX-ACCESS read-only
    STATUS     current
    DESCRIPTION
	    "Number of chunk buffers returned back to the
	    free list to date.	Chunk buffers are blocks of
	    shared memory common to the msftesql-Exchange
	    service and the filter daemons."
    ::= { ex2Service 16 }

ex2svcCBsTotal OBJECT-TYPE
    SYNTAX     Gauge32
    MAX-ACCESS read-only
    STATUS     current
    DESCRIPTION
	    "Current total number of chunk buffers.  Chunk
	    buffers are blocks of shared memory common to
	    the msftesql-Exchange service and the filter
	    daemons."
    ::= { ex2Service 17 }

ex2svcCatalogsMonitored OBJECT-TYPE
    SYNTAX     Gauge32
    MAX-ACCESS read-only
    STATUS     current
    DESCRIPTION
	    "Number of catalogs with PERFMON counters"
    ::= { ex2Service 18 }

ex2svcCatalogsMounted OBJECT-TYPE
    SYNTAX     Gauge32
    MAX-ACCESS read-only
    STATUS     current
    DESCRIPTION
	    "Number of catalogs mounted"
    ::= { ex2Service 19 }

ex2svcFDHDCBEmpty OBJECT-TYPE
    SYNTAX     Gauge32
    MAX-ACCESS read-only
    STATUS     current
    DESCRIPTION
	    "Number of times to date that the huge document
	    filter daemons have run out of chunk buffers."
    ::= { ex2Service 20 }

ex2svcFDHDActive OBJECT-TYPE
    SYNTAX     Gauge32
    MAX-ACCESS read-only
    STATUS     current
    DESCRIPTION
	    "Number of active huge document filter daemons"
    ::= { ex2Service 21 }

ex2svcFDHDLaunched OBJECT-TYPE
    SYNTAX     Gauge32
    MAX-ACCESS read-only
    STATUS     current
    DESCRIPTION
	    "Number of launched huge document filter
	    daemons to date"
    ::= { ex2Service 22 }

ex2svcFDHDTerminatedAV OBJECT-TYPE
    SYNTAX     Gauge32
    MAX-ACCESS read-only
    STATUS     current
    DESCRIPTION
	    "Number of terminated huge document filter
	    daemons to date due to an access violation. 
	    This type of error indicates that the filter
	    daemon process may be unstable or corrupt and
	    consequently, it is recycled."
    ::= { ex2Service 23 }

ex2svcFDHDTerminatedExcessiveMem OBJECT-TYPE
    SYNTAX     Gauge32
    MAX-ACCESS read-only
    STATUS     current
    DESCRIPTION
	    "Number of terminated huge document filter
	    daemons to date due to excessive Mem usage. 
	    The max, by default, is a percentage of the
	    pagefile however an explicit Mem amount can be
	    set using the
	    FTE_SingleThreadedFilterDaemonMemMax admin
	    parameter."
    ::= { ex2Service 24 }

ex2svcFDHDTerminatedIdle OBJECT-TYPE
    SYNTAX     Gauge32
    MAX-ACCESS read-only
    STATUS     current
    DESCRIPTION
	    "Number of terminated huge document filter
	    daemons to date due to having been idle.  Each
	    time the filter daemon gets work, the clock is
	    reset to 0.  The idle time interval can be
	    explicitly set by the
	    FTE_FilterDaemonIdleTimeMax admin paramer."
    ::= { ex2Service 25 }

ex2svcFDHDTerminatedOther OBJECT-TYPE
    SYNTAX     Gauge32
    MAX-ACCESS read-only
    STATUS     current
    DESCRIPTION
	    "Number of terminated huge document filter
	    daemons to date due to a variety of other
	    errors.  Further details may be found in the
	    crawl log, through retail tracing if configured
	    and through watson reporting if configured."
    ::= { ex2Service 26 }

ex2svcFDHDTerminatedPipe OBJECT-TYPE
    SYNTAX     Gauge32
    MAX-ACCESS read-only
    STATUS     current
    DESCRIPTION
	    "Number of huge document filter daemons  that
	    appear to have exited abruptly as indicated by
	    an interprocess communication failure which may
	    have been due to an unhandled error.  A watson
	    report should be generated in this case to
	    allow further analaysis."
    ::= { ex2Service 27 }

ex2svcFDHDTerminatedTimeOut OBJECT-TYPE
    SYNTAX     Gauge32
    MAX-ACCESS read-only
    STATUS     current
    DESCRIPTION
	    "Number of terminated huge document filter
	    daemons to date due to a time-out.	  A time
	    out occurs when the FD takes too long to
	    process a document.  These timeouts are
	    controlled by the
	    FTE_FilterDaemonBatchAgingInterval and
	    FTE_ChunkBufferTimeOutSeconds admin
	    parameters."
    ::= { ex2Service 28 }

ex2svcFDHDUnresponsiveToShutdown OBJECT-TYPE
    SYNTAX     Gauge32
    MAX-ACCESS read-only
    STATUS     current
    DESCRIPTION
	    "Number of times to date that the huge document
	    filter daemons were given a directive to
	    shutdown but didn't respond in time."
    ::= { ex2Service 29 }

ex2svcFDMTCBEmpty OBJECT-TYPE
    SYNTAX     Gauge32
    MAX-ACCESS read-only
    STATUS     current
    DESCRIPTION
	    "Number of times to date that the
	    multi-threaded filter daemons have run out of
	    chunk buffers."
    ::= { ex2Service 30 }

ex2svcFDMTActive OBJECT-TYPE
    SYNTAX     Gauge32
    MAX-ACCESS read-only
    STATUS     current
    DESCRIPTION
	    "Number of multi-threaded filter daemons
	    currently active"
    ::= { ex2Service 31 }

ex2svcFDMTLaunched OBJECT-TYPE
    SYNTAX     Gauge32
    MAX-ACCESS read-only
    STATUS     current
    DESCRIPTION
	    "Number of launched multi-threaded filter
	    daemons to date"
    ::= { ex2Service 32 }

ex2svcFDMTTerminatedAV OBJECT-TYPE
    SYNTAX     Gauge32
    MAX-ACCESS read-only
    STATUS     current
    DESCRIPTION
	    "Number of terminated multi-threaded filter
	    daemons to date due to an access violation. 
	    This type of error indicates that the filter
	    daemon process may be unstable or corrupt and
	    consequently, it is recycled."
    ::= { ex2Service 33 }

ex2svcFDMTTerminatedExcessiveMem OBJECT-TYPE
    SYNTAX     Gauge32
    MAX-ACCESS read-only
    STATUS     current
    DESCRIPTION
	    "Number of terminated multi-threaded filter
	    daemons to date due to excessive Mem usage. 
	    The max, by default, is a percentage of the
	    pagefile however an explicit Mem amount can be
	    set using the
	    FTE_MultiThreadedFilterDaemonMemMax admin
	    parameter."
    ::= { ex2Service 34 }

ex2svcFDMTTerminatedIdle OBJECT-TYPE
    SYNTAX     Gauge32
    MAX-ACCESS read-only
    STATUS     current
    DESCRIPTION
	    "Number of terminated multi-threaded filter
	    daemons to date due to having been idle.  Each
	    time the filter daemon gets work, the clock is
	    reset to 0.  The idle time interval can be
	    explicitly set by the
	    FTE_FilterDaemonIdleTimeMax admin paramer."
    ::= { ex2Service 35 }

ex2svcFDMTTerminatedOther OBJECT-TYPE
    SYNTAX     Gauge32
    MAX-ACCESS read-only
    STATUS     current
    DESCRIPTION
	    "Number of terminated multi-threaded filter
	    daemons to date due to a variety of other
	    errors.  Further details may be found in the
	    crawl log, through retail tracing if configured
	    and through watson reporting if configured."
    ::= { ex2Service 36 }

ex2svcFDMTTerminatedPipe OBJECT-TYPE
    SYNTAX     Gauge32
    MAX-ACCESS read-only
    STATUS     current
    DESCRIPTION
	    "Number of multi-threaded filter daemons that
	    appear to have exited abruptly as indicated by
	    an interprocess communication failure which may
	    have been due to an unhandled error.  A watson
	    report should be generated in this case to
	    allow further analaysis."
    ::= { ex2Service 37 }

ex2svcFDMTTerminatedTimeOut OBJECT-TYPE
    SYNTAX     Gauge32
    MAX-ACCESS read-only
    STATUS     current
    DESCRIPTION
	    "Number of terminated multi-threaded filter
	    daemons to date due to a time-out.	A time out
	    occurs when the FD takes too long to process a
	    document.  These timeouts are controlled by the
	    FTE_FilterDaemonBatchAgingInterval and
	    FTE_ChunkBufferTimeOutSeconds admin
	    parameters."
    ::= { ex2Service 38 }

ex2svcFDMTUnresponsiveToShutdown OBJECT-TYPE
    SYNTAX     Gauge32
    MAX-ACCESS read-only
    STATUS     current
    DESCRIPTION
	    "Number of times to date that the
	    multi-threaded filter daemons were given a
	    directive to shutdown but didn't respond in
	    time."
    ::= { ex2Service 39 }

ex2svcFDSTCBEmpty OBJECT-TYPE
    SYNTAX     Gauge32
    MAX-ACCESS read-only
    STATUS     current
    DESCRIPTION
	    "Number of times to date that the
	    single-threaded filter daemons have run out of
	    chunk buffers."
    ::= { ex2Service 40 }

ex2svcFDSTActive OBJECT-TYPE
    SYNTAX     Gauge32
    MAX-ACCESS read-only
    STATUS     current
    DESCRIPTION
	    "Number of single-threaded filter daemons
	    currently active"
    ::= { ex2Service 41 }

ex2svcFDSTLaunched OBJECT-TYPE
    SYNTAX     Gauge32
    MAX-ACCESS read-only
    STATUS     current
    DESCRIPTION
	    "Number of launched single-threaded filter
	    daemons to date"
    ::= { ex2Service 42 }

ex2svcFDSTTerminatedAV OBJECT-TYPE
    SYNTAX     Gauge32
    MAX-ACCESS read-only
    STATUS     current
    DESCRIPTION
	    "Number of terminated single-threaded filter
	    daemons to date due to an access violation. 
	    This type of error indicates that the filter
	    daemon process may be unstable or corrupt and
	    consequently, it is recycled."
    ::= { ex2Service 43 }

ex2svcFDSTTerminatedExcessiveMem OBJECT-TYPE
    SYNTAX     Gauge32
    MAX-ACCESS read-only
    STATUS     current
    DESCRIPTION
	    "Number of terminated single-threaded filter
	    daemons to date due to excessive Mem usage. 
	    The max, by default, is a percentage of the
	    pagefile however an explicit Mem amount can be
	    set using the
	    FTE_SingleThreadedFilterDaemonMemMax admin
	    parameter."
    ::= { ex2Service 44 }

ex2svcFDSTTerminatedIdle OBJECT-TYPE
    SYNTAX     Gauge32
    MAX-ACCESS read-only
    STATUS     current
    DESCRIPTION
	    "Number of terminated single-threaded filter
	    daemons to date due to having been idle.  Each
	    time the filter daemon gets work, the clock is
	    reset to 0.  The idle time interval can be
	    explicitly set by the
	    FTE_FilterDaemonIdleTimeMax admin paramer."
    ::= { ex2Service 45 }

ex2svcFDSTTerminatedOther OBJECT-TYPE
    SYNTAX     Gauge32
    MAX-ACCESS read-only
    STATUS     current
    DESCRIPTION
	    "Number of terminated single-threaded filter
	    daemons to date due to a variety of other
	    errors.  Further details may be found in the
	    crawl log, through retail tracing if configured
	    and through watson reporting if configured."
    ::= { ex2Service 46 }

ex2svcFDSTTerminatedPipe OBJECT-TYPE
    SYNTAX     Gauge32
    MAX-ACCESS read-only
    STATUS     current
    DESCRIPTION
	    "Number of single-threaded filter daemons that
	    appear to have exited abruptly as indicated by
	    an interprocess communication failure which may
	    have been due to an unhandled error.  A watson
	    report should be generated in this case to
	    allow further analaysis."
    ::= { ex2Service 47 }

ex2svcFDSTTerminatedTimeOut OBJECT-TYPE
    SYNTAX     Gauge32
    MAX-ACCESS read-only
    STATUS     current
    DESCRIPTION
	    "Number of terminated single-threaded filter
	    daemons to date due to a time-out.	  A time
	    out occurs when the FD takes too long to
	    process a document.  These timeouts are
	    controlled by the
	    FTE_FilterDaemonBatchAgingInterval and
	    FTE_ChunkBufferTimeOutSeconds admin
	    parameters."
    ::= { ex2Service 48 }

ex2svcFDSTUnresponsiveToShutdown OBJECT-TYPE
    SYNTAX     Gauge32
    MAX-ACCESS read-only
    STATUS     current
    DESCRIPTION
	    "Number of times to date that the
	    single-threaded filter daemons were given a
	    directive to shutdown but didn't respond in
	    time."
    ::= { ex2Service 49 }

ex2svcHeartbeats OBJECT-TYPE
    SYNTAX     Gauge32
    MAX-ACCESS read-only
    STATUS     current
    DESCRIPTION
	    "Incremented by a timer task which does
	    maintenance and self-monitoring"
    ::= { ex2Service 50 }

ex2svcIndexPerfLevel OBJECT-TYPE
    SYNTAX     Gauge32
    MAX-ACCESS read-only
    STATUS     current
    DESCRIPTION
	    "Indexing performance level"
    ::= { ex2Service 51 }

ex2svcQueryPerfLevel OBJECT-TYPE
    SYNTAX     Gauge32
    MAX-ACCESS read-only
    STATUS     current
    DESCRIPTION
	    "Query performance level"
    ::= { ex2Service 52 }

ex2svcTotalNoiseWordFiles OBJECT-TYPE
    SYNTAX     Gauge32
    MAX-ACCESS read-only
    STATUS     current
    DESCRIPTION
	    "Number of noise word files loaded to date"
    ::= { ex2Service 53 }

ex2svcTotalStemmers OBJECT-TYPE
    SYNTAX     Gauge32
    MAX-ACCESS read-only
    STATUS     current
    DESCRIPTION
	    "Number of stemmers loaded to date"
    ::= { ex2Service 54 }

ex2svcTotalThesaurus OBJECT-TYPE
    SYNTAX     Gauge32
    MAX-ACCESS read-only
    STATUS     current
    DESCRIPTION
	    "Number of thesaurus files loaded to date"
    ::= { ex2Service 55 }

ex2svcTotalWordbreakers OBJECT-TYPE
    SYNTAX     Gauge32
    MAX-ACCESS read-only
    STATUS     current
    DESCRIPTION
	    "Number of wordbreakers loaded to date"
    ::= { ex2Service 56 }

END
