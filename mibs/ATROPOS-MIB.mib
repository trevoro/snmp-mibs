-- extracted from draft-bush-inline-predictive-mgt-00.txt
-- at Fri Aug  2 06:10:20 2002

               ATROPOS-MIB DEFINITIONS ::= BEGIN

               IMPORTS
               MODULE-IDENTITY, OBJECT-TYPE, experimental,
               Counter32, TimeTicks
               FROM SNMPv2-SMI
               DisplayString
               FROM SNMPv2-TC;

               atroposMIB MODULE-IDENTITY
               LAST-UPDATED "9801010000Z"
               ORGANIZATION "GE CRD"
               CONTACT-INFO
               "Stephen F. Bush bushsf@crd.ge.com"
               DESCRIPTION
               "Experimental MIB modules for the Active Virtual Network
               Management Prediction (Atropos) system."
               ::= { experimental active(75) 4 }

               --
               -- Logical Process Table
               --
               lP OBJECT IDENTIFIER ::= { atroposMIB 1 }

               lPTable OBJECT-TYPE
               SYNTAX SEQUENCE OF LPEntry
               MAX-ACCESS not-accessible
               STATUS current
               DESCRIPTION
               "Table of Atropos LP information."
               ::= { lP 1 }

               lPEntry OBJECT-TYPE
               SYNTAX LPEntry
               MAX-ACCESS not-accessible
               STATUS current
               DESCRIPTION
               "Table of Atropos LP information."
               INDEX { lPIndex }
               ::= { lPTable 1 }

               LPEntry ::= SEQUENCE {
               lPIndex          INTEGER,
               lPID             DisplayString,
               lPLVT            INTEGER,
               lPQRSize         INTEGER,
               lPQSSize         INTEGER,
               lPCausalityRollbacks INTEGER,
               lPToleranceRollbacks INTEGER,
               lPSQSize         INTEGER,
               lPTolerance      INTEGER,
               lPGVT            INTEGER,
               lPLookAhead      INTEGER,
               lPGvtUpdate      INTEGER,
               lPStepSize       INTEGER,
               lPReal           INTEGER,
               lPVirtual        INTEGER,
               lPNumPkts        INTEGER,
               lPNumAnti        INTEGER,
               lPPredAcc        DisplayString,
               lPPropX 	        DisplayString,
               lPPropY          DisplayString,
               lPETask          DisplayString,
               lPETrb           DisplayString,
               lPVmRate         DisplayString,
               lPReRate         DisplayString,
               lPSpeedup        DisplayString,
               lPLookahead      DisplayString,
               lPNumNoState     INTEGER,
               lPStatePred      DisplayString,
               lPPktPred        DisplayString,
               lPTdiff          DisplayString,
               lPStateError     DisplayString,
               lPUptime         TimeTicks
               }

               lPIndex OBJECT-TYPE
               SYNTAX INTEGER (0..2147483647)
               MAX-ACCESS not-accessible
               STATUS current
               DESCRIPTION
               "The LP table index."
               ::= { lPEntry 1 }

               lPID OBJECT-TYPE
               SYNTAX DisplayString
               MAX-ACCESS read-only
               STATUS current
               DESCRIPTION
               "The LP identifier."
               ::= { lPEntry 2 }

               lPLVT OBJECT-TYPE
               SYNTAX INTEGER (0..2147483647)
               MAX-ACCESS read-only
               STATUS current
               DESCRIPTION
               "This is the LP Local Virtual Time."
               ::= { lPEntry 3 }

               lPQRSize OBJECT-TYPE
               SYNTAX INTEGER (0..2147483647)
               MAX-ACCESS read-only
               STATUS current
               DESCRIPTION
               "This is the LP Receive Queue Size."
               ::= { lPEntry 4 }

               lPQSSize OBJECT-TYPE
               SYNTAX INTEGER (0..2147483647)
               MAX-ACCESS read-only
               STATUS current
               DESCRIPTION
               "This is the LP send queue size."
               ::= { lPEntry 5 }

               lPCausalityRollbacks OBJECT-TYPE
               SYNTAX INTEGER (0..2147483647)
               MAX-ACCESS read-only
               STATUS current
               DESCRIPTION
               "This is the number of rollbacks this LP has suffered."
               ::= { lPEntry 6 }

               lPToleranceRollbacks OBJECT-TYPE
               SYNTAX INTEGER (0..2147483647)
               MAX-ACCESS read-only
               STATUS current
               DESCRIPTION
               "This is the number of rollbacks this LP has suffered."
               ::= { lPEntry 7 }

               lPSQSize OBJECT-TYPE
               SYNTAX INTEGER (0..2147483647)
               MAX-ACCESS read-only
               STATUS current
               DESCRIPTION
               "This is the LP state queue size."
               ::= { lPEntry 8 }

               lPTolerance OBJECT-TYPE
               SYNTAX INTEGER (0..2147483647)
               MAX-ACCESS read-only
               STATUS current
               DESCRIPTION
               "This is the allowable deviation between process's
               predicted state and the actual state."
               ::= { lPEntry 9 }

               lPGVT  OBJECT-TYPE
               SYNTAX INTEGER (0..2147483647)
               MAX-ACCESS read-only
               STATUS current
               DESCRIPTION
               "This is this system's notion of Global Virtual Time."
               ::= { lPEntry 10 }

               lPLookAhead  OBJECT-TYPE
               SYNTAX INTEGER (0..2147483647)
               MAX-ACCESS read-only
               STATUS current
               DESCRIPTION
               "This is this system's maximum time into which it can
               predict."
               ::= { lPEntry 11 }
               lPGvtUpdate OBJECT-TYPE
               SYNTAX INTEGER (0..2147483647)
               MAX-ACCESS read-only
               STATUS current
               DESCRIPTION
               "This is the GVT update rate."
               ::= { lPEntry 12 }

               lPStepSize OBJECT-TYPE
               SYNTAX INTEGER (0..2147483647)
               MAX-ACCESS read-only
               STATUS current
               DESCRIPTION
               "This is the lookahead (Delta) in milliseconds for each
               virtual message as generated from the driving process."
               ::= { lPEntry 13 }

               lPReal OBJECT-TYPE
               SYNTAX INTEGER (0..2147483647)
               MAX-ACCESS read-only
               STATUS current
               DESCRIPTION
               "This is the total number of real messages received."
               ::= { lPEntry 14 }

               lPVirtual OBJECT-TYPE
               SYNTAX INTEGER (0..2147483647)
               MAX-ACCESS read-only
               STATUS current
               DESCRIPTION
               "This is the total number of virtual messages
               received."
               ::= { lPEntry 15 }

               lPNumPkts OBJECT-TYPE
               SYNTAX INTEGER (0..2147483647)
               MAX-ACCESS read-only
               STATUS current
               DESCRIPTION
               "This is the total number of all Atropos packets
               received."
               ::= { lPEntry 16 }

               lPNumAnti OBJECT-TYPE
               SYNTAX INTEGER (0..2147483647)
               MAX-ACCESS read-only
               STATUS current
               DESCRIPTION
               "This is the total number of Anti-Messages transmitted
               by this Logical Process."
               ::= { lPEntry 17 }

               lPPredAcc OBJECT-TYPE
               SYNTAX DisplayString
               MAX-ACCESS read-only
               STATUS current
               DESCRIPTION
               "This is the prediction accuracy based upon time
               weighted average of the difference between predicted and real
               values."
               ::= { lPEntry 18 }

               lPPropX OBJECT-TYPE
               SYNTAX DisplayString
               MAX-ACCESS read-only
               STATUS current
               DESCRIPTION
               "This is the proportion of out-of-order messages
               received at this Logical Process."
               ::= { lPEntry 19 }

               lPPropY OBJECT-TYPE
               SYNTAX DisplayString
               MAX-ACCESS read-only
               STATUS current
               DESCRIPTION
               "This is the proportion of out-of-tolerance messages
               received at this Logical Process."
               ::= { lPEntry 20 }

               lPETask OBJECT-TYPE
               SYNTAX DisplayString
               MAX-ACCESS read-only
               STATUS current
               DESCRIPTION
               "This is the expected task execution wallclock time for this
               Logical Process."
               ::= { lPEntry 21 }

               lPETrb OBJECT-TYPE
               SYNTAX DisplayString
               MAX-ACCESS read-only
               STATUS current
               DESCRIPTION
               "This is the expected wallclock time spent performing a
               rollback for this Logical Process."
               ::= { lPEntry 22 }

               lPVmRate OBJECT-TYPE
               SYNTAX DisplayString
               MAX-ACCESS read-only
               STATUS current
               DESCRIPTION
               "This is the rate at which virtual messages were
               processed by this Logical Process."
               ::= { lPEntry 23 }

               lPReRate OBJECT-TYPE
               SYNTAX DisplayString
               MAX-ACCESS read-only
               STATUS current
               DESCRIPTION
               "This is the time until next virtual message."
               ::= { lPEntry 24 }

               lPSpeedup OBJECT-TYPE
               SYNTAX DisplayString
               MAX-ACCESS read-only
               STATUS current
               DESCRIPTION
               "This is the speedup, ratio of virtual time to wallclock time,
               of this logical process."
               ::= { lPEntry 25 }

               lPLookahead OBJECT-TYPE
               SYNTAX DisplayString
               MAX-ACCESS read-only
               STATUS current
               DESCRIPTION
               "This is the expected lookahead in milliseconds of this
               Logical Process."
               ::= { lPEntry 26 }

               lPNumNoState OBJECT-TYPE
               SYNTAX INTEGER (0..2147483647)
               MAX-ACCESS read-only
               STATUS current
               DESCRIPTION
               "This is the number of times there was no valid state to
               restore when needed by a rollback or when required to check
               prediction accuracy."
               ::= { lPEntry 27 }

               lPStatePred OBJECT-TYPE
               SYNTAX DisplayString
               MAX-ACCESS read-only
               STATUS current
               DESCRIPTION
               "This is the cached value of the state at the nearest
               time to the current time."
               ::= { lPEntry 28 }

               lPPktPred OBJECT-TYPE
               SYNTAX DisplayString
               MAX-ACCESS read-only
               STATUS current
               DESCRIPTION
               "This is the predicted value in a virtual message."
               ::= { lPEntry 29 }

               lPTdiff OBJECT-TYPE
               SYNTAX DisplayString
               MAX-ACCESS read-only
               STATUS current
               DESCRIPTION
               "This is the time difference between a predicted and an
               actual value."
               ::= { lPEntry 30 }

               lPStateError OBJECT-TYPE
               SYNTAX DisplayString
               MAX-ACCESS read-only
               STATUS current
               DESCRIPTION
               "This is the difference between the contents of an application
               value and the state value as seen within the virtual message."
               ::= { lPEntry 31 }

               lPUptime OBJECT-TYPE
               SYNTAX INTEGER (0..2147483647)
               --SYNTAX DisplayString
               MAX-ACCESS read-only
               STATUS current
               DESCRIPTION
               "This is the time in milliseconds that Atropos has been
               running on this node."
               ::= { lPEntry 32 }

               END

-- 
--    Copyright (C) The Internet Society (2002).  All Rights Reserved.
-- 
--    This document and translations of it may be copied and furnished to
--    others, and derivative works that comment on or otherwise explain it
--    or assist in its implementation may be prepared, copied, published
--    and distributed, in whole or in part, without restriction of any
--    kind, provided that the above copyright notice and this paragraph are
--    included on all such copies and derivative works.  However, this
--    document itself may not be modified in any way, such as by removing
--    the copyright notice or references to the Internet Society or other
--    Internet organizations, except as needed for the purpose of
--    developing Internet standards in which case the procedures for
--    copyrights defined in the Internet Standards process must be
--    followed, or as required to translate it into languages other than
--    English.
-- 
--    The limited permissions granted above are perpetual and will not be
--    revoked by the Internet Society or its successors or assigns.
-- 
--    This document and the information contained herein is provided on an
--    "AS IS" basis and THE INTERNET SOCIETY AND THE INTERNET ENGINEERING
--    TASK FORCE DISCLAIMS ALL WARRANTIES, EXPRESS OR IMPLIED, INCLUDING
--    BUT NOT LIMITED TO ANY WARRANTY THAT THE USE OF THE INFORMATION
--    HEREIN WILL NOT INFRINGE ANY RIGHTS OR ANY IMPLIED WARRANTIES OF
--    MERCHANTABILITY OR FITNESS FOR A PARTICULAR PURPOSE.
--
