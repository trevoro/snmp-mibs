SNMPEXT-MIB 

   --FORCE-INCLUDE <mib.h>
   --FORCE-INCLUDE <snmpdefs.h>
   --FORCE-INCLUDE <snmpstat.h>
   --FORCE-INCLUDE "mibproto.h"
 
	DEFINITIONS ::= BEGIN

	IMPORTS
		MODULE-IDENTITY, OBJECT-TYPE,IpAddress, Integer32
			FROM SNMPv2-SMI
		RowStatus,DisplayString
			FROM SNMPv2-TC
		TRAP-TYPE
			FROM RFC-1215
		snmpExt
			FROM APENT-MIB;

--SNMPEXT MIB

    apSnmpExtMib MODULE-IDENTITY
	   LAST-UPDATED "9707202000Z" -- Wed July 20 20:00:00 EST 1997
	   ORGANIZATION "ArrowPoint Communications Inc."
	   CONTACT-INFO
	   "                Steven Colby
	   Postal:               ArrowPoint Communications Inc.
				                 50 Nagog Park
				                 Acton, Massachusetts 01720
	   Tel:                   +1 978-206-3000  option 1
	   E-Mail:                support@arrowpoint.com"
       DESCRIPTION
			""
      ::= { snmpExt 1}



apSnmpExtTrapGeneric OBJECT-TYPE
	SYNTAX          INTEGER {
							enable(1),
							disable(0)
							}
	MAX-ACCESS      read-write
    STATUS          current
    DESCRIPTION
      "This object controls the state of Generic trap generation.  ArrowPoint
       supports the following generic traps: 1) Cold start, 2) Warm start,
       3) Link down, 4) Link up, 5) SNMP authentication failure.  SNMP
       authentication failure traps can be individually disallowed using 
       the snmpEnableAuthenTraps object."
	::= { snmpExt 2}

apSnmpExtTrapEnterprise OBJECT-TYPE
	SYNTAX          INTEGER {
							enable(1),
							disable(0)
							}
	MAX-ACCESS      read-write
    STATUS          current
    DESCRIPTION
      "This object controls the state of Enterprise trap generation.  RMON
       event traps are treated as enterprise traps."
	::= { snmpExt 3}

apSnmpExtCommunityTable OBJECT-TYPE
	SYNTAX          SEQUENCE OF APSNMPExtCommunityEntry
	MAX-ACCESS      not-accessible
	STATUS          current
	DESCRIPTION
		"A table of SNMP community information used to determine whether 
         read or write access is permitted to the MIBs.  A maximum of 5
         concurrent communities are supported."
	::= { snmpExt 4 }

apSnmpExtCommunityEntry OBJECT-TYPE
	SYNTAX          APSNMPExtCommunityEntry
	MAX-ACCESS      not-accessible
	STATUS          current
	DESCRIPTION
		"An SNMP community entry describing one community name"
	INDEX   { apSnmpExtCommunityName }
	::= { apSnmpExtCommunityTable 1 }

APSNMPExtCommunityEntry ::= SEQUENCE {
		apSnmpExtCommunityName   DisplayString,
		apSnmpExtCommunityType   INTEGER,
		apSnmpExtCommunityStatus RowStatus
}

apSnmpExtCommunityName OBJECT-TYPE
	SYNTAX          DisplayString (SIZE(1..12))
    MAX-ACCESS      read-create
	STATUS          current
	DESCRIPTION     
			"A community name used for SNMP access to this system"
	::= { apSnmpExtCommunityEntry 1}

apSnmpExtCommunityType OBJECT-TYPE
	SYNTAX  		INTEGER {
							 ro(0),
							 rw(1)
							}
	MAX-ACCESS      read-create
	STATUS  		current
	DESCRIPTION     
		"The privilge level of the associated community name when accessing
		 this system.  A community level of <ro> allows read-only access,
         a community level of <rw> allows read and write access."
	::= {apSnmpExtCommunityEntry 2}

apSnmpExtCommunityStatus OBJECT-TYPE
	SYNTAX          RowStatus
	MAX-ACCESS      read-create
	STATUS          current
	DESCRIPTION      
		"Status entry for this row "
	::= {apSnmpExtCommunityEntry 3}


apSnmpExtTrapTable OBJECT-TYPE
	SYNTAX          SEQUENCE OF APSNMPExtTrapEntry
	MAX-ACCESS      not-accessible
	STATUS          current
	DESCRIPTION
		""
	::= { snmpExt 5 }


apSnmpExtTrapEntry OBJECT-TYPE
	SYNTAX          APSNMPExtTrapEntry
	MAX-ACCESS      not-accessible
	STATUS          current
	DESCRIPTION
		"This table contains the configured trap hosts.  All entries in this
         table will receive SNMP traps when generated.  A maximum of 5
         concurrent trap hosts are supported."
	INDEX   { apSnmpExtTrapIp }
	::= { apSnmpExtTrapTable 1 }

APSNMPExtTrapEntry ::= SEQUENCE {
		apSnmpExtTrapIp          IpAddress,
		apSnmpExtTrapCommunity   DisplayString,
		apSnmpExtTrapStatus      RowStatus
}

apSnmpExtTrapIp OBJECT-TYPE
	SYNTAX          IpAddress
    MAX-ACCESS      read-create
	STATUS          current
	DESCRIPTION     
			"An IP Address of a host configured to receive traps"
	::= { apSnmpExtTrapEntry 1}

apSnmpExtTrapCommunity OBJECT-TYPE
	SYNTAX  		DisplayString (SIZE(1..12))
	MAX-ACCESS      read-create
	STATUS  		current
	DESCRIPTION     
		"The community name to use when sending traps to this device"
	::= {apSnmpExtTrapEntry 2}

apSnmpExtTrapStatus OBJECT-TYPE
	SYNTAX          RowStatus
	MAX-ACCESS      read-create
	STATUS          current
	DESCRIPTION      
		"Status entry for this row "
	::= {apSnmpExtTrapEntry 3}


apSnmpExtReloadConfigVal OBJECT-TYPE
	SYNTAX          Integer32
	MAX-ACCESS      read-write
    STATUS          current
    DESCRIPTION
      "This object is used to control apSnmpExtReloadSet, which provides
       a SNMP based reboot capability.  When this object is set to 0, SNMP
       based reboot is not allowed.  When this object is set between 1 -
       (2^32) - 2, the equivalent value must be written to apSnmpExtReloadSet
       to cause a reboot.  When this object is set to (2^32) -1, a reboot
       may be caused with any write value to apSnmpExtReloadSet.  For 
       security purposes this object always returns 0 on read"
	::= { snmpExt 6}

apSnmpExtReloadSet OBJECT-TYPE
	SYNTAX          Integer32
	MAX-ACCESS      read-write
    STATUS          current
    DESCRIPTION
      "This object provides SNMP based reboot capabilities.  The required
       set value to effect a reboot is explained in apSnmpExtReloadConfigVal."
	::= { snmpExt 7}

apSnmpExtServiceTraps OBJECT-TYPE
	SYNTAX          INTEGER
                    {
                    disable(0),
                    enable(1)
                    }
	MAX-ACCESS      read-write
    STATUS          current
    DESCRIPTION
      "This object controls the generation of ArrowPoint enterprise traps
       conincident with service transition.  See the trap definition in 
       the svcExt.mib name apSvcTransitionTrap."
	::= { snmpExt 8}

apSnmpExtLoginFailTraps OBJECT-TYPE
	SYNTAX          INTEGER
                    {
                    disable(0),
                    enable(1)
                    }
	MAX-ACCESS      read-write
    STATUS          current
    DESCRIPTION
      "This object controls the generation of ArrowPoint enterprise traps
       conincident with FTP/Console/Telnet authentication failure."
	::= { snmpExt 9}

apSnmpExtReloadTraps OBJECT-TYPE
	SYNTAX          INTEGER
                    {
                    disable(0),
                    enable(1)
                    }
	MAX-ACCESS      read-write
    STATUS          current
    DESCRIPTION
      "This object controls the generation of ArrowPoint enterprise traps
       conincident a system reload"
	::= { snmpExt 10}

apSnmpExtLastTrap OBJECT-TYPE
	SYNTAX          DisplayString (SIZE (1 .. 255))
	MAX-ACCESS      read-only
    STATUS          current
    DESCRIPTION
      "This object contains a string which details the last trap which was
       generated in the system"
	::= { snmpExt 11}

apSnmpExtRedundancyTraps OBJECT-TYPE
	SYNTAX          INTEGER
                    {
                    disable(0),
                    enable(1)
                    }
	MAX-ACCESS      read-write
    STATUS          current
    DESCRIPTION
      "This object controls the generation of ArrowPoint enterprise traps
	   on Redundancy state changes."
	::= { snmpExt 12}

apSnmpExtForceDumpConfigVal OBJECT-TYPE
	SYNTAX          Integer32
	MAX-ACCESS      read-write
    STATUS          current
    DESCRIPTION
      "This object is used to control apSnmpExtForceDump, which provides
       a SNMP based dump capability.  When this object is set to 0, SNMP
       based dumping is not allowed.  When this object is set between 1 -
       (2^32) - 2, the equivalent value must be written to apSnmpExtForceDump
       to cause a dump.  When this object is set to (2^32) -1, a dump
       may be caused with any write value to apSnmpExtReloadSet.  For 
       security purposes this object always returns 0 on read."
	::= { snmpExt 13}

apSnmpExtForceDumpSlot OBJECT-TYPE
	SYNTAX          Integer32
	MAX-ACCESS      read-write
    STATUS          current
    DESCRIPTION
      "This object provides SNMP based dumping capabilities on the
       CS800. This is the slot number of the module to force to dump
       and then reload. On the cs100 this object is not used. For
       security purposes this object always returns a 0."
	::= { snmpExt 14}

apSnmpExtForceDumpSubSlot OBJECT-TYPE
	SYNTAX          Integer32
	MAX-ACCESS      read-write
    STATUS          current
    DESCRIPTION
      "This object provides SNMP based dumping capabilities on the
       CS800. This is the sub-slot number of the module to force 
       to dump and then reload. On the cs100 this object is not used.
       For security purposes this object always returns a 0."
	::= { snmpExt 15}

apSnmpExtForceDump OBJECT-TYPE
	SYNTAX          Integer32
	MAX-ACCESS      read-write
    STATUS          current
    DESCRIPTION
      "This object provides SNMP based dumping capabilities. Setting
       this value to non-zero will force a dump and reload the unit.
       On a cs800 the apSnmpExtForceDumpSlot and apSnmapExtForceDumpSubSlot
       objects must be set to valid values or the setting of this object
       is ignored. For security purposes this object always returns a 0.
       The required set value to effect a reboot is explained in 
       apSnmpExtForceDumpConfigVal."
	::= { snmpExt 16}

apSnmpExtDosSynTraps OBJECT-TYPE
	SYNTAX          INTEGER
                    {
                    disable(0),
                    enable(1)
                    }
	MAX-ACCESS      read-write
    STATUS          current
    DESCRIPTION
      "This object controls the generation of ArrowPoint enterprise traps
       conincident with Denial of Service (DOS) SYN attacks. See the trap
       definition in the flowMgrExt.mib name apFlowMgrExtDosSynTrap."
	DEFVAL { disable }
	::= { snmpExt 17}

apSnmpExtDosLandTraps OBJECT-TYPE
	SYNTAX          INTEGER
                    {
                    disable(0),
                    enable(1)
                    }
	MAX-ACCESS      read-write
    STATUS          current
    DESCRIPTION
      "This object controls the generation of ArrowPoint enterprise traps
       conincident with Denial of Service (DOS) LAND attacks. See the trap
       definition in the flowMgrExt.mib name apFlowMgrExtDosLandTrap."
	DEFVAL { disable }
	::= { snmpExt 18}

apSnmpExtDosIllegalTraps OBJECT-TYPE
	SYNTAX          INTEGER
                    {
                    disable(0),
                    enable(1)
                    }
	MAX-ACCESS      read-write
    STATUS          current
    DESCRIPTION
      "This object controls the generation of ArrowPoint enterprise traps
       conincident with Denial of Service (DOS) Illegal packet format 
       attacks. See the trap definition in the flowMgrExt.mib name 
       apFlowMgrExtDosIllegalTrap."
	DEFVAL { disable }
	::= { snmpExt 19}

apSnmpExtDosPingTraps OBJECT-TYPE
	SYNTAX          INTEGER
                    {
                    disable(0),
                    enable(1)
                    }
	MAX-ACCESS      read-write
    STATUS          obsolete
    DESCRIPTION
      "This object controls the generation of ArrowPoint enterprise traps
       conincident with Denial of Service (DOS) Ping of Death attacks. 
       See the trap definition in the flowMgrExt.mib name 
       apFlowMgrExtDosPingTrap."
	DEFVAL { disable }
	::= { snmpExt 20}

apSnmpExtDosSmurfTraps OBJECT-TYPE
	SYNTAX          INTEGER
                    {
                    disable(0),
                    enable(1)
                    }
	MAX-ACCESS      read-write
    STATUS          current
    DESCRIPTION
      "This object controls the generation of ArrowPoint enterprise traps
       conincident with Denial of Service (DOS) Smurf attacks. 
       See the trap definition in the flowMgrExt.mib name 
       apFlowMgrExtDosSmurfTrap."
	DEFVAL { disable }
	::= { snmpExt 21}

apSnmpExtDosSynTrapThreshold OBJECT-TYPE
	SYNTAX          INTEGER ( 1..65535 )
	MAX-ACCESS      read-write
    STATUS          current
    DESCRIPTION
      "This object controls the generation of ArrowPoint enterprise traps
       conincident with Denial of Service (DOS) SYN attacks. It is the
       threshold over which a trap will be generated."
	DEFVAL { 10 }
	::= { snmpExt 22}

apSnmpExtDosLandTrapThreshold OBJECT-TYPE
	SYNTAX          INTEGER ( 1..65535 )
	MAX-ACCESS      read-write
    STATUS          current
    DESCRIPTION
      "This object controls the generation of ArrowPoint enterprise traps
       conincident with Denial of Service (DOS) LAND attacks. It is the
       threshold over which a trap will be generated."
    DEFVAL { 1 }
	::= { snmpExt 23}

apSnmpExtDosIllegalTrapThreshold OBJECT-TYPE
	SYNTAX          INTEGER ( 1..65535 )
	MAX-ACCESS      read-write
    STATUS          current
    DESCRIPTION
      "This object controls the generation of ArrowPoint enterprise traps
       conincident with Denial of Service (DOS) attacks due to invalid
       packets. It is the threshold over which a trap will be generated."
    DEFVAL { 1 }
   	::= { snmpExt 24}

apSnmpExtDosPingTrapThreshold OBJECT-TYPE
	SYNTAX          INTEGER ( 1..65535 )
	MAX-ACCESS      read-write
    STATUS          obsolete
    DESCRIPTION
      "This object controls the generation of ArrowPoint enterprise traps
       conincident with Denial of Service (DOS) Ping of Death attacks. 
       It is the threshold over which a trap will be generated."
    DEFVAL { 30 }
	::= { snmpExt 25}

apSnmpExtDosSmurfTrapThreshold OBJECT-TYPE
	SYNTAX          INTEGER ( 1..65535 )
	MAX-ACCESS      read-write
    STATUS          current
    DESCRIPTION
      "This object controls the generation of ArrowPoint enterprise traps
       conincident with Denial of Service (DOS) Smurf attacks. 
       It is the threshold over which a trap will be generated."
    DEFVAL { 1 }
	::= { snmpExt 26}

apSnmpExtReloadTrap TRAP-TYPE
	ENTERPRISE snmpExt
	DESCRIPTION
	   "This trap is generated when a reboot of the system is performed."
	::= 1
END
