-- ZyXEL Communications Corporation
-- Private Enterprise MIB definition 
  
-- This file describes the ZyXEL Communications Corporation Enterprise MIB.
-- It contains ZyXEL products OIDs, and common managed objects.

-- $Log: zyxel.mib $ 
-- Revision 1.65  2011/03/04 08:54:17  mandy 
-- Add ies5106 and ies5112 
-- Revision 1.64  2011/03/04 08:37:32  mandy 
-- Add ves1724-58b 
-- Revision 1.63  2010/11/24 11:03:16  jennyhsu 
-- add ves1602fe57 
-- Revision 1.62  2010/09/17 02:20:45  mandy 
-- Add gponSeries, gponSeriesCommon, and o-00240v-p 
-- Revision 1.61  2010/02/11 06:52:45  jennyhsu 
-- Add ves1608fe57 
-- Revision 1.60  2009/10/02 11:23:01  jennyhsu 
-- Add VES-1608FE-53A 
-- Revision 1.59  2009/09/15 06:43:25  jennyhsu 
-- Add EONU24240/16160/2400/1600 
-- Revision 1.58  2009/04/21 06:25:38  jennyhsu 
-- Add gs2200-48 
-- Revision 1.57  2009/04/09 10:40:05  TM3003EWTMi 
-- Add VES1624FTV55A 
-- Revision 1.56  2009/03/19 06:03:17  jennyhsu 
-- Add VES-1616CTB-54 and VES-1624CTB-54 
-- Revision 1.55  2009/03/11 08:27:13  jennyhsu 
-- Change OLT-2300-22 OLT-2300v3 
-- Revision 1.54  2009/01/09 07:09:32  jennyhsu 
-- Assigned OID for VES-1616FT-54 and OLT-2300-22.  
-- Revision 1.53  2008/11/06 06:54:15  TM3003EWTMi 
-- Revision 1.52  2008/07/24 09:44:56  jack 
-- Add ves1616fb35, ves1608pe35 to vesSeries. 
-- Revision 1.51  2008/07/15 02:13:05  jack 
-- Add ves1616fe55a, ves1624ft55a to vesSeries. 
-- Revision 1.50  2008/07/07 08:03:25  jack 
-- Add mes3528, xgs2726 in esSeries 
-- Revision 1.49  2008/06/06 07:57:27  jack 
-- Revise ESSeries product: revise mm7201 to ms7206, mm7201 is a management card for ms7206. 
-- Revision 1.48  2008/06/06 07:12:20  jack 
-- Add ves1616cta54,ves1624cta54,ves1608cea54,ves1616cea54	 in vesSeries 
-- Revision 1.47  2008/05/28 05:53:57  jack 
-- Add PON series product: olt2300, olt1308s22 
-- Revision 1.46  2008/05/21 06:59:47  jack 
-- Add GS-4012F NCIC 
-- Revision 1.45  2008/03/31 03:12:50  jack 
-- Add ies5006. 
-- Revision 1.44  2008/03/26 07:10:33  jack 
-- Chang the OID of vopSeries to '16'. 
-- Revision 1.43  2008/03/24 06:03:02  jack 
-- Add vopSeries, vopSeriesCommon and vop1224-61. 
-- Revision 1.42  2008/01/08 06:36:16  jack 
-- add ves1608fc54, ves1616fc54, ves1624ft54, ves1624ftv54. 
-- Revision 1.41  2007/12/21 03:17:59  jack 
-- mark gs2012 with OID 'esSeriesCommon.25' 
-- Added comments  jack [2007/12/21 03:27:06 GMT] 
-- mark gs3012, not gs2012 
-- Revision 1.40  2007/11/14 01:28:17  jack 
-- Revision 1.39  2007/10/19 03:50:36  jack 
-- Revision 1.38  2007/09/11 03:00:43  jack 
-- Add VES-1624FA34 
-- Revision 1.37  2007/07/16 08:49:29  jack 
-- Add ies708-22a-stuc and ies708-22a-stur. 
-- Revision 1.36  2007/06/25 08:07:36  jack 
-- Add VES-1624FT. 
-- Revision 1.35  2007/05/16 03:52:54  jack 
-- Add an OID for IES-1248-51V. 
-- Revision 1.34  2007/04/26 05:49:43  jack 
-- Add OID for VES1616FA54/55, VES1624FA54/55 
-- Revision 1.33  2007/01/26 10:25:14  jack 
-- Add VES1616FA34-co4 and VES1616FA35-co4, and shift the OIDs of VES1608FA34 and VES1608FA35. 
-- Revision 1.32  2007/01/26 08:14:25  jack 
-- Add VES1608FA34 and VES1608FA35. 
-- Revision 1.31  2007/01/02 11:28:10  jack 
-- Add the object ves1616fa44. 
-- Revision 1.30  2006/12/21 06:20:35  jack 
-- Add ES-2024PWR, ES-3724, ES-2108F, ES-2226, ES-3124F, VES1624-FA44. 
-- Revision 1.29  2006/06/02 09:11:03  Jack 
-- Add ES-3148, ES-2108, ES-2108G, GS-4012F, ES-2108PWR, ES-2108LC, ES-2048, ES-4124, GS-3012, ES-3124-4F and WiMAX. 
-- Revision 1.27  2006/05/12 08:14:18  Jack 
-- Add the object 'sam1216-22'. 
-- Revision 1.26  2006/05/02 11:33:36  Jack 
-- Add vsg1200v2 
-- Revision 1.25  2006/03/06 09:36:29  Jack 
-- Change oid of IES5005 
-- Revision 1.24  2005/11/17 02:32:23  mandy 
-- Add alc1224-51, alc1224-53 
-- Revision 1.23  2005/10/27 01:49:26  Mandy 
-- add IES-5000, IES-5005 
-- Revision 1.22  2005/10/24 08:56:40  Jack 
-- Add ves1616f34, ves1616f44 and ves1624f44. 
-- Revision 1.21  2005/09/06 09:14:25  Jack 
-- Add ies1248-51, ies1248-53 
-- Revision 1.20  2005/06/17 05:33:47  jackho 
-- Revision 1.19  2005/06/09 07:29:05  jennyhsu 
-- Revision 1.18  2005/05/04 01:15:38  jennyhsu 
-- Revision 1.17  2005/03/07 11:22:32  Admin 
-- change IES1248-71 and IES1248-73 OID 
-- Revision 1.16  2004/06/08 10:13:33  jenny 
--  
-- Revision 1.15  2004/05/20 08:24:00  jennyhsu 
-- Revision 1.14  2004/05/19 10:47:37  jennyhsu 
-- add system OID for new products 
-- Revision 1.13  2004/03/01 07:06:56  jennyhsu 
-- add object alc1124-71 
-- Revision 1.12  2004/02/25 08:41:34  jennyhsu 
-- add vlc1124 and ves1124 
-- Revision 1.11  2003/09/10 00:58:52  jennyhsu 
-- Add product OID for ves1416  
-- Revision 1.10  2003/05/27 08:12:05  jennyhsu 
-- Add object accessSwitchCommonATM 
-- Revision 1.9  2003/05/07 06:46:20  jennyhsu 
-- Remove ves2000 
-- Revision 1.8  2003/03/28 01:36:38  jennyhsu 
-- Add OID for ves1316, vlc1316 and ves2000 
-- Revision 1.7  2003/03/10 02:54:32  jennyhsu 
-- Add ether switch products 
-- Revision 1.6  2002/11/12 07:41:52  jennyhsu 
-- Revision 1.5  2002/09/02 11:48:40  jennyhsu 
-- Revision 1.4  2002/01/10 05:10:37  jennyhsu 
-- Revision 1.3  2001/10/26 02:50:02  jennyhsu 
-- Revision 1.2  2001/10/03 09:03:20  jennyhsu 
-- Revision 1.1  2001/08/25 06:01:16  jennyhsu 
-- Initial revision 

    ZYXEL-MIB DEFINITIONS ::= BEGIN

    IMPORTS
	enterprises		FROM RFC1155-SMI;
	
	

	zyxel			OBJECT IDENTIFIER ::= { enterprises 890 }
	
	products		OBJECT IDENTIFIER ::= { zyxel 1 }
	
	prestige 		OBJECT IDENTIFIER ::= { products 2 }
	rack			OBJECT IDENTIFIER ::= { products 3 }
	dslam			OBJECT IDENTIFIER ::= { products 4 }
	accessSwitch  		OBJECT IDENTIFIER ::= { products 5 }
	zywall			OBJECT IDENTIFIER ::= { products 6 }
	atmEncryptor		OBJECT IDENTIFIER ::= { products 7 }
	serviceGateway  	OBJECT IDENTIFIER ::= { products 8 }
	proWireless	  	OBJECT IDENTIFIER ::= { products 9 }
	wirelessController	OBJECT IDENTIFIER ::= { products 10 }
	ipav			OBJECT IDENTIFIER ::= { products 11 }
	wimax		  	OBJECT IDENTIFIER ::= { products 12 }

	-- Prestige products

	prestigeCommon		OBJECT IDENTIFIER ::= { prestige 1 }
	p200Series		OBJECT IDENTIFIER ::= { prestige 2 }
	p300Series		OBJECT IDENTIFIER ::= { prestige 3 }
	p400Series		OBJECT IDENTIFIER ::= { prestige 4 }
	p500Series		OBJECT IDENTIFIER ::= { prestige 5 }
	p600Series		OBJECT IDENTIFIER ::= { prestige 6 }
	p641			OBJECT IDENTIFIER ::= { p600Series 1 }
	p642			OBJECT IDENTIFIER ::= { p600Series 2 }
	p643			OBJECT IDENTIFIER ::= { p600Series 3 }	
	p700Series		OBJECT IDENTIFIER ::= { prestige 7 }
	p794ra			OBJECT IDENTIFIER ::= { p700Series 1 }
	p794rb			OBJECT IDENTIFIER ::= { p700Series 2 }	
	p800Series		OBJECT IDENTIFIER ::= { prestige 8 }
	p900Series		OBJECT IDENTIFIER ::= { prestige 9 }
	
	-- Access Switch products
	accessSwitchCommon	OBJECT IDENTIFIER ::= { accessSwitch 1 }
	aes100			OBJECT IDENTIFIER ::= { accessSwitch 2 }
	pes100			OBJECT IDENTIFIER ::= { accessSwitch 3 }
	ves1012			OBJECT IDENTIFIER ::= { accessSwitch 4 }
	sesSeries		OBJECT IDENTIFIER ::= { accessSwitch 5 }
	p1600			OBJECT IDENTIFIER ::= { accessSwitch 6 }
	p1400			OBJECT IDENTIFIER ::= { accessSwitch 7 }
	esSeries		OBJECT IDENTIFIER ::= { accessSwitch 8 }
	aes100-1		OBJECT IDENTIFIER ::= { accessSwitch 9 }
	pes1014			OBJECT IDENTIFIER ::= { accessSwitch 10 }
	aesSeries		OBJECT IDENTIFIER ::= { accessSwitch 11 }
	vesSeries		OBJECT IDENTIFIER ::= { accessSwitch 12 }
	iesSeries		OBJECT IDENTIFIER ::= { accessSwitch 13 }
	accessSwitchCommonATM	OBJECT IDENTIFIER ::= { accessSwitch 14 }	
	ponSeries		OBJECT IDENTIFIER ::= { accessSwitch 15 }
	vopSeries		OBJECT IDENTIFIER ::= { accessSwitch 16 }
	gponSeries		OBJECT IDENTIFIER ::= { accessSwitch 17 }	
	
	-- SES Series
	sesSeriesCommon		OBJECT IDENTIFIER ::= { sesSeries 1 }
	sam1008			OBJECT IDENTIFIER ::= { sesSeries 2 }
	ses1024			OBJECT IDENTIFIER ::= { sesSeries 3 }
	slc1024			OBJECT IDENTIFIER ::= { sesSeries 4 }
	slc1224-22		OBJECT IDENTIFIER ::= { sesSeries 5 }
	sam1216-22		OBJECT IDENTIFIER ::= { sesSeries 6 }
	ies708-22a-stuc		OBJECT IDENTIFIER ::= { sesSeries 7 }
	ies708-22a-stur		OBJECT IDENTIFIER ::= { sesSeries 8 }	
			
	-- ES Series	
	esSeriesCommon		OBJECT IDENTIFIER ::= { esSeries 1 }
	ees1024af		OBJECT IDENTIFIER ::= { esSeries 2 }
	es2008			OBJECT IDENTIFIER ::= { esSeries 3 }
	es2008-gtp		OBJECT IDENTIFIER ::= { esSeries 4 }
	es2008-sc		OBJECT IDENTIFIER ::= { esSeries 5 }
	es2008-sc30		OBJECT IDENTIFIER ::= { esSeries 6 }
	es3024			OBJECT IDENTIFIER ::= { esSeries 7 }
	es4024			OBJECT IDENTIFIER ::= { esSeries 8 }
	es2024			OBJECT IDENTIFIER ::= { esSeries 9 }
	gs3012			OBJECT IDENTIFIER ::= { esSeries 10 }
	gs3012f			OBJECT IDENTIFIER ::= { esSeries 11 }
	es3124			OBJECT IDENTIFIER ::= { esSeries 12 }
	gs4024			OBJECT IDENTIFIER ::= { esSeries 13 }
	es3124pwr		OBJECT IDENTIFIER ::= { esSeries 14 }
	gs2024			OBJECT IDENTIFIER ::= { esSeries 15 }
	es2024a			OBJECT IDENTIFIER ::= { esSeries 16 }
	es3148			OBJECT IDENTIFIER ::= { esSeries 17 }
	es2108			OBJECT IDENTIFIER ::= { esSeries 18 }
	es2108g			OBJECT IDENTIFIER ::= { esSeries 19 }
	gs4012f			OBJECT IDENTIFIER ::= { esSeries 20 }
	es2108pwr		OBJECT IDENTIFIER ::= { esSeries 21 }
	es2108lc		OBJECT IDENTIFIER ::= { esSeries 22 }
	es2048			OBJECT IDENTIFIER ::= { esSeries 23 }
	es4124			OBJECT IDENTIFIER ::= { esSeries 24 }
--	gs3012			OBJECT IDENTIFIER ::= { esSeries 25 }
	es3124-4f		OBJECT IDENTIFIER ::= { esSeries 26 }
	es2024pwr		OBJECT IDENTIFIER ::= { esSeries 27 }
	es3724			OBJECT IDENTIFIER ::= { esSeries 28 }
	es2108f			OBJECT IDENTIFIER ::= { esSeries 29 }
	es2226			OBJECT IDENTIFIER ::= { esSeries 30 }
	es3124f			OBJECT IDENTIFIER ::= { esSeries 31 }
	es1528			OBJECT IDENTIFIER ::= { esSeries 32 }
	es1552			OBJECT IDENTIFIER ::= { esSeries 33 }
	ms7206			OBJECT IDENTIFIER ::= { esSeries 34 }
	gs2724			OBJECT IDENTIFIER ::= { esSeries 35 }
	gs1524			OBJECT IDENTIFIER ::= { esSeries 36 }
	gs1548			OBJECT IDENTIFIER ::= { esSeries 37 }
	es305			OBJECT IDENTIFIER ::= { esSeries 38 }
	xsg4528f		OBJECT IDENTIFIER ::= { esSeries 39 }
	es3528			OBJECT IDENTIFIER ::= { esSeries 40 }
	es315			OBJECT IDENTIFIER ::= { esSeries 41 }
	es315f			OBJECT IDENTIFIER ::= { esSeries 42 }
	gs2726			OBJECT IDENTIFIER ::= { esSeries 43 }
	gs2750			OBJECT IDENTIFIER ::= { esSeries 44 }
	mes3728			OBJECT IDENTIFIER ::= { esSeries 45 }
	xgs4728f		OBJECT IDENTIFIER ::= { esSeries 46 }
	mgs3712			OBJECT IDENTIFIER ::= { esSeries 47 }
	mgs3712f		OBJECT IDENTIFIER ::= { esSeries 48 }
	es2105			OBJECT IDENTIFIER ::= { esSeries 49 }
	gs4012f-ncic		OBJECT IDENTIFIER ::= { esSeries 50 }  
	mes3528			OBJECT IDENTIFIER ::= { esSeries 51 } 
	xgs2726			OBJECT IDENTIFIER ::= { esSeries 52 }
	gs2200-48		OBJECT IDENTIFIER ::= { esSeries 53 }
		
	-- AES Series	
	aesSeriesCommon		OBJECT IDENTIFIER ::= { aesSeries 1 }
	aes1024			OBJECT IDENTIFIER ::= { aesSeries 2 }
	alc1024-61		OBJECT IDENTIFIER ::= { aesSeries 3 }
	aam1008-63		OBJECT IDENTIFIER ::= { aesSeries 4 }
	alc1024-63		OBJECT IDENTIFIER ::= { aesSeries 5 }
	aam1008-61		OBJECT IDENTIFIER ::= { aesSeries 6 }
	alc1224-71		OBJECT IDENTIFIER ::= { aesSeries 7 }
	ies1248-71		OBJECT IDENTIFIER ::= { aesSeries 9 }
	ies1248-73		OBJECT IDENTIFIER ::= { aesSeries 10 }
	aam1212-51		OBJECT IDENTIFIER ::= { aesSeries 11 }
	aam1212-53		OBJECT IDENTIFIER ::= { aesSeries 12 }
	ies1248-51		OBJECT IDENTIFIER ::= { aesSeries 13 }
	ies1248-53		OBJECT IDENTIFIER ::= { aesSeries 14 }
	alc1224-51		OBJECT IDENTIFIER ::= { aesSeries 15 }
	alc1224-53		OBJECT IDENTIFIER ::= { aesSeries 16 }
	ies1248-51v		OBJECT IDENTIFIER ::= { aesSeries 17 }
	
	-- VES Series			
	vesSeriesCommon		OBJECT IDENTIFIER ::= { vesSeries 1 }
	ves1008			OBJECT IDENTIFIER ::= { vesSeries 2 }
--	vmb2024			OBJECT IDENTIFIER ::= { vesSeries 3 }
	ves1024			OBJECT IDENTIFIER ::= { vesSeries 4 }
	vlc1012			OBJECT IDENTIFIER ::= { vesSeries 5 }
	ves1316			OBJECT IDENTIFIER ::= { vesSeries 6 }	
	ves1416			OBJECT IDENTIFIER ::= { vesSeries 7 }
	vlc1124			OBJECT IDENTIFIER ::= { vesSeries 8 }
	ves1124			OBJECT IDENTIFIER ::= { vesSeries 9 }
	ves1616f34		OBJECT IDENTIFIER ::= { vesSeries 10 }
	ves1616f44		OBJECT IDENTIFIER ::= { vesSeries 11 }
	ves1624f44		OBJECT IDENTIFIER ::= { vesSeries 12 }
	ves1624fa44		OBJECT IDENTIFIER ::= { vesSeries 13 }
	ves1616fa44		OBJECT IDENTIFIER ::= { vesSeries 14 }
	ves1616fa34-co4		OBJECT IDENTIFIER ::= { vesSeries 15 }
	ves1616fa35-co4		OBJECT IDENTIFIER ::= { vesSeries 16 }	
	ves1608fa34		OBJECT IDENTIFIER ::= { vesSeries 17 }
	ves1608fa35		OBJECT IDENTIFIER ::= { vesSeries 18 }
	ves1616fa54		OBJECT IDENTIFIER ::= { vesSeries 19 }	
	ves1624fa54		OBJECT IDENTIFIER ::= { vesSeries 20 }	
	ves1616fa55		OBJECT IDENTIFIER ::= { vesSeries 21 }	
	ves1624fa55		OBJECT IDENTIFIER ::= { vesSeries 22 }
	ves1624ft			OBJECT IDENTIFIER ::= { vesSeries 23 }
	ves1624fa34		OBJECT IDENTIFIER ::= { vesSeries 24 }
	ves1608fc54		OBJECT IDENTIFIER ::= { vesSeries 25 }
	ves1616fc54		OBJECT IDENTIFIER ::= { vesSeries 26 }
	ves1624ft54		OBJECT IDENTIFIER ::= { vesSeries 27 }
	ves1624ftv54		OBJECT IDENTIFIER ::= { vesSeries 28 }
	ves1616cta54		OBJECT IDENTIFIER ::= { vesSeries 29 }
	ves1624cta54		OBJECT IDENTIFIER ::= { vesSeries 30 }
	ves1608cea54		OBJECT IDENTIFIER ::= { vesSeries 31 }
	ves1616cea54		OBJECT IDENTIFIER ::= { vesSeries 32 }
	ves1616fe55a		OBJECT IDENTIFIER ::= { vesSeries 33 }
	ves1624ft55a		OBJECT IDENTIFIER ::= { vesSeries 34 }
	ves1616fb35		OBJECT IDENTIFIER ::= { vesSeries 35 }
	ves1608pe35		OBJECT IDENTIFIER ::= { vesSeries 36 }
	ves1616fe53a 		OBJECT IDENTIFIER ::= { vesSeries 37 }
	ves1616ft54		OBJECT IDENTIFIER ::= { vesSeries 38 }
	ves1616ctb54		OBJECT IDENTIFIER ::= { vesSeries 39 }
	ves1624ctb54		OBJECT IDENTIFIER ::= { vesSeries 40 }
	ves1624ftv55a		OBJECT IDENTIFIER ::= { vesSeries 41 }
	ves1608fe53a		OBJECT IDENTIFIER ::= { vesSeries 42 }
	ves1608fe57		OBJECT IDENTIFIER ::= { vesSeries 43 }
        ves1602fe57             OBJECT IDENTIFIER ::= { vesSeries 44 }
        ves1724-58b			OBJECT IDENTIFIER ::= { vesSeries 45 }

	-- IES Series	
	iesSeriesCommon		OBJECT IDENTIFIER ::= { iesSeries 1 }			
	ies2000			OBJECT IDENTIFIER ::= { iesSeries 2 }
	ies3000			OBJECT IDENTIFIER ::= { iesSeries 3 }
	ies5000			OBJECT IDENTIFIER ::= { iesSeries 5 }
	ies5005			OBJECT IDENTIFIER ::= { iesSeries 7 }
	ies6000			OBJECT IDENTIFIER ::= { iesSeries 8 }
	ies5006			OBJECT IDENTIFIER ::= { iesSeries 9 }
	ies5106			OBJECT IDENTIFIER ::= { iesSeries 10 }
	ies5112			OBJECT IDENTIFIER ::= { iesSeries 11 }
	
	-- PON Series
	olt1308			OBJECT IDENTIFIER ::= { ponSeries 1 }
	lt20h			OBJECT IDENTIFIER ::= { ponSeries 2 }
	olt2300-12		OBJECT IDENTIFIER ::= { ponSeries 3 }
	olt1308s22		OBJECT IDENTIFIER ::= { ponSeries 4 }
	olt2300v3		OBJECT IDENTIFIER ::= { ponSeries 5 }
	eonu24240		OBJECT IDENTIFIER ::= { ponSeries 6 }
	eonu16160		OBJECT IDENTIFIER ::= { ponSeries 7 }
	eonu2400		OBJECT IDENTIFIER ::= { ponSeries 8 }
	eonu1600		OBJECT IDENTIFIER ::= { ponSeries 9 }

	-- VOP Series
	vopSeriesCommon		OBJECT IDENTIFIER ::= { vopSeries 1 }			
	vop1224-61		OBJECT IDENTIFIER ::= { vopSeries 2 }
	
	-- GPON Series
	gponSeriesCommon		OBJECT IDENTIFIER ::= { gponSeries 1 }			
	o-00240v-p		OBJECT IDENTIFIER ::= { gponSeries 2 }
	
	-- DSLAM products
	dslamCommon             OBJECT IDENTIFIER ::= { dslam 1 }
		
	-- Service Gateway products
	serviceGWCommon			OBJECT IDENTIFIER ::= { serviceGateway 1 }
	vsg1000				OBJECT IDENTIFIER ::= { serviceGateway 2 }
	vsg1200				OBJECT IDENTIFIER ::= { serviceGateway 3 }
	vsg1200v2			OBJECT IDENTIFIER ::= { serviceGateway 4 }
	
END
