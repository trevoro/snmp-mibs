-- *****************************************************************
-- tiaranet-qos.mib: Tiara Networks Quality of Service MIB
--
-- Feb 07 2000, mkumar
--
-- Copyright (c) 1999-2000 by Tiara Networks, Inc.
-- All rights reserved.
--
-- *****************************************************************

TIARA-QOS-MIB DEFINITIONS ::= BEGIN

IMPORTS
        MODULE-IDENTITY, OBJECT-TYPE,
        IpAddress, Integer32, Counter32    FROM SNMPv2-SMI
        DisplayString                      FROM RFC1213-MIB
        TruthValue                         FROM SNMPv2-TC
        tiaraIpIfIndex                     FROM TIARA-IP-MIB
        tiaraMgmt                          FROM TIARA-NETWORKS-SMI;

tiaraQosMib MODULE-IDENTITY
        LAST-UPDATED   "0006100000Z" 
        ORGANIZATION   "Tiara Networks Inc."
        CONTACT-INFO 
                       "Tiara Networks
                        Customer Support

                        525 Race Street, Suite 100,
                        San Jose, CA 95126
                        USA

                        Tel: +1 408-216-4700
                        Fax: +1 408-216-4701
 
                        E-mail: support@tiaranetworks.com"

        DESCRIPTION     "QoS MIB for configuring Quality of Service
                        parameters on a WAN interface."
        REVISION        "0002070000Z" 
        DESCRIPTION     "Initial revision"

        ::= { tiaraMgmt 17 }

-- RedConfigTable definition
-- This table consists of all the parameters that are needed to configure
-- Random Early Detection (RED) on a given WAN interface. When a WAN
-- interface is first configured, default values are set for these
-- parameters.

tiaraRedConfigTable     OBJECT-TYPE
        SYNTAX              SEQUENCE OF TiaraRedConfigEntry
        MAX-ACCESS          not-accessible
        STATUS              current
        DESCRIPTION         "This table consists of all parameters that are
                            needed to configure RED on a WAN interface."
        ::= { tiaraQosMib 1 }

tiaraRedConfigEntry     OBJECT-TYPE
        SYNTAX              TiaraRedConfigEntry
        MAX-ACCESS          not-accessible
        STATUS              current
        DESCRIPTION         "Describes an entry in the RED configuration
                            table."
        INDEX               { tiaraIpIfIndex }
        ::= { tiaraRedConfigTable 1 }
 
TiaraRedConfigEntry ::= SEQUENCE {
        redTxMaxThreshold   Integer32,
        redTxMinThreshold   Integer32 ,
        redTxWqBiasFactor   Integer32 (3..20),
        redTxEnable         TruthValue
        }
 
redTxMaxThreshold       OBJECT-TYPE
        SYNTAX              Integer32
        MAX-ACCESS          read-write
        STATUS              current
        DESCRIPTION         "This is the upper limit for the average queue
                            size for a given WAN interface. If the average
                            queue size exceeds this value, RED drops all
                            packets that are destined for that WAN interface.
                            When a WAN interface is created, the maximum 
                            threshold is initialized to three times the minimum 
                            threshold. Setting maximum threshold to greater 
                            than two times minimum threshold is recommended for 
                            proper operation."
        ::= { tiaraRedConfigEntry 1 }
 
redTxMinThreshold       OBJECT-TYPE
        SYNTAX              Integer32
        MAX-ACCESS          read-write
        STATUS              current
        DESCRIPTION         "This is the threshold at which RED begins
                            dropping packets. When the average queue size for
                            a WAN interface increases above the minimum 
                            threshold, RED drops packets with a certain 
                            probability that increases linearly as the average 
                            queue size increases from the minimum to the maximum 
                            threshold. Below the minimum threshold, RED allows 
                            all packets. When a WAN interface is created, the 
                            minimum threshold is initialized to a value that is 
                            dependent on the bandwidth of the interface. Setting 
                            the minimum threshold to less than this value may 
                            cause unnecessary packet drops at close to 100%
                            utilization."
        ::= { tiaraRedConfigEntry 2 }
 
redTxWqBiasFactor       OBJECT-TYPE
        SYNTAX              Integer32 (3..20)
        MAX-ACCESS          read-write
        STATUS              current
        DESCRIPTION         "This is the exponential weighting/bias factor
                            used to calculate the moving average of the queue
                            size. A higher value smooths out the peaks
                            and troughs in the instantaneous queue size and, hence, 
                            better accomodates bursts. A lower value is more
                            responsive to changes in queue size. It is 
                            important to select the optimum value. Using
                            the default of 5 is recommended."
        ::= { tiaraRedConfigEntry 3 }
 
redTxEnable             OBJECT-TYPE
        SYNTAX              TruthValue
        MAX-ACCESS          read-write
        STATUS              current
        DESCRIPTION         "This is used to enable or disable RED on a WAN
                            interface. RED is enabled by default."
        ::= { tiaraRedConfigEntry 4 }
         
 
-- red Stats Table
-- This table gives all statistics related to Random Early Detection (RED)
-- on a given WAN interface.
 
tiaraRedStatTable       OBJECT-TYPE
        SYNTAX              SEQUENCE OF TiaraRedStatEntry
        MAX-ACCESS          not-accessible
        STATUS              current
        DESCRIPTION         "This table gives RED statistics for a given WAN
                            interface."
        ::= { tiaraQosMib 2 }
 
tiaraRedStatEntry       OBJECT-TYPE
        SYNTAX              TiaraRedStatEntry
        MAX-ACCESS          not-accessible
        STATUS              current
        DESCRIPTION         "Describes an entry in the RED statistics table."
        INDEX               { tiaraIpIfIndex }
        ::= { tiaraRedStatTable 1 }
 
TiaraRedStatEntry ::= SEQUENCE {
        redTxLoanedCount                Counter32,
        redTxMaxLoanedCount             Counter32,
        redTxAvgQueueSize               Counter32,
        redTxMaxAvgQueueSize            Counter32,
        redTxDropRate                   Counter32,
        redTxMinThresholdSuccess        Counter32,
        redTxMaxThresholdFailure        Counter32,
        redTxMinMaxRangeSuccess         Counter32,
        redTxMinMaxRangeFailure         Counter32,
        redTxControlSuccess             Counter32
    }
    
redTxLoanedCount        OBJECT-TYPE
        SYNTAX              Counter32
        MAX-ACCESS          read-only
        STATUS              current
        DESCRIPTION         "This is the instantaneous queue size measured by
                            RED for a given WAN interface."
        ::= { tiaraRedStatEntry 1 }
    
redTxMaxLoanedCount     OBJECT-TYPE
        SYNTAX              Counter32
        MAX-ACCESS          read-only
        STATUS              current
        DESCRIPTION         "This is the maximum instantaneous queue size
                            seen on a given WAN interface. In other words,
                            it is the maximum number of packets that had been
                            queued for transmission on the WAN interface."
        ::= { tiaraRedStatEntry 2 }
    
redTxAvgQueueSize       OBJECT-TYPE
        SYNTAX              Counter32
        MAX-ACCESS          read-only
        STATUS              current
        DESCRIPTION         "This is the current value of the average queue
                            size on a given WAN interface and is a measure of
                            congestion on that interface. RED attempts to 
                            keep this value between the minimum and maximum 
                            thresholds." 
        ::= { tiaraRedStatEntry 3 }

redTxMaxAvgQueueSize    OBJECT-TYPE 
        SYNTAX              Counter32
        MAX-ACCESS          read-only
        STATUS              current
        DESCRIPTION         "This is the maximum value that the average queue
                            size on a given WAN interface has reached."
        ::= { tiaraRedStatEntry 4 }

redTxDropRate           OBJECT-TYPE 
        SYNTAX              Counter32
        MAX-ACCESS          read-only
        STATUS              current
        DESCRIPTION         "This is the rate at which RED drops packets
                            when the average queue size is between the minimum
                            and maximum thresholds. A value of N indicates that
                            one out of N packets will be dropped."
        ::= { tiaraRedStatEntry 5 }

redTxMinThresholdSuccess    OBJECT-TYPE
        SYNTAX                  Counter32
        MAX-ACCESS              read-only
        STATUS                  current
        DESCRIPTION             "This is the number of packets allowed by RED
                                while the average queue size (for a given WAN
                                interface) is below the minimum threshold."
        ::= { tiaraRedStatEntry 6 }
 
redTxMaxThresholdFailure    OBJECT-TYPE
        SYNTAX                  Counter32
        MAX-ACCESS              read-only
        STATUS                  current
        DESCRIPTION             "This is the number of packets dropped by RED
                                when the average queue size exceeds the
                                maximum threshold."
        ::= { tiaraRedStatEntry 7 }

redTxMinMaxRangeSuccess     OBJECT-TYPE
        SYNTAX                  Counter32
        MAX-ACCESS              read-only
        STATUS                  current
        DESCRIPTION             "This is the number of packets allowed by RED
                                while the average queue size is between the
                                minimum and maximum thresholds."
        ::= { tiaraRedStatEntry 8 }

redTxMinMaxRangeFailure     OBJECT-TYPE
        SYNTAX                  Counter32
        MAX-ACCESS              read-only
        STATUS                  current
        DESCRIPTION             "This is the number of packets dropped by RED
                                while the average queue size is between the
                                minimum and maximum thresholds."
        ::= { tiaraRedStatEntry 9 }

redTxControlSuccess     OBJECT-TYPE 
        SYNTAX              Counter32
        MAX-ACCESS          read-only
        STATUS              current
        DESCRIPTION         "This is the number of control packets (for e.g.,
                            routing updates) that need to be dropped,
                            but are allowed by RED. Routing updates are
                            detected by RED and are not dropped."
        ::= { tiaraRedStatEntry 10 }

-- cbq Config Table
-- This table consists of all the parameters required to configure
-- a traffic class for Bandwidth Management (CBQ) on any interface
-- of the TIARA system. This table essentially describes all of
-- the configurable parameters associated with a traffic class. 

 
tiaraCbqConfigTable         OBJECT-TYPE
        SYNTAX              SEQUENCE OF TiaraCbqConfigEntry
        MAX-ACCESS          not-accessible
        STATUS              current
        DESCRIPTION         "This table consists of all the parameters 
        					required to configure a CBQ traffic class on
                            an interface."
        ::= { tiaraQosMib 3 }
 
tiaraCbqConfigEntry         OBJECT-TYPE
        SYNTAX              TiaraCbqConfigEntry
        MAX-ACCESS          not-accessible
        STATUS              current
        DESCRIPTION         "Describes an entry in the CBQ config table."
        INDEX               { tiaraIpIfIndex, cbqClassIndex }
        ::= { tiaraCbqConfigTable 1 }
 
TiaraCbqConfigEntry ::= SEQUENCE {
		cbqClassIndex					INTEGER,
        cbqClassName	                DisplayString,
        cbqClassParentName				DisplayString,
        cbqClassBandwidth				INTEGER,
		cbqClassBurstTolerance			INTEGER,
		cbqClassKeyType 				INTEGER,
		cbqClassIsDefault				TruthValue,
		cbqClassAverageBandwidth		INTEGER
		}


cbqClassIndex	     OBJECT-TYPE 
        SYNTAX              INTEGER
        MAX-ACCESS          read-only
        STATUS              current
        DESCRIPTION         ""
        ::= { tiaraCbqConfigEntry 1 }

cbqClassName	     OBJECT-TYPE 
        SYNTAX              DisplayString
        MAX-ACCESS          read-only
        STATUS              current
        DESCRIPTION         ""
        ::= { tiaraCbqConfigEntry 2 }

cbqClassParentName	     OBJECT-TYPE 
        SYNTAX              DisplayString
        MAX-ACCESS          read-only
        STATUS              current
        DESCRIPTION         ""
        ::= { tiaraCbqConfigEntry 3 }

cbqClassBandwidth	     OBJECT-TYPE 
        SYNTAX              INTEGER
        MAX-ACCESS          read-only
        STATUS              current
        DESCRIPTION         ""
        ::= { tiaraCbqConfigEntry 4 }
cbqClassBurstTolerance	     OBJECT-TYPE 
        SYNTAX              INTEGER
        MAX-ACCESS          read-only
        STATUS              current
        DESCRIPTION         ""
        ::= { tiaraCbqConfigEntry 5 }
cbqClassKeyType	     OBJECT-TYPE 
        SYNTAX              INTEGER {
        					cbqClassifyTypeNotSet 	(1),
        					cbqClassifySrcIp 		(2),
        					cbqClassifyDestIp			(3),
        					cbqClassifySrcPort		(4),
        					cbqClassifyDestPort		(5),
        					cbqClassifyProtocolType	(6),
							cbqClassifyVlanId			(7)
        					}
        MAX-ACCESS          read-only
        STATUS              current
        DESCRIPTION         ""
        ::= { tiaraCbqConfigEntry 6 }
cbqClassIsDefault	     OBJECT-TYPE 
        SYNTAX              TruthValue
        MAX-ACCESS          read-only
        STATUS              current
        DESCRIPTION         ""
        ::= { tiaraCbqConfigEntry 7 }

cbqClassAverageBandwidth	     OBJECT-TYPE 
        SYNTAX              INTEGER
        MAX-ACCESS          read-only
        STATUS              current
        DESCRIPTION         ""
        ::= { tiaraCbqConfigEntry 8}





-- cbq Class Key Table
 
tiaraCbqClassKeyTable         OBJECT-TYPE
        SYNTAX              SEQUENCE OF TiaraCbqClassKeyTableEntry
        MAX-ACCESS          not-accessible
        STATUS              current
        DESCRIPTION         ""
        ::= { tiaraQosMib 4 }
 
tiaraCbqClassKeyTableEntry         OBJECT-TYPE
        SYNTAX              TiaraCbqClassKeyTableEntry
        MAX-ACCESS          not-accessible
        STATUS              current
        DESCRIPTION         ""
        INDEX               { tiaraIpIfIndex, cbqClassIndex, cbqClassKeyIndex }
        ::= { tiaraCbqClassKeyTable 1 }

TiaraCbqClassKeyTableEntry ::= SEQUENCE {
		cbqClassKeyIndex	INTEGER,
        	cbqKeyClassName        	DisplayString,
		cbqClassKeyVlanId	INTEGER,
		cbqClassKeyIpAddress	IpAddress,
		cbqClassKeyIpNetMask	IpAddress,
		cbqClassKeyPort			INTEGER,
		cbqClassKeyProtocolType	INTEGER
		}


cbqClassKeyIndex		 OBJECT-TYPE 
        SYNTAX              INTEGER
        MAX-ACCESS          read-only
        STATUS              current
        DESCRIPTION         ""
        ::= { tiaraCbqClassKeyTableEntry 1 }
cbqKeyClassName	     OBJECT-TYPE 
        SYNTAX              DisplayString
        MAX-ACCESS          read-only
        STATUS              current
        DESCRIPTION         ""
        ::= { tiaraCbqClassKeyTableEntry 2 }
cbqClassKeyVlanId	     OBJECT-TYPE 
        SYNTAX              INTEGER
        MAX-ACCESS          read-only
        STATUS              current
        DESCRIPTION         ""
        ::= { tiaraCbqClassKeyTableEntry 3 }
cbqClassKeyIpAddress  OBJECT-TYPE 
        SYNTAX              IpAddress
        MAX-ACCESS          read-only
        STATUS              current
        DESCRIPTION         ""
        ::= { tiaraCbqClassKeyTableEntry 4 }

cbqClassKeyIpNetMask	     OBJECT-TYPE 
        SYNTAX              IpAddress
        MAX-ACCESS          read-only
        STATUS              current
        DESCRIPTION         ""
        ::= { tiaraCbqClassKeyTableEntry 5 }

cbqClassKeyPort	     OBJECT-TYPE 
        SYNTAX              INTEGER
        MAX-ACCESS          read-only
        STATUS              current
        DESCRIPTION         ""
        ::= { tiaraCbqClassKeyTableEntry 6 }

cbqClassKeyProtocolType	     OBJECT-TYPE 
        SYNTAX              INTEGER
        MAX-ACCESS          read-only
        STATUS              current
        DESCRIPTION         ""
        ::= { tiaraCbqClassKeyTableEntry 7 }



-- cbq Stats Table
-- This table gives all statistics related to a traffic class for
-- Bandwidth management (CBQ) on any interface of the TIARA box.
 
tiaraCbqStatsTable       OBJECT-TYPE
        SYNTAX              SEQUENCE OF TiaraCbqStatsEntry
        MAX-ACCESS          not-accessible
        STATUS              current
        DESCRIPTION         "This table gives CBQ's traffic class statistics 
        					for a given TIARA interface."
        ::= { tiaraQosMib 5 }
 
tiaraCbqStatsEntry       OBJECT-TYPE
        SYNTAX              TiaraCbqStatsEntry
        MAX-ACCESS          not-accessible
        STATUS              current
        DESCRIPTION         "Describes an entry in the CBQ's statistics table."
        INDEX               { tiaraIpIfIndex, cbqClassIndex   }
        ::= { tiaraCbqStatsTable 1 }
 
TiaraCbqStatsEntry ::= SEQUENCE {
        	cbqStatsClassName            		DisplayString,
		cbqClassPacketsForwarded		Counter32,
		cbqClassBytesForwarded			Counter32,
		cbqClassPacketsDropped			Counter32,
		cbqClassBytesDropped			Counter32,
		cbqClassBurstExceedCount		Counter32
    }

cbqStatsClassName	     OBJECT-TYPE 
        SYNTAX              DisplayString
        MAX-ACCESS          read-only
        STATUS              current
        DESCRIPTION         ""
        ::= { tiaraCbqStatsEntry 1 }

cbqClassPacketsForwarded	     OBJECT-TYPE 
        SYNTAX              Counter32
        MAX-ACCESS          read-only
        STATUS              current
        DESCRIPTION         ""
        ::= { tiaraCbqStatsEntry 2 }


cbqClassBytesForwarded	     OBJECT-TYPE 
        SYNTAX              Counter32
        MAX-ACCESS          read-only
        STATUS              current
        DESCRIPTION         ""
        ::= { tiaraCbqStatsEntry 3 }

cbqClassPacketsDropped	     OBJECT-TYPE 
        SYNTAX              Counter32
        MAX-ACCESS          read-only
        STATUS              current
        DESCRIPTION         ""
        ::= { tiaraCbqStatsEntry 4 }

cbqClassBytesDropped	     OBJECT-TYPE 
        SYNTAX              Counter32
        MAX-ACCESS          read-only
        STATUS              current
        DESCRIPTION         ""
        ::= { tiaraCbqStatsEntry 5 }

cbqClassBurstExceedCount	     OBJECT-TYPE 
        SYNTAX              Counter32
        MAX-ACCESS          read-only
        STATUS              current
        DESCRIPTION         ""
        ::= { tiaraCbqStatsEntry 6 }



END
