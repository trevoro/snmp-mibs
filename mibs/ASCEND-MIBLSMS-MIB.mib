--			Ascend miblsms MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBLSMS-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    miblsmsProfile  OBJECT IDENTIFIER ::= { configuration 150}

	-- The miblsmsProfile table
	--
	-- This table contains parameters for the miblsmsProfile profile
	--

    miblsmsProfileTable	OBJECT-TYPE
	SYNTAX		SEQUENCE OF MiblsmsProfileEntry
	ACCESS		not-accessible
	STATUS		mandatory
	DESCRIPTION	"A list of miblsmsProfile profile entries."
	::= { miblsmsProfile 1 }

    miblsmsProfileEntry	OBJECT-TYPE
	SYNTAX		MiblsmsProfileEntry
	ACCESS		not-accessible
	STATUS		mandatory
	DESCRIPTION	"A miblsmsProfile entry containing objects that
			 maps to the parameters of miblsmsProfile profile."
	INDEX		{ lsmsProfile-Index-o }
	::= { miblsmsProfileTable 1 }

    MiblsmsProfileEntry ::=
	SEQUENCE {
	    lsmsProfile-Index-o
		INTEGER,
	    lsmsProfile-Active
		INTEGER,
	    lsmsProfile-LsmsIpAddr
		IpAddress,
	    lsmsProfile-NocGatewayIpAddr
		IpAddress,
	    lsmsProfile-Spi
		DisplayString,
	    lsmsProfile-PresharedKey
		DisplayString,
	    lsmsProfile-AllowInsecure
		INTEGER,
	    lsmsProfile-Action-o
		INTEGER
	}

    lsmsProfile-Index-o	OBJECT-TYPE
	SYNTAX	INTEGER
	ACCESS	read-only
	STATUS	mandatory
	DESCRIPTION	""
	::= { miblsmsProfileEntry 1 }

    lsmsProfile-Active	OBJECT-TYPE
	SYNTAX	INTEGER {
		    no (1),
		    yes (2)
		}
	ACCESS	read-write
	STATUS	mandatory
	DESCRIPTION	"This field is used to control whether Communications with the LSMS should be active or not (Yes/No). More specifically, if the router should start to listen for requests from the LSMS."
	::= { miblsmsProfileEntry 2 }

    lsmsProfile-LsmsIpAddr	OBJECT-TYPE
	SYNTAX	IpAddress
	ACCESS	read-write
	STATUS	mandatory
	DESCRIPTION	"IP address of the LSMS. It is used in validating requests from the LSMS and to communicate in an in-secure fashion directly with the LSMS."
	::= { miblsmsProfileEntry 3 }

    lsmsProfile-NocGatewayIpAddr	OBJECT-TYPE
	SYNTAX	IpAddress
	ACCESS	read-write
	STATUS	mandatory
	DESCRIPTION	"IP address of NOC Gateway to the LSMS. This is the Tunnel Endpoint address of the Secure Communications Channel. It is essentially the address of the device that terminates the tunnel with the router and sits between the LSMS and router."
	::= { miblsmsProfileEntry 4 }

    lsmsProfile-Spi	OBJECT-TYPE
	SYNTAX	DisplayString
	ACCESS	read-write
	STATUS	mandatory
	DESCRIPTION	"Security Parameter Index that is used for Encrypting Secure Communications Channel (IPsec Tunnel) traffic between the Router and LSMS. The SPI is used to distinguish among different security associations terminating at the same destination and using the same IPsec protocol."
	::= { miblsmsProfileEntry 5 }

    lsmsProfile-PresharedKey	OBJECT-TYPE
	SYNTAX	DisplayString
	ACCESS	read-write
	STATUS	mandatory
	DESCRIPTION	"Preshared Key used to create Authentication and Encryption keys that are used to create the IPsec tunnel for the Secure Communications Channel."
	::= { miblsmsProfileEntry 6 }

    lsmsProfile-AllowInsecure	OBJECT-TYPE
	SYNTAX	INTEGER {
		    no (1),
		    yes (2)
		}
	ACCESS	read-write
	STATUS	mandatory
	DESCRIPTION	"This field is used to permit insecure communications. Insecure communications allows data to be sent in clear outside of an IPsec tunnel (Yes/No)."
	::= { miblsmsProfileEntry 7 }

    lsmsProfile-Action-o	OBJECT-TYPE
	SYNTAX	INTEGER {
		    noAction (1),
		    createProfile (2),
		    deleteProfile (3)
		}
	ACCESS	read-write
	STATUS	mandatory
	DESCRIPTION	""
	::= { miblsmsProfileEntry 8 }

END
