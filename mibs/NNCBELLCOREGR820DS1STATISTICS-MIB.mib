-------------------------------------------------------------------------------
-- file: NncBellcoreGR820Ds1Statistics.mib 
--
-- description:
--	This file contains the SNMP definitions for the Bellcore GR820 
--      statistics for DS1 lines. The definitions of all the statistics
--      are based on Bellcore document no. GR-820-CORE issue 1, November 1994
--
-- history:
--       %%history-start%%
--       1999.03.30 mkayali 31A1237: Creation 
--       1999.06.22 mkayali P.281779: Added nncBellcoreGR820Ds1CurrPathFC, 
--         nncBellcoreGR820Ds1IntervalPathFC, and 
--         nncBellcoreGR820Ds1TotalPathFC 
--       %%history-end%%
-- Copyright 1999 Newbridge Networks Corporation.  All Rights Reserved
-------------------------------------------------------------------------------
NNCBELLCOREGR820DS1STATISTICS-MIB DEFINITIONS ::= BEGIN
  
  IMPORTS
    MODULE-IDENTITY, OBJECT-TYPE, Counter32    FROM SNMPv2-SMI
    MODULE-COMPLIANCE, OBJECT-GROUP            FROM SNMPv2-CONF
    ifIndex                                    FROM IF-MIB	
    nncExtensions                              FROM NNCGNI0001-SMI;

			
  nncBellcoreGR820Ds1Statistics MODULE-IDENTITY	
    LAST-UPDATED 	"9902151200Z"
    ORGANIZATION 	"Newbridge Networks Corporation"
    CONTACT-INFO
            		"Newbridge Networks Corporation
             		 Postal: 600 March Road
                         Kanata, Ontario
                         Canada K2K 2E6

             		 Phone:  +1 613 591 3600
             		 Fax:    +1 613 591 3680"
		
    DESCRIPTION	"This module contains the definitions for the Bellcore GR820 
                 statistics for DS1 lines."
	
  ::= { nncExtensions 70}


  nncBellcoreGR820Ds1StatisticsObjects OBJECT IDENTIFIER ::=     { nncBellcoreGR820Ds1Statistics 1 }
  nncBellcoreGR820Ds1StatisticsGroups OBJECT IDENTIFIER ::=      { nncBellcoreGR820Ds1Statistics 2 }
  nncBellcoreGR820Ds1StatisticsCompliances OBJECT IDENTIFIER ::= { nncBellcoreGR820Ds1Statistics 3 }

--------------------------------------------------------------------------------
-- NOTE:
-- 
-- For T1CE cards on the 36170, not all the Bellcore GR820 statistics can be
-- retrieved in all AAL1 layer port modes (i.e. UDT, UDT-MON, and SDT). For
-- more details, please refer to 31FS0088.
-- The following table lists for each statistic the applicable AAL1 layer
-- modes:
--
--          Statistic                Applicable AAL1 layer mode(s)
--          =========               ==============================
--
--           LineCV                         UDT,UDT-MON,SDT
--           LineES                         UDT,UDT-MON,SDT
--           LineLOSS                       UDT,UDT-MON,SDT
--           PathCV                           UDT-MON,SDT
--           PathES                           UDT-MON,SDT
--           PathSES                          UDT-MON,SDT
--           PathAISS                         UDT-MON,SDT
--           PathCSS                              SDT  
--           PathUAS                          UDT-MON,SDT
--           PathSAS                          UDT-MON,SDT
--
--------------------------------------------------------------------------------


--------------------------------------------------------------------------------
--
-- This MIB module contains the following tables:
--	Bellcore-GR820Ds1 Current Statistics
--      Bellcore-GR820Ds1 Interval Statistics
--      Bellcore-GR820Ds1 Total Statistics
-- 
--------------------------------------------------------------------------------


-- The Bellcore-GR820Ds1 Current Statistics Table (per interface)

  nncBellcoreGR820Ds1CurrStatsTable  OBJECT-TYPE
             SYNTAX		  SEQUENCE OF NncBellcoreGR820Ds1CurrStatsEntry       
             MAX-ACCESS           not-accessible
             STATUS     	  current
             DESCRIPTION	  "The Bellcore-GR820Ds1 Current Statistics
                                   table maintains per-interfce statistics for 
                                   the fifteen-minute interval currently
                                   being collected."
  ::= { nncBellcoreGR820Ds1StatisticsObjects 1 }

  nncBellcoreGR820Ds1CurrStatsEntry  OBJECT-TYPE
             SYNTAX               NncBellcoreGR820Ds1CurrStatsEntry
             MAX-ACCESS           not-accessible
	     STATUS               current
             DESCRIPTION          "An entry in the Bellcore-GR820Ds1 Current 
                                   Statistics table"
	     INDEX                { ifIndex }
  ::= { nncBellcoreGR820Ds1CurrStatsTable 1 }

  NncBellcoreGR820Ds1CurrStatsEntry ::=
         SEQUENCE {
            nncBellcoreGR820Ds1CurrLineCV        Counter32,
            nncBellcoreGR820Ds1CurrLineES        Counter32,
            nncBellcoreGR820Ds1CurrLineLOSS      Counter32,
            nncBellcoreGR820Ds1CurrPathCV        Counter32,
            nncBellcoreGR820Ds1CurrPathES        Counter32,
	    nncBellcoreGR820Ds1CurrPathSES       Counter32,
            nncBellcoreGR820Ds1CurrPathAISS      Counter32,
            nncBellcoreGR820Ds1CurrPathCSS       Counter32,
	    nncBellcoreGR820Ds1CurrPathUAS       Counter32,
            nncBellcoreGR820Ds1CurrPathSAS       Counter32,
	    nncBellcoreGR820Ds1CurrPathFC        Counter32
         }

  nncBellcoreGR820Ds1CurrLineCV  OBJECT-TYPE
	     SYNTAX         Counter32
             MAX-ACCESS     read-only
             STATUS         current
             DESCRIPTION    "The number of Line Code Violations encountered
                             by a DS1 interface in the current 15-minute
                             interval."
  ::= { nncBellcoreGR820Ds1CurrStatsEntry 1 }

  nncBellcoreGR820Ds1CurrLineES   OBJECT-TYPE
	     SYNTAX          Counter32
             MAX-ACCESS      read-only
             STATUS          current
             DESCRIPTION     "The number of Line Errored Seconds encountered 
                              by a DS1 interface in the current 15-minute
                              interval."
  ::= { nncBellcoreGR820Ds1CurrStatsEntry 2 }

  nncBellcoreGR820Ds1CurrLineLOSS  OBJECT-TYPE
	     SYNTAX           Counter32
             MAX-ACCESS       read-only
             STATUS           current
             DESCRIPTION      "The number of Line Loss of Signal Seconds
                               encountered by a DS1 interface in the current 
                               15-minute inetrval."
  ::= { nncBellcoreGR820Ds1CurrStatsEntry 3 }

  nncBellcoreGR820Ds1CurrPathCV  OBJECT-TYPE
             SYNTAX         Counter32
             MAX-ACCESS     read-only
             STATUS         current
             DESCRIPTION    "The number of Path Code Violations encountered 
                             by a DS1 interface in the current 15-minute
                             interval."
  ::= { nncBellcoreGR820Ds1CurrStatsEntry 4 }

  nncBellcoreGR820Ds1CurrPathES  OBJECT-TYPE
             SYNTAX         Counter32
             MAX-ACCESS     read-only
             STATUS         current
             DESCRIPTION    "The number of Path Errored Seconds encountered
                             by a DS1 interface in the current 15-minute
                             interval."
  ::= { nncBellcoreGR820Ds1CurrStatsEntry 5 }

  nncBellcoreGR820Ds1CurrPathSES  OBJECT-TYPE
	     SYNTAX          Counter32
             MAX-ACCESS      read-only
             STATUS          current
             DESCRIPTION     "The number of Path Severely Errored Seconds
                              encountered by a DS1 interface in the current 
                              15-minute interval."
  ::= { nncBellcoreGR820Ds1CurrStatsEntry 6 }

  nncBellcoreGR820Ds1CurrPathAISS  OBJECT-TYPE
	     SYNTAX           Counter32
             MAX-ACCESS       read-only
             STATUS           current
             DESCRIPTION     "The number of Path Alarm Indication Signal 
                              Seconds encountered by a DS1 interface in
                              the current 15-minute interval."
  ::= { nncBellcoreGR820Ds1CurrStatsEntry 7 }

  nncBellcoreGR820Ds1CurrPathCSS  OBJECT-TYPE
	     SYNTAX          Counter32
             MAX-ACCESS      read-only
             STATUS          current
             DESCRIPTION     "The number of Path Controlled Slip Seconds
                              encountered by a DS1 interface in the current 
                              15-minute interval."
  ::= { nncBellcoreGR820Ds1CurrStatsEntry 8 }

  nncBellcoreGR820Ds1CurrPathUAS  OBJECT-TYPE
	     SYNTAX          Counter32
             MAX-ACCESS      read-only
             STATUS          current
             DESCRIPTION     "The number of Path Unavailable Seconds
                              encountered by a DS1 interface in the current 
                              15-minute interval."
  ::= { nncBellcoreGR820Ds1CurrStatsEntry 9 }
 
  nncBellcoreGR820Ds1CurrPathSAS  OBJECT-TYPE
	     SYNTAX          Counter32
             MAX-ACCESS      read-only
             STATUS          current
             DESCRIPTION     "The number of Path Severely Errored Frame/
                              Alarm Indication Signal Seconds encountered 
                              by a DS1 interface in the current 15-minute 
                              interval."
  ::= { nncBellcoreGR820Ds1CurrStatsEntry 10 }

  nncBellcoreGR820Ds1CurrPathFC  OBJECT-TYPE
	     SYNTAX          Counter32
             MAX-ACCESS      read-only
             STATUS          current
             DESCRIPTION     "The count of Path Failure events
                              encountered by a DS1 interface in 
			      the current 15-minute interval."
  ::= { nncBellcoreGR820Ds1CurrStatsEntry 11 }




-- The Bellcore-GR820Ds1 Interval Statistics Table (per interface and time interval)
 
  nncBellcoreGR820Ds1IntervalStatsTable  OBJECT-TYPE
	     SYNTAX	              SEQUENCE OF NncBellcoreGR820Ds1IntervalStatsEntry       
	     MAX-ACCESS               not-accessible
             STATUS                   current
             DESCRIPTION	      "The Bellcore-GR820Ds1 Interval Statistics
 	                               table maintains per-interfce statistics
                                       for the last 96 fifteen-minute intervals"
  ::= { nncBellcoreGR820Ds1StatisticsObjects 2 }

  nncBellcoreGR820Ds1IntervalStatsEntry  OBJECT-TYPE
             SYNTAX                   NncBellcoreGR820Ds1IntervalStatsEntry
             MAX-ACCESS               not-accessible
	     STATUS                   current
             DESCRIPTION              "An entry in the Bellcore-GR820Ds1
                                       Interval Statistics table"
	     INDEX                    {ifIndex, nncBellcoreGR820Ds1IntervalIndex }
  ::= { nncBellcoreGR820Ds1IntervalStatsTable 1 }

  NncBellcoreGR820Ds1IntervalStatsEntry ::=
         SEQUENCE {
	    nncBellcoreGR820Ds1IntervalIndex       INTEGER,
            nncBellcoreGR820Ds1IntervalLineCV        Counter32,
            nncBellcoreGR820Ds1IntervalLineES        Counter32,
            nncBellcoreGR820Ds1IntervalLineLOSS      Counter32,
            nncBellcoreGR820Ds1IntervalPathCV        Counter32,
            nncBellcoreGR820Ds1IntervalPathES        Counter32,
	    nncBellcoreGR820Ds1IntervalPathSES       Counter32,
            nncBellcoreGR820Ds1IntervalPathAISS      Counter32,
            nncBellcoreGR820Ds1IntervalPathCSS       Counter32,
	    nncBellcoreGR820Ds1IntervalPathUAS       Counter32,
            nncBellcoreGR820Ds1IntervalPathSAS       Counter32,
	    nncBellcoreGR820Ds1IntervalPathFC        Counter32
         }

  nncBellcoreGR820Ds1IntervalIndex  OBJECT-TYPE
             SYNTAX              INTEGER (1..96)
             MAX-ACCESS          read-only
             STATUS              current
             DESCRIPTION         "A number between 1 and 96, which identifies the
                                  interval for which the set of statistics in this
                                  entry was collected.  The interval identified by
                                  1 is the most recently completed 15 minute
                                  interval, and the interval identified by 96 is
                                  the least recently completed 15 minute interval
                                  (assuming that all 96 inetrvals are valid)."
  ::= { nncBellcoreGR820Ds1IntervalStatsEntry 1 }

  nncBellcoreGR820Ds1IntervalLineCV  OBJECT-TYPE
	     SYNTAX             Counter32
             MAX-ACCESS         read-only
             STATUS             current
             DESCRIPTION        "The number of Line Code Violations encountered
                                 by a DS1 interface in one of the previous 
                                 15-minute intervals."
  ::= { nncBellcoreGR820Ds1IntervalStatsEntry 2 }

  nncBellcoreGR820Ds1IntervalLineES  OBJECT-TYPE
	     SYNTAX             Counter32
             MAX-ACCESS         read-only
             STATUS             current
             DESCRIPTION        "The number of Line Errored Seconds encountered 
                                 by a DS1 interface in one of the previous
                                 15-minute intervals."
  ::= { nncBellcoreGR820Ds1IntervalStatsEntry 3 }

  nncBellcoreGR820Ds1IntervalLineLOSS  OBJECT-TYPE
	     SYNTAX               Counter32
             MAX-ACCESS           read-only
             STATUS               current
             DESCRIPTION          "The number of Line Loss of Signal Seconds
                                   encountered by a DS1 interface in one of 
                                   the previous 15-minute inetrvals."
  ::= { nncBellcoreGR820Ds1IntervalStatsEntry 4 }

  nncBellcoreGR820Ds1IntervalPathCV  OBJECT-TYPE
             SYNTAX             Counter32
             MAX-ACCESS         read-only
             STATUS             current
             DESCRIPTION        "The number of Path Code Violations encountered 
                                 by a DS1 interface in one of the previous
                                 15-minute intervals."
  ::= { nncBellcoreGR820Ds1IntervalStatsEntry 5 }

  nncBellcoreGR820Ds1IntervalPathES  OBJECT-TYPE
             SYNTAX             Counter32
             MAX-ACCESS         read-only
             STATUS             current
             DESCRIPTION        "The number of Path Errored Seconds encountered
                                 by a DS1 interface in one of the previous
                                 15-minute intervals."
  ::= { nncBellcoreGR820Ds1IntervalStatsEntry 6 }  

  nncBellcoreGR820Ds1IntervalPathSES  OBJECT-TYPE
	     SYNTAX              Counter32
             MAX-ACCESS          read-only
             STATUS              current
             DESCRIPTION         "The number of Path Severely Errored Seconds
                                  encountered by a DS1 interface in one of
                                  the previous 15-minute intervals."
  ::= { nncBellcoreGR820Ds1IntervalStatsEntry 7 }

  nncBellcoreGR820Ds1IntervalPathAISS  OBJECT-TYPE
	     SYNTAX               Counter32
             MAX-ACCESS           read-only
             STATUS               current
             DESCRIPTION          "The number of Path Alarm Indication Signal 
                                   Seconds encountered by a DS1 interface in
                                   one of the previous 15-minute intervals."
  ::= { nncBellcoreGR820Ds1IntervalStatsEntry 8 }

  nncBellcoreGR820Ds1IntervalPathCSS  OBJECT-TYPE
	     SYNTAX              Counter32
             MAX-ACCESS          read-only
             STATUS              current
             DESCRIPTION         "The number of Path Controlled Slip Seconds
                                  encountered by a DS1 interface in one of 
                                  the previous 15-minute intervals."
  ::= { nncBellcoreGR820Ds1IntervalStatsEntry 9 }

  nncBellcoreGR820Ds1IntervalPathUAS  OBJECT-TYPE
	     SYNTAX              Counter32
             MAX-ACCESS          read-only
             STATUS              current
             DESCRIPTION         "The number of Path Unavailable Seconds
                                  encountered by a DS1 interface in one of 
                                  the previous 15-minute intervals."
  ::= { nncBellcoreGR820Ds1IntervalStatsEntry 10 } 
  
  nncBellcoreGR820Ds1IntervalPathSAS  OBJECT-TYPE
	     SYNTAX              Counter32
             MAX-ACCESS          read-only
             STATUS              current
             DESCRIPTION         "The number of Path Severely Errored Frame/
                                  Alarm Indication Signal Seconds encountered 
                                  by a DS1 interface in one of the previous
                                  15-minute intervals."
  ::= { nncBellcoreGR820Ds1IntervalStatsEntry 11 }

  nncBellcoreGR820Ds1IntervalPathFC  OBJECT-TYPE
	     SYNTAX              Counter32
             MAX-ACCESS          read-only
             STATUS              current
             DESCRIPTION         "The count of Path Failure events
                                  encountered by a DS1 interface in one 
				  of the previous 15-minute intervals."
  ::= { nncBellcoreGR820Ds1IntervalStatsEntry 12 }
  


-- The Bellcore-GR820Ds1 Total Statistics Table (per interface)

  nncBellcoreGR820Ds1TotalStatsTable   OBJECT-TYPE
             SYNTAX	   	    SEQUENCE OF NncBellcoreGR820Ds1TotalStatsEntry       
             MAX-ACCESS             not-accessible
             STATUS     	    current
             DESCRIPTION	    "The Bellcore-GR820Ds1 Total Statistics table 
                                     contains the per-interface cumulative sum of 
                                     the various statistics for the 24-hour period 
                                     preceding the current 15-minute interval."
  ::= { nncBellcoreGR820Ds1StatisticsObjects 3 }

  nncBellcoreGR820Ds1TotalStatsEntry  OBJECT-TYPE
             SYNTAX                NncBellcoreGR820Ds1TotalStatsEntry
             MAX-ACCESS            not-accessible
	     STATUS                current
             DESCRIPTION           "An entry in the Bellcore-GR820Ds1 Total 
                                    Statistics table"
	     INDEX                 { ifIndex }
  ::= { nncBellcoreGR820Ds1TotalStatsTable 1 }

  NncBellcoreGR820Ds1TotalStatsEntry ::=
         SEQUENCE {
            nncBellcoreGR820Ds1TotalLineCV        Counter32,
            nncBellcoreGR820Ds1TotalLineES        Counter32,
            nncBellcoreGR820Ds1TotalLineLOSS      Counter32,
            nncBellcoreGR820Ds1TotalPathCV        Counter32,
            nncBellcoreGR820Ds1TotalPathES        Counter32,
	    nncBellcoreGR820Ds1TotalPathSES       Counter32,
            nncBellcoreGR820Ds1TotalPathAISS      Counter32,
            nncBellcoreGR820Ds1TotalPathCSS       Counter32,
	    nncBellcoreGR820Ds1TotalPathUAS       Counter32,
            nncBellcoreGR820Ds1TotalPathSAS       Counter32,
            nncBellcoreGR820Ds1TotalPathFC        Counter32
         }

  nncBellcoreGR820Ds1TotalLineCV  OBJECT-TYPE
	     SYNTAX          Counter32
             MAX-ACCESS      read-only
             STATUS          current
             DESCRIPTION     "The number of Line Code Violations encountered
                              by a DS1 interface in the previous 24-hour 
                              interval."
  ::= { nncBellcoreGR820Ds1TotalStatsEntry 1 }

  nncBellcoreGR820Ds1TotalLineES   OBJECT-TYPE
	     SYNTAX           Counter32
             MAX-ACCESS       read-only
             STATUS           current
             DESCRIPTION      "The number of Line Errored Seconds encountered 
                               by a DS1 interface in the previous 24-hour
                               interval."
  ::= { nncBellcoreGR820Ds1TotalStatsEntry 2 }

  nncBellcoreGR820Ds1TotalLineLOSS  OBJECT-TYPE
	     SYNTAX            Counter32
             MAX-ACCESS        read-only
             STATUS            current
             DESCRIPTION       "The number of Line Loss of Signal Seconds
                                encountered by a DS1 interface in the 
                                previous 24-hour inetrval."
  ::= { nncBellcoreGR820Ds1TotalStatsEntry 3 }

  nncBellcoreGR820Ds1TotalPathCV  OBJECT-TYPE
             SYNTAX          Counter32
             MAX-ACCESS      read-only
             STATUS          current
             DESCRIPTION     "The number of Path Code Violations encountered 
                              by a DS1 interface in the previous 24-hour
                              interval."
  ::= { nncBellcoreGR820Ds1TotalStatsEntry 4 }

  nncBellcoreGR820Ds1TotalPathES  OBJECT-TYPE
             SYNTAX          Counter32
             MAX-ACCESS      read-only
             STATUS          current
             DESCRIPTION     "The number of Path Errored Seconds encountered
                              by a DS1 interface in the previous 24-hour
                              interval."
  ::= { nncBellcoreGR820Ds1TotalStatsEntry 5 }

  nncBellcoreGR820Ds1TotalPathSES  OBJECT-TYPE
	     SYNTAX           Counter32
             MAX-ACCESS       read-only
             STATUS           current
             DESCRIPTION      "The number of Path Severely Errored Seconds
                               encountered by a DS1 interface in the previous 
                               24-hour interval."
  ::= { nncBellcoreGR820Ds1TotalStatsEntry 6 }

  nncBellcoreGR820Ds1TotalPathAISS  OBJECT-TYPE
	     SYNTAX            Counter32
             MAX-ACCESS        read-only
             STATUS            current
             DESCRIPTION      "The number of Path Alarm Indication Signal 
                               Seconds encountered by a DS1 interface in
                               the previous 24-hour inetrval."
  ::= { nncBellcoreGR820Ds1TotalStatsEntry 7 }

  nncBellcoreGR820Ds1TotalPathCSS  OBJECT-TYPE
	     SYNTAX           Counter32
             MAX-ACCESS       read-only
             STATUS           current
             DESCRIPTION      "The number of Path Controlled Slip Seconds
                               encountered by a DS1 interface in the previous
                               24-hour"
  ::= { nncBellcoreGR820Ds1TotalStatsEntry 8 }

  nncBellcoreGR820Ds1TotalPathUAS  OBJECT-TYPE
	     SYNTAX           Counter32
             MAX-ACCESS       read-only
             STATUS           current
             DESCRIPTION      "The number of Path Unavailable Seconds
                               encountered by a DS1 interface in the previous
                               24-hour interval."
  ::= { nncBellcoreGR820Ds1TotalStatsEntry 9 }
 
  nncBellcoreGR820Ds1TotalPathSAS  OBJECT-TYPE
	     SYNTAX           Counter32
             MAX-ACCESS       read-only
             STATUS           current
             DESCRIPTION      "The number of Path Severely Errored Frame/
                               Alarm Indication Signal Seconds encountered 
                               by a DS1 interface in the previous 24-hour 
                               interval."
  ::= { nncBellcoreGR820Ds1TotalStatsEntry 10 }

  nncBellcoreGR820Ds1TotalPathFC  OBJECT-TYPE
	     SYNTAX           Counter32
             MAX-ACCESS       read-only
             STATUS           current
             DESCRIPTION      "The count of Path Failure events
                               encountered by a DS1 interface in the
			       previous 24-hour interval."
  ::= { nncBellcoreGR820Ds1TotalStatsEntry 11 }

-------------------------------------------------------------------------------
-- Conformance Group Definitions
-------------------------------------------------------------------------------
 nncBellcoreGR820Ds1CurrStatsGroup   OBJECT-GROUP
   OBJECTS { 
	nncBellcoreGR820Ds1CurrLineCV,
        nncBellcoreGR820Ds1CurrLineES,
        nncBellcoreGR820Ds1CurrLineLOSS,
        nncBellcoreGR820Ds1CurrPathCV,
        nncBellcoreGR820Ds1CurrPathES,
	nncBellcoreGR820Ds1CurrPathSES,
        nncBellcoreGR820Ds1CurrPathAISS,
        nncBellcoreGR820Ds1CurrPathCSS,
	nncBellcoreGR820Ds1CurrPathUAS,
        nncBellcoreGR820Ds1CurrPathSAS,
	nncBellcoreGR820Ds1CurrPathFC
   }
    STATUS          current
    DESCRIPTION     "A collection of objects providing 15 Min current 
                     monitoring data for Ds1 interfaces based on 
                     Bellcore-GR820Ds1 specification"

   ::= { nncBellcoreGR820Ds1StatisticsGroups 1 } 

 nncBellcoreGR820Ds1IntervalStatsGroup   OBJECT-GROUP
   OBJECTS { 
	nncBellcoreGR820Ds1IntervalIndex,
	nncBellcoreGR820Ds1IntervalLineCV,
        nncBellcoreGR820Ds1IntervalLineES,
        nncBellcoreGR820Ds1IntervalLineLOSS,
        nncBellcoreGR820Ds1IntervalPathCV,
        nncBellcoreGR820Ds1IntervalPathES,
	nncBellcoreGR820Ds1IntervalPathSES,
        nncBellcoreGR820Ds1IntervalPathAISS,
        nncBellcoreGR820Ds1IntervalPathCSS,
	nncBellcoreGR820Ds1IntervalPathUAS,
        nncBellcoreGR820Ds1IntervalPathSAS,
	nncBellcoreGR820Ds1IntervalPathFC
   }
    STATUS          current
    DESCRIPTION     "A collection of objects providing 15 Min history 
                     monitoring data for Ds1 interfaces based on 
                     Bellcore-GR820Ds1 specification"

   ::= { nncBellcoreGR820Ds1StatisticsGroups 2 } 

 nncBellcoreGR820Ds1TotalStatsGroup   OBJECT-GROUP
   OBJECTS { 
	nncBellcoreGR820Ds1TotalLineCV,
        nncBellcoreGR820Ds1TotalLineES,
        nncBellcoreGR820Ds1TotalLineLOSS,
        nncBellcoreGR820Ds1TotalPathCV,
        nncBellcoreGR820Ds1TotalPathES,
	nncBellcoreGR820Ds1TotalPathSES,
        nncBellcoreGR820Ds1TotalPathAISS,
        nncBellcoreGR820Ds1TotalPathCSS,
	nncBellcoreGR820Ds1TotalPathUAS,
        nncBellcoreGR820Ds1TotalPathSAS,
	nncBellcoreGR820Ds1TotalPathFC
   }
    STATUS          current
    DESCRIPTION     "A collection of objects providing a cumulative sum of
                     monitoring data for the previous 24-hour for Ds1 interfaces 
                     based on Bellcore-GR820Ds1 specification"

   ::= { nncBellcoreGR820Ds1StatisticsGroups 3 } 

-------------------------------------------------------------------------------
-- Compliance Statements 
-------------------------------------------------------------------------------
  nncBellcoreGR820Ds1StatisticsCompliance      MODULE-COMPLIANCE
    STATUS          current
    DESCRIPTION     "The complicance statement for Newbridge SNMP entities 
                     which have Ds1 Performance monitoring capabilities"
    MODULE
      MANDATORY-GROUPS { 
          nncBellcoreGR820Ds1CurrStatsGroup,
          nncBellcoreGR820Ds1IntervalStatsGroup,
          nncBellcoreGR820Ds1TotalStatsGroup
      }
  ::= { nncBellcoreGR820Ds1StatisticsCompliances 1 } 

END -- DEFINITION OF NNCBELLCOREGR820DS1STATISTICS-MIB
