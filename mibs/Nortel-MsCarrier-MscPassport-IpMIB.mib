Nortel-MsCarrier-MscPassport-IpMIB
DEFINITIONS ::= BEGIN



IMPORTS

      OBJECT-TYPE
   FROM RFC-1212

      IpAddress
   FROM RFC1155-SMI

      mscPassportMIBs
   FROM Nortel-MsCarrier-MscPassport-UsefulDefinitionsMIB

      Counter32,
      PhysAddress,
      Gauge32,
      RowPointer,
      DisplayString,
      StorageType,
      RowStatus,
      AreaID,
      InterfaceIndex,
      RouterID,
      Integer32,
      Unsigned32
   FROM Nortel-MsCarrier-MscPassport-StandardTextualConventionsMIB

      AsciiString,
      DashedHexString,
      NonReplicated,
      HexString,
      Link,
      AsciiStringIndex
   FROM Nortel-MsCarrier-MscPassport-TextualConventionsMIB

      mscVrIndex,
      mscVrPp,
      mscVrPpIndex,
      mscVr
   FROM Nortel-MsCarrier-MscPassport-VirtualRouterMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     Ip Enterprise MIB."

ipMIB OBJECT IDENTIFIER ::= { mscPassportMIBs 27 }










-- Vr<string> Pp<string> IpPort
-- The IpPort component contains IP attributes specific to this port.

mscVrPpIpPort OBJECT IDENTIFIER ::= { mscVrPp 5 }



mscVrPpIpPortRowStatusTable OBJECT-TYPE
   SYNTAX     SEQUENCE OF MscVrPpIpPortRowStatusEntry
   ACCESS     not-accessible
   STATUS     mandatory
   DESCRIPTION
     "This entry controls the addition and deletion of 
      mscVrPpIpPort components."
::= { mscVrPpIpPort 1 }

mscVrPpIpPortRowStatusEntry OBJECT-TYPE
   SYNTAX     MscVrPpIpPortRowStatusEntry
   ACCESS     not-accessible
   STATUS     mandatory
   DESCRIPTION
     "A single entry in the table represents a single 
      mscVrPpIpPort component."
   INDEX {
      mscVrIndex,
      mscVrPpIndex,
      mscVrPpIpPortIndex }
::= { mscVrPpIpPortRowStatusTable 1 }

MscVrPpIpPortRowStatusEntry ::= SEQUENCE {
   mscVrPpIpPortRowStatus
      RowStatus,
   mscVrPpIpPortComponentName
      DisplayString,
   mscVrPpIpPortStorageType
      StorageType,
   mscVrPpIpPortIndex
      NonReplicated }

mscVrPpIpPortRowStatus OBJECT-TYPE
   SYNTAX     RowStatus 
   ACCESS     read-write
   STATUS     mandatory
   DESCRIPTION
     "This variable is used as the basis for SNMP naming of
      mscVrPpIpPort components.
      These components can be added and deleted."
::= { mscVrPpIpPortRowStatusEntry 1 }

mscVrPpIpPortComponentName OBJECT-TYPE
   SYNTAX     DisplayString 
   ACCESS     read-only
   STATUS     mandatory
   DESCRIPTION
     "This variable provides the component's string name for
      use with the ASCII Console Interface"
::= { mscVrPpIpPortRowStatusEntry 2 }

mscVrPpIpPortStorageType OBJECT-TYPE
   SYNTAX     StorageType 
   ACCESS     read-only
   STATUS     mandatory
   DESCRIPTION
     "This variable represents the storage type value for the
      mscVrPpIpPort tables."
::= { mscVrPpIpPortRowStatusEntry 4 }

mscVrPpIpPortIndex OBJECT-TYPE
   SYNTAX     NonReplicated 
   ACCESS     not-accessible
   STATUS     mandatory
   DESCRIPTION
     "This variable represents the index for the mscVrPpIpPort tables."
::= { mscVrPpIpPortRowStatusEntry 10 }

mscVrPpIpPortProvTable OBJECT-TYPE
   SYNTAX     SEQUENCE OF MscVrPpIpPortProvEntry
   ACCESS     not-accessible
   STATUS     mandatory
   DESCRIPTION
     "This group contains provisionable attributes for IP ports."
::= { mscVrPpIpPort 10 }

mscVrPpIpPortProvEntry OBJECT-TYPE
   SYNTAX     MscVrPpIpPortProvEntry
   ACCESS     not-accessible
   STATUS     mandatory
   DESCRIPTION
     "An entry in the mscVrPpIpPortProvTable."
   INDEX {
      mscVrIndex,
      mscVrPpIndex,
      mscVrPpIpPortIndex }
::= { mscVrPpIpPortProvTable 1 }

MscVrPpIpPortProvEntry ::= SEQUENCE {
   mscVrPpIpPortMaxTxUnit
      Unsigned32,
   mscVrPpIpPortArpStatus
      INTEGER,
   mscVrPpIpPortProxyArpStatus
      INTEGER,
   mscVrPpIpPortArpNoLearn
      INTEGER,
   mscVrPpIpPortSendRedirect
      INTEGER,
   mscVrPpIpPortMulticastStatus
      INTEGER,
   mscVrPpIpPortRelayAddress
      IpAddress,
   mscVrPpIpPortRelayBroadcast
      INTEGER,
   mscVrPpIpPortLinkModel
      INTEGER,
   mscVrPpIpPortLanModel
      INTEGER,
   mscVrPpIpPortEncap
      INTEGER,
   mscVrPpIpPortIcmpMaskReply
      INTEGER,
   mscVrPpIpPortDirectedBroadcast
      INTEGER,
   mscVrPpIpPortAssignedQos
      Unsigned32,
   mscVrPpIpPortAllowMcastMacDest
      INTEGER,
   mscVrPpIpPortCosPolicyAssignment
      Link }

mscVrPpIpPortMaxTxUnit OBJECT-TYPE
   SYNTAX     Unsigned32 (0..0 | 576..18944)
   ACCESS     read-write
   STATUS     mandatory
   DESCRIPTION
     "This attribute specifies the IP MTU (Maximum Transmission Unit) 
      supported by this IpPort. The specified MTU must be within the valid 
      range for the IpPort media type."
   DEFVAL     { 0 }
::= { mscVrPpIpPortProvEntry 2 }

mscVrPpIpPortArpStatus OBJECT-TYPE
   SYNTAX     INTEGER  {
                 enabled(1),
                 disabled(2),
                 auto(3) }
   ACCESS     read-write
   STATUS     mandatory
   DESCRIPTION
     "This attribute specifies whether ARP is enabled or disabled on this 
      IpPort. If auto is specified, an appropriate value will be selected based 
      on the IpPort media type."
   DEFVAL     { auto }
::= { mscVrPpIpPortProvEntry 3 }

mscVrPpIpPortProxyArpStatus OBJECT-TYPE
   SYNTAX     INTEGER  {
                 enabled(1),
                 disabled(2) }
   ACCESS     read-write
   STATUS     mandatory
   DESCRIPTION
     "This attribute specifies whether Proxy ARP is enabled or disabled for 
      this IpPort."
   DEFVAL     { disabled }
::= { mscVrPpIpPortProvEntry 4 }

mscVrPpIpPortArpNoLearn OBJECT-TYPE
   SYNTAX     INTEGER  {
                 enabled(1),
                 disabled(2) }
   ACCESS     read-write
   STATUS     mandatory
   DESCRIPTION
     "This attribute specifies whether or not dynamic host entries will be 
      installed in the ARP table when ARP packets are received on this 
      IpPort."
   DEFVAL     { disabled }
::= { mscVrPpIpPortProvEntry 5 }

mscVrPpIpPortSendRedirect OBJECT-TYPE
   SYNTAX     INTEGER  {
                 enabled(1),
                 disabled(2) }
   ACCESS     read-write
   STATUS     mandatory
   DESCRIPTION
     "This attribute specifies whether or not ICMP host redirects will be sent 
      out this IpPort."
   DEFVAL     { enabled }
::= { mscVrPpIpPortProvEntry 6 }

mscVrPpIpPortMulticastStatus OBJECT-TYPE
   SYNTAX     INTEGER  {
                 enabled(1),
                 disabled(2),
                 auto(3) }
   ACCESS     read-write
   STATUS     mandatory
   DESCRIPTION
     "This attribute specifies whether or not IP multicast packets can be sent 
      out this IpPort. If auto is specified, an appropriate value will be selected 
      based on the IpPort media type."
   DEFVAL     { auto }
::= { mscVrPpIpPortProvEntry 7 }

mscVrPpIpPortRelayAddress OBJECT-TYPE
   SYNTAX     IpAddress 
   ACCESS     read-write
   STATUS     mandatory
   DESCRIPTION
     "This attribute specifies a relay broadcast address for this IpPort. Each 
      packet, received on this IpPort, meeting the relay broadcast criteria will 
      be forwarded to the specified relay broadcast address. An relay address 
      of all zero's indicates no relay broadcast address."
   DEFVAL     { '00000000'H }  -- "0.0.0.0"
::= { mscVrPpIpPortProvEntry 8 }

mscVrPpIpPortRelayBroadcast OBJECT-TYPE
   SYNTAX     INTEGER  {
                 enabled(1),
                 disabled(2),
                 auto(3) }
   ACCESS     read-write
   STATUS     mandatory
   DESCRIPTION
     "This attribute specifies how packets, received on other IpPorts, meeting 
      the relay broadcast criteria, will be forwarded out this IpPort. The three 
      options are described as follows:
      enabled: packets will be forwarded out this IpPort.
      disabled: packets will not be forwarded out this IpPort.
      auto: packets will be forwarded out this IpPort only when the bridge 
      state is forwarding."
   DEFVAL     { disabled }
::= { mscVrPpIpPortProvEntry 9 }

mscVrPpIpPortLinkModel OBJECT-TYPE
   SYNTAX     INTEGER  {
                 localAreaNetwork(1),
                 pointToPoint(2) }
   ACCESS     read-write
   STATUS     mandatory
   DESCRIPTION
     "This attribute specifies the link model to use when the media type for 
      this IpPort is PPP (Point to Point Protocol). A value of 
      localAreaNetwork causes IP to treat this IpPort like a LAN. A value of 
      pointToPoint causes IP to treat this IpPort like two directly connected 
      IP hosts."
   DEFVAL     { localAreaNetwork }
::= { mscVrPpIpPortProvEntry 10 }

mscVrPpIpPortLanModel OBJECT-TYPE
   SYNTAX     INTEGER  {
                 localAreaNetwork(1),
                 nonBroadcastMultipleAccess(2) }
   ACCESS     read-write
   STATUS     mandatory
   DESCRIPTION
     "This attribute specifies the lan model to use for this IpPort."
   DEFVAL     { localAreaNetwork }
::= { mscVrPpIpPortProvEntry 11 }

mscVrPpIpPortEncap OBJECT-TYPE
   SYNTAX     INTEGER  {
                 ieee8023(1),
                 ethernet(2),
                 auto(3) }
   ACCESS     read-write
   STATUS     mandatory
   DESCRIPTION
     "This attribute specifies the encapsulation type to be used when sending 
      packets out this IpPort. If auto is specified, an appropriate value is 
      selected based on the IpPort media type. The values ieee8023 and 
      ethernet can only be specified if the media type is ethernet. Otherwise, 
      auto must be specified. For ethernet media type, the default 
      encapsulation is ethernet."
   DEFVAL     { auto }
::= { mscVrPpIpPortProvEntry 12 }

mscVrPpIpPortIcmpMaskReply OBJECT-TYPE
   SYNTAX     INTEGER  {
                 enabled(1),
                 disabled(2) }
   ACCESS     read-write
   STATUS     mandatory
   DESCRIPTION
     "This attribute specifies whether or not replies will be generated in 
      response to ICMP Address Mask Requests received on this IpPort."
   DEFVAL     { enabled }
::= { mscVrPpIpPortProvEntry 13 }

mscVrPpIpPortDirectedBroadcast OBJECT-TYPE
   SYNTAX     INTEGER  {
                 enabled(1),
                 disabled(2) }
   ACCESS     read-write
   STATUS     mandatory
   DESCRIPTION
     "This attribute specifies whether or not directed broadcast to physical 
      broadcast translation is enabled for incoming traffic on this IpPort. The 
      IP router requirement (RFC1812) says this translation should be 
      enabled; however, in some network environments, setting this attribute 
      to disabled may prevent operational problem such as broadcast storms. 
      Note that in some configuration, setting this attribute to disabled may 
      cause Bootp to fail."
   DEFVAL     { enabled }
::= { mscVrPpIpPortProvEntry 14 }

mscVrPpIpPortAssignedQos OBJECT-TYPE
   SYNTAX     Unsigned32 (0..3)
   ACCESS     read-write
   STATUS     mandatory
   DESCRIPTION
     "This attribute specifies the initial Class of Service (CoS) given to each 
      packet received on the IpPort. The CoS value n is used to select Vr/
      <string> QosP/n. which determines the QualityofService-Profile to be 
      used when the packet is forwarded.
      
      The initial CoS given to a packet by the assignedQoS attribute may be 
      overridden under certain circumstances (see the description of the Vr 
      Qosp component, the cosPolicyAssignment attribute on the IpPort and Ip 
      components, and the ipCos attribute on any of the frameRelayDte 
      staticDlci, frameRelayDte dynamicDlciDefaults, and atmMpe 
      atmConnection components)."
   DEFVAL     { 0 }
::= { mscVrPpIpPortProvEntry 15 }

mscVrPpIpPortAllowMcastMacDest OBJECT-TYPE
   SYNTAX     INTEGER  {
                 enabled(1),
                 disabled(2) }
   ACCESS     read-write
   STATUS     mandatory
   DESCRIPTION
     "This attribute specifies whether a multicast destination MAC address is 
      valid on this IpPort or not. Enabling it is non-standard. It can be used for 
      applications such as transparent server backup. Multicast destination 
      MAC address is only supported on LAN media."
   DEFVAL     { disabled }
::= { mscVrPpIpPortProvEntry 16 }

mscVrPpIpPortCosPolicyAssignment OBJECT-TYPE
   SYNTAX     Link 
   ACCESS     read-write
   STATUS     mandatory
   DESCRIPTION
     "This attribute specifies the CosPolicyGroup component this IpPort 
      component is using. Assigning a particular policy group to the IpPort 
      may override the effect of the assignedQos; this depends on the actual 
      policies provisioned under the policy group."
::= { mscVrPpIpPortProvEntry 17 }

mscVrPpIpPortSresProvTable OBJECT-TYPE
   SYNTAX     SEQUENCE OF MscVrPpIpPortSresProvEntry
   ACCESS     not-accessible
   STATUS     mandatory
   DESCRIPTION
     "This group contains the provisioned attributes for 
      SourceRouteEndStation support."
::= { mscVrPpIpPort 11 }

mscVrPpIpPortSresProvEntry OBJECT-TYPE
   SYNTAX     MscVrPpIpPortSresProvEntry
   ACCESS     not-accessible
   STATUS     mandatory
   DESCRIPTION
     "An entry in the mscVrPpIpPortSresProvTable."
   INDEX {
      mscVrIndex,
      mscVrPpIndex,
      mscVrPpIpPortIndex }
::= { mscVrPpIpPortSresProvTable 1 }

MscVrPpIpPortSresProvEntry ::= SEQUENCE {
   mscVrPpIpPortSourceRouteEndStationSupport
      INTEGER }

mscVrPpIpPortSourceRouteEndStationSupport OBJECT-TYPE
   SYNTAX     INTEGER  {
                 enable(1),
                 disable(2) }
   ACCESS     read-write
   STATUS     mandatory
   DESCRIPTION
     "This attribute is used to enable or disable support for 
      SourceRouteEndStation (Sres). If set to enable, Sres will be supported 
      on this protocol on this ProtocolPort (Pp). If set to disable, it will not be 
      supported. An Sres component must be provisioned under the 
      VirtualRouter if this attribute is set to enable. If this attribute is set to 
      enable and this Pp has its linkToMedia attribute set, it must be linked to 
      a LanApplication (La) that has its Framer interfaceName linked to a 
      Fddi or TokenRing component."
   DEFVAL     { disable }
::= { mscVrPpIpPortSresProvEntry 1 }

mscVrPpIpPortAdminControlTable OBJECT-TYPE
   SYNTAX     SEQUENCE OF MscVrPpIpPortAdminControlEntry
   ACCESS     not-accessible
   STATUS     mandatory
   DESCRIPTION
     "This group includes the Administrative Control attribute. This 
      attribute defines the current administrative state of this component."
::= { mscVrPpIpPort 12 }

mscVrPpIpPortAdminControlEntry OBJECT-TYPE
   SYNTAX     MscVrPpIpPortAdminControlEntry
   ACCESS     not-accessible
   STATUS     mandatory
   DESCRIPTION
     "An entry in the mscVrPpIpPortAdminControlTable."
   INDEX {
      mscVrIndex,
      mscVrPpIndex,
      mscVrPpIpPortIndex }
::= { mscVrPpIpPortAdminControlTable 1 }

MscVrPpIpPortAdminControlEntry ::= SEQUENCE {
   mscVrPpIpPortSnmpAdminStatus
      INTEGER }

mscVrPpIpPortSnmpAdminStatus OBJECT-TYPE
   SYNTAX     INTEGER  {
                 up(1),
                 down(2),
                 testing(3) }
   ACCESS     read-write
   STATUS     mandatory
   DESCRIPTION
     "The desired state of the interface. The up state indicates the 
      interface is operational and packet forwarding is allowed. The down 
      state indicates the interface is not operational and packet forwarding 
      is unavailable. The testing state indicates that no operational 
      packets can be passed."
   DEFVAL     { up }
::= { mscVrPpIpPortAdminControlEntry 1 }

mscVrPpIpPortOperTable OBJECT-TYPE
   SYNTAX     SEQUENCE OF MscVrPpIpPortOperEntry
   ACCESS     not-accessible
   STATUS     mandatory
   DESCRIPTION
     "This group contains operational attributes for an IpPort."
::= { mscVrPpIpPort 13 }

mscVrPpIpPortOperEntry OBJECT-TYPE
   SYNTAX     MscVrPpIpPortOperEntry
   ACCESS     not-accessible
   STATUS     mandatory
   DESCRIPTION
     "An entry in the mscVrPpIpPortOperTable."
   INDEX {
      mscVrIndex,
      mscVrPpIndex,
      mscVrPpIpPortIndex }
::= { mscVrPpIpPortOperTable 1 }

MscVrPpIpPortOperEntry ::= SEQUENCE {
   mscVrPpIpPortMediaType
      INTEGER,
   mscVrPpIpPortOperMtu
      Unsigned32,
   mscVrPpIpPortOperArpStatus
      INTEGER,
   mscVrPpIpPortOperMulticastStatus
      INTEGER,
   mscVrPpIpPortOperEncap
      INTEGER,
   mscVrPpIpPortOperCosPolicyAssignment
      RowPointer }

mscVrPpIpPortMediaType OBJECT-TYPE
   SYNTAX     INTEGER  {
                 ethernet(1),
                 fddi(2),
                 tokenRing(3),
                 ppp(4),
                 vcpEther(5),
                 vcpToken(6),
                 vns(7),
                 x25(8),
                 frameRelay(9),
                 clusterBridge(10),
                 smds(11),
                 invalid(12),
                 atmMpeVcEncap(13),
                 atmMpeLlcEncap(14),
                 lecEther(15),
                 lecToken(16),
                 tunnel(17),
                 virtual(18) }
   ACCESS     read-only
   STATUS     mandatory
   DESCRIPTION
     "This attribute indicates the media type of this IpPort."
   DEFVAL     { invalid }
::= { mscVrPpIpPortOperEntry 1 }

mscVrPpIpPortOperMtu OBJECT-TYPE
   SYNTAX     Unsigned32 (0..0 | 576..18944)
   ACCESS     read-only
   STATUS     mandatory
   DESCRIPTION
     "This attribute indicates the current operational IP MTU for this IpPort. 
      Note that this value may be different than the provisioned maxTxUnit."
   DEFVAL     { 0 }
::= { mscVrPpIpPortOperEntry 2 }

mscVrPpIpPortOperArpStatus OBJECT-TYPE
   SYNTAX     INTEGER  {
                 enabled(1),
                 disabled(2) }
   ACCESS     read-only
   STATUS     mandatory
   DESCRIPTION
     "This attribute indicates the current operational ARP status. If the 
      provisioned arpStatus is set to auto, then the IP application 
      automatically determines the operArpStatus based on the IpPort media 
      type."
   DEFVAL     { disabled }
::= { mscVrPpIpPortOperEntry 3 }

mscVrPpIpPortOperMulticastStatus OBJECT-TYPE
   SYNTAX     INTEGER  {
                 enabled(1),
                 disabled(2) }
   ACCESS     read-only
   STATUS     mandatory
   DESCRIPTION
     "This attribute indicates the current operational Multicast status. If the 
      provisioned multicastStatus is set to auto, then the IP application 
      automatically determines the operMulticastStatus based on the IpPort 
      media type."
   DEFVAL     { disabled }
::= { mscVrPpIpPortOperEntry 4 }

mscVrPpIpPortOperEncap OBJECT-TYPE
   SYNTAX     INTEGER  {
                 ieee8023(1),
                 ethernet(2),
                 notApplicable(3) }
   ACCESS     read-only
   STATUS     mandatory
   DESCRIPTION
     "This attribute indicates the current operational encapsulation type. If the 
      provisioned encap is set to auto, then the IP application automatically 
      determines the operEncap based on the IpPort media type."
   DEFVAL     { notApplicable }
::= { mscVrPpIpPortOperEntry 5 }

mscVrPpIpPortOperCosPolicyAssignment OBJECT-TYPE
   SYNTAX     RowPointer 
   ACCESS     read-only
   STATUS     mandatory
   DESCRIPTION
     "This attribute specifies the CosPolicyGroup component this IpPort 
      component is using."
::= { mscVrPpIpPortOperEntry 433 }

mscVrPpIpPortRelayBcOperTable OBJECT-TYPE
   SYNTAX     SEQUENCE OF MscVrPpIpPortRelayBcOperEntry
   ACCESS     not-accessible
   STATUS     mandatory
   DESCRIPTION
     "This group contains operational attributes for an IpPort's RelayBc 
      counters."
::= { mscVrPpIpPort 14 }

mscVrPpIpPortRelayBcOperEntry OBJECT-TYPE
   SYNTAX     MscVrPpIpPortRelayBcOperEntry
   ACCESS     not-accessible
   STATUS     mandatory
   DESCRIPTION
     "An entry in the mscVrPpIpPortRelayBcOperTable."
   INDEX {
      mscVrIndex,
      mscVrPpIndex,
      mscVrPpIpPortIndex }
::= { mscVrPpIpPortRelayBcOperTable 1 }

MscVrPpIpPortRelayBcOperEntry ::= SEQUENCE {
   mscVrPpIpPortRelayAddressCount
      Counter32,
   mscVrPpIpPortRelayBcCount
      Counter32 }

mscVrPpIpPortRelayAddressCount OBJECT-TYPE
   SYNTAX     Counter32 
   ACCESS     read-only
   STATUS     mandatory
   DESCRIPTION
     "This attribute indicates the number of frames received on this IpPort 
      which were forwarded to the provisioned relayAddress for this port. This 
      counter wraps to zero when it reaches it's maximum."
::= { mscVrPpIpPortRelayBcOperEntry 1 }

mscVrPpIpPortRelayBcCount OBJECT-TYPE
   SYNTAX     Counter32 
   ACCESS     read-only
   STATUS     mandatory
   DESCRIPTION
     "This attribute indicates the number of frames received on this port which 
      were forwarded to the broadcastAddress on other IpPorts. This counter 
      is incremented once for every frame received on this port regardless of 
      how many other ports it was sent on. This counter wraps to zero when it 
      reaches it's maximum."
::= { mscVrPpIpPortRelayBcOperEntry 2 }

mscVrPpIpPortStateTable OBJECT-TYPE
   SYNTAX     SEQUENCE OF MscVrPpIpPortStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscVrPpIpPort 15 }

mscVrPpIpPortStateEntry OBJECT-TYPE
   SYNTAX     MscVrPpIpPortStateEntry
   ACCESS     not-accessible
   STATUS     mandatory
   DESCRIPTION
     "An entry in the mscVrPpIpPortStateTable."
   INDEX {
      mscVrIndex,
      mscVrPpIndex,
      mscVrPpIpPortIndex }
::= { mscVrPpIpPortStateTable 1 }

MscVrPpIpPortStateEntry ::= SEQUENCE {
   mscVrPpIpPortAdminState
      INTEGER,
   mscVrPpIpPortOperationalState
      INTEGER,
   mscVrPpIpPortUsageState
      INTEGER }

mscVrPpIpPortAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscVrPpIpPortStateEntry 1 }

mscVrPpIpPortOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscVrPpIpPortStateEntry 2 }

mscVrPpIpPortUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscVrPpIpPortStateEntry 3 }

mscVrPpIpPortOperStatusTable OBJECT-TYPE
   SYNTAX     SEQUENCE OF MscVrPpIpPortOperStatusEntry
   ACCESS     not-accessible
   STATUS     mandatory
   DESCRIPTION
     "This group includes the Operational Status attribute. This attribute 
      defines the current operational state of this component."
::= { mscVrPpIpPort 16 }

mscVrPpIpPortOperStatusEntry OBJECT-TYPE
   SYNTAX     MscVrPpIpPortOperStatusEntry
   ACCESS     not-accessible
   STATUS     mandatory
   DESCRIPTION
     "An entry in the mscVrPpIpPortOperStatusTable."
   INDEX {
      mscVrIndex,
      mscVrPpIndex,
      mscVrPpIpPortIndex }
::= { mscVrPpIpPortOperStatusTable 1 }

MscVrPpIpPortOperStatusEntry ::= SEQUENCE {
   mscVrPpIpPortSnmpOperStatus
      INTEGER }

mscVrPpIpPortSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscVrPpIpPortOperStatusEntry 1 }


-- The IpLogicalIf component defines a single IpPort address on a logical 
-- IP network. In general, IpPort's can have multiple IpLogicalIf's. 
-- However, if the media type is PPP (Point to Point Protocol), then only 
-- one IpLogicalIf is allowed for that IpPort.

mscVrPpIpPortLogicalIf OBJECT IDENTIFIER ::= { mscVrPpIpPort 2 }



mscVrPpIpPortLogicalIfRowStatusTable OBJECT-TYPE
   SYNTAX     SEQUENCE OF MscVrPpIpPortLogicalIfRowStatusEntry
   ACCESS     not-accessible
   STATUS     mandatory
   DESCRIPTION
     "This entry controls the addition and deletion of 
      mscVrPpIpPortLogicalIf components."
::= { mscVrPpIpPortLogicalIf 1 }

mscVrPpIpPortLogicalIfRowStatusEntry OBJECT-TYPE
   SYNTAX     MscVrPpIpPortLogicalIfRowStatusEntry
   ACCESS     not-accessible
   STATUS     mandatory
   DESCRIPTION
     "A single entry in the table represents a single 
      mscVrPpIpPortLogicalIf component."
   INDEX {
      mscVrIndex,
      mscVrPpIndex,
      mscVrPpIpPortIndex,
      mscVrPpIpPortLogicalIfAddressIndex }
::= { mscVrPpIpPortLogicalIfRowStatusTable 1 }

MscVrPpIpPortLogicalIfRowStatusEntry ::= SEQUENCE {
   mscVrPpIpPortLogicalIfRowStatus
      RowStatus,
   mscVrPpIpPortLogicalIfComponentName
      DisplayString,
   mscVrPpIpPortLogicalIfStorageType
      StorageType,
   mscVrPpIpPortLogicalIfAddressIndex
      IpAddress }

mscVrPpIpPortLogicalIfRowStatus OBJECT-TYPE
   SYNTAX     RowStatus 
   ACCESS     read-write
   STATUS     mandatory
   DESCRIPTION
     "This variable is used as the basis for SNMP naming of
      mscVrPpIpPortLogicalIf components.
      These components can be added and deleted."
::= { mscVrPpIpPortLogicalIfRowStatusEntry 1 }

mscVrPpIpPortLogicalIfComponentName OBJECT-TYPE
   SYNTAX     DisplayString 
   ACCESS     read-only
   STATUS     mandatory
   DESCRIPTION
     "This variable provides the component's string name for
      use with the ASCII Console Interface"
::= { mscVrPpIpPortLogicalIfRowStatusEntry 2 }

mscVrPpIpPortLogicalIfStorageType OBJECT-TYPE
   SYNTAX     StorageType 
   ACCESS     read-only
   STATUS     mandatory
   DESCRIPTION
     "This variable represents the storage type value for the
      mscVrPpIpPortLogicalIf tables."
::= { mscVrPpIpPortLogicalIfRowStatusEntry 4 }

mscVrPpIpPortLogicalIfAddressIndex OBJECT-TYPE
   SYNTAX     IpAddress 
   ACCESS     not-accessible
   STATUS     mandatory
   DESCRIPTION
     "This variable represents the index for the mscVrPpIpPortLogicalIf tables."
::= { mscVrPpIpPortLogicalIfRowStatusEntry 10 }

mscVrPpIpPortLogicalIfProvTable OBJECT-TYPE
   SYNTAX     SEQUENCE OF MscVrPpIpPortLogicalIfProvEntry
   ACCESS     not-accessible
   STATUS     mandatory
   DESCRIPTION
     "This group contains attributes required to define an IpLogicalIf."
::= { mscVrPpIpPortLogicalIf 10 }

mscVrPpIpPortLogicalIfProvEntry OBJECT-TYPE
   SYNTAX     MscVrPpIpPortLogicalIfProvEntry
   ACCESS     not-accessible
   STATUS     mandatory
   DESCRIPTION
     "An entry in the mscVrPpIpPortLogicalIfProvTable."
   INDEX {
      mscVrIndex,
      mscVrPpIndex,
      mscVrPpIpPortIndex,
      mscVrPpIpPortLogicalIfAddressIndex }
::= { mscVrPpIpPortLogicalIfProvTable 1 }

MscVrPpIpPortLogicalIfProvEntry ::= SEQUENCE {
   mscVrPpIpPortLogicalIfNetMask
      IpAddress,
   mscVrPpIpPortLogicalIfBroadcastAddress
      IpAddress,
   mscVrPpIpPortLogicalIfLinkDestinationAddress
      IpAddress }

mscVrPpIpPortLogicalIfNetMask OBJECT-TYPE
   SYNTAX     IpAddress 
   ACCESS     read-write
   STATUS     mandatory
   DESCRIPTION
     "This attribute specifies the subnet mask for this IpLogicalIf. This 
      attribute must be specified because the IP application will not 
      automatically provide a default value."
   DEFVAL     { '00000000'H }  -- "0.0.0.0"
::= { mscVrPpIpPortLogicalIfProvEntry 1 }

mscVrPpIpPortLogicalIfBroadcastAddress OBJECT-TYPE
   SYNTAX     IpAddress 
   ACCESS     read-write
   STATUS     mandatory
   DESCRIPTION
     "This attribute specifies the broadcast address for this IpLogicalIf. This 
      attribute is ignored if the IpPort mediaType is ppp (Point to Point 
      Protocol). If the value is 0.0.0.0, the actual broadcast address will be 
      derived from the IP address of this LogicalIf and the netmask attribute."
   DEFVAL     { '00000000'H }  -- "0.0.0.0"
::= { mscVrPpIpPortLogicalIfProvEntry 2 }

mscVrPpIpPortLogicalIfLinkDestinationAddress OBJECT-TYPE
   SYNTAX     IpAddress 
   ACCESS     read-write
   STATUS     mandatory
   DESCRIPTION
     "This attribute specifies the address for the link destination for this 
      IpLogicalIf. This attribute is only required if the IpPort media type is 
      PPP (Point to Point Protocol)."
   DEFVAL     { '00000000'H }  -- "0.0.0.0"
::= { mscVrPpIpPortLogicalIfProvEntry 3 }


-- Vr/<string> Pp/<string> IpPort logicalIf/<Ip Address> ospfIf
-- An OspfIf component can be created under each logicalIf to run OSPF 
-- protocol.

mscVrPpIpPortLogicalIfOspfIf OBJECT IDENTIFIER ::= { mscVrPpIpPortLogicalIf 2 }



mscVrPpIpPortLogicalIfOspfIfRowStatusTable OBJECT-TYPE
   SYNTAX     SEQUENCE OF MscVrPpIpPortLogicalIfOspfIfRowStatusEntry
   ACCESS     not-accessible
   STATUS     mandatory
   DESCRIPTION
     "This entry controls the addition and deletion of 
      mscVrPpIpPortLogicalIfOspfIf components."
::= { mscVrPpIpPortLogicalIfOspfIf 1 }

mscVrPpIpPortLogicalIfOspfIfRowStatusEntry OBJECT-TYPE
   SYNTAX     MscVrPpIpPortLogicalIfOspfIfRowStatusEntry
   ACCESS     not-accessible
   STATUS     mandatory
   DESCRIPTION
     "A single entry in the table represents a single 
      mscVrPpIpPortLogicalIfOspfIf component."
   INDEX {
      mscVrIndex,
      mscVrPpIndex,
      mscVrPpIpPortIndex,
      mscVrPpIpPortLogicalIfAddressIndex,
      mscVrPpIpPortLogicalIfOspfIfIndex }
::= { mscVrPpIpPortLogicalIfOspfIfRowStatusTable 1 }

MscVrPpIpPortLogicalIfOspfIfRowStatusEntry ::= SEQUENCE {
   mscVrPpIpPortLogicalIfOspfIfRowStatus
      RowStatus,
   mscVrPpIpPortLogicalIfOspfIfComponentName
      DisplayString,
   mscVrPpIpPortLogicalIfOspfIfStorageType
      StorageType,
   mscVrPpIpPortLogicalIfOspfIfIndex
      NonReplicated }

mscVrPpIpPortLogicalIfOspfIfRowStatus OBJECT-TYPE
   SYNTAX     RowStatus 
   ACCESS     read-write
   STATUS     mandatory
   DESCRIPTION
     "This variable is used as the basis for SNMP naming of
      mscVrPpIpPortLogicalIfOspfIf components.
      These components can be added and deleted."
::= { mscVrPpIpPortLogicalIfOspfIfRowStatusEntry 1 }

mscVrPpIpPortLogicalIfOspfIfComponentName OBJECT-TYPE
   SYNTAX     DisplayString 
   ACCESS     read-only
   STATUS     mandatory
   DESCRIPTION
     "This variable provides the component's string name for
      use with the ASCII Console Interface"
::= { mscVrPpIpPortLogicalIfOspfIfRowStatusEntry 2 }

mscVrPpIpPortLogicalIfOspfIfStorageType OBJECT-TYPE
   SYNTAX     StorageType 
   ACCESS     read-only
   STATUS     mandatory
   DESCRIPTION
     "This variable represents the storage type value for the
      mscVrPpIpPortLogicalIfOspfIf tables."
::= { mscVrPpIpPortLogicalIfOspfIfRowStatusEntry 4 }

mscVrPpIpPortLogicalIfOspfIfIndex OBJECT-TYPE
   SYNTAX     NonReplicated 
   ACCESS     not-accessible
   STATUS     mandatory
   DESCRIPTION
     "This variable represents the index for the mscVrPpIpPortLogicalIfOspfIf tables."
::= { mscVrPpIpPortLogicalIfOspfIfRowStatusEntry 10 }

mscVrPpIpPortLogicalIfOspfIfProvTable OBJECT-TYPE
   SYNTAX     SEQUENCE OF MscVrPpIpPortLogicalIfOspfIfProvEntry
   ACCESS     not-accessible
   STATUS     mandatory
   DESCRIPTION
     "This group of attributes identifies a provisionable set of attributes."
::= { mscVrPpIpPortLogicalIfOspfIf 10 }

mscVrPpIpPortLogicalIfOspfIfProvEntry OBJECT-TYPE
   SYNTAX     MscVrPpIpPortLogicalIfOspfIfProvEntry
   ACCESS     not-accessible
   STATUS     mandatory
   DESCRIPTION
     "An entry in the mscVrPpIpPortLogicalIfOspfIfProvTable."
   INDEX {
      mscVrIndex,
      mscVrPpIndex,
      mscVrPpIpPortIndex,
      mscVrPpIpPortLogicalIfAddressIndex,
      mscVrPpIpPortLogicalIfOspfIfIndex }
::= { mscVrPpIpPortLogicalIfOspfIfProvTable 1 }

MscVrPpIpPortLogicalIfOspfIfProvEntry ::= SEQUENCE {
   mscVrPpIpPortLogicalIfOspfIfAreaId
      AreaID,
   mscVrPpIpPortLogicalIfOspfIfIfType
      INTEGER,
   mscVrPpIpPortLogicalIfOspfIfSnmpAdminStatus
      INTEGER,
   mscVrPpIpPortLogicalIfOspfIfRtrPriority
      Unsigned32,
   mscVrPpIpPortLogicalIfOspfIfTransitDelay
      Unsigned32,
   mscVrPpIpPortLogicalIfOspfIfRetransInterval
      Unsigned32,
   mscVrPpIpPortLogicalIfOspfIfHelloInterval
      Unsigned32,
   mscVrPpIpPortLogicalIfOspfIfRtrDeadInterval
      Unsigned32,
   mscVrPpIpPortLogicalIfOspfIfPollInterval
      Unsigned32,
   mscVrPpIpPortLogicalIfOspfIfAuthKey
      HexString,
   mscVrPpIpPortLogicalIfOspfIfMulticastForwarding
      INTEGER }

mscVrPpIpPortLogicalIfOspfIfAreaId OBJECT-TYPE
   SYNTAX     AreaID 
   ACCESS     read-write
   STATUS     mandatory
   DESCRIPTION
     "The area Id this Ospf interface belongs to."
   DEFVAL     { '00000000'H }  -- "0.0.0.0"
::= { mscVrPpIpPortLogicalIfOspfIfProvEntry 1 }

mscVrPpIpPortLogicalIfOspfIfIfType OBJECT-TYPE
   SYNTAX     INTEGER  {
                 broadcast(1),
                 nbma(2),
                 pointToPoint(3) }
   ACCESS     read-write
   STATUS     mandatory
   DESCRIPTION
     "This attribute indicates the type of this Ospf interface. This interface 
      type does not necessarily correlate with the type of the interface set on 
      the logicalIf entry under IpPort."
::= { mscVrPpIpPortLogicalIfOspfIfProvEntry 2 }

mscVrPpIpPortLogicalIfOspfIfSnmpAdminStatus OBJECT-TYPE
   SYNTAX     INTEGER  {
                 up(1),
                 down(2) }
   ACCESS     read-write
   STATUS     mandatory
   DESCRIPTION
     "The administrative status of this Ospf interface."
   DEFVAL     { up }
::= { mscVrPpIpPortLogicalIfOspfIfProvEntry 3 }

mscVrPpIpPortLogicalIfOspfIfRtrPriority OBJECT-TYPE
   SYNTAX     Unsigned32 (0..255)
   ACCESS     read-write
   STATUS     mandatory
   DESCRIPTION
     "The priority of this interface. Used in multi-access networks, this field is 
      used in the designated router election algorithm. The value 0 signifies 
      that the router is not eligible to become the designated router on this 
      particular protocol port. In the event of a tie in this value, routers will 
      use their routerId as a tie breaker."
   DEFVAL     { 1 }
::= { mscVrPpIpPortLogicalIfOspfIfProvEntry 4 }

mscVrPpIpPortLogicalIfOspfIfTransitDelay OBJECT-TYPE
   SYNTAX     Unsigned32 (1..3600)
   ACCESS     read-write
   STATUS     mandatory
   DESCRIPTION
     "The estimated number of seconds it takes to transmit a link-state update 
      packet over this interface."
   DEFVAL     { 1 }
::= { mscVrPpIpPortLogicalIfOspfIfProvEntry 5 }

mscVrPpIpPortLogicalIfOspfIfRetransInterval OBJECT-TYPE
   SYNTAX     Unsigned32 (1..3600)
   ACCESS     read-write
   STATUS     mandatory
   DESCRIPTION
     "The number of seconds between link-state advertisements 
      retransmissions, for adjacencies belonging to this interface. This value is 
      also used when retransmitting database description and link-state 
      request packets."
   DEFVAL     { 5 }
::= { mscVrPpIpPortLogicalIfOspfIfProvEntry 6 }

mscVrPpIpPortLogicalIfOspfIfHelloInterval OBJECT-TYPE
   SYNTAX     Unsigned32 (1..3600)
   ACCESS     read-write
   STATUS     mandatory
   DESCRIPTION
     "The length of time, in seconds, between the Hello packets that the router 
      sends on the interface. This value must be the same for all routers 
      attached to a common network."
   DEFVAL     { 10 }
::= { mscVrPpIpPortLogicalIfOspfIfProvEntry 7 }

mscVrPpIpPortLogicalIfOspfIfRtrDeadInterval OBJECT-TYPE
   SYNTAX     Unsigned32 (1..3600)
   ACCESS     read-write
   STATUS     mandatory
   DESCRIPTION
     "The number of seconds that a router's hello packets have not been seen 
      before it's neighbors declare the router down. This should be some 
      multiple of the helloIntereval. This value must be the same for all 
      routers attached to a common network."
   DEFVAL     { 40 }
::= { mscVrPpIpPortLogicalIfOspfIfProvEntry 8 }

mscVrPpIpPortLogicalIfOspfIfPollInterval OBJECT-TYPE
   SYNTAX     Unsigned32 (1..3600)
   ACCESS     read-write
   STATUS     mandatory
   DESCRIPTION
     "The largest time interval, in seconds, between the hello packets sent to 
      an inactive non-broadcast multi-access neighbor."
   DEFVAL     { 120 }
::= { mscVrPpIpPortLogicalIfOspfIfProvEntry 9 }

mscVrPpIpPortLogicalIfOspfIfAuthKey OBJECT-TYPE
   SYNTAX     HexString (SIZE (1..8))
   ACCESS     write-only
   STATUS     mandatory
   DESCRIPTION
     "The Authentication Key. If the value of the attribute authType of an 
      AreaEntry is simplePassword, and the authKey length is shorter than 8 
      octets, then the value of authKey will be left adjusted zero-filled to 8 
      octets."
   DEFVAL     { '0000000000000000'H }  -- "0000000000000000"
::= { mscVrPpIpPortLogicalIfOspfIfProvEntry 10 }

mscVrPpIpPortLogicalIfOspfIfMulticastForwarding OBJECT-TYPE
   SYNTAX     INTEGER  {
                 blocked(1) }
   ACCESS     read-write
   STATUS     mandatory
   DESCRIPTION
     "The way multicasts should be forwarded on this interface; non 
      forwarded, forwarded as data-link multicasts, or forwarded as data-link 
      unicasts. Data-link multicasting is not meaningful on point-to-point and 
      NBMA(No Broadcast Multi Access) interfaces, and setting this attribute 
      to blocked effectively disables all multicast forwarding."
   DEFVAL     { blocked }
::= { mscVrPpIpPortLogicalIfOspfIfProvEntry 12 }

mscVrPpIpPortLogicalIfOspfIfOperTable OBJECT-TYPE
   SYNTAX     SEQUENCE OF MscVrPpIpPortLogicalIfOspfIfOperEntry
   ACCESS     not-accessible
   STATUS     mandatory
   DESCRIPTION
     "This group of attributes identifies operational state that this interface is 
      performing."
::= { mscVrPpIpPortLogicalIfOspfIf 11 }

mscVrPpIpPortLogicalIfOspfIfOperEntry OBJECT-TYPE
   SYNTAX     MscVrPpIpPortLogicalIfOspfIfOperEntry
   ACCESS     not-accessible
   STATUS     mandatory
   DESCRIPTION
     "An entry in the mscVrPpIpPortLogicalIfOspfIfOperTable."
   INDEX {
      mscVrIndex,
      mscVrPpIndex,
      mscVrPpIpPortIndex,
      mscVrPpIpPortLogicalIfAddressIndex,
      mscVrPpIpPortLogicalIfOspfIfIndex }
::= { mscVrPpIpPortLogicalIfOspfIfOperTable 1 }

MscVrPpIpPortLogicalIfOspfIfOperEntry ::= SEQUENCE {
   mscVrPpIpPortLogicalIfOspfIfState
      INTEGER,
   mscVrPpIpPortLogicalIfOspfIfDesignatedRouter
      IpAddress,
   mscVrPpIpPortLogicalIfOspfIfBackupDesignatedRouter
      IpAddress,
   mscVrPpIpPortLogicalIfOspfIfEvents
      Counter32 }

mscVrPpIpPortLogicalIfOspfIfState OBJECT-TYPE
   SYNTAX     INTEGER  {
                 down(1),
                 loopback(2),
                 waiting(3),
                 pointToPoint(4),
                 designatedRouter(5),
                 backupDesignatedRouter(6),
                 otherDesignatedRouter(7) }
   ACCESS     read-only
   STATUS     mandatory
   DESCRIPTION
     "The state of the OSPF interface."
   DEFVAL     { designatedRouter }
::= { mscVrPpIpPortLogicalIfOspfIfOperEntry 1 }

mscVrPpIpPortLogicalIfOspfIfDesignatedRouter OBJECT-TYPE
   SYNTAX     IpAddress 
   ACCESS     read-only
   STATUS     mandatory
   DESCRIPTION
     "The Ip address of the designated router."
::= { mscVrPpIpPortLogicalIfOspfIfOperEntry 2 }

mscVrPpIpPortLogicalIfOspfIfBackupDesignatedRouter OBJECT-TYPE
   SYNTAX     IpAddress 
   ACCESS     read-only
   STATUS     mandatory
   DESCRIPTION
     "The Ip address of the backup designated router"
::= { mscVrPpIpPortLogicalIfOspfIfOperEntry 3 }

mscVrPpIpPortLogicalIfOspfIfEvents OBJECT-TYPE
   SYNTAX     Counter32 
   ACCESS     read-only
   STATUS     mandatory
   DESCRIPTION
     "The number of times this OSPF interface has changed its state or an 
      error has occurred."
::= { mscVrPpIpPortLogicalIfOspfIfOperEntry 4 }

mscVrPpIpPortLogicalIfOspfIfMetricTable OBJECT-TYPE
   SYNTAX     SEQUENCE OF MscVrPpIpPortLogicalIfOspfIfMetricEntry
   ACCESS     not-accessible
   STATUS     mandatory
   DESCRIPTION
     "This group contains the operational metric attribute of this interface."
::= { mscVrPpIpPortLogicalIfOspfIf 12 }

mscVrPpIpPortLogicalIfOspfIfMetricEntry OBJECT-TYPE
   SYNTAX     MscVrPpIpPortLogicalIfOspfIfMetricEntry
   ACCESS     not-accessible
   STATUS     mandatory
   DESCRIPTION
     "An entry in the mscVrPpIpPortLogicalIfOspfIfMetricTable."
   INDEX {
      mscVrIndex,
      mscVrPpIndex,
      mscVrPpIpPortIndex,
      mscVrPpIpPortLogicalIfAddressIndex,
      mscVrPpIpPortLogicalIfOspfIfIndex }
::= { mscVrPpIpPortLogicalIfOspfIfMetricTable 1 }

MscVrPpIpPortLogicalIfOspfIfMetricEntry ::= SEQUENCE {
   mscVrPpIpPortLogicalIfOspfIfMetric
      Unsigned32 }

mscVrPpIpPortLogicalIfOspfIfMetric OBJECT-TYPE
   SYNTAX     Unsigned32 (0..4294967295)
   ACCESS     read-only
   STATUS     mandatory
   DESCRIPTION
     "This attribute indicates the metric being used by this OspfIf. The metric 
      is derived in one of two ways:
      1. If there is a TypeOfService component provisioned under this OspfIf 
      component, then the value of the metric attribute is copied from the 
      provisionable attribute tosMetric.
      2. Otherwise, the metric is computed based on the interface speed. If the 
      interface speed is greater than 100 Mbit/s, then the metric is 1. If the 
      interface speed is less than 100 Mbit/s, then the metric is 100 Mbit/s 
      divided by the interface speed. If the interface speed is unknown, then it 
      is treated as 1.54 Mbit/s during the calculation.
      The value of interface speed is available by displaying the ifSpeed 
      attribute of the corresponding IfTableEntry component."
::= { mscVrPpIpPortLogicalIfOspfIfMetricEntry 1 }


-- Vr/<string> Pp/<string> IpPort logicalIf/<Ip Address> ospfIf 
-- OspfIfTypeOfService/<Decimal>
-- This component describes the metrics to be advertised for a specified 
-- interface at various types-of-service.

mscVrPpIpPortLogicalIfOspfIfTOS OBJECT IDENTIFIER ::= { mscVrPpIpPortLogicalIfOspfIf 2 }



mscVrPpIpPortLogicalIfOspfIfTOSRowStatusTable OBJECT-TYPE
   SYNTAX     SEQUENCE OF MscVrPpIpPortLogicalIfOspfIfTOSRowStatusEntry
   ACCESS     not-accessible
   STATUS     mandatory
   DESCRIPTION
     "This entry controls the addition and deletion of 
      mscVrPpIpPortLogicalIfOspfIfTOS components."
::= { mscVrPpIpPortLogicalIfOspfIfTOS 1 }

mscVrPpIpPortLogicalIfOspfIfTOSRowStatusEntry OBJECT-TYPE
   SYNTAX     MscVrPpIpPortLogicalIfOspfIfTOSRowStatusEntry
   ACCESS     not-accessible
   STATUS     mandatory
   DESCRIPTION
     "A single entry in the table represents a single 
      mscVrPpIpPortLogicalIfOspfIfTOS component."
   INDEX {
      mscVrIndex,
      mscVrPpIndex,
      mscVrPpIpPortIndex,
      mscVrPpIpPortLogicalIfAddressIndex,
      mscVrPpIpPortLogicalIfOspfIfIndex,
      mscVrPpIpPortLogicalIfOspfIfTOSMetricTosIndex }
::= { mscVrPpIpPortLogicalIfOspfIfTOSRowStatusTable 1 }

MscVrPpIpPortLogicalIfOspfIfTOSRowStatusEntry ::= SEQUENCE {
   mscVrPpIpPortLogicalIfOspfIfTOSRowStatus
      RowStatus,
   mscVrPpIpPortLogicalIfOspfIfTOSComponentName
      DisplayString,
   mscVrPpIpPortLogicalIfOspfIfTOSStorageType
      StorageType,
   mscVrPpIpPortLogicalIfOspfIfTOSMetricTosIndex
      Integer32 }

mscVrPpIpPortLogicalIfOspfIfTOSRowStatus OBJECT-TYPE
   SYNTAX     RowStatus 
   ACCESS     read-write
   STATUS     mandatory
   DESCRIPTION
     "This variable is used as the basis for SNMP naming of
      mscVrPpIpPortLogicalIfOspfIfTOS components.
      These components can be added and deleted."
::= { mscVrPpIpPortLogicalIfOspfIfTOSRowStatusEntry 1 }

mscVrPpIpPortLogicalIfOspfIfTOSComponentName OBJECT-TYPE
   SYNTAX     DisplayString 
   ACCESS     read-only
   STATUS     mandatory
   DESCRIPTION
     "This variable provides the component's string name for
      use with the ASCII Console Interface"
::= { mscVrPpIpPortLogicalIfOspfIfTOSRowStatusEntry 2 }

mscVrPpIpPortLogicalIfOspfIfTOSStorageType OBJECT-TYPE
   SYNTAX     StorageType 
   ACCESS     read-only
   STATUS     mandatory
   DESCRIPTION
     "This variable represents the storage type value for the
      mscVrPpIpPortLogicalIfOspfIfTOS tables."
::= { mscVrPpIpPortLogicalIfOspfIfTOSRowStatusEntry 4 }

mscVrPpIpPortLogicalIfOspfIfTOSMetricTosIndex OBJECT-TYPE
   SYNTAX     Integer32 (0..0)
   ACCESS     not-accessible
   STATUS     mandatory
   DESCRIPTION
     "This variable represents the index for the mscVrPpIpPortLogicalIfOspfIfTOS tables."
::= { mscVrPpIpPortLogicalIfOspfIfTOSRowStatusEntry 10 }

mscVrPpIpPortLogicalIfOspfIfTOSProvTable OBJECT-TYPE
   SYNTAX     SEQUENCE OF MscVrPpIpPortLogicalIfOspfIfTOSProvEntry
   ACCESS     not-accessible
   STATUS     mandatory
   DESCRIPTION
     "Identifies a provisionable set of attributes."
::= { mscVrPpIpPortLogicalIfOspfIfTOS 10 }

mscVrPpIpPortLogicalIfOspfIfTOSProvEntry OBJECT-TYPE
   SYNTAX     MscVrPpIpPortLogicalIfOspfIfTOSProvEntry
   ACCESS     not-accessible
   STATUS     mandatory
   DESCRIPTION
     "An entry in the mscVrPpIpPortLogicalIfOspfIfTOSProvTable."
   INDEX {
      mscVrIndex,
      mscVrPpIndex,
      mscVrPpIpPortIndex,
      mscVrPpIpPortLogicalIfAddressIndex,
      mscVrPpIpPortLogicalIfOspfIfIndex,
      mscVrPpIpPortLogicalIfOspfIfTOSMetricTosIndex }
::= { mscVrPpIpPortLogicalIfOspfIfTOSProvTable 1 }

MscVrPpIpPortLogicalIfOspfIfTOSProvEntry ::= SEQUENCE {
   mscVrPpIpPortLogicalIfOspfIfTOSTosMetric
      Unsigned32 }

mscVrPpIpPortLogicalIfOspfIfTOSTosMetric OBJECT-TYPE
   SYNTAX     Unsigned32 (0..65535)
   ACCESS     read-write
   STATUS     mandatory
   DESCRIPTION
     "The metric using this typeOfService on this interface."
::= { mscVrPpIpPortLogicalIfOspfIfTOSProvEntry 1 }


-- Vr/<string> Pp/<string> IpPort logicalIf/<Ip Address> ospfIf 
-- OspfIfNeighbor/<Ip Address>
-- This component specifies the neighbors on a multi-access non-broadcast 
-- media. This can also be viewed as the provisioned entries of Ospf 
-- NeighborTable.

mscVrPpIpPortLogicalIfOspfIfNbr OBJECT IDENTIFIER ::= { mscVrPpIpPortLogicalIfOspfIf 3 }



mscVrPpIpPortLogicalIfOspfIfNbrRowStatusTable OBJECT-TYPE
   SYNTAX     SEQUENCE OF MscVrPpIpPortLogicalIfOspfIfNbrRowStatusEntry
   ACCESS     not-accessible
   STATUS     mandatory
   DESCRIPTION
     "This entry controls the addition and deletion of 
      mscVrPpIpPortLogicalIfOspfIfNbr components."
::= { mscVrPpIpPortLogicalIfOspfIfNbr 1 }

mscVrPpIpPortLogicalIfOspfIfNbrRowStatusEntry OBJECT-TYPE
   SYNTAX     MscVrPpIpPortLogicalIfOspfIfNbrRowStatusEntry
   ACCESS     not-accessible
   STATUS     mandatory
   DESCRIPTION
     "A single entry in the table represents a single 
      mscVrPpIpPortLogicalIfOspfIfNbr component."
   INDEX {
      mscVrIndex,
      mscVrPpIndex,
      mscVrPpIpPortIndex,
      mscVrPpIpPortLogicalIfAddressIndex,
      mscVrPpIpPortLogicalIfOspfIfIndex,
      mscVrPpIpPortLogicalIfOspfIfNbrAddressIndex }
::= { mscVrPpIpPortLogicalIfOspfIfNbrRowStatusTable 1 }

MscVrPpIpPortLogicalIfOspfIfNbrRowStatusEntry ::= SEQUENCE {
   mscVrPpIpPortLogicalIfOspfIfNbrRowStatus
      RowStatus,
   mscVrPpIpPortLogicalIfOspfIfNbrComponentName
      DisplayString,
   mscVrPpIpPortLogicalIfOspfIfNbrStorageType
      StorageType,
   mscVrPpIpPortLogicalIfOspfIfNbrAddressIndex
      IpAddress }

mscVrPpIpPortLogicalIfOspfIfNbrRowStatus OBJECT-TYPE
   SYNTAX     RowStatus 
   ACCESS     read-write
   STATUS     mandatory
   DESCRIPTION
     "This variable is used as the basis for SNMP naming of
      mscVrPpIpPortLogicalIfOspfIfNbr components.
      These components can be added and deleted."
::= { mscVrPpIpPortLogicalIfOspfIfNbrRowStatusEntry 1 }

mscVrPpIpPortLogicalIfOspfIfNbrComponentName OBJECT-TYPE
   SYNTAX     DisplayString 
   ACCESS     read-only
   STATUS     mandatory
   DESCRIPTION
     "This variable provides the component's string name for
      use with the ASCII Console Interface"
::= { mscVrPpIpPortLogicalIfOspfIfNbrRowStatusEntry 2 }

mscVrPpIpPortLogicalIfOspfIfNbrStorageType OBJECT-TYPE
   SYNTAX     StorageType 
   ACCESS     read-only
   STATUS     mandatory
   DESCRIPTION
     "This variable represents the storage type value for the
      mscVrPpIpPortLogicalIfOspfIfNbr tables."
::= { mscVrPpIpPortLogicalIfOspfIfNbrRowStatusEntry 4 }

mscVrPpIpPortLogicalIfOspfIfNbrAddressIndex OBJECT-TYPE
   SYNTAX     IpAddress 
   ACCESS     not-accessible
   STATUS     mandatory
   DESCRIPTION
     "This variable represents the index for the mscVrPpIpPortLogicalIfOspfIfNbr tables."
::= { mscVrPpIpPortLogicalIfOspfIfNbrRowStatusEntry 10 }

mscVrPpIpPortLogicalIfOspfIfNbrProvTable OBJECT-TYPE
   SYNTAX     SEQUENCE OF MscVrPpIpPortLogicalIfOspfIfNbrProvEntry
   ACCESS     not-accessible
   STATUS     mandatory
   DESCRIPTION
     "Identifies a group of Provisionable attributes."
::= { mscVrPpIpPortLogicalIfOspfIfNbr 10 }

mscVrPpIpPortLogicalIfOspfIfNbrProvEntry OBJECT-TYPE
   SYNTAX     MscVrPpIpPortLogicalIfOspfIfNbrProvEntry
   ACCESS     not-accessible
   STATUS     mandatory
   DESCRIPTION
     "An entry in the mscVrPpIpPortLogicalIfOspfIfNbrProvTable."
   INDEX {
      mscVrIndex,
      mscVrPpIndex,
      mscVrPpIpPortIndex,
      mscVrPpIpPortLogicalIfAddressIndex,
      mscVrPpIpPortLogicalIfOspfIfIndex,
      mscVrPpIpPortLogicalIfOspfIfNbrAddressIndex }
::= { mscVrPpIpPortLogicalIfOspfIfNbrProvTable 1 }

MscVrPpIpPortLogicalIfOspfIfNbrProvEntry ::= SEQUENCE {
   mscVrPpIpPortLogicalIfOspfIfNbrPriority
      Unsigned32 }

mscVrPpIpPortLogicalIfOspfIfNbrPriority OBJECT-TYPE
   SYNTAX     Unsigned32 (0..255)
   ACCESS     read-write
   STATUS     mandatory
   DESCRIPTION
     "The priority of this neighbor in the designated router election algorithm. 
      The value 0 signifies that the neighbor is not eligible to become the 
      designated router on this particular network. The higher the number, the 
      better are the chances of being a designated router."
   DEFVAL     { 1 }
::= { mscVrPpIpPortLogicalIfOspfIfNbrProvEntry 1 }

mscVrPpIpPortLogicalIfOspfIfNbrOperTable OBJECT-TYPE
   SYNTAX     SEQUENCE OF MscVrPpIpPortLogicalIfOspfIfNbrOperEntry
   ACCESS     not-accessible
   STATUS     mandatory
   DESCRIPTION
     "Contains the Operational set of attributes for the Neighbor."
::= { mscVrPpIpPortLogicalIfOspfIfNbr 11 }

mscVrPpIpPortLogicalIfOspfIfNbrOperEntry OBJECT-TYPE
   SYNTAX     MscVrPpIpPortLogicalIfOspfIfNbrOperEntry
   ACCESS     not-accessible
   STATUS     mandatory
   DESCRIPTION
     "An entry in the mscVrPpIpPortLogicalIfOspfIfNbrOperTable."
   INDEX {
      mscVrIndex,
      mscVrPpIndex,
      mscVrPpIpPortIndex,
      mscVrPpIpPortLogicalIfAddressIndex,
      mscVrPpIpPortLogicalIfOspfIfIndex,
      mscVrPpIpPortLogicalIfOspfIfNbrAddressIndex }
::= { mscVrPpIpPortLogicalIfOspfIfNbrOperTable 1 }

MscVrPpIpPortLogicalIfOspfIfNbrOperEntry ::= SEQUENCE {
   mscVrPpIpPortLogicalIfOspfIfNbrRtrId
      RouterID,
   mscVrPpIpPortLogicalIfOspfIfNbrOptions
      Unsigned32,
   mscVrPpIpPortLogicalIfOspfIfNbrState
      INTEGER,
   mscVrPpIpPortLogicalIfOspfIfNbrEvents
      Counter32,
   mscVrPpIpPortLogicalIfOspfIfNbrLsRetransQlen
      Gauge32,
   mscVrPpIpPortLogicalIfOspfIfNbrExchangeStatus
      INTEGER,
   mscVrPpIpPortLogicalIfOspfIfNbrPermanance
      INTEGER }

mscVrPpIpPortLogicalIfOspfIfNbrRtrId OBJECT-TYPE
   SYNTAX     RouterID 
   ACCESS     read-only
   STATUS     mandatory
   DESCRIPTION
     "An Ip Address uniquely identifying the neighboring router in the 
      Autonomous System."
::= { mscVrPpIpPortLogicalIfOspfIfNbrOperEntry 1 }

mscVrPpIpPortLogicalIfOspfIfNbrOptions OBJECT-TYPE
   SYNTAX     Unsigned32 (0..15)
   ACCESS     read-only
   STATUS     mandatory
   DESCRIPTION
     "A bit mask corresponding to the neighbor's options field. Bit 0, if set, 
      indicates that the area accepts and operates on external information, if 
      zero, it is a stub area. Bit 1, if set, indicates that the system will operate 
      on Type of Service metrics other than TOS 0. If zero, the neighbor will 
      ignore all metrics except the TOS 0 metric. Bit 2, if set, indicates that 
      the system is Network Multicast capable; i.e., that it implements OSPF 
      Multicast Routing."
::= { mscVrPpIpPortLogicalIfOspfIfNbrOperEntry 2 }

mscVrPpIpPortLogicalIfOspfIfNbrState OBJECT-TYPE
   SYNTAX     INTEGER  {
                 down(1),
                 attempt(2),
                 init(3),
                 twoWay(4),
                 exchangeStart(5),
                 exchange(6),
                 loading(7),
                 full(8) }
   ACCESS     read-only
   STATUS     mandatory
   DESCRIPTION
     "The state of the relationship with this neighbor."
::= { mscVrPpIpPortLogicalIfOspfIfNbrOperEntry 3 }

mscVrPpIpPortLogicalIfOspfIfNbrEvents OBJECT-TYPE
   SYNTAX     Counter32 
   ACCESS     read-only
   STATUS     mandatory
   DESCRIPTION
     "The number of times this neighbor relationship has changed state, or an 
      error has occurred."
::= { mscVrPpIpPortLogicalIfOspfIfNbrOperEntry 4 }

mscVrPpIpPortLogicalIfOspfIfNbrLsRetransQlen OBJECT-TYPE
   SYNTAX     Gauge32 (0..4294967295)
   ACCESS     read-only
   STATUS     mandatory
   DESCRIPTION
     "The current length of the Retransmission queue."
::= { mscVrPpIpPortLogicalIfOspfIfNbrOperEntry 5 }

mscVrPpIpPortLogicalIfOspfIfNbrExchangeStatus OBJECT-TYPE
   SYNTAX     INTEGER  {
                 master(1),
                 slave(2) }
   ACCESS     read-only
   STATUS     mandatory
   DESCRIPTION
     "Indicates the exchange status for a neighbor Entry."
::= { mscVrPpIpPortLogicalIfOspfIfNbrOperEntry 6 }

mscVrPpIpPortLogicalIfOspfIfNbrPermanance OBJECT-TYPE
   SYNTAX     INTEGER  {
                 permanent(1),
                 dynamic(2) }
   ACCESS     read-only
   STATUS     mandatory
   DESCRIPTION
     "This attribute displays how the neighbor became an entry."
   DEFVAL     { permanent }
::= { mscVrPpIpPortLogicalIfOspfIfNbrOperEntry 9 }


-- Vr/<X> Pp/<X> IpPort LogicalIf/<Ip Address> RipInterface
-- This component is used to configure a LogicalIf to run RIP protocol.

mscVrPpIpPortLogicalIfRipIf OBJECT IDENTIFIER ::= { mscVrPpIpPortLogicalIf 3 }



mscVrPpIpPortLogicalIfRipIfRowStatusTable OBJECT-TYPE
   SYNTAX     SEQUENCE OF MscVrPpIpPortLogicalIfRipIfRowStatusEntry
   ACCESS     not-accessible
   STATUS     mandatory
   DESCRIPTION
     "This entry controls the addition and deletion of 
      mscVrPpIpPortLogicalIfRipIf components."
::= { mscVrPpIpPortLogicalIfRipIf 1 }

mscVrPpIpPortLogicalIfRipIfRowStatusEntry OBJECT-TYPE
   SYNTAX     MscVrPpIpPortLogicalIfRipIfRowStatusEntry
   ACCESS     not-accessible
   STATUS     mandatory
   DESCRIPTION
     "A single entry in the table represents a single 
      mscVrPpIpPortLogicalIfRipIf component."
   INDEX {
      mscVrIndex,
      mscVrPpIndex,
      mscVrPpIpPortIndex,
      mscVrPpIpPortLogicalIfAddressIndex,
      mscVrPpIpPortLogicalIfRipIfIndex }
::= { mscVrPpIpPortLogicalIfRipIfRowStatusTable 1 }

MscVrPpIpPortLogicalIfRipIfRowStatusEntry ::= SEQUENCE {
   mscVrPpIpPortLogicalIfRipIfRowStatus
      RowStatus,
   mscVrPpIpPortLogicalIfRipIfComponentName
      DisplayString,
   mscVrPpIpPortLogicalIfRipIfStorageType
      StorageType,
   mscVrPpIpPortLogicalIfRipIfIndex
      NonReplicated }

mscVrPpIpPortLogicalIfRipIfRowStatus OBJECT-TYPE
   SYNTAX     RowStatus 
   ACCESS     read-write
   STATUS     mandatory
   DESCRIPTION
     "This variable is used as the basis for SNMP naming of
      mscVrPpIpPortLogicalIfRipIf components.
      These components can be added and deleted."
::= { mscVrPpIpPortLogicalIfRipIfRowStatusEntry 1 }

mscVrPpIpPortLogicalIfRipIfComponentName OBJECT-TYPE
   SYNTAX     DisplayString 
   ACCESS     read-only
   STATUS     mandatory
   DESCRIPTION
     "This variable provides the component's string name for
      use with the ASCII Console Interface"
::= { mscVrPpIpPortLogicalIfRipIfRowStatusEntry 2 }

mscVrPpIpPortLogicalIfRipIfStorageType OBJECT-TYPE
   SYNTAX     StorageType 
   ACCESS     read-only
   STATUS     mandatory
   DESCRIPTION
     "This variable represents the storage type value for the
      mscVrPpIpPortLogicalIfRipIf tables."
::= { mscVrPpIpPortLogicalIfRipIfRowStatusEntry 4 }

mscVrPpIpPortLogicalIfRipIfIndex OBJECT-TYPE
   SYNTAX     NonReplicated 
   ACCESS     not-accessible
   STATUS     mandatory
   DESCRIPTION
     "This variable represents the index for the mscVrPpIpPortLogicalIfRipIf tables."
::= { mscVrPpIpPortLogicalIfRipIfRowStatusEntry 10 }

mscVrPpIpPortLogicalIfRipIfProvTable OBJECT-TYPE
   SYNTAX     SEQUENCE OF MscVrPpIpPortLogicalIfRipIfProvEntry
   ACCESS     not-accessible
   STATUS     mandatory
   DESCRIPTION
     "This group contains the provisionable attributes of the RipIf component."
::= { mscVrPpIpPortLogicalIfRipIf 10 }

mscVrPpIpPortLogicalIfRipIfProvEntry OBJECT-TYPE
   SYNTAX     MscVrPpIpPortLogicalIfRipIfProvEntry
   ACCESS     not-accessible
   STATUS     mandatory
   DESCRIPTION
     "An entry in the mscVrPpIpPortLogicalIfRipIfProvTable."
   INDEX {
      mscVrIndex,
      mscVrPpIndex,
      mscVrPpIpPortIndex,
      mscVrPpIpPortLogicalIfAddressIndex,
      mscVrPpIpPortLogicalIfRipIfIndex }
::= { mscVrPpIpPortLogicalIfRipIfProvTable 1 }

MscVrPpIpPortLogicalIfRipIfProvEntry ::= SEQUENCE {
   mscVrPpIpPortLogicalIfRipIfSnmpAdminStatus
      INTEGER,
   mscVrPpIpPortLogicalIfRipIfMetric
      Unsigned32,
   mscVrPpIpPortLogicalIfRipIfSilentFlag
      INTEGER,
   mscVrPpIpPortLogicalIfRipIfPoisonReverseFlag
      INTEGER,
   mscVrPpIpPortLogicalIfRipIfFlashUpdateFlag
      INTEGER,
   mscVrPpIpPortLogicalIfRipIfNetworkRouteStatus
      INTEGER,
   mscVrPpIpPortLogicalIfRipIfDefaultRouteMetric
      Unsigned32,
   mscVrPpIpPortLogicalIfRipIfAcceptDefault
      INTEGER,
   mscVrPpIpPortLogicalIfRipIfIfConfSend
      INTEGER,
   mscVrPpIpPortLogicalIfRipIfIfConfReceive
      INTEGER }

mscVrPpIpPortLogicalIfRipIfSnmpAdminStatus OBJECT-TYPE
   SYNTAX     INTEGER  {
                 up(1),
                 down(2) }
   ACCESS     read-write
   STATUS     mandatory
   DESCRIPTION
     "Identifies the administrative status of this RipInterface. Setting this value 
      to disabled will have the effect of rendering it inactive."
   DEFVAL     { up }
::= { mscVrPpIpPortLogicalIfRipIfProvEntry 1 }

mscVrPpIpPortLogicalIfRipIfMetric OBJECT-TYPE
   SYNTAX     Unsigned32 (1..16)
   ACCESS     read-write
   STATUS     mandatory
   DESCRIPTION
     "This attribute is the RIP metric for this logical interface."
   DEFVAL     { 1 }
::= { mscVrPpIpPortLogicalIfRipIfProvEntry 2 }

mscVrPpIpPortLogicalIfRipIfSilentFlag OBJECT-TYPE
   SYNTAX     INTEGER  {
                 true(1),
                 false(2) }
   ACCESS     read-write
   STATUS     obsolete
   DESCRIPTION
     "If the value of this attribute is set to true, the protocol will only listen to 
      RIP updates, If set to false, then Rip will listen and send RIP 
      updates.This attribute has been migrated to ifConfSend."
   DEFVAL     { false }
::= { mscVrPpIpPortLogicalIfRipIfProvEntry 3 }

mscVrPpIpPortLogicalIfRipIfPoisonReverseFlag OBJECT-TYPE
   SYNTAX     INTEGER  {
                 true(1),
                 false(2) }
   ACCESS     read-write
   STATUS     mandatory
   DESCRIPTION
     "If the value of this attribute is set to true, then poison reverse algorithm 
      is used when sending out the updates otherwise use split horizon only."
   DEFVAL     { false }
::= { mscVrPpIpPortLogicalIfRipIfProvEntry 4 }

mscVrPpIpPortLogicalIfRipIfFlashUpdateFlag OBJECT-TYPE
   SYNTAX     INTEGER  {
                 true(1),
                 false(2) }
   ACCESS     read-write
   STATUS     mandatory
   DESCRIPTION
     "This attribute when set to true will send updates when updates are 
      received; otherwise RIP will wait till the next update period."
   DEFVAL     { true }
::= { mscVrPpIpPortLogicalIfRipIfProvEntry 5 }

mscVrPpIpPortLogicalIfRipIfNetworkRouteStatus OBJECT-TYPE
   SYNTAX     INTEGER  {
                 naturalNetWithOutDefaultRoute(1),
                 naturalNetWithDefaultRoute(2),
                 defaultRouteOnly(3),
                 subnetsOnly(4) }
   ACCESS     read-write
   STATUS     mandatory
   DESCRIPTION
     "This attribute determines what type of network routes will be sent and 
      whether a default route will be generated for this RipInterface. 
      Generated default routes will not go into the routing table, but are sent in 
      the updates going out on the interface. The possible values for this 
      attribute are:
      
      naturalNetWithOutDefaultRoute - This value will cause normal RIP 
      network routes to be put in the update. This means that the address of 
      logicalIf pertaining to this RipInterface knowledge is taken into account 
      in determining if the subnetted network or the natural network is sent for 
      any route going into this update.
      
      naturalNetWithDefaultRoute - Selecting this value will cause a default 
      route to be generated with the value of the metric selected for the 
      attribute defaultRouteMetric.
      
      defaultRouteOnly - Selection of this value causes the default route to be 
      generated with the value of the metric selected for the attribute 
      defaultRouteMetric.
      NOTE: No other routes will go in the update.
      
      subnetsOnly - selection of this value will cause only subnet information 
      to be put in the update. No default routes will be generated or passed on. 
      Only subnetted routes that are part of the same subnetted network that 
      this logicalInterface is on will be put in the update.
      NOTE: this also effects receiving of updates on this interface. Only 
      subnetted routes that are part of the same subnetted network that this 
      logicalInterface is on will be accepted on a received RIP update on this 
      RipInterface."
   DEFVAL     { naturalNetWithOutDefaultRoute }
::= { mscVrPpIpPortLogicalIfRipIfProvEntry 6 }

mscVrPpIpPortLogicalIfRipIfDefaultRouteMetric OBJECT-TYPE
   SYNTAX     Unsigned32 (1..16)
   ACCESS     read-write
   STATUS     mandatory
   DESCRIPTION
     "This attribute identifies the metric value for the default route. This value 
      is only used if the attribute networkRouteStatus is configured with a 
      value of either naturalNetWithDefaultRoute or defaultRouteOnly"
   DEFVAL     { 1 }
::= { mscVrPpIpPortLogicalIfRipIfProvEntry 7 }

mscVrPpIpPortLogicalIfRipIfAcceptDefault OBJECT-TYPE
   SYNTAX     INTEGER  {
                 true(1),
                 false(2) }
   ACCESS     read-write
   STATUS     mandatory
   DESCRIPTION
     "If this attribute is set to true, then accept the default route from this 
      interface."
   DEFVAL     { true }
::= { mscVrPpIpPortLogicalIfRipIfProvEntry 8 }

mscVrPpIpPortLogicalIfRipIfIfConfSend OBJECT-TYPE
   SYNTAX     INTEGER  {
                 doNotSend(1),
                 ripVersion1(2),
                 rip1Compatible(3),
                 ripVersion2(4) }
   ACCESS     read-write
   STATUS     mandatory
   DESCRIPTION
     "This attribute identifies what the router sends on this RipIf. ripVersion1 
      implies sending RIP updates compliant with  RFC  1058.   
      rip1Compatible implies broadcasting RIP-2 updates according to RFC 
      1058.  ripVersion2 implies multicasting RIP-2 updates."
   DEFVAL     { rip1Compatible }
::= { mscVrPpIpPortLogicalIfRipIfProvEntry 12 }

mscVrPpIpPortLogicalIfRipIfIfConfReceive OBJECT-TYPE
   SYNTAX     INTEGER  {
                 rip1(1),
                 rip2(2),
                 rip1OrRip2(3),
                 doNotReceive(4) }
   ACCESS     read-write
   STATUS     mandatory
   DESCRIPTION
     "This attribute identifies which version of RIP updates are to be accepted 
      on this RipIf.  Note that rip2 and rip1OrRip2 implies reception of 
      multicast packets."
   DEFVAL     { rip1OrRip2 }
::= { mscVrPpIpPortLogicalIfRipIfProvEntry 13 }

mscVrPpIpPortLogicalIfRipIfStatTable OBJECT-TYPE
   SYNTAX     SEQUENCE OF MscVrPpIpPortLogicalIfRipIfStatEntry
   ACCESS     not-accessible
   STATUS     mandatory
   DESCRIPTION
     "This group contains operational attributes of the RipIf component. These 
      attributes are statistical data corresponding to the RIP-2 standard MIB 
      (rfc 1724) rip2Status table."
::= { mscVrPpIpPortLogicalIfRipIf 11 }

mscVrPpIpPortLogicalIfRipIfStatEntry OBJECT-TYPE
   SYNTAX     MscVrPpIpPortLogicalIfRipIfStatEntry
   ACCESS     not-accessible
   STATUS     mandatory
   DESCRIPTION
     "An entry in the mscVrPpIpPortLogicalIfRipIfStatTable."
   INDEX {
      mscVrIndex,
      mscVrPpIndex,
      mscVrPpIpPortIndex,
      mscVrPpIpPortLogicalIfAddressIndex,
      mscVrPpIpPortLogicalIfRipIfIndex }
::= { mscVrPpIpPortLogicalIfRipIfStatTable 1 }

MscVrPpIpPortLogicalIfRipIfStatEntry ::= SEQUENCE {
   mscVrPpIpPortLogicalIfRipIfIfBadPacketRcv
      Unsigned32,
   mscVrPpIpPortLogicalIfRipIfIfBadRouteRcv
      Unsigned32,
   mscVrPpIpPortLogicalIfRipIfIfTriggeredUpdates
      Unsigned32 }

mscVrPpIpPortLogicalIfRipIfIfBadPacketRcv OBJECT-TYPE
   SYNTAX     Unsigned32 (0..4294967295)
   ACCESS     read-only
   STATUS     mandatory
   DESCRIPTION
     "This attribute counts the number of RIP response packets recieved by 
      the RIP process which were subsequently discarded for any reason."
   DEFVAL     { 0 }
::= { mscVrPpIpPortLogicalIfRipIfStatEntry 1 }

mscVrPpIpPortLogicalIfRipIfIfBadRouteRcv OBJECT-TYPE
   SYNTAX     Unsigned32 (0..4294967295)
   ACCESS     read-only
   STATUS     mandatory
   DESCRIPTION
     "This attribute counts how many routes, in valid RIP packets, were 
      ignored for any reason."
   DEFVAL     { 0 }
::= { mscVrPpIpPortLogicalIfRipIfStatEntry 2 }

mscVrPpIpPortLogicalIfRipIfIfTriggeredUpdates OBJECT-TYPE
   SYNTAX     Unsigned32 (0..4294967295)
   ACCESS     read-only
   STATUS     mandatory
   DESCRIPTION
     "This attribute counts the number of triggered updates actually sent on 
      this interface. This explicitly does NOT include full updates sent 
      containing new information."
   DEFVAL     { 0 }
::= { mscVrPpIpPortLogicalIfRipIfStatEntry 3 }


-- Vr/<string> Pp/<string> IpPort logicalIf/<Ip Address> RipIf 
-- Neighbor/<Ip address>
-- This component is used to configure the Ip Address of the non broadcast 
-- multi access (NBMA) neighbor.

mscVrPpIpPortLogicalIfRipIfNbr OBJECT IDENTIFIER ::= { mscVrPpIpPortLogicalIfRipIf 2 }



mscVrPpIpPortLogicalIfRipIfNbrRowStatusTable OBJECT-TYPE
   SYNTAX     SEQUENCE OF MscVrPpIpPortLogicalIfRipIfNbrRowStatusEntry
   ACCESS     not-accessible
   STATUS     mandatory
   DESCRIPTION
     "This entry controls the addition and deletion of 
      mscVrPpIpPortLogicalIfRipIfNbr components."
::= { mscVrPpIpPortLogicalIfRipIfNbr 1 }

mscVrPpIpPortLogicalIfRipIfNbrRowStatusEntry OBJECT-TYPE
   SYNTAX     MscVrPpIpPortLogicalIfRipIfNbrRowStatusEntry
   ACCESS     not-accessible
   STATUS     mandatory
   DESCRIPTION
     "A single entry in the table represents a single 
      mscVrPpIpPortLogicalIfRipIfNbr component."
   INDEX {
      mscVrIndex,
      mscVrPpIndex,
      mscVrPpIpPortIndex,
      mscVrPpIpPortLogicalIfAddressIndex,
      mscVrPpIpPortLogicalIfRipIfIndex,
      mscVrPpIpPortLogicalIfRipIfNbrIndex }
::= { mscVrPpIpPortLogicalIfRipIfNbrRowStatusTable 1 }

MscVrPpIpPortLogicalIfRipIfNbrRowStatusEntry ::= SEQUENCE {
   mscVrPpIpPortLogicalIfRipIfNbrRowStatus
      RowStatus,
   mscVrPpIpPortLogicalIfRipIfNbrComponentName
      DisplayString,
   mscVrPpIpPortLogicalIfRipIfNbrStorageType
      StorageType,
   mscVrPpIpPortLogicalIfRipIfNbrIndex
      IpAddress }

mscVrPpIpPortLogicalIfRipIfNbrRowStatus OBJECT-TYPE
   SYNTAX     RowStatus 
   ACCESS     read-write
   STATUS     mandatory
   DESCRIPTION
     "This variable is used as the basis for SNMP naming of
      mscVrPpIpPortLogicalIfRipIfNbr components.
      These components can be added and deleted."
::= { mscVrPpIpPortLogicalIfRipIfNbrRowStatusEntry 1 }

mscVrPpIpPortLogicalIfRipIfNbrComponentName OBJECT-TYPE
   SYNTAX     DisplayString 
   ACCESS     read-only
   STATUS     mandatory
   DESCRIPTION
     "This variable provides the component's string name for
      use with the ASCII Console Interface"
::= { mscVrPpIpPortLogicalIfRipIfNbrRowStatusEntry 2 }

mscVrPpIpPortLogicalIfRipIfNbrStorageType OBJECT-TYPE
   SYNTAX     StorageType 
   ACCESS     read-only
   STATUS     mandatory
   DESCRIPTION
     "This variable represents the storage type value for the
      mscVrPpIpPortLogicalIfRipIfNbr tables."
::= { mscVrPpIpPortLogicalIfRipIfNbrRowStatusEntry 4 }

mscVrPpIpPortLogicalIfRipIfNbrIndex OBJECT-TYPE
   SYNTAX     IpAddress 
   ACCESS     not-accessible
   STATUS     mandatory
   DESCRIPTION
     "This variable represents the index for the mscVrPpIpPortLogicalIfRipIfNbr tables."
::= { mscVrPpIpPortLogicalIfRipIfNbrRowStatusEntry 10 }


-- This component allows the configuration of NetSentry filters for this 
-- IpPort.

mscVrPpIpPortNs OBJECT IDENTIFIER ::= { mscVrPpIpPort 3 }



mscVrPpIpPortNsRowStatusTable OBJECT-TYPE
   SYNTAX     SEQUENCE OF MscVrPpIpPortNsRowStatusEntry
   ACCESS     not-accessible
   STATUS     mandatory
   DESCRIPTION
     "This entry controls the addition and deletion of 
      mscVrPpIpPortNs components."
::= { mscVrPpIpPortNs 1 }

mscVrPpIpPortNsRowStatusEntry OBJECT-TYPE
   SYNTAX     MscVrPpIpPortNsRowStatusEntry
   ACCESS     not-accessible
   STATUS     mandatory
   DESCRIPTION
     "A single entry in the table represents a single 
      mscVrPpIpPortNs component."
   INDEX {
      mscVrIndex,
      mscVrPpIndex,
      mscVrPpIpPortIndex,
      mscVrPpIpPortNsIndex }
::= { mscVrPpIpPortNsRowStatusTable 1 }

MscVrPpIpPortNsRowStatusEntry ::= SEQUENCE {
   mscVrPpIpPortNsRowStatus
      RowStatus,
   mscVrPpIpPortNsComponentName
      DisplayString,
   mscVrPpIpPortNsStorageType
      StorageType,
   mscVrPpIpPortNsIndex
      NonReplicated }

mscVrPpIpPortNsRowStatus OBJECT-TYPE
   SYNTAX     RowStatus 
   ACCESS     read-write
   STATUS     mandatory
   DESCRIPTION
     "This variable is used as the basis for SNMP naming of
      mscVrPpIpPortNs components.
      These components can be added and deleted."
::= { mscVrPpIpPortNsRowStatusEntry 1 }

mscVrPpIpPortNsComponentName OBJECT-TYPE
   SYNTAX     DisplayString 
   ACCESS     read-only
   STATUS     mandatory
   DESCRIPTION
     "This variable provides the component's string name for
      use with the ASCII Console Interface"
::= { mscVrPpIpPortNsRowStatusEntry 2 }

mscVrPpIpPortNsStorageType OBJECT-TYPE
   SYNTAX     StorageType 
   ACCESS     read-only
   STATUS     mandatory
   DESCRIPTION
     "This variable represents the storage type value for the
      mscVrPpIpPortNs tables."
::= { mscVrPpIpPortNsRowStatusEntry 4 }

mscVrPpIpPortNsIndex OBJECT-TYPE
   SYNTAX     NonReplicated 
   ACCESS     not-accessible
   STATUS     mandatory
   DESCRIPTION
     "This variable represents the index for the mscVrPpIpPortNs tables."
::= { mscVrPpIpPortNsRowStatusEntry 10 }

mscVrPpIpPortNsProvTable OBJECT-TYPE
   SYNTAX     SEQUENCE OF MscVrPpIpPortNsProvEntry
   ACCESS     not-accessible
   STATUS     mandatory
   DESCRIPTION
     "This group contains the attributes required by NetSentry to be applied to 
      all IP packets going through this IpPort."
::= { mscVrPpIpPortNs 10 }

mscVrPpIpPortNsProvEntry OBJECT-TYPE
   SYNTAX     MscVrPpIpPortNsProvEntry
   ACCESS     not-accessible
   STATUS     mandatory
   DESCRIPTION
     "An entry in the mscVrPpIpPortNsProvTable."
   INDEX {
      mscVrIndex,
      mscVrPpIndex,
      mscVrPpIpPortIndex,
      mscVrPpIpPortNsIndex }
::= { mscVrPpIpPortNsProvTable 1 }

MscVrPpIpPortNsProvEntry ::= SEQUENCE {
   mscVrPpIpPortNsIncomingFilter
      AsciiString,
   mscVrPpIpPortNsOutgoingFilter
      AsciiString }

mscVrPpIpPortNsIncomingFilter OBJECT-TYPE
   SYNTAX     AsciiString (SIZE (0..32))
   ACCESS     read-write
   STATUS     mandatory
   DESCRIPTION
     "An ASCII string which provides the name of the NetSentry filter which 
      will be applied to all IP datagrams arriving from this IpPort."
   DEFVAL     { ''H }  -- ""
::= { mscVrPpIpPortNsProvEntry 1 }

mscVrPpIpPortNsOutgoingFilter OBJECT-TYPE
   SYNTAX     AsciiString (SIZE (0..32))
   ACCESS     read-write
   STATUS     mandatory
   DESCRIPTION
     "An ASCII string which provides the name of NetSentry filter which will 
      be applied to all IP datagrams sent to this IpPort."
   DEFVAL     { ''H }  -- ""
::= { mscVrPpIpPortNsProvEntry 2 }


-- Vr/<string> Pp/<string> IpPort BootpPort
-- An BootpPort component must be provisioned for each IpPort where 
-- BOOTP request messages will be received. Each BootpPort component 
-- can be provisioned with a set of relay addresses. Each BOOTP request 
-- message received on this port will be sent to the provisioned set of relay 
-- addresses.

mscVrPpIpPortBootpP OBJECT IDENTIFIER ::= { mscVrPpIpPort 4 }



mscVrPpIpPortBootpPRowStatusTable OBJECT-TYPE
   SYNTAX     SEQUENCE OF MscVrPpIpPortBootpPRowStatusEntry
   ACCESS     not-accessible
   STATUS     mandatory
   DESCRIPTION
     "This entry controls the addition and deletion of 
      mscVrPpIpPortBootpP components."
::= { mscVrPpIpPortBootpP 1 }

mscVrPpIpPortBootpPRowStatusEntry OBJECT-TYPE
   SYNTAX     MscVrPpIpPortBootpPRowStatusEntry
   ACCESS     not-accessible
   STATUS     mandatory
   DESCRIPTION
     "A single entry in the table represents a single 
      mscVrPpIpPortBootpP component."
   INDEX {
      mscVrIndex,
      mscVrPpIndex,
      mscVrPpIpPortIndex,
      mscVrPpIpPortBootpPIndex }
::= { mscVrPpIpPortBootpPRowStatusTable 1 }

MscVrPpIpPortBootpPRowStatusEntry ::= SEQUENCE {
   mscVrPpIpPortBootpPRowStatus
      RowStatus,
   mscVrPpIpPortBootpPComponentName
      DisplayString,
   mscVrPpIpPortBootpPStorageType
      StorageType,
   mscVrPpIpPortBootpPIndex
      NonReplicated }

mscVrPpIpPortBootpPRowStatus OBJECT-TYPE
   SYNTAX     RowStatus 
   ACCESS     read-write
   STATUS     mandatory
   DESCRIPTION
     "This variable is used as the basis for SNMP naming of
      mscVrPpIpPortBootpP components.
      These components can be added and deleted."
::= { mscVrPpIpPortBootpPRowStatusEntry 1 }

mscVrPpIpPortBootpPComponentName OBJECT-TYPE
   SYNTAX     DisplayString 
   ACCESS     read-only
   STATUS     mandatory
   DESCRIPTION
     "This variable provides the component's string name for
      use with the ASCII Console Interface"
::= { mscVrPpIpPortBootpPRowStatusEntry 2 }

mscVrPpIpPortBootpPStorageType OBJECT-TYPE
   SYNTAX     StorageType 
   ACCESS     read-only
   STATUS     mandatory
   DESCRIPTION
     "This variable represents the storage type value for the
      mscVrPpIpPortBootpP tables."
::= { mscVrPpIpPortBootpPRowStatusEntry 4 }

mscVrPpIpPortBootpPIndex OBJECT-TYPE
   SYNTAX     NonReplicated 
   ACCESS     not-accessible
   STATUS     mandatory
   DESCRIPTION
     "This variable represents the index for the mscVrPpIpPortBootpP tables."
::= { mscVrPpIpPortBootpPRowStatusEntry 10 }

mscVrPpIpPortBootpPProvTable OBJECT-TYPE
   SYNTAX     SEQUENCE OF MscVrPpIpPortBootpPProvEntry
   ACCESS     not-accessible
   STATUS     mandatory
   DESCRIPTION
     "This group contains provisionable attributes for the BootpPort 
      component."
::= { mscVrPpIpPortBootpP 10 }

mscVrPpIpPortBootpPProvEntry OBJECT-TYPE
   SYNTAX     MscVrPpIpPortBootpPProvEntry
   ACCESS     not-accessible
   STATUS     mandatory
   DESCRIPTION
     "An entry in the mscVrPpIpPortBootpPProvTable."
   INDEX {
      mscVrIndex,
      mscVrPpIndex,
      mscVrPpIpPortIndex,
      mscVrPpIpPortBootpPIndex }
::= { mscVrPpIpPortBootpPProvTable 1 }

MscVrPpIpPortBootpPProvEntry ::= SEQUENCE {
   mscVrPpIpPortBootpPRelayForwardStatus
      INTEGER,
   mscVrPpIpPortBootpPBootpLogicalInterface
      IpAddress }

mscVrPpIpPortBootpPRelayForwardStatus OBJECT-TYPE
   SYNTAX     INTEGER  {
                 enabled(1),
                 disabled(2),
                 auto(3) }
   ACCESS     read-write
   STATUS     mandatory
   DESCRIPTION
     "This attribute controls how BOOTP request packets, received on another 
      port, will be flooded out this port. If relayForwardStatus is enabled, 
      BOOTP requests received on another port will be broadcast out this port. 
      When relayForwardStatus is disabled, BOOTP requests will not be 
      broadcast out this port. If auto is used, the bridge spanning tree database 
      is used to determine if BOOTP requests should be broadcast out this 
      port.
      
      Note that when using enabled, it is possible to create misconfigurations 
      which will result in broadcast storms. When using this feature with 
      multiple routers, make sure there are no broadcast forwarding loops. 
      Using auto with bridge spanning tree is safer to use if the network is 
      running bridge spanning tree.
      
      Note that for auto to have effect, bridge spanning tree must be running 
      on the corresponding VirtualRouter ProtocolPort."
   DEFVAL     { disabled }
::= { mscVrPpIpPortBootpPProvEntry 2 }

mscVrPpIpPortBootpPBootpLogicalInterface OBJECT-TYPE
   SYNTAX     IpAddress 
   ACCESS     read-write
   STATUS     mandatory
   DESCRIPTION
     "This attribute identifies the logical interface whose address is to be the 
      GIADDR of this BOOTP port. If not set, the address of the first logical 
      port is chosen."
   DEFVAL     { '00000000'H }  -- "0.0.0.0"
::= { mscVrPpIpPortBootpPProvEntry 3 }

mscVrPpIpPortBootpPAdminControlTable OBJECT-TYPE
   SYNTAX     SEQUENCE OF MscVrPpIpPortBootpPAdminControlEntry
   ACCESS     not-accessible
   STATUS     mandatory
   DESCRIPTION
     "This group includes the Administrative Control attribute. This 
      attribute defines the current administrative state of this component."
::= { mscVrPpIpPortBootpP 11 }

mscVrPpIpPortBootpPAdminControlEntry OBJECT-TYPE
   SYNTAX     MscVrPpIpPortBootpPAdminControlEntry
   ACCESS     not-accessible
   STATUS     mandatory
   DESCRIPTION
     "An entry in the mscVrPpIpPortBootpPAdminControlTable."
   INDEX {
      mscVrIndex,
      mscVrPpIndex,
      mscVrPpIpPortIndex,
      mscVrPpIpPortBootpPIndex }
::= { mscVrPpIpPortBootpPAdminControlTable 1 }

MscVrPpIpPortBootpPAdminControlEntry ::= SEQUENCE {
   mscVrPpIpPortBootpPSnmpAdminStatus
      INTEGER }

mscVrPpIpPortBootpPSnmpAdminStatus OBJECT-TYPE
   SYNTAX     INTEGER  {
                 up(1),
                 down(2),
                 testing(3) }
   ACCESS     read-write
   STATUS     mandatory
   DESCRIPTION
     "The desired state of the interface. The up state indicates the 
      interface is operational and packet forwarding is allowed. The down 
      state indicates the interface is not operational and packet forwarding 
      is unavailable. The testing state indicates that no operational 
      packets can be passed."
   DEFVAL     { up }
::= { mscVrPpIpPortBootpPAdminControlEntry 1 }

mscVrPpIpPortBootpPOperStatusTable OBJECT-TYPE
   SYNTAX     SEQUENCE OF MscVrPpIpPortBootpPOperStatusEntry
   ACCESS     not-accessible
   STATUS     mandatory
   DESCRIPTION
     "This group includes the Operational Status attribute. This attribute 
      defines the current operational state of this component."
::= { mscVrPpIpPortBootpP 12 }

mscVrPpIpPortBootpPOperStatusEntry OBJECT-TYPE
   SYNTAX     MscVrPpIpPortBootpPOperStatusEntry
   ACCESS     not-accessible
   STATUS     mandatory
   DESCRIPTION
     "An entry in the mscVrPpIpPortBootpPOperStatusTable."
   INDEX {
      mscVrIndex,
      mscVrPpIndex,
      mscVrPpIpPortIndex,
      mscVrPpIpPortBootpPIndex }
::= { mscVrPpIpPortBootpPOperStatusTable 1 }

MscVrPpIpPortBootpPOperStatusEntry ::= SEQUENCE {
   mscVrPpIpPortBootpPSnmpOperStatus
      INTEGER }

mscVrPpIpPortBootpPSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscVrPpIpPortBootpPOperStatusEntry 1 }

mscVrPpIpPortBootpPStateTable OBJECT-TYPE
   SYNTAX     SEQUENCE OF MscVrPpIpPortBootpPStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscVrPpIpPortBootpP 13 }

mscVrPpIpPortBootpPStateEntry OBJECT-TYPE
   SYNTAX     MscVrPpIpPortBootpPStateEntry
   ACCESS     not-accessible
   STATUS     mandatory
   DESCRIPTION
     "An entry in the mscVrPpIpPortBootpPStateTable."
   INDEX {
      mscVrIndex,
      mscVrPpIndex,
      mscVrPpIpPortIndex,
      mscVrPpIpPortBootpPIndex }
::= { mscVrPpIpPortBootpPStateTable 1 }

MscVrPpIpPortBootpPStateEntry ::= SEQUENCE {
   mscVrPpIpPortBootpPAdminState
      INTEGER,
   mscVrPpIpPortBootpPOperationalState
      INTEGER,
   mscVrPpIpPortBootpPUsageState
      INTEGER }

mscVrPpIpPortBootpPAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscVrPpIpPortBootpPStateEntry 1 }

mscVrPpIpPortBootpPOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscVrPpIpPortBootpPStateEntry 2 }

mscVrPpIpPortBootpPUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscVrPpIpPortBootpPStateEntry 3 }

mscVrPpIpPortBootpPStatsTable OBJECT-TYPE
   SYNTAX     SEQUENCE OF MscVrPpIpPortBootpPStatsEntry
   ACCESS     not-accessible
   STATUS     mandatory
   DESCRIPTION
     "This group contains BootpPortEntry component statistics."
::= { mscVrPpIpPortBootpP 14 }

mscVrPpIpPortBootpPStatsEntry OBJECT-TYPE
   SYNTAX     MscVrPpIpPortBootpPStatsEntry
   ACCESS     not-accessible
   STATUS     mandatory
   DESCRIPTION
     "An entry in the mscVrPpIpPortBootpPStatsTable."
   INDEX {
      mscVrIndex,
      mscVrPpIndex,
      mscVrPpIpPortIndex,
      mscVrPpIpPortBootpPIndex }
::= { mscVrPpIpPortBootpPStatsTable 1 }

MscVrPpIpPortBootpPStatsEntry ::= SEQUENCE {
   mscVrPpIpPortBootpPInRequests
      Counter32,
   mscVrPpIpPortBootpPInReplies
      Counter32,
   mscVrPpIpPortBootpPOutRequests
      Counter32,
   mscVrPpIpPortBootpPOutReplies
      Counter32,
   mscVrPpIpPortBootpPInRequestErrors
      Counter32,
   mscVrPpIpPortBootpPInReplyErrors
      Counter32 }

mscVrPpIpPortBootpPInRequests OBJECT-TYPE
   SYNTAX     Counter32 
   ACCESS     read-only
   STATUS     mandatory
   DESCRIPTION
     "This attribute counts the total number of BOOTP Request messages 
      received on this port."
::= { mscVrPpIpPortBootpPStatsEntry 1 }

mscVrPpIpPortBootpPInReplies OBJECT-TYPE
   SYNTAX     Counter32 
   ACCESS     read-only
   STATUS     mandatory
   DESCRIPTION
     "This attribute counts the total number of BOOTP Reply messages 
      received on this port."
::= { mscVrPpIpPortBootpPStatsEntry 2 }

mscVrPpIpPortBootpPOutRequests OBJECT-TYPE
   SYNTAX     Counter32 
   ACCESS     read-only
   STATUS     mandatory
   DESCRIPTION
     "This attribute counts total the number of BOOTP Request messages 
      broadcast out on this port."
::= { mscVrPpIpPortBootpPStatsEntry 3 }

mscVrPpIpPortBootpPOutReplies OBJECT-TYPE
   SYNTAX     Counter32 
   ACCESS     read-only
   STATUS     mandatory
   DESCRIPTION
     "This attribute counts the total number of BOOTP Reply messages sent 
      out on this port."
::= { mscVrPpIpPortBootpPStatsEntry 4 }

mscVrPpIpPortBootpPInRequestErrors OBJECT-TYPE
   SYNTAX     Counter32 
   ACCESS     read-only
   STATUS     mandatory
   DESCRIPTION
     "This attribute counts the number of BOOTP Request messages received 
      on this port but not forwarded due to an error. An error occurs if the 
      BOOTP hop limit has been exceeded."
::= { mscVrPpIpPortBootpPStatsEntry 5 }

mscVrPpIpPortBootpPInReplyErrors OBJECT-TYPE
   SYNTAX     Counter32 
   ACCESS     read-only
   STATUS     mandatory
   DESCRIPTION
     "This attribute counts the number of BOOTP Reply messages received on 
      this port but not forwarded due to an error. An error occurs if the giaddr 
      field in the BOOTP reply does not match an IP address assigned to this 
      VirtualRouter, or if the output IpPort for the BOOTP reply is not 
      provisioned for BOOTP."
::= { mscVrPpIpPortBootpPStatsEntry 6 }

mscVrPpIpPortBootpPAddrTable OBJECT-TYPE
   SYNTAX     SEQUENCE OF MscVrPpIpPortBootpPAddrEntry
   ACCESS     not-accessible
   STATUS     mandatory
   DESCRIPTION
     "This attribute identifies a list of relay addresses. When a BOOTP request 
      message is received on this port, the request will be forwarded to the IP 
      addresses provisioned in relayAddress. Note that BOOTP requests are 
      also broadcast out all other BootpPort's according to the 
      relayForwardStatus of the outgoing port."
::= { mscVrPpIpPortBootpP 290 }

mscVrPpIpPortBootpPAddrEntry OBJECT-TYPE
   SYNTAX     MscVrPpIpPortBootpPAddrEntry
   ACCESS     not-accessible
   STATUS     mandatory
   DESCRIPTION
     "An entry in the mscVrPpIpPortBootpPAddrTable."
   INDEX {
      mscVrIndex,
      mscVrPpIndex,
      mscVrPpIpPortIndex,
      mscVrPpIpPortBootpPIndex,
      mscVrPpIpPortBootpPAddrValue }
::= { mscVrPpIpPortBootpPAddrTable 1 }

MscVrPpIpPortBootpPAddrEntry ::= SEQUENCE {
   mscVrPpIpPortBootpPAddrValue
      IpAddress,
   mscVrPpIpPortBootpPAddrRowStatus
      RowStatus }

mscVrPpIpPortBootpPAddrValue OBJECT-TYPE
   SYNTAX     IpAddress 
   ACCESS     read-write
   STATUS     mandatory
   DESCRIPTION
     "This variable represents both the value and the index for the
      mscVrPpIpPortBootpPAddrTable."
::= { mscVrPpIpPortBootpPAddrEntry 1 }

mscVrPpIpPortBootpPAddrRowStatus OBJECT-TYPE
   SYNTAX     RowStatus 
   ACCESS     write-only
   STATUS     mandatory
   DESCRIPTION
     "This variable is used to control the addition and deletion 
      of individual values of the mscVrPpIpPortBootpPAddrTable."
::= { mscVrPpIpPortBootpPAddrEntry 2 }


-- Vr/<string> Ip 
-- This component represents the instance of IP protocol running on this 
-- virtual router.

mscVrIp OBJECT IDENTIFIER ::= { mscVr 6 }



mscVrIpRowStatusTable OBJECT-TYPE
   SYNTAX     SEQUENCE OF MscVrIpRowStatusEntry
   ACCESS     not-accessible
   STATUS     mandatory
   DESCRIPTION
     "This entry controls the addition and deletion of 
      mscVrIp components."
::= { mscVrIp 1 }

mscVrIpRowStatusEntry OBJECT-TYPE
   SYNTAX     MscVrIpRowStatusEntry
   ACCESS     not-accessible
   STATUS     mandatory
   DESCRIPTION
     "A single entry in the table represents a single 
      mscVrIp component."
   INDEX {
      mscVrIndex,
      mscVrIpIndex }
::= { mscVrIpRowStatusTable 1 }

MscVrIpRowStatusEntry ::= SEQUENCE {
   mscVrIpRowStatus
      RowStatus,
   mscVrIpComponentName
      DisplayString,
   mscVrIpStorageType
      StorageType,
   mscVrIpIndex
      NonReplicated }

mscVrIpRowStatus OBJECT-TYPE
   SYNTAX     RowStatus 
   ACCESS     read-write
   STATUS     mandatory
   DESCRIPTION
     "This variable is used as the basis for SNMP naming of
      mscVrIp components.
      These components can be added and deleted."
::= { mscVrIpRowStatusEntry 1 }

mscVrIpComponentName OBJECT-TYPE
   SYNTAX     DisplayString 
   ACCESS     read-only
   STATUS     mandatory
   DESCRIPTION
     "This variable provides the component's string name for
      use with the ASCII Console Interface"
::= { mscVrIpRowStatusEntry 2 }

mscVrIpStorageType OBJECT-TYPE
   SYNTAX     StorageType 
   ACCESS     read-only
   STATUS     mandatory
   DESCRIPTION
     "This variable represents the storage type value for the
      mscVrIp tables."
::= { mscVrIpRowStatusEntry 4 }

mscVrIpIndex OBJECT-TYPE
   SYNTAX     NonReplicated 
   ACCESS     not-accessible
   STATUS     mandatory
   DESCRIPTION
     "This variable represents the index for the mscVrIp tables."
::= { mscVrIpRowStatusEntry 10 }

mscVrIpProvTable OBJECT-TYPE
   SYNTAX     SEQUENCE OF MscVrIpProvEntry
   ACCESS     not-accessible
   STATUS     mandatory
   DESCRIPTION
     "This group contains global attributes for IP."
::= { mscVrIp 100 }

mscVrIpProvEntry OBJECT-TYPE
   SYNTAX     MscVrIpProvEntry
   ACCESS     not-accessible
   STATUS     mandatory
   DESCRIPTION
     "An entry in the mscVrIpProvTable."
   INDEX {
      mscVrIndex,
      mscVrIpIndex }
::= { mscVrIpProvTable 1 }

MscVrIpProvEntry ::= SEQUENCE {
   mscVrIpForwarding
      INTEGER,
   mscVrIpDefaultTtl
      Unsigned32,
   mscVrIpCosPolicyAssignment
      Link }

mscVrIpForwarding OBJECT-TYPE
   SYNTAX     INTEGER  {
                 gateway(1) }
   ACCESS     read-write
   STATUS     mandatory
   DESCRIPTION
     "This attribute indicates whether or not this VR is acting as an IP gateway 
      in respect to the forwarding of datagrams received by, but not addressed 
      to, this VR"
   DEFVAL     { gateway }
::= { mscVrIpProvEntry 2 }

mscVrIpDefaultTtl OBJECT-TYPE
   SYNTAX     Unsigned32 (255..255)
   ACCESS     read-write
   STATUS     mandatory
   DESCRIPTION
     "This attribute is the default value inserted into the Time-To-Live field of 
      the IP header of datagrams originated at this entity, whenever a Time-
      To-Live value is not supplied by the transport layer protocol.
      
      The value of this attribute deviates from the MIB requirement that it will 
      always have a value of 255."
   DEFVAL     { 255 }
::= { mscVrIpProvEntry 3 }

mscVrIpCosPolicyAssignment OBJECT-TYPE
   SYNTAX     Link 
   ACCESS     read-write
   STATUS     mandatory
   DESCRIPTION
     "This attribute specifies the default cosPolicyGroup component that is 
      associated with the IpPort of every protocol port on the virtual router. 
      An individual IpPort can override this default using its own 
      cosPolicyAssignment attribute.
      
      If this attribute is empty, CoS policy groups are assigned to only those 
      IP ports where the cosPolicyAssignment attribute under the IpPort 
      component is non-empty."
::= { mscVrIpProvEntry 4 }

mscVrIpStatsTable OBJECT-TYPE
   SYNTAX     SEQUENCE OF MscVrIpStatsEntry
   ACCESS     not-accessible
   STATUS     mandatory
   DESCRIPTION
     "This is the GROUP holding the struct which contains statistical 
      attributes for IP."
::= { mscVrIp 101 }

mscVrIpStatsEntry OBJECT-TYPE
   SYNTAX     MscVrIpStatsEntry
   ACCESS     not-accessible
   STATUS     mandatory
   DESCRIPTION
     "An entry in the mscVrIpStatsTable."
   INDEX {
      mscVrIndex,
      mscVrIpIndex }
::= { mscVrIpStatsTable 1 }

MscVrIpStatsEntry ::= SEQUENCE {
   mscVrIpInReceives
      Counter32,
   mscVrIpInHdrErrors
      Counter32,
   mscVrIpInAddrErrors
      Counter32,
   mscVrIpForwDatagrams
      Counter32,
   mscVrIpInUnknownProtos
      Counter32,
   mscVrIpInDiscards
      Counter32,
   mscVrIpInDelivers
      Counter32,
   mscVrIpOutRequests
      Counter32,
   mscVrIpOutDiscards
      Counter32,
   mscVrIpOutNoRoutes
      Counter32,
   mscVrIpReasmTimeOut
      Unsigned32,
   mscVrIpReasmReqds
      Counter32,
   mscVrIpReasmOks
      Counter32,
   mscVrIpReasmFails
      Counter32,
   mscVrIpFragOks
      Counter32,
   mscVrIpFragFails
      Counter32,
   mscVrIpFragCreates
      Counter32,
   mscVrIpRoutingDiscards
      Counter32 }

mscVrIpInReceives OBJECT-TYPE
   SYNTAX     Counter32 
   ACCESS     read-only
   STATUS     mandatory
   DESCRIPTION
     "This is the number of input datagrams received from the interfaces, 
      including those received in error		. inReceives wraps to zero if reaches its 
      maximum defined value."
::= { mscVrIpStatsEntry 1 }

mscVrIpInHdrErrors OBJECT-TYPE
   SYNTAX     Counter32 
   ACCESS     read-only
   STATUS     mandatory
   DESCRIPTION
     "The number of input datagrams discarded due to errors in their IP 
      headers, including bad checksums, version number mismatch, other 
      format errors, time-to-live exceeded, errors discovered in processing 
      their IP options, etc. inHdrErrors wraps to zero if reaches its maximum 
      defined value."
::= { mscVrIpStatsEntry 2 }

mscVrIpInAddrErrors OBJECT-TYPE
   SYNTAX     Counter32 
   ACCESS     read-only
   STATUS     mandatory
   DESCRIPTION
     "The number of input datagrams discarded due to errors such as invalid 
      address, unsupported address class. inAddrErrors wraps to zero if 
      reaches its maximum defined value."
::= { mscVrIpStatsEntry 3 }

mscVrIpForwDatagrams OBJECT-TYPE
   SYNTAX     Counter32 
   ACCESS     read-only
   STATUS     mandatory
   DESCRIPTION
     "The number of input datagrams for which this router was not their final 
      IP destination, as a result of which an attempt was made to find a route 
      to forward them to that final destination. forwDatagrams wraps to zero 
      if reaches it's maximum defined value."
::= { mscVrIpStatsEntry 4 }

mscVrIpInUnknownProtos OBJECT-TYPE
   SYNTAX     Counter32 
   ACCESS     read-only
   STATUS     mandatory
   DESCRIPTION
     "The number of locally-addressed datagrams received successfully but 
      discarded because of an unknown or unsupported protocol 
      inUnknownProtos wraps to zero if reaches its maximum defined value."
::= { mscVrIpStatsEntry 5 }

mscVrIpInDiscards OBJECT-TYPE
   SYNTAX     Counter32 
   ACCESS     read-only
   STATUS     mandatory
   DESCRIPTION
     "The number of input datagrams for which no problems were 
      encountered to prevent their continued processing, but which were 
      discarded due to the lack of buffers. This does not include any datagram 
      discarded while awaiting for re-assembly. inDiscards wraps to zero if 
      reaches its maximum defined value."
::= { mscVrIpStatsEntry 6 }

mscVrIpInDelivers OBJECT-TYPE
   SYNTAX     Counter32 
   ACCESS     read-only
   STATUS     mandatory
   DESCRIPTION
     "The number of input datagrams successfully delivered to IP user-
      protocols (including ICMP). inDelivers wraps to zero if reaches its 
      maximum defined value."
::= { mscVrIpStatsEntry 7 }

mscVrIpOutRequests OBJECT-TYPE
   SYNTAX     Counter32 
   ACCESS     read-only
   STATUS     mandatory
   DESCRIPTION
     "The number of datagrams which local IP user-protocols (including 
      ICMP) supplied to IP in requests for transmission. This sum does not 
      include datagrams counted in ForwDatagrams. outRequests wraps to 
      zero if reaches its maximum defined value."
::= { mscVrIpStatsEntry 8 }

mscVrIpOutDiscards OBJECT-TYPE
   SYNTAX     Counter32 
   ACCESS     read-only
   STATUS     mandatory
   DESCRIPTION
     "The number of outbound datagrams that were discarded due to the lack 
      of buffers. This sum also includes datagrams counted in forwDatagrams 
      if any such packets met the discard criterion. outDiscards wraps to zero 
      if reaches its maximum defined value."
::= { mscVrIpStatsEntry 9 }

mscVrIpOutNoRoutes OBJECT-TYPE
   SYNTAX     Counter32 
   ACCESS     read-only
   STATUS     mandatory
   DESCRIPTION
     "The number of outbound datagrams discarded because no route could be 
      found to transmit them to their destination. This counter includes any 
      datagrams counted in forwDatagrams. outNoRoutes wraps to zero if 
      reaches its maximum defined value."
::= { mscVrIpStatsEntry 10 }

mscVrIpReasmTimeOut OBJECT-TYPE
   SYNTAX     Unsigned32 (0..5)
   ACCESS     read-only
   STATUS     mandatory
   DESCRIPTION
     "The maximum number of seconds, which received fragments are held 
      while they are awaiting reassembly at this gateway."
   DEFVAL     { 5 }
::= { mscVrIpStatsEntry 11 }

mscVrIpReasmReqds OBJECT-TYPE
   SYNTAX     Counter32 
   ACCESS     read-only
   STATUS     mandatory
   DESCRIPTION
     "The number of the IP fragments received by this gateway which needed 
      to be reassembled. reasmReqds wraps to zero if reaches its maximum 
      defined value."
::= { mscVrIpStatsEntry 12 }

mscVrIpReasmOks OBJECT-TYPE
   SYNTAX     Counter32 
   ACCESS     read-only
   STATUS     mandatory
   DESCRIPTION
     "The number of IP fragments successfully reassembled by this gateway. 
      reasmOks wraps to zero if reaches its maximum defined value."
::= { mscVrIpStatsEntry 13 }

mscVrIpReasmFails OBJECT-TYPE
   SYNTAX     Counter32 
   ACCESS     read-only
   STATUS     mandatory
   DESCRIPTION
     "The number of times this gateway is unabled to assemble IP-fragments 
      for whatever reasons. reasmFails wraps to zero if reaches its maximum 
      defined value."
::= { mscVrIpStatsEntry 14 }

mscVrIpFragOks OBJECT-TYPE
   SYNTAX     Counter32 
   ACCESS     read-only
   STATUS     mandatory
   DESCRIPTION
     "The number of IP datagrams that have been successfully fragmented by 
      this gateway. fragOks wraps to zero if reaches its maximum defined 
      value."
::= { mscVrIpStatsEntry 15 }

mscVrIpFragFails OBJECT-TYPE
   SYNTAX     Counter32 
   ACCESS     read-only
   STATUS     mandatory
   DESCRIPTION
     "The number of IP-fragments that have been discarded because they 
      needed to be fragmented but could not be. For example, their Don't 
      Fragment flag was set. fragFails wraps to zero if reaches its maximum 
      defined value."
::= { mscVrIpStatsEntry 16 }

mscVrIpFragCreates OBJECT-TYPE
   SYNTAX     Counter32 
   ACCESS     read-only
   STATUS     mandatory
   DESCRIPTION
     "This number of IP fragments that have been generated as a result of 
      fragmentation by this gateway. fragCreates wraps to zero if reaches its 
      maximum defined value."
::= { mscVrIpStatsEntry 17 }

mscVrIpRoutingDiscards OBJECT-TYPE
   SYNTAX     Counter32 
   ACCESS     read-only
   STATUS     mandatory
   DESCRIPTION
     "The number of routing entries which were chosen to be discarded even 
      though they are valid. One possible reason for discarding such an entry 
      could be to free -up buffer space for other routing entries. In this 
      implementation, this number is always zero because IP never deletes a 
      valid routing entry."
::= { mscVrIpStatsEntry 18 }

mscVrIpAdminControlTable OBJECT-TYPE
   SYNTAX     SEQUENCE OF MscVrIpAdminControlEntry
   ACCESS     not-accessible
   STATUS     mandatory
   DESCRIPTION
     "This group includes the Administrative Control attribute. This 
      attribute defines the current administrative state of this component."
::= { mscVrIp 102 }

mscVrIpAdminControlEntry OBJECT-TYPE
   SYNTAX     MscVrIpAdminControlEntry
   ACCESS     not-accessible
   STATUS     mandatory
   DESCRIPTION
     "An entry in the mscVrIpAdminControlTable."
   INDEX {
      mscVrIndex,
      mscVrIpIndex }
::= { mscVrIpAdminControlTable 1 }

MscVrIpAdminControlEntry ::= SEQUENCE {
   mscVrIpSnmpAdminStatus
      INTEGER }

mscVrIpSnmpAdminStatus OBJECT-TYPE
   SYNTAX     INTEGER  {
                 up(1),
                 down(2),
                 testing(3) }
   ACCESS     read-write
   STATUS     mandatory
   DESCRIPTION
     "The desired state of the interface. The up state indicates the 
      interface is operational and packet forwarding is allowed. The down 
      state indicates the interface is not operational and packet forwarding 
      is unavailable. The testing state indicates that no operational 
      packets can be passed."
   DEFVAL     { up }
::= { mscVrIpAdminControlEntry 1 }

mscVrIpStateTable OBJECT-TYPE
   SYNTAX     SEQUENCE OF MscVrIpStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscVrIp 104 }

mscVrIpStateEntry OBJECT-TYPE
   SYNTAX     MscVrIpStateEntry
   ACCESS     not-accessible
   STATUS     mandatory
   DESCRIPTION
     "An entry in the mscVrIpStateTable."
   INDEX {
      mscVrIndex,
      mscVrIpIndex }
::= { mscVrIpStateTable 1 }

MscVrIpStateEntry ::= SEQUENCE {
   mscVrIpAdminState
      INTEGER,
   mscVrIpOperationalState
      INTEGER,
   mscVrIpUsageState
      INTEGER }

mscVrIpAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscVrIpStateEntry 1 }

mscVrIpOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscVrIpStateEntry 2 }

mscVrIpUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscVrIpStateEntry 3 }

mscVrIpOperStatusTable OBJECT-TYPE
   SYNTAX     SEQUENCE OF MscVrIpOperStatusEntry
   ACCESS     not-accessible
   STATUS     mandatory
   DESCRIPTION
     "This group includes the Operational Status attribute. This attribute 
      defines the current operational state of this component."
::= { mscVrIp 107 }

mscVrIpOperStatusEntry OBJECT-TYPE
   SYNTAX     MscVrIpOperStatusEntry
   ACCESS     not-accessible
   STATUS     mandatory
   DESCRIPTION
     "An entry in the mscVrIpOperStatusTable."
   INDEX {
      mscVrIndex,
      mscVrIpIndex }
::= { mscVrIpOperStatusTable 1 }

MscVrIpOperStatusEntry ::= SEQUENCE {
   mscVrIpSnmpOperStatus
      INTEGER }

mscVrIpSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscVrIpOperStatusEntry 1 }

mscVrIpCtsTable OBJECT-TYPE
   SYNTAX     SEQUENCE OF MscVrIpCtsEntry
   ACCESS     not-accessible
   STATUS     mandatory
   DESCRIPTION
     "This attribute specifies the maximum number of entries that can exist in 
      the IP local cache table on each LP. This attribute provides a way to 
      control the resources allocated to the IP cache tables.
      The default cache table size is 3000 for an FP and 100 for a CP, is used 
      if this attribute is not specified explicitly. The attribute value must be 
      multiple of 100."
::= { mscVrIp 394 }

mscVrIpCtsEntry OBJECT-TYPE
   SYNTAX     MscVrIpCtsEntry
   ACCESS     not-accessible
   STATUS     mandatory
   DESCRIPTION
     "An entry in the mscVrIpCtsTable."
   INDEX {
      mscVrIndex,
      mscVrIpIndex,
      mscVrIpCtsIndex }
::= { mscVrIpCtsTable 1 }

MscVrIpCtsEntry ::= SEQUENCE {
   mscVrIpCtsIndex
      Integer32,
   mscVrIpCtsValue
      Unsigned32 }

mscVrIpCtsIndex OBJECT-TYPE
   SYNTAX     Integer32 (0..15)
   ACCESS     not-accessible
   STATUS     mandatory
   DESCRIPTION
     "This variable represents the mscVrIpCtsTable
      specific index for the mscVrIpCtsTable."
::= { mscVrIpCtsEntry 1 }

mscVrIpCtsValue OBJECT-TYPE
   SYNTAX     Unsigned32 (100..8000)
   ACCESS     read-write
   STATUS     mandatory
   DESCRIPTION
     "This variable represents an individual value for the
      mscVrIpCtsTable."
::= { mscVrIpCtsEntry 2 }

-- 
-- *** THIS SUBTREE CURRENTLY NOT IMPLEMENTED ***
-- 

-- Vr/<string> Ip ForwardTable/<Ip Address>,<Ip 
-- Address>,<Decimal>,<IP Address>
-- This component contains the information to forward data.This table 
-- holds the best route information sent from Routing table.

mscVrIpFwd OBJECT IDENTIFIER ::= { mscVrIp 3 }



mscVrIpFwdRowStatusTable OBJECT-TYPE
   SYNTAX     SEQUENCE OF MscVrIpFwdRowStatusEntry
   ACCESS     not-accessible
   STATUS     mandatory
   DESCRIPTION
     "*** THIS TABLE CURRENTLY NOT IMPLEMENTED ***

      This entry controls the addition and deletion of 
      mscVrIpFwd components."
::= { mscVrIpFwd 1 }

mscVrIpFwdRowStatusEntry OBJECT-TYPE
   SYNTAX     MscVrIpFwdRowStatusEntry
   ACCESS     not-accessible
   STATUS     mandatory
   DESCRIPTION
     "A single entry in the table represents a single 
      mscVrIpFwd component."
   INDEX {
      mscVrIndex,
      mscVrIpIndex,
      mscVrIpFwdDestAddressIndex,
      mscVrIpFwdDestMaskIndex,
      mscVrIpFwdTypeOfServiceIndex,
      mscVrIpFwdGatewayIndex }
::= { mscVrIpFwdRowStatusTable 1 }

MscVrIpFwdRowStatusEntry ::= SEQUENCE {
   mscVrIpFwdRowStatus
      RowStatus,
   mscVrIpFwdComponentName
      DisplayString,
   mscVrIpFwdStorageType
      StorageType,
   mscVrIpFwdDestAddressIndex
      IpAddress,
   mscVrIpFwdDestMaskIndex
      IpAddress,
   mscVrIpFwdTypeOfServiceIndex
      Integer32,
   mscVrIpFwdGatewayIndex
      IpAddress }

mscVrIpFwdRowStatus OBJECT-TYPE
   SYNTAX     RowStatus 
   ACCESS     read-only
   STATUS     mandatory
   DESCRIPTION
     "This variable is used as the basis for SNMP naming of
      mscVrIpFwd components.
      These components cannot be added nor deleted."
::= { mscVrIpFwdRowStatusEntry 1 }

mscVrIpFwdComponentName OBJECT-TYPE
   SYNTAX     DisplayString 
   ACCESS     read-only
   STATUS     mandatory
   DESCRIPTION
     "This variable provides the component's string name for
      use with the ASCII Console Interface"
::= { mscVrIpFwdRowStatusEntry 2 }

mscVrIpFwdStorageType OBJECT-TYPE
   SYNTAX     StorageType 
   ACCESS     read-only
   STATUS     mandatory
   DESCRIPTION
     "This variable represents the storage type value for the
      mscVrIpFwd tables."
::= { mscVrIpFwdRowStatusEntry 4 }

mscVrIpFwdDestAddressIndex OBJECT-TYPE
   SYNTAX     IpAddress 
   ACCESS     not-accessible
   STATUS     mandatory
   DESCRIPTION
     "This variable represents an index for the mscVrIpFwd tables."
::= { mscVrIpFwdRowStatusEntry 10 }

mscVrIpFwdDestMaskIndex OBJECT-TYPE
   SYNTAX     IpAddress 
   ACCESS     not-accessible
   STATUS     mandatory
   DESCRIPTION
     "This variable represents an index for the mscVrIpFwd tables."
::= { mscVrIpFwdRowStatusEntry 11 }

mscVrIpFwdTypeOfServiceIndex OBJECT-TYPE
   SYNTAX     Integer32 (0..31)
   ACCESS     not-accessible
   STATUS     mandatory
   DESCRIPTION
     "This variable represents an index for the mscVrIpFwd tables."
::= { mscVrIpFwdRowStatusEntry 12 }

mscVrIpFwdGatewayIndex OBJECT-TYPE
   SYNTAX     IpAddress 
   ACCESS     not-accessible
   STATUS     mandatory
   DESCRIPTION
     "This variable represents an index for the mscVrIpFwd tables."
::= { mscVrIpFwdRowStatusEntry 13 }

mscVrIpFwdOperTable OBJECT-TYPE
   SYNTAX     SEQUENCE OF MscVrIpFwdOperEntry
   ACCESS     not-accessible
   STATUS     mandatory
   DESCRIPTION
     "*** THIS TABLE CURRENTLY NOT IMPLEMENTED ***

      Identifies a group of operational attributes associated with each entry in 
      the Forward Table."
::= { mscVrIpFwd 10 }

mscVrIpFwdOperEntry OBJECT-TYPE
   SYNTAX     MscVrIpFwdOperEntry
   ACCESS     not-accessible
   STATUS     mandatory
   DESCRIPTION
     "An entry in the mscVrIpFwdOperTable."
   INDEX {
      mscVrIndex,
      mscVrIpIndex,
      mscVrIpFwdDestAddressIndex,
      mscVrIpFwdDestMaskIndex,
      mscVrIpFwdTypeOfServiceIndex,
      mscVrIpFwdGatewayIndex }
::= { mscVrIpFwdOperTable 1 }

MscVrIpFwdOperEntry ::= SEQUENCE {
   mscVrIpFwdIfIndex
      InterfaceIndex,
   mscVrIpFwdType
      INTEGER,
   mscVrIpFwdProtocol
      INTEGER,
   mscVrIpFwdAge
      Gauge32,
   mscVrIpFwdProtocolPortName
      RowPointer,
   mscVrIpFwdNextHopAs
      Unsigned32,
   mscVrIpFwdMetric
      INTEGER }

mscVrIpFwdIfIndex OBJECT-TYPE
   SYNTAX     InterfaceIndex (1..65535)
   ACCESS     read-only
   STATUS     mandatory
   DESCRIPTION
     "This attribute specifies the SNMP index associated with the 
      protocol port represented by the attribute protocolPortName, which 
      identifies the local interface through which the next hop of this route 
      should be reached."
::= { mscVrIpFwdOperEntry 1 }

mscVrIpFwdType OBJECT-TYPE
   SYNTAX     INTEGER  {
                 notDefined(1),
                 invalid(2),
                 localInterface(3),
                 remoteDestination(4) }
   ACCESS     read-only
   STATUS     mandatory
   DESCRIPTION
     "Specifies the type of the route,"
::= { mscVrIpFwdOperEntry 2 }

mscVrIpFwdProtocol OBJECT-TYPE
   SYNTAX     INTEGER  {
                 other(1),
                 local(2),
                 netmgmt(3),
                 icmp(4),
                 egp(5),
                 ggp(6),
                 hello(7),
                 rip(8),
                 isIs(9),
                 esIs(10),
                 ciscoIgrp(11),
                 bbnSpfIgp(12),
                 ospf(13),
                 bgp(14),
                 idpr(15),
                 mpls(16) }
   ACCESS     read-only
   STATUS     mandatory
   DESCRIPTION
     "This Attribute identifies the routing mechanism by which this route was 
      learned."
::= { mscVrIpFwdOperEntry 3 }

mscVrIpFwdAge OBJECT-TYPE
   SYNTAX     Gauge32 (0..4294967295)
   ACCESS     read-only
   STATUS     mandatory
   DESCRIPTION
     "This attribute specifies the number of seconds since this route was last 
      updated or otherwise determined to be correct."
::= { mscVrIpFwdOperEntry 4 }

mscVrIpFwdProtocolPortName OBJECT-TYPE
   SYNTAX     RowPointer 
   ACCESS     read-only
   STATUS     mandatory
   DESCRIPTION
     "Indicates the name of the protocol port by which the next hop of this 
      route should be reached."
::= { mscVrIpFwdOperEntry 5 }

mscVrIpFwdNextHopAs OBJECT-TYPE
   SYNTAX     Unsigned32 (0..429467295)
   ACCESS     read-only
   STATUS     mandatory
   DESCRIPTION
     "This attribute specifies the Autonomous System number of the Next 
      Hop. If unknown or not relevant to the protocol indicated by the attribute 
      protocol, the value should be zero."
::= { mscVrIpFwdOperEntry 7 }

mscVrIpFwdMetric OBJECT-TYPE
   SYNTAX     INTEGER (-1..65535)
   ACCESS     read-only
   STATUS     mandatory
   DESCRIPTION
     "This attribute specifies the primary routing metric for this route. The 
      semantics of this metric are determined by the routing protocol specified 
      by the value of the attribute protocol. If this metric is not used, its value 
      should be set to -1."
   DEFVAL     { -1 }
::= { mscVrIpFwdOperEntry 8 }

-- 
-- *** THIS SUBTREE CURRENTLY NOT IMPLEMENTED ***
-- 

-- Vr/<string> Ip RouteDataBaseEntry/
-- <destAddress>,<destMask>,<protocol>
-- This component is used to display the information in the Ip routing 
-- database. destAddress and destMask indicates the address and mask of 
-- the route in the RoutingDatabase. protocol indicates the protocol this 
-- entry is learned from. gateway indicates the nextHop address for remote 
-- routes. The value of gateway for the localInterface routes will be the 
-- same value as the destAddress.

mscVrIpRdb OBJECT IDENTIFIER ::= { mscVrIp 4 }



mscVrIpRdbRowStatusTable OBJECT-TYPE
   SYNTAX     SEQUENCE OF MscVrIpRdbRowStatusEntry
   ACCESS     not-accessible
   STATUS     mandatory
   DESCRIPTION
     "*** THIS TABLE CURRENTLY NOT IMPLEMENTED ***

      This entry controls the addition and deletion of 
      mscVrIpRdb components."
::= { mscVrIpRdb 1 }

mscVrIpRdbRowStatusEntry OBJECT-TYPE
   SYNTAX     MscVrIpRdbRowStatusEntry
   ACCESS     not-accessible
   STATUS     mandatory
   DESCRIPTION
     "A single entry in the table represents a single 
      mscVrIpRdb component."
   INDEX {
      mscVrIndex,
      mscVrIpIndex,
      mscVrIpRdbDestAddressIndex,
      mscVrIpRdbDestMaskIndex,
      mscVrIpRdbProtocolIndex,
      mscVrIpRdbGatewayIndex }
::= { mscVrIpRdbRowStatusTable 1 }

MscVrIpRdbRowStatusEntry ::= SEQUENCE {
   mscVrIpRdbRowStatus
      RowStatus,
   mscVrIpRdbComponentName
      DisplayString,
   mscVrIpRdbStorageType
      StorageType,
   mscVrIpRdbDestAddressIndex
      IpAddress,
   mscVrIpRdbDestMaskIndex
      IpAddress,
   mscVrIpRdbProtocolIndex
      INTEGER,
   mscVrIpRdbGatewayIndex
      IpAddress }

mscVrIpRdbRowStatus OBJECT-TYPE
   SYNTAX     RowStatus 
   ACCESS     read-only
   STATUS     mandatory
   DESCRIPTION
     "This variable is used as the basis for SNMP naming of
      mscVrIpRdb components.
      These components cannot be added nor deleted."
::= { mscVrIpRdbRowStatusEntry 1 }

mscVrIpRdbComponentName OBJECT-TYPE
   SYNTAX     DisplayString 
   ACCESS     read-only
   STATUS     mandatory
   DESCRIPTION
     "This variable provides the component's string name for
      use with the ASCII Console Interface"
::= { mscVrIpRdbRowStatusEntry 2 }

mscVrIpRdbStorageType OBJECT-TYPE
   SYNTAX     StorageType 
   ACCESS     read-only
   STATUS     mandatory
   DESCRIPTION
     "This variable represents the storage type value for the
      mscVrIpRdb tables."
::= { mscVrIpRdbRowStatusEntry 4 }

mscVrIpRdbDestAddressIndex OBJECT-TYPE
   SYNTAX     IpAddress 
   ACCESS     not-accessible
   STATUS     mandatory
   DESCRIPTION
     "This variable represents an index for the mscVrIpRdb tables."
::= { mscVrIpRdbRowStatusEntry 10 }

mscVrIpRdbDestMaskIndex OBJECT-TYPE
   SYNTAX     IpAddress 
   ACCESS     not-accessible
   STATUS     mandatory
   DESCRIPTION
     "This variable represents an index for the mscVrIpRdb tables."
::= { mscVrIpRdbRowStatusEntry 11 }

mscVrIpRdbProtocolIndex OBJECT-TYPE
   SYNTAX     INTEGER  {
                 bogus(1),
                 local(2),
                 remote(3),
                 special(4),
                 ospf(5),
                 ospfExternal(6),
                 ospfType3Discard(7),
                 ospfType7Discard(8),
                 rip(9),
                 ripDiscard(10),
                 egp(11),
                 bgpExternal(12),
                 bgpInternal(13),
                 bgpAggrDiscard(14),
                 redistrib(15),
                 mpls(16) }
   ACCESS     not-accessible
   STATUS     mandatory
   DESCRIPTION
     "This variable represents an index for the mscVrIpRdb tables."
::= { mscVrIpRdbRowStatusEntry 12 }

mscVrIpRdbGatewayIndex OBJECT-TYPE
   SYNTAX     IpAddress 
   ACCESS     not-accessible
   STATUS     mandatory
   DESCRIPTION
     "This variable represents an index for the mscVrIpRdb tables."
::= { mscVrIpRdbRowStatusEntry 13 }

mscVrIpRdbOperTable OBJECT-TYPE
   SYNTAX     SEQUENCE OF MscVrIpRdbOperEntry
   ACCESS     not-accessible
   STATUS     mandatory
   DESCRIPTION
     "*** THIS TABLE CURRENTLY NOT IMPLEMENTED ***

      Identifies a group of operational attributes associated with each entry in 
      the routing database."
::= { mscVrIpRdb 10 }

mscVrIpRdbOperEntry OBJECT-TYPE
   SYNTAX     MscVrIpRdbOperEntry
   ACCESS     not-accessible
   STATUS     mandatory
   DESCRIPTION
     "An entry in the mscVrIpRdbOperTable."
   INDEX {
      mscVrIndex,
      mscVrIpIndex,
      mscVrIpRdbDestAddressIndex,
      mscVrIpRdbDestMaskIndex,
      mscVrIpRdbProtocolIndex,
      mscVrIpRdbGatewayIndex }
::= { mscVrIpRdbOperTable 1 }

MscVrIpRdbOperEntry ::= SEQUENCE {
   mscVrIpRdbMetric
      INTEGER,
   mscVrIpRdbPreference
      Unsigned32,
   mscVrIpRdbAge
      Gauge32 }

mscVrIpRdbMetric OBJECT-TYPE
   SYNTAX     INTEGER (-1..65535)
   ACCESS     read-only
   STATUS     mandatory
   DESCRIPTION
     "This attribute specifies the primary routing metric for this route. The 
      semantics of this metric are determined by the routing protocol specified 
      by the value of the index to this entry protocol. If this metric is not used, 
      its value should be set to -1."
   DEFVAL     { -1 }
::= { mscVrIpRdbOperEntry 1 }

mscVrIpRdbPreference OBJECT-TYPE
   SYNTAX     Unsigned32 (0..255)
   ACCESS     read-only
   STATUS     mandatory
   DESCRIPTION
     "This attribute specifies the the preference value of this particular 
      entry. The value of this attribute affects the way the routeEntries in this 
      database are selected for installing it in the forwardingTable. The lower 
      the preference value of this entry, the higher are the chances that this 
      entry will be selected to install in the ForwardTable."
::= { mscVrIpRdbOperEntry 2 }

mscVrIpRdbAge OBJECT-TYPE
   SYNTAX     Gauge32 (0..4294967295)
   ACCESS     read-only
   STATUS     mandatory
   DESCRIPTION
     "This attribute specifies the number of seconds since this route was last 
      updated or otherwise determined to be correct."
::= { mscVrIpRdbOperEntry 3 }

-- 
-- *** THIS SUBTREE CURRENTLY NOT IMPLEMENTED ***
-- 

-- Vr/<string> Ip InterfaceEntry/<IpAddr>
-- 
-- This component contains information about all the provisioned logicalIf 
-- entries under all ipPort components.

mscVrIpIf OBJECT IDENTIFIER ::= { mscVrIp 5 }



mscVrIpIfRowStatusTable OBJECT-TYPE
   SYNTAX     SEQUENCE OF MscVrIpIfRowStatusEntry
   ACCESS     not-accessible
   STATUS     mandatory
   DESCRIPTION
     "*** THIS TABLE CURRENTLY NOT IMPLEMENTED ***

      This entry controls the addition and deletion of 
      mscVrIpIf components."
::= { mscVrIpIf 1 }

mscVrIpIfRowStatusEntry OBJECT-TYPE
   SYNTAX     MscVrIpIfRowStatusEntry
   ACCESS     not-accessible
   STATUS     mandatory
   DESCRIPTION
     "A single entry in the table represents a single 
      mscVrIpIf component."
   INDEX {
      mscVrIndex,
      mscVrIpIndex,
      mscVrIpIfInterfaceAddressIndex }
::= { mscVrIpIfRowStatusTable 1 }

MscVrIpIfRowStatusEntry ::= SEQUENCE {
   mscVrIpIfRowStatus
      RowStatus,
   mscVrIpIfComponentName
      DisplayString,
   mscVrIpIfStorageType
      StorageType,
   mscVrIpIfInterfaceAddressIndex
      IpAddress }

mscVrIpIfRowStatus OBJECT-TYPE
   SYNTAX     RowStatus 
   ACCESS     read-only
   STATUS     mandatory
   DESCRIPTION
     "This variable is used as the basis for SNMP naming of
      mscVrIpIf components.
      These components cannot be added nor deleted."
::= { mscVrIpIfRowStatusEntry 1 }

mscVrIpIfComponentName OBJECT-TYPE
   SYNTAX     DisplayString 
   ACCESS     read-only
   STATUS     mandatory
   DESCRIPTION
     "This variable provides the component's string name for
      use with the ASCII Console Interface"
::= { mscVrIpIfRowStatusEntry 2 }

mscVrIpIfStorageType OBJECT-TYPE
   SYNTAX     StorageType 
   ACCESS     read-only
   STATUS     mandatory
   DESCRIPTION
     "This variable represents the storage type value for the
      mscVrIpIf tables."
::= { mscVrIpIfRowStatusEntry 4 }

mscVrIpIfInterfaceAddressIndex OBJECT-TYPE
   SYNTAX     IpAddress 
   ACCESS     not-accessible
   STATUS     mandatory
   DESCRIPTION
     "This variable represents the index for the mscVrIpIf tables."
::= { mscVrIpIfRowStatusEntry 10 }

mscVrIpIfOperTable OBJECT-TYPE
   SYNTAX     SEQUENCE OF MscVrIpIfOperEntry
   ACCESS     not-accessible
   STATUS     mandatory
   DESCRIPTION
     "*** THIS TABLE CURRENTLY NOT IMPLEMENTED ***

      Identifies a group of operational attributes associated with each entry in 
      the Ip interface table."
::= { mscVrIpIf 10 }

mscVrIpIfOperEntry OBJECT-TYPE
   SYNTAX     MscVrIpIfOperEntry
   ACCESS     not-accessible
   STATUS     mandatory
   DESCRIPTION
     "An entry in the mscVrIpIfOperTable."
   INDEX {
      mscVrIndex,
      mscVrIpIndex,
      mscVrIpIfInterfaceAddressIndex }
::= { mscVrIpIfOperTable 1 }

MscVrIpIfOperEntry ::= SEQUENCE {
   mscVrIpIfInterfaceMask
      IpAddress,
   mscVrIpIfStatus
      INTEGER,
   mscVrIpIfPPName
      AsciiString,
   mscVrIpIfMediaType
      INTEGER,
   mscVrIpIfHardwareAddress
      DashedHexString,
   mscVrIpIfMtu
      Unsigned32,
   mscVrIpIfBroadcastAddress
      IpAddress,
   mscVrIpIfNcHardwareAddress
      DashedHexString }

mscVrIpIfInterfaceMask OBJECT-TYPE
   SYNTAX     IpAddress 
   ACCESS     read-only
   STATUS     mandatory
   DESCRIPTION
     "This attribute indicates the mask for this interface entry."
::= { mscVrIpIfOperEntry 1 }

mscVrIpIfStatus OBJECT-TYPE
   SYNTAX     INTEGER  {
                 up(1),
                 down(2),
                 disabled(3) }
   ACCESS     read-only
   STATUS     mandatory
   DESCRIPTION
     "This attribute specifies the status of the provisioned Ip 
      logicalInterface entry. A value of disabled is used when the parent 
      components Vr, Ip or ipPort is in a disabled state. A value of up is used 
      when the interface is in an operational state. A state of down is used if 
      the media associated with this interface is not ready or disabled."
::= { mscVrIpIfOperEntry 2 }

mscVrIpIfPPName OBJECT-TYPE
   SYNTAX     AsciiString (SIZE (1..23))
   ACCESS     read-only
   STATUS     mandatory
   DESCRIPTION
     "Indicates the name of the protocol port this logicalIfEntry belongs to."
::= { mscVrIpIfOperEntry 3 }

mscVrIpIfMediaType OBJECT-TYPE
   SYNTAX     INTEGER  {
                 none(1),
                 tokenRing(2),
                 ethernet(3),
                 fddi(4),
                 x25(5),
                 frameRelay(6),
                 ppp(7),
                 clusterBridge(8),
                 virtualLink(9),
                 vcpEther(10),
                 vcpToken(11),
                 vns(12),
                 smds(13),
                 atmMpeVcEncap(14),
                 atmMpeLlcEncap(15),
                 lecEther(16),
                 lecToken(17),
                 tunnel(18),
                 virtual(19) }
   ACCESS     read-only
   STATUS     mandatory
   DESCRIPTION
     "This attribute indicates the media type of interface. When the 
      interface is down, a value of none indicates the media stays 
      down from the beginning. When the interface is down, a value 
      of some valid media type indicates the media is brought down 
      after it was up. Otherwise, when the interface is up or 
      disabled, this attribute should reflect the proper media type of 
      the interface."
::= { mscVrIpIfOperEntry 4 }

mscVrIpIfHardwareAddress OBJECT-TYPE
   SYNTAX     DashedHexString (SIZE (0..8))
   ACCESS     read-only
   STATUS     mandatory
   DESCRIPTION
     "This attribute specifies the hardware address of the media in canonical 
      form if applicable. The non-canonical version of this address is 
      indicated in ncHardwareAddress."
::= { mscVrIpIfOperEntry 5 }

mscVrIpIfMtu OBJECT-TYPE
   SYNTAX     Unsigned32 (0..0 | 576..18944)
   ACCESS     read-only
   STATUS     mandatory
   DESCRIPTION
     "This attribute specifies the maximum transmission unit applicable for 
      this logicalInterface. A value of 0 is used for the interfaces where all the 
      necessary information is not available to compute the mtu applicable for 
      this interface."
::= { mscVrIpIfOperEntry 6 }

mscVrIpIfBroadcastAddress OBJECT-TYPE
   SYNTAX     IpAddress 
   ACCESS     read-only
   STATUS     mandatory
   DESCRIPTION
     "This attribute indicates the destination IP address to be used by any 
      application which needs to broadcast on this interface. The value is 
      determined by the corresponding LogicalIf component's 
      broadcastAddress attribute."
::= { mscVrIpIfOperEntry 7 }

mscVrIpIfNcHardwareAddress OBJECT-TYPE
   SYNTAX     DashedHexString (SIZE (0..8))
   ACCESS     read-only
   STATUS     mandatory
   DESCRIPTION
     "This attribute is the non-canonical version of hardwareAddress. This 
      attribute is not displayed for interfaces on non-LAN media."
::= { mscVrIpIfOperEntry 8 }


-- Vr/<string> Ip Egp
-- This is used to run the Exterior Gateway Protocol for IP.

mscVrIpEgp OBJECT IDENTIFIER ::= { mscVrIp 6 }



mscVrIpEgpRowStatusTable OBJECT-TYPE
   SYNTAX     SEQUENCE OF MscVrIpEgpRowStatusEntry
   ACCESS     not-accessible
   STATUS     mandatory
   DESCRIPTION
     "This entry controls the addition and deletion of 
      mscVrIpEgp components."
::= { mscVrIpEgp 1 }

mscVrIpEgpRowStatusEntry OBJECT-TYPE
   SYNTAX     MscVrIpEgpRowStatusEntry
   ACCESS     not-accessible
   STATUS     mandatory
   DESCRIPTION
     "A single entry in the table represents a single 
      mscVrIpEgp component."
   INDEX {
      mscVrIndex,
      mscVrIpIndex,
      mscVrIpEgpIndex }
::= { mscVrIpEgpRowStatusTable 1 }

MscVrIpEgpRowStatusEntry ::= SEQUENCE {
   mscVrIpEgpRowStatus
      RowStatus,
   mscVrIpEgpComponentName
      DisplayString,
   mscVrIpEgpStorageType
      StorageType,
   mscVrIpEgpIndex
      NonReplicated }

mscVrIpEgpRowStatus OBJECT-TYPE
   SYNTAX     RowStatus 
   ACCESS     read-write
   STATUS     mandatory
   DESCRIPTION
     "This variable is used as the basis for SNMP naming of
      mscVrIpEgp components.
      These components can be added and deleted."
::= { mscVrIpEgpRowStatusEntry 1 }

mscVrIpEgpComponentName OBJECT-TYPE
   SYNTAX     DisplayString 
   ACCESS     read-only
   STATUS     mandatory
   DESCRIPTION
     "This variable provides the component's string name for
      use with the ASCII Console Interface"
::= { mscVrIpEgpRowStatusEntry 2 }

mscVrIpEgpStorageType OBJECT-TYPE
   SYNTAX     StorageType 
   ACCESS     read-only
   STATUS     mandatory
   DESCRIPTION
     "This variable represents the storage type value for the
      mscVrIpEgp tables."
::= { mscVrIpEgpRowStatusEntry 4 }

mscVrIpEgpIndex OBJECT-TYPE
   SYNTAX     NonReplicated 
   ACCESS     not-accessible
   STATUS     mandatory
   DESCRIPTION
     "This variable represents the index for the mscVrIpEgp tables."
::= { mscVrIpEgpRowStatusEntry 10 }

mscVrIpEgpProvTable OBJECT-TYPE
   SYNTAX     SEQUENCE OF MscVrIpEgpProvEntry
   ACCESS     not-accessible
   STATUS     mandatory
   DESCRIPTION
     "This group contains the provisionable attributes for the EGP component"
::= { mscVrIpEgp 10 }

mscVrIpEgpProvEntry OBJECT-TYPE
   SYNTAX     MscVrIpEgpProvEntry
   ACCESS     not-accessible
   STATUS     mandatory
   DESCRIPTION
     "An entry in the mscVrIpEgpProvTable."
   INDEX {
      mscVrIndex,
      mscVrIpIndex,
      mscVrIpEgpIndex }
::= { mscVrIpEgpProvTable 1 }

MscVrIpEgpProvEntry ::= SEQUENCE {
   mscVrIpEgpAsId
      Unsigned32,
   mscVrIpEgpDefaultHelloInterval
      Unsigned32,
   mscVrIpEgpDefaultPollInterval
      Unsigned32,
   mscVrIpEgpMaxNatNets
      Unsigned32,
   mscVrIpEgpMaxBufferSize
      Unsigned32 }

mscVrIpEgpAsId OBJECT-TYPE
   SYNTAX     Unsigned32 (1..65535)
   ACCESS     read-write
   STATUS     mandatory
   DESCRIPTION
     "The autonomous system identifier for this EGP entity. The 
      value of this asId can not be equal to the value of 
      EgpNeighborEntry asId."
::= { mscVrIpEgpProvEntry 2 }

mscVrIpEgpDefaultHelloInterval OBJECT-TYPE
   SYNTAX     Unsigned32 (30..900)
   ACCESS     read-write
   STATUS     mandatory
   DESCRIPTION
     "This attribute is used to configure the default hello interval for each 
      neighbor. This attribute's value is used by the application for each 
      EgpNeighbor whose helloInterval has not been set."
   DEFVAL     { 30 }
::= { mscVrIpEgpProvEntry 3 }

mscVrIpEgpDefaultPollInterval OBJECT-TYPE
   SYNTAX     Unsigned32 (120..3600)
   ACCESS     read-write
   STATUS     mandatory
   DESCRIPTION
     "This attribute is used to configure the default polling interval for the 
      EGP Neighbor. This attribute's value is used by the application for each 
      EgpNeighbor whose pollInterval has not been set."
   DEFVAL     { 120 }
::= { mscVrIpEgpProvEntry 4 }

mscVrIpEgpMaxNatNets OBJECT-TYPE
   SYNTAX     Unsigned32 (1..65535)
   ACCESS     read-write
   STATUS     mandatory
   DESCRIPTION
     "This attribute is used to configure the maximum number of external 
      natural networks this virtual router will be advertising via EGP."
   DEFVAL     { 500 }
::= { mscVrIpEgpProvEntry 5 }

mscVrIpEgpMaxBufferSize OBJECT-TYPE
   SYNTAX     Unsigned32 (2..16)
   ACCESS     read-write
   STATUS     mandatory
   DESCRIPTION
     "This attribute specifies the maximum buffer size (in 1024 byte memory 
      blocks) to be used for an EGP update to be sent."
   DEFVAL     { 4 }
::= { mscVrIpEgpProvEntry 6 }

mscVrIpEgpStatsTable OBJECT-TYPE
   SYNTAX     SEQUENCE OF MscVrIpEgpStatsEntry
   ACCESS     not-accessible
   STATUS     mandatory
   DESCRIPTION
     "These set of attributes identifies the statistics for the EGP component."
::= { mscVrIpEgp 11 }

mscVrIpEgpStatsEntry OBJECT-TYPE
   SYNTAX     MscVrIpEgpStatsEntry
   ACCESS     not-accessible
   STATUS     mandatory
   DESCRIPTION
     "An entry in the mscVrIpEgpStatsTable."
   INDEX {
      mscVrIndex,
      mscVrIpIndex,
      mscVrIpEgpIndex }
::= { mscVrIpEgpStatsTable 1 }

MscVrIpEgpStatsEntry ::= SEQUENCE {
   mscVrIpEgpInMsgs
      Counter32,
   mscVrIpEgpInErrorMsgs
      Counter32,
   mscVrIpEgpOutErrorMsgs
      Counter32,
   mscVrIpEgpInErrors
      Counter32,
   mscVrIpEgpOutMsgs
      Counter32,
   mscVrIpEgpOutErrors
      Counter32 }

mscVrIpEgpInMsgs OBJECT-TYPE
   SYNTAX     Counter32 
   ACCESS     read-only
   STATUS     mandatory
   DESCRIPTION
     "Identifies the number of EGP messages received without error. This 
      counter will wraparound once the value reaches the maximum value."
::= { mscVrIpEgpStatsEntry 1 }

mscVrIpEgpInErrorMsgs OBJECT-TYPE
   SYNTAX     Counter32 
   ACCESS     read-only
   STATUS     mandatory
   DESCRIPTION
     "Identifies the sum of EGP error messages from all the neighbors. This 
      counter will wraparound once the value reaches the maximum value."
::= { mscVrIpEgpStatsEntry 2 }

mscVrIpEgpOutErrorMsgs OBJECT-TYPE
   SYNTAX     Counter32 
   ACCESS     read-only
   STATUS     mandatory
   DESCRIPTION
     "Indicates the sum of Egp error messages sent to all the neighbors. This 
      counter will wraparound once the value reaches the maximum value."
::= { mscVrIpEgpStatsEntry 3 }

mscVrIpEgpInErrors OBJECT-TYPE
   SYNTAX     Counter32 
   ACCESS     read-only
   STATUS     mandatory
   DESCRIPTION
     "Identifies the number of EGP messages that proved to be in error. This 
      counter will wraparound once the value reaches the maximum value."
::= { mscVrIpEgpStatsEntry 4 }

mscVrIpEgpOutMsgs OBJECT-TYPE
   SYNTAX     Counter32 
   ACCESS     read-only
   STATUS     mandatory
   DESCRIPTION
     "The total number of locally generated EGP messages. This counter will 
      wraparound once the value reaches the maximum value."
::= { mscVrIpEgpStatsEntry 5 }

mscVrIpEgpOutErrors OBJECT-TYPE
   SYNTAX     Counter32 
   ACCESS     read-only
   STATUS     mandatory
   DESCRIPTION
     "The number of EGP messages that were locally generated but were not 
      sent out due to resource limitations within an EGP entity.This counter 
      will wraparound once the value reaches the maximum value."
::= { mscVrIpEgpStatsEntry 6 }

mscVrIpEgpStateTable OBJECT-TYPE
   SYNTAX     SEQUENCE OF MscVrIpEgpStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscVrIpEgp 12 }

mscVrIpEgpStateEntry OBJECT-TYPE
   SYNTAX     MscVrIpEgpStateEntry
   ACCESS     not-accessible
   STATUS     mandatory
   DESCRIPTION
     "An entry in the mscVrIpEgpStateTable."
   INDEX {
      mscVrIndex,
      mscVrIpIndex,
      mscVrIpEgpIndex }
::= { mscVrIpEgpStateTable 1 }

MscVrIpEgpStateEntry ::= SEQUENCE {
   mscVrIpEgpAdminState
      INTEGER,
   mscVrIpEgpOperationalState
      INTEGER,
   mscVrIpEgpUsageState
      INTEGER }

mscVrIpEgpAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscVrIpEgpStateEntry 1 }

mscVrIpEgpOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscVrIpEgpStateEntry 2 }

mscVrIpEgpUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscVrIpEgpStateEntry 3 }

mscVrIpEgpAdminControlTable OBJECT-TYPE
   SYNTAX     SEQUENCE OF MscVrIpEgpAdminControlEntry
   ACCESS     not-accessible
   STATUS     mandatory
   DESCRIPTION
     "This group includes the Administrative Control attribute. This 
      attribute defines the current administrative state of this component."
::= { mscVrIpEgp 13 }

mscVrIpEgpAdminControlEntry OBJECT-TYPE
   SYNTAX     MscVrIpEgpAdminControlEntry
   ACCESS     not-accessible
   STATUS     mandatory
   DESCRIPTION
     "An entry in the mscVrIpEgpAdminControlTable."
   INDEX {
      mscVrIndex,
      mscVrIpIndex,
      mscVrIpEgpIndex }
::= { mscVrIpEgpAdminControlTable 1 }

MscVrIpEgpAdminControlEntry ::= SEQUENCE {
   mscVrIpEgpSnmpAdminStatus
      INTEGER }

mscVrIpEgpSnmpAdminStatus OBJECT-TYPE
   SYNTAX     INTEGER  {
                 up(1),
                 down(2),
                 testing(3) }
   ACCESS     read-write
   STATUS     mandatory
   DESCRIPTION
     "The desired state of the interface. The up state indicates the 
      interface is operational and packet forwarding is allowed. The down 
      state indicates the interface is not operational and packet forwarding 
      is unavailable. The testing state indicates that no operational 
      packets can be passed."
   DEFVAL     { up }
::= { mscVrIpEgpAdminControlEntry 1 }

mscVrIpEgpOperStatusTable OBJECT-TYPE
   SYNTAX     SEQUENCE OF MscVrIpEgpOperStatusEntry
   ACCESS     not-accessible
   STATUS     mandatory
   DESCRIPTION
     "This group includes the Operational Status attribute. This attribute 
      defines the current operational state of this component."
::= { mscVrIpEgp 16 }

mscVrIpEgpOperStatusEntry OBJECT-TYPE
   SYNTAX     MscVrIpEgpOperStatusEntry
   ACCESS     not-accessible
   STATUS     mandatory
   DESCRIPTION
     "An entry in the mscVrIpEgpOperStatusTable."
   INDEX {
      mscVrIndex,
      mscVrIpIndex,
      mscVrIpEgpIndex }
::= { mscVrIpEgpOperStatusTable 1 }

MscVrIpEgpOperStatusEntry ::= SEQUENCE {
   mscVrIpEgpSnmpOperStatus
      INTEGER }

mscVrIpEgpSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscVrIpEgpOperStatusEntry 1 }


-- Vr/<string> Ip Egp NeighborEntry/<Ip Address>
-- This component identifies the properties of each EGP neighbor.
-- The index value of this entry should belong to one of the subnets 
-- provisioned as logicalIfEntry under one of the IpPort.

mscVrIpEgpNbr OBJECT IDENTIFIER ::= { mscVrIpEgp 2 }



mscVrIpEgpNbrRowStatusTable OBJECT-TYPE
   SYNTAX     SEQUENCE OF MscVrIpEgpNbrRowStatusEntry
   ACCESS     not-accessible
   STATUS     mandatory
   DESCRIPTION
     "This entry controls the addition and deletion of 
      mscVrIpEgpNbr components."
::= { mscVrIpEgpNbr 1 }

mscVrIpEgpNbrRowStatusEntry OBJECT-TYPE
   SYNTAX     MscVrIpEgpNbrRowStatusEntry
   ACCESS     not-accessible
   STATUS     mandatory
   DESCRIPTION
     "A single entry in the table represents a single 
      mscVrIpEgpNbr component."
   INDEX {
      mscVrIndex,
      mscVrIpIndex,
      mscVrIpEgpIndex,
      mscVrIpEgpNbrNeighborAddressIndex }
::= { mscVrIpEgpNbrRowStatusTable 1 }

MscVrIpEgpNbrRowStatusEntry ::= SEQUENCE {
   mscVrIpEgpNbrRowStatus
      RowStatus,
   mscVrIpEgpNbrComponentName
      DisplayString,
   mscVrIpEgpNbrStorageType
      StorageType,
   mscVrIpEgpNbrNeighborAddressIndex
      IpAddress }

mscVrIpEgpNbrRowStatus OBJECT-TYPE
   SYNTAX     RowStatus 
   ACCESS     read-write
   STATUS     mandatory
   DESCRIPTION
     "This variable is used as the basis for SNMP naming of
      mscVrIpEgpNbr components.
      These components can be added and deleted."
::= { mscVrIpEgpNbrRowStatusEntry 1 }

mscVrIpEgpNbrComponentName OBJECT-TYPE
   SYNTAX     DisplayString 
   ACCESS     read-only
   STATUS     mandatory
   DESCRIPTION
     "This variable provides the component's string name for
      use with the ASCII Console Interface"
::= { mscVrIpEgpNbrRowStatusEntry 2 }

mscVrIpEgpNbrStorageType OBJECT-TYPE
   SYNTAX     StorageType 
   ACCESS     read-only
   STATUS     mandatory
   DESCRIPTION
     "This variable represents the storage type value for the
      mscVrIpEgpNbr tables."
::= { mscVrIpEgpNbrRowStatusEntry 4 }

mscVrIpEgpNbrNeighborAddressIndex OBJECT-TYPE
   SYNTAX     IpAddress 
   ACCESS     not-accessible
   STATUS     mandatory
   DESCRIPTION
     "This variable represents the index for the mscVrIpEgpNbr tables."
::= { mscVrIpEgpNbrRowStatusEntry 10 }

mscVrIpEgpNbrProvTable OBJECT-TYPE
   SYNTAX     SEQUENCE OF MscVrIpEgpNbrProvEntry
   ACCESS     not-accessible
   STATUS     mandatory
   DESCRIPTION
     "This group of attributes identify the provisionable attributes for this EGP 
      neighbor."
::= { mscVrIpEgpNbr 10 }

mscVrIpEgpNbrProvEntry OBJECT-TYPE
   SYNTAX     MscVrIpEgpNbrProvEntry
   ACCESS     not-accessible
   STATUS     mandatory
   DESCRIPTION
     "An entry in the mscVrIpEgpNbrProvTable."
   INDEX {
      mscVrIndex,
      mscVrIpIndex,
      mscVrIpEgpIndex,
      mscVrIpEgpNbrNeighborAddressIndex }
::= { mscVrIpEgpNbrProvTable 1 }

MscVrIpEgpNbrProvEntry ::= SEQUENCE {
   mscVrIpEgpNbrAsId
      Unsigned32,
   mscVrIpEgpNbrMode
      INTEGER,
   mscVrIpEgpNbrGenerateDefaultRoute
      INTEGER,
   mscVrIpEgpNbrDefaultRouteMetric
      Unsigned32,
   mscVrIpEgpNbrDefaultMetric
      Unsigned32,
   mscVrIpEgpNbrHelloInterval
      Unsigned32,
   mscVrIpEgpNbrPollInterval
      Unsigned32 }

mscVrIpEgpNbrAsId OBJECT-TYPE
   SYNTAX     Unsigned32 (1..65535)
   ACCESS     read-write
   STATUS     mandatory
   DESCRIPTION
     "The autonomous system identifier of this EGP peer. 
      The value of this neighbor's asId should not be equal to the asId value 
      of Egp entity"
::= { mscVrIpEgpNbrProvEntry 1 }

mscVrIpEgpNbrMode OBJECT-TYPE
   SYNTAX     INTEGER  {
                 active(1),
                 passive(2) }
   ACCESS     read-write
   STATUS     mandatory
   DESCRIPTION
     "This attribute will indicate whether this neighbor is being configured as 
      an active or passive neighbor."
   DEFVAL     { active }
::= { mscVrIpEgpNbrProvEntry 2 }

mscVrIpEgpNbrGenerateDefaultRoute OBJECT-TYPE
   SYNTAX     INTEGER  {
                 yes(1),
                 no(2) }
   ACCESS     read-write
   STATUS     mandatory
   DESCRIPTION
     "This attribute distinguishes whether or not the default route should be 
      generated. This route is put in the EGP update along with the normal 
      EGP update routes when updates are sent to this EGP neighbor"
   DEFVAL     { no }
::= { mscVrIpEgpNbrProvEntry 3 }

mscVrIpEgpNbrDefaultRouteMetric OBJECT-TYPE
   SYNTAX     Unsigned32 (0..255)
   ACCESS     read-write
   STATUS     mandatory
   DESCRIPTION
     "This attribute identifies the Metric to be used for propagating the 
      'Default Route'. The value of defaultRouteMetric is used only in the 
      case where the value of the attribute generateDefaultRoute is set to yes."
   DEFVAL     { 128 }
::= { mscVrIpEgpNbrProvEntry 4 }

mscVrIpEgpNbrDefaultMetric OBJECT-TYPE
   SYNTAX     Unsigned32 (0..255)
   ACCESS     read-write
   STATUS     mandatory
   DESCRIPTION
     "This attribute identifies the default metric value for routes that are 
      exported to this EgpNeighbor. This value is used when exporting routes 
      to this neighbor and no Export policy applies a different metric."
   DEFVAL     { 128 }
::= { mscVrIpEgpNbrProvEntry 5 }

mscVrIpEgpNbrHelloInterval OBJECT-TYPE
   SYNTAX     Unsigned32 (30..120)
   ACCESS     read-write
   STATUS     mandatory
   DESCRIPTION
     "This attribute identifies the interval in seconds, between EGP hello 
      command retransmissions. This is the P1 timer in the RFC904. This 
      value may change in operation due to negotiations."
   DEFVAL     { 30 }
::= { mscVrIpEgpNbrProvEntry 6 }

mscVrIpEgpNbrPollInterval OBJECT-TYPE
   SYNTAX     Unsigned32 (120..480)
   ACCESS     read-write
   STATUS     mandatory
   DESCRIPTION
     "This attribute identifies the interval in seconds, between EGP poll 
      command retransmissions. This is the P2 timer in the RFC904. This 
      value may change in operation due to negotiations."
   DEFVAL     { 120 }
::= { mscVrIpEgpNbrProvEntry 7 }

mscVrIpEgpNbrOperTable OBJECT-TYPE
   SYNTAX     SEQUENCE OF MscVrIpEgpNbrOperEntry
   ACCESS     not-accessible
   STATUS     mandatory
   DESCRIPTION
     "This group of attributes identifies the operational set of attributes for the 
      NeighborEntry component."
::= { mscVrIpEgpNbr 11 }

mscVrIpEgpNbrOperEntry OBJECT-TYPE
   SYNTAX     MscVrIpEgpNbrOperEntry
   ACCESS     not-accessible
   STATUS     mandatory
   DESCRIPTION
     "An entry in the mscVrIpEgpNbrOperTable."
   INDEX {
      mscVrIndex,
      mscVrIpIndex,
      mscVrIpEgpIndex,
      mscVrIpEgpNbrNeighborAddressIndex }
::= { mscVrIpEgpNbrOperTable 1 }

MscVrIpEgpNbrOperEntry ::= SEQUENCE {
   mscVrIpEgpNbrState
      INTEGER,
   mscVrIpEgpNbrInMsgs
      Counter32,
   mscVrIpEgpNbrInErrors
      Counter32,
   mscVrIpEgpNbrOutMsgs
      Counter32,
   mscVrIpEgpNbrOutErrors
      Counter32,
   mscVrIpEgpNbrInErrorMsgs
      Counter32,
   mscVrIpEgpNbrOutErrorMsgs
      Counter32,
   mscVrIpEgpNbrStateUps
      Counter32,
   mscVrIpEgpNbrStateDowns
      Counter32,
   mscVrIpEgpNbrEventTrigger
      INTEGER }

mscVrIpEgpNbrState OBJECT-TYPE
   SYNTAX     INTEGER  {
                 idle(1),
                 acquisition(2),
                 down(3),
                 up(4),
                 cease(5) }
   ACCESS     read-only
   STATUS     mandatory
   DESCRIPTION
     "This attribute describes the state of the local system with respect to this 
      entry's EGP Neighbor."
::= { mscVrIpEgpNbrOperEntry 1 }

mscVrIpEgpNbrInMsgs OBJECT-TYPE
   SYNTAX     Counter32 
   ACCESS     read-only
   STATUS     mandatory
   DESCRIPTION
     "The number of EGP messages received without error from the EGP 
      peer. This counter will wraparound once the value reaches the maximum 
      value."
::= { mscVrIpEgpNbrOperEntry 2 }

mscVrIpEgpNbrInErrors OBJECT-TYPE
   SYNTAX     Counter32 
   ACCESS     read-only
   STATUS     mandatory
   DESCRIPTION
     "The number of messages received from this EGP peer that proved to be 
      in error. This counter will wraparound once the value reaches the 
      maximum value."
::= { mscVrIpEgpNbrOperEntry 3 }

mscVrIpEgpNbrOutMsgs OBJECT-TYPE
   SYNTAX     Counter32 
   ACCESS     read-only
   STATUS     mandatory
   DESCRIPTION
     "The number of locally generated EGP messages for this EGP peer. This 
      counter will wraparound once the value reaches the maximum value."
::= { mscVrIpEgpNbrOperEntry 4 }

mscVrIpEgpNbrOutErrors OBJECT-TYPE
   SYNTAX     Counter32 
   ACCESS     read-only
   STATUS     mandatory
   DESCRIPTION
     "The number of locally generated EGP messages not sent to this EGP 
      peer due to resource limitations within an EGP entity.This counter will 
      wraparound once the value reaches the maximum value."
::= { mscVrIpEgpNbrOperEntry 5 }

mscVrIpEgpNbrInErrorMsgs OBJECT-TYPE
   SYNTAX     Counter32 
   ACCESS     read-only
   STATUS     mandatory
   DESCRIPTION
     "The number of EGP-defined error messages received from this EGP 
      peer.This counter will wraparound once the value reaches the maximum 
      value."
::= { mscVrIpEgpNbrOperEntry 6 }

mscVrIpEgpNbrOutErrorMsgs OBJECT-TYPE
   SYNTAX     Counter32 
   ACCESS     read-only
   STATUS     mandatory
   DESCRIPTION
     "The number of EGP-defined error messages sent to this EGP peer.This 
      counter will wraparound once the value reaches the maximum value."
::= { mscVrIpEgpNbrOperEntry 7 }

mscVrIpEgpNbrStateUps OBJECT-TYPE
   SYNTAX     Counter32 
   ACCESS     read-only
   STATUS     mandatory
   DESCRIPTION
     "The number of EGP state transitions to the UP state with this EGP peer. 
      This counter will wraparound once the value reaches the maximum 
      value."
::= { mscVrIpEgpNbrOperEntry 8 }

mscVrIpEgpNbrStateDowns OBJECT-TYPE
   SYNTAX     Counter32 
   ACCESS     read-only
   STATUS     mandatory
   DESCRIPTION
     "The number of EGP state transitions from the UP state to any other state 
      with this EGP peer. This counter will wraparound once the value reaches 
      the maximum value."
::= { mscVrIpEgpNbrOperEntry 9 }

mscVrIpEgpNbrEventTrigger OBJECT-TYPE
   SYNTAX     INTEGER  {
                 start(1),
                 stop(2) }
   ACCESS     read-only
   STATUS     mandatory
   DESCRIPTION
     "This attribute is used to control the state of the Neighbor. It is not 
      allowed to change.
      This attribute from SNMP perspective deviates from MIB that it is made 
      READONLY."
   DEFVAL     { start }
::= { mscVrIpEgpNbrOperEntry 10 }


-- Vr/<string> Ip Egp Import/n
-- This component controls the functionality of route leaking. In other 
-- words, this component will determine what routes are used by EGP.

mscVrIpEgpImport OBJECT IDENTIFIER ::= { mscVrIpEgp 3 }



mscVrIpEgpImportRowStatusTable OBJECT-TYPE
   SYNTAX     SEQUENCE OF MscVrIpEgpImportRowStatusEntry
   ACCESS     not-accessible
   STATUS     mandatory
   DESCRIPTION
     "This entry controls the addition and deletion of 
      mscVrIpEgpImport components."
::= { mscVrIpEgpImport 1 }

mscVrIpEgpImportRowStatusEntry OBJECT-TYPE
   SYNTAX     MscVrIpEgpImportRowStatusEntry
   ACCESS     not-accessible
   STATUS     mandatory
   DESCRIPTION
     "A single entry in the table represents a single 
      mscVrIpEgpImport component."
   INDEX {
      mscVrIndex,
      mscVrIpIndex,
      mscVrIpEgpIndex,
      mscVrIpEgpImportIndex }
::= { mscVrIpEgpImportRowStatusTable 1 }

MscVrIpEgpImportRowStatusEntry ::= SEQUENCE {
   mscVrIpEgpImportRowStatus
      RowStatus,
   mscVrIpEgpImportComponentName
      DisplayString,
   mscVrIpEgpImportStorageType
      StorageType,
   mscVrIpEgpImportIndex
      Integer32 }

mscVrIpEgpImportRowStatus OBJECT-TYPE
   SYNTAX     RowStatus 
   ACCESS     read-write
   STATUS     mandatory
   DESCRIPTION
     "This variable is used as the basis for SNMP naming of
      mscVrIpEgpImport components.
      These components can be added and deleted."
::= { mscVrIpEgpImportRowStatusEntry 1 }

mscVrIpEgpImportComponentName OBJECT-TYPE
   SYNTAX     DisplayString 
   ACCESS     read-only
   STATUS     mandatory
   DESCRIPTION
     "This variable provides the component's string name for
      use with the ASCII Console Interface"
::= { mscVrIpEgpImportRowStatusEntry 2 }

mscVrIpEgpImportStorageType OBJECT-TYPE
   SYNTAX     StorageType 
   ACCESS     read-only
   STATUS     mandatory
   DESCRIPTION
     "This variable represents the storage type value for the
      mscVrIpEgpImport tables."
::= { mscVrIpEgpImportRowStatusEntry 4 }

mscVrIpEgpImportIndex OBJECT-TYPE
   SYNTAX     Integer32 (0..65535)
   ACCESS     not-accessible
   STATUS     mandatory
   DESCRIPTION
     "This variable represents the index for the mscVrIpEgpImport tables."
::= { mscVrIpEgpImportRowStatusEntry 10 }

mscVrIpEgpImportProvTable OBJECT-TYPE
   SYNTAX     SEQUENCE OF MscVrIpEgpImportProvEntry
   ACCESS     not-accessible
   STATUS     mandatory
   DESCRIPTION
     "These set of attributes describe the provisionable attributes for the 
      import component."
::= { mscVrIpEgpImport 10 }

mscVrIpEgpImportProvEntry OBJECT-TYPE
   SYNTAX     MscVrIpEgpImportProvEntry
   ACCESS     not-accessible
   STATUS     mandatory
   DESCRIPTION
     "An entry in the mscVrIpEgpImportProvTable."
   INDEX {
      mscVrIndex,
      mscVrIpIndex,
      mscVrIpEgpIndex,
      mscVrIpEgpImportIndex }
::= { mscVrIpEgpImportProvTable 1 }

MscVrIpEgpImportProvEntry ::= SEQUENCE {
   mscVrIpEgpImportUsageFlag
      INTEGER,
   mscVrIpEgpImportImportMetric
      Unsigned32,
   mscVrIpEgpImportNbrAsId
      Unsigned32 }

mscVrIpEgpImportUsageFlag OBJECT-TYPE
   SYNTAX     INTEGER  {
                 use(1),
                 ignore(2) }
   ACCESS     read-write
   STATUS     mandatory
   DESCRIPTION
     "This flag will determine whether or not EGP will use or ignore 
      information in updates received. If the attribute nbrAsId is not specified 
      or any of the NetworkList components are not added, then this attribute 
      when set to ignore will ignore all incoming information."
   DEFVAL     { use }
::= { mscVrIpEgpImportProvEntry 1 }

mscVrIpEgpImportImportMetric OBJECT-TYPE
   SYNTAX     Unsigned32 (0..255)
   ACCESS     read-write
   STATUS     mandatory
   DESCRIPTION
     "This attribute is used to set the metric value to be included in the routing 
      table for any routes sent because this particular import instance was it's 
      'best match' policy.
      However this attribute is not a selection key. It should not use or ignore 
      a particular metric value. If the value for this attribute is not specified, 
      then the metric value received in an Egp update will be used.
      
      Note: 
      
      When setting this value, caution should be taken to set the metric value 
      in all relevant Import components to make sure that all matching 
      policies for a given route have the same metric set. This will insure that 
      there are no situations where a specific metric was desired, but doesn't 
      get used in the update because the 'best match' policy for that situation 
      did not set the metric parameter.
      
      If the attribute usageFlag for this import policy is set to ignore, then the 
      importMetric value will be ignored by the application. The importMetric 
      value is not used to select which routes to use or ignore but is used to set 
      the metric value for the routes being imported. A value of zero indicates 
      that the metric 
      received in the update will be used."
   DEFVAL     { 0 }
::= { mscVrIpEgpImportProvEntry 2 }

mscVrIpEgpImportNbrAsId OBJECT-TYPE
   SYNTAX     Unsigned32 (0..65535)
   ACCESS     read-write
   STATUS     mandatory
   DESCRIPTION
     "The autonomous system Id this import policy will apply to.
      Note: The Valid value of an asId is from 1 to 65,535.
      This attribute's value when set to 0 will be ignored."
::= { mscVrIpEgpImportProvEntry 3 }


-- Vr/<string> Ip Egp Import/<Decimal> NetworkList/<Decimal>
-- This is an optional subcomponent of Import and identifies a set of 
-- networks that this import policy will apply to.

mscVrIpEgpImportNet OBJECT IDENTIFIER ::= { mscVrIpEgpImport 2 }



mscVrIpEgpImportNetRowStatusTable OBJECT-TYPE
   SYNTAX     SEQUENCE OF MscVrIpEgpImportNetRowStatusEntry
   ACCESS     not-accessible
   STATUS     mandatory
   DESCRIPTION
     "This entry controls the addition and deletion of 
      mscVrIpEgpImportNet components."
::= { mscVrIpEgpImportNet 1 }

mscVrIpEgpImportNetRowStatusEntry OBJECT-TYPE
   SYNTAX     MscVrIpEgpImportNetRowStatusEntry
   ACCESS     not-accessible
   STATUS     mandatory
   DESCRIPTION
     "A single entry in the table represents a single 
      mscVrIpEgpImportNet component."
   INDEX {
      mscVrIndex,
      mscVrIpIndex,
      mscVrIpEgpIndex,
      mscVrIpEgpImportIndex,
      mscVrIpEgpImportNetIndex }
::= { mscVrIpEgpImportNetRowStatusTable 1 }

MscVrIpEgpImportNetRowStatusEntry ::= SEQUENCE {
   mscVrIpEgpImportNetRowStatus
      RowStatus,
   mscVrIpEgpImportNetComponentName
      DisplayString,
   mscVrIpEgpImportNetStorageType
      StorageType,
   mscVrIpEgpImportNetIndex
      Integer32 }

mscVrIpEgpImportNetRowStatus OBJECT-TYPE
   SYNTAX     RowStatus 
   ACCESS     read-write
   STATUS     mandatory
   DESCRIPTION
     "This variable is used as the basis for SNMP naming of
      mscVrIpEgpImportNet components.
      These components can be added and deleted."
::= { mscVrIpEgpImportNetRowStatusEntry 1 }

mscVrIpEgpImportNetComponentName OBJECT-TYPE
   SYNTAX     DisplayString 
   ACCESS     read-only
   STATUS     mandatory
   DESCRIPTION
     "This variable provides the component's string name for
      use with the ASCII Console Interface"
::= { mscVrIpEgpImportNetRowStatusEntry 2 }

mscVrIpEgpImportNetStorageType OBJECT-TYPE
   SYNTAX     StorageType 
   ACCESS     read-only
   STATUS     mandatory
   DESCRIPTION
     "This variable represents the storage type value for the
      mscVrIpEgpImportNet tables."
::= { mscVrIpEgpImportNetRowStatusEntry 4 }

mscVrIpEgpImportNetIndex OBJECT-TYPE
   SYNTAX     Integer32 (0..65535)
   ACCESS     not-accessible
   STATUS     mandatory
   DESCRIPTION
     "This variable represents the index for the mscVrIpEgpImportNet tables."
::= { mscVrIpEgpImportNetRowStatusEntry 10 }

mscVrIpEgpImportNetProvTable OBJECT-TYPE
   SYNTAX     SEQUENCE OF MscVrIpEgpImportNetProvEntry
   ACCESS     not-accessible
   STATUS     mandatory
   DESCRIPTION
     "This group identifies attributes for the NetworkList component for 
      which the import policy will be applied to"
::= { mscVrIpEgpImportNet 10 }

mscVrIpEgpImportNetProvEntry OBJECT-TYPE
   SYNTAX     MscVrIpEgpImportNetProvEntry
   ACCESS     not-accessible
   STATUS     mandatory
   DESCRIPTION
     "An entry in the mscVrIpEgpImportNetProvTable."
   INDEX {
      mscVrIndex,
      mscVrIpIndex,
      mscVrIpEgpIndex,
      mscVrIpEgpImportIndex,
      mscVrIpEgpImportNetIndex }
::= { mscVrIpEgpImportNetProvTable 1 }

MscVrIpEgpImportNetProvEntry ::= SEQUENCE {
   mscVrIpEgpImportNetIpAddress
      IpAddress }

mscVrIpEgpImportNetIpAddress OBJECT-TYPE
   SYNTAX     IpAddress 
   ACCESS     read-write
   STATUS     mandatory
   DESCRIPTION
     "This attribute identifies the IP address that needs to be matched against 
      in this network list for the Import policy to be applied to."
::= { mscVrIpEgpImportNetProvEntry 1 }


-- Vr/<string> Ip Egp Export/n
-- Each instance of this component specifies an EGP export policy. An 
-- EGP export policy is used to decide if a route in the IP forwarding table 
-- should be blocked or advertised as EGP routes onto one or all attached 
-- EGP autonomous systems of the virtual router.
-- Passport IP EGP by default advertises all local routes to all attached 
-- EGP autonomous systems using the metric 128.

mscVrIpEgpExport OBJECT IDENTIFIER ::= { mscVrIpEgp 4 }



mscVrIpEgpExportRowStatusTable OBJECT-TYPE
   SYNTAX     SEQUENCE OF MscVrIpEgpExportRowStatusEntry
   ACCESS     not-accessible
   STATUS     mandatory
   DESCRIPTION
     "This entry controls the addition and deletion of 
      mscVrIpEgpExport components."
::= { mscVrIpEgpExport 1 }

mscVrIpEgpExportRowStatusEntry OBJECT-TYPE
   SYNTAX     MscVrIpEgpExportRowStatusEntry
   ACCESS     not-accessible
   STATUS     mandatory
   DESCRIPTION
     "A single entry in the table represents a single 
      mscVrIpEgpExport component."
   INDEX {
      mscVrIndex,
      mscVrIpIndex,
      mscVrIpEgpIndex,
      mscVrIpEgpExportIndex }
::= { mscVrIpEgpExportRowStatusTable 1 }

MscVrIpEgpExportRowStatusEntry ::= SEQUENCE {
   mscVrIpEgpExportRowStatus
      RowStatus,
   mscVrIpEgpExportComponentName
      DisplayString,
   mscVrIpEgpExportStorageType
      StorageType,
   mscVrIpEgpExportIndex
      Integer32 }

mscVrIpEgpExportRowStatus OBJECT-TYPE
   SYNTAX     RowStatus 
   ACCESS     read-write
   STATUS     mandatory
   DESCRIPTION
     "This variable is used as the basis for SNMP naming of
      mscVrIpEgpExport components.
      These components can be added and deleted."
::= { mscVrIpEgpExportRowStatusEntry 1 }

mscVrIpEgpExportComponentName OBJECT-TYPE
   SYNTAX     DisplayString 
   ACCESS     read-only
   STATUS     mandatory
   DESCRIPTION
     "This variable provides the component's string name for
      use with the ASCII Console Interface"
::= { mscVrIpEgpExportRowStatusEntry 2 }

mscVrIpEgpExportStorageType OBJECT-TYPE
   SYNTAX     StorageType 
   ACCESS     read-only
   STATUS     mandatory
   DESCRIPTION
     "This variable represents the storage type value for the
      mscVrIpEgpExport tables."
::= { mscVrIpEgpExportRowStatusEntry 4 }

mscVrIpEgpExportIndex OBJECT-TYPE
   SYNTAX     Integer32 (0..65535)
   ACCESS     not-accessible
   STATUS     mandatory
   DESCRIPTION
     "This variable represents the index for the mscVrIpEgpExport tables."
::= { mscVrIpEgpExportRowStatusEntry 10 }

mscVrIpEgpExportProvTable OBJECT-TYPE
   SYNTAX     SEQUENCE OF MscVrIpEgpExportProvEntry
   ACCESS     not-accessible
   STATUS     mandatory
   DESCRIPTION
     "This group contains all the provisioned attributes for the Export 
      component."
::= { mscVrIpEgpExport 10 }

mscVrIpEgpExportProvEntry OBJECT-TYPE
   SYNTAX     MscVrIpEgpExportProvEntry
   ACCESS     not-accessible
   STATUS     mandatory
   DESCRIPTION
     "An entry in the mscVrIpEgpExportProvTable."
   INDEX {
      mscVrIndex,
      mscVrIpIndex,
      mscVrIpEgpIndex,
      mscVrIpEgpExportIndex }
::= { mscVrIpEgpExportProvTable 1 }

MscVrIpEgpExportProvEntry ::= SEQUENCE {
   mscVrIpEgpExportAdvertiseStatus
      INTEGER,
   mscVrIpEgpExportExportMetric
      Unsigned32,
   mscVrIpEgpExportProtocol
      INTEGER,
   mscVrIpEgpExportRipInterface
      IpAddress,
   mscVrIpEgpExportRipNeighbor
      IpAddress,
   mscVrIpEgpExportInEgpAsId
      Unsigned32,
   mscVrIpEgpExportOspfTag
      Unsigned32,
   mscVrIpEgpExportOutAutonomousSystem
      Unsigned32 }

mscVrIpEgpExportAdvertiseStatus OBJECT-TYPE
   SYNTAX     INTEGER  {
                 send(1),
                 block(2) }
   ACCESS     read-write
   STATUS     mandatory
   DESCRIPTION
     "This attribute specifies if the routes that match this export policy are 
      advertised (send) or not advertised (block)."
   DEFVAL     { send }
::= { mscVrIpEgpExportProvEntry 1 }

mscVrIpEgpExportExportMetric OBJECT-TYPE
   SYNTAX     Unsigned32 (0..255)
   ACCESS     read-write
   STATUS     mandatory
   DESCRIPTION
     "This attribute specifies the metric to be used on the routes being 
      exported as a result of matching this export policy.
      If the attribute advertiseStatus is set to block, then the value of 
      exportMetric is ignored. The exportMetric value is not used to select 
      which routes to block or send, but rather the metric value advertised for 
      the routes.
      A value of 0 indicates that the metric associated with the route in the 
      forwarding table is used."
   DEFVAL     { 0 }
::= { mscVrIpEgpExportProvEntry 2 }

mscVrIpEgpExportProtocol OBJECT-TYPE
   SYNTAX     INTEGER  {
                 all(1),
                 egp(2),
                 rip(3),
                 ospfInternal(4),
                 ospfExternal(5),
                 staticLocal(6),
                 staticRemote(7) }
   ACCESS     read-write
   STATUS     mandatory
   DESCRIPTION
     "This attribute specifies the routes to which this export policy applies 
      based on the routing protocol of how the routes are learned. If it is set to 
      all, this export policy applies to all routes in the forwarding table."
   DEFVAL     { all }
::= { mscVrIpEgpExportProvEntry 3 }

mscVrIpEgpExportRipInterface OBJECT-TYPE
   SYNTAX     IpAddress 
   ACCESS     read-write
   STATUS     mandatory
   DESCRIPTION
     "This attribute specifies the RIP learned routes to which this export policy 
      applies, based on the RIP interface from which the routes are learned.
      This attribute can only be non zero when the protocol is set to rip. The 
      value of 0.0.0.0 implies any RIP interface on the same virtual router; 
      otherwise the value of this attribute must match the interface address of 
      a LogicalIf that has a RipIf on the same virtual router."
   DEFVAL     { '00000000'H }  -- "0.0.0.0"
::= { mscVrIpEgpExportProvEntry 4 }

mscVrIpEgpExportRipNeighbor OBJECT-TYPE
   SYNTAX     IpAddress 
   ACCESS     read-write
   STATUS     mandatory
   DESCRIPTION
     "This attribute specifies the RIP learned routes to which this export policy 
      applies, based on the RIP neighbor of which the routes are learned from.
      This attribute can only be non zero when the protocol is set to rip. The 
      value of 0.0.0.0 implies any RIP neighbor."
   DEFVAL     { '00000000'H }  -- "0.0.0.0"
::= { mscVrIpEgpExportProvEntry 5 }

mscVrIpEgpExportInEgpAsId OBJECT-TYPE
   SYNTAX     Unsigned32 (0..65535)
   ACCESS     read-write
   STATUS     mandatory
   DESCRIPTION
     "This attribute specifies the EGP learned routes to which this export 
      policy applies, based on the EGP autonomous system identifier of which 
      the routes are learned from.
      This attribute can only be non zero when protocol is set to egp. The 
      value of 0 implies any EGP autonomous system; otherwise the value of 
      this attribute must match the asId of an EGP neighbor on the same 
      virtual router."
   DEFVAL     { 0 }
::= { mscVrIpEgpExportProvEntry 6 }

mscVrIpEgpExportOspfTag OBJECT-TYPE
   SYNTAX     Unsigned32 (0..4294967295)
   ACCESS     read-write
   STATUS     mandatory
   DESCRIPTION
     "This attribute specifies the OSPF learned external routes to which this 
      export policy applies, based on the learned OSPF tag of the routes.
      This attribute can only be set to a non default value when protocol is set 
      to ospfExternal. The value of 4294967295 implies any tag."
   DEFVAL     { 4294967295 }
::= { mscVrIpEgpExportProvEntry 7 }

mscVrIpEgpExportOutAutonomousSystem OBJECT-TYPE
   SYNTAX     Unsigned32 (0..65535)
   ACCESS     read-write
   STATUS     mandatory
   DESCRIPTION
     "This attribute specifies the EGP autonomous system to which routes are 
      exported to as a result of matching this export policy.
      If the attribute advertiseStatus is set to block, then the value of 
      outAutonomousSystem is ignored. The outAutonomousSystem value is 
      not used to select which routes to block or send but where to export the 
      routes.
      A value of 0 indicates that the routes are exported to all EGP 
      autonomous systems of which the virtual router is a neighbor. 
      Otherwise, the value of this attribute must match the asId of an EGP 
      neighbor on the same virtual router."
   DEFVAL     { 0 }
::= { mscVrIpEgpExportProvEntry 8 }


-- Vr/<string> Ip Egp Export/<Decimal> NetworkList/<Decimal>
-- This component identifies a set of attributes when matched determines 
-- the export policy applied. 

mscVrIpEgpExportNet OBJECT IDENTIFIER ::= { mscVrIpEgpExport 2 }



mscVrIpEgpExportNetRowStatusTable OBJECT-TYPE
   SYNTAX     SEQUENCE OF MscVrIpEgpExportNetRowStatusEntry
   ACCESS     not-accessible
   STATUS     mandatory
   DESCRIPTION
     "This entry controls the addition and deletion of 
      mscVrIpEgpExportNet components."
::= { mscVrIpEgpExportNet 1 }

mscVrIpEgpExportNetRowStatusEntry OBJECT-TYPE
   SYNTAX     MscVrIpEgpExportNetRowStatusEntry
   ACCESS     not-accessible
   STATUS     mandatory
   DESCRIPTION
     "A single entry in the table represents a single 
      mscVrIpEgpExportNet component."
   INDEX {
      mscVrIndex,
      mscVrIpIndex,
      mscVrIpEgpIndex,
      mscVrIpEgpExportIndex,
      mscVrIpEgpExportNetIndex }
::= { mscVrIpEgpExportNetRowStatusTable 1 }

MscVrIpEgpExportNetRowStatusEntry ::= SEQUENCE {
   mscVrIpEgpExportNetRowStatus
      RowStatus,
   mscVrIpEgpExportNetComponentName
      DisplayString,
   mscVrIpEgpExportNetStorageType
      StorageType,
   mscVrIpEgpExportNetIndex
      Integer32 }

mscVrIpEgpExportNetRowStatus OBJECT-TYPE
   SYNTAX     RowStatus 
   ACCESS     read-write
   STATUS     mandatory
   DESCRIPTION
     "This variable is used as the basis for SNMP naming of
      mscVrIpEgpExportNet components.
      These components can be added and deleted."
::= { mscVrIpEgpExportNetRowStatusEntry 1 }

mscVrIpEgpExportNetComponentName OBJECT-TYPE
   SYNTAX     DisplayString 
   ACCESS     read-only
   STATUS     mandatory
   DESCRIPTION
     "This variable provides the component's string name for
      use with the ASCII Console Interface"
::= { mscVrIpEgpExportNetRowStatusEntry 2 }

mscVrIpEgpExportNetStorageType OBJECT-TYPE
   SYNTAX     StorageType 
   ACCESS     read-only
   STATUS     mandatory
   DESCRIPTION
     "This variable represents the storage type value for the
      mscVrIpEgpExportNet tables."
::= { mscVrIpEgpExportNetRowStatusEntry 4 }

mscVrIpEgpExportNetIndex OBJECT-TYPE
   SYNTAX     Integer32 (0..65535)
   ACCESS     not-accessible
   STATUS     mandatory
   DESCRIPTION
     "This variable represents the index for the mscVrIpEgpExportNet tables."
::= { mscVrIpEgpExportNetRowStatusEntry 10 }

mscVrIpEgpExportNetProvTable OBJECT-TYPE
   SYNTAX     SEQUENCE OF MscVrIpEgpExportNetProvEntry
   ACCESS     not-accessible
   STATUS     mandatory
   DESCRIPTION
     "This group identifies the set of provisionable attributes for the 
      ExportNetworkList component."
::= { mscVrIpEgpExportNet 10 }

mscVrIpEgpExportNetProvEntry OBJECT-TYPE
   SYNTAX     MscVrIpEgpExportNetProvEntry
   ACCESS     not-accessible
   STATUS     mandatory
   DESCRIPTION
     "An entry in the mscVrIpEgpExportNetProvTable."
   INDEX {
      mscVrIndex,
      mscVrIpIndex,
      mscVrIpEgpIndex,
      mscVrIpEgpExportIndex,
      mscVrIpEgpExportNetIndex }
::= { mscVrIpEgpExportNetProvTable 1 }

MscVrIpEgpExportNetProvEntry ::= SEQUENCE {
   mscVrIpEgpExportNetIpAddress
      IpAddress }

mscVrIpEgpExportNetIpAddress OBJECT-TYPE
   SYNTAX     IpAddress 
   ACCESS     read-write
   STATUS     mandatory
   DESCRIPTION
     "This attribute identifies the 32 bit IP address to match against."
::= { mscVrIpEgpExportNetProvEntry 1 }


-- This component is configured to control the Open Shortest Path First IP 
-- routing protocol.

mscVrIpOspf OBJECT IDENTIFIER ::= { mscVrIp 7 }



mscVrIpOspfRowStatusTable OBJECT-TYPE
   SYNTAX     SEQUENCE OF MscVrIpOspfRowStatusEntry
   ACCESS     not-accessible
   STATUS     mandatory
   DESCRIPTION
     "This entry controls the addition and deletion of 
      mscVrIpOspf components."
::= { mscVrIpOspf 1 }

mscVrIpOspfRowStatusEntry OBJECT-TYPE
   SYNTAX     MscVrIpOspfRowStatusEntry
   ACCESS     not-accessible
   STATUS     mandatory
   DESCRIPTION
     "A single entry in the table represents a single 
      mscVrIpOspf component."
   INDEX {
      mscVrIndex,
      mscVrIpIndex,
      mscVrIpOspfIndex }
::= { mscVrIpOspfRowStatusTable 1 }

MscVrIpOspfRowStatusEntry ::= SEQUENCE {
   mscVrIpOspfRowStatus
      RowStatus,
   mscVrIpOspfComponentName
      DisplayString,
   mscVrIpOspfStorageType
      StorageType,
   mscVrIpOspfIndex
      NonReplicated }

mscVrIpOspfRowStatus OBJECT-TYPE
   SYNTAX     RowStatus 
   ACCESS     read-write
   STATUS     mandatory
   DESCRIPTION
     "This variable is used as the basis for SNMP naming of
      mscVrIpOspf components.
      These components can be added and deleted."
::= { mscVrIpOspfRowStatusEntry 1 }

mscVrIpOspfComponentName OBJECT-TYPE
   SYNTAX     DisplayString 
   ACCESS     read-only
   STATUS     mandatory
   DESCRIPTION
     "This variable provides the component's string name for
      use with the ASCII Console Interface"
::= { mscVrIpOspfRowStatusEntry 2 }

mscVrIpOspfStorageType OBJECT-TYPE
   SYNTAX     StorageType 
   ACCESS     read-only
   STATUS     mandatory
   DESCRIPTION
     "This variable represents the storage type value for the
      mscVrIpOspf tables."
::= { mscVrIpOspfRowStatusEntry 4 }

mscVrIpOspfIndex OBJECT-TYPE
   SYNTAX     NonReplicated 
   ACCESS     not-accessible
   STATUS     mandatory
   DESCRIPTION
     "This variable represents the index for the mscVrIpOspf tables."
::= { mscVrIpOspfRowStatusEntry 10 }

mscVrIpOspfProvTable OBJECT-TYPE
   SYNTAX     SEQUENCE OF MscVrIpOspfProvEntry
   ACCESS     not-accessible
   STATUS     mandatory
   DESCRIPTION
     "This group of attributes are used to configure the OSPF component."
::= { mscVrIpOspf 100 }

mscVrIpOspfProvEntry OBJECT-TYPE
   SYNTAX     MscVrIpOspfProvEntry
   ACCESS     not-accessible
   STATUS     mandatory
   DESCRIPTION
     "An entry in the mscVrIpOspfProvTable."
   INDEX {
      mscVrIndex,
      mscVrIpIndex,
      mscVrIpOspfIndex }
::= { mscVrIpOspfProvTable 1 }

MscVrIpOspfProvEntry ::= SEQUENCE {
   mscVrIpOspfRouterId
      RouterID,
   mscVrIpOspfSnmpAdminStatus
      INTEGER,
   mscVrIpOspfAsBdrRtrStatus
      INTEGER,
   mscVrIpOspfTosSupport
      INTEGER,
   mscVrIpOspfExtLsdbLimit
      INTEGER,
   mscVrIpOspfMulticastForward
      Unsigned32,
   mscVrIpOspfMigrateRip
      INTEGER,
   mscVrIpOspfGenerateDefaultRouteMetric
      INTEGER,
   mscVrIpOspfRedistributeIbgp
      INTEGER }

mscVrIpOspfRouterId OBJECT-TYPE
   SYNTAX     RouterID 
   ACCESS     read-write
   STATUS     mandatory
   DESCRIPTION
     "This attribute is an Ip Address that uniquely identifies the router in the 
      autonomous system."
::= { mscVrIpOspfProvEntry 1 }

mscVrIpOspfSnmpAdminStatus OBJECT-TYPE
   SYNTAX     INTEGER  {
                 up(1),
                 down(2),
                 testing(3) }
   ACCESS     read-write
   STATUS     mandatory
   DESCRIPTION
     "The administrative status of the OSPF Component in this Virtual Router."
   DEFVAL     { up }
::= { mscVrIpOspfProvEntry 2 }

mscVrIpOspfAsBdrRtrStatus OBJECT-TYPE
   SYNTAX     INTEGER  {
                 true(1),
                 false(2) }
   ACCESS     read-write
   STATUS     mandatory
   DESCRIPTION
     "This attribute is a flag to note whether this router is an autonomous 
      system border router. If this router is configured to export any routes 
      learned from other than OSPF-internal protocol, this attribute should be 
      configured as autonomous system border router."
   DEFVAL     { false }
::= { mscVrIpOspfProvEntry 3 }

mscVrIpOspfTosSupport OBJECT-TYPE
   SYNTAX     INTEGER  {
                 false(2) }
   ACCESS     read-write
   STATUS     mandatory
   DESCRIPTION
     "The router's support for type-of-service routing. Only one value will be 
      allowed. This is a deviation from supporting the MIB."
   DEFVAL     { false }
::= { mscVrIpOspfProvEntry 4 }

mscVrIpOspfExtLsdbLimit OBJECT-TYPE
   SYNTAX     INTEGER (-1..2147483647)
   ACCESS     read-write
   STATUS     mandatory
   DESCRIPTION
     "The maximum number of external link-state entries that can be stored in 
      the link-state database. If the value is -1, then there is no limit,
      that is the maximum number of external OSPF routes that this 
      autonomous system border router will originate. 
      It will begin to flush LSA(Link State Advertisement)s, if an ASBR 
      might receive bursts of external routes (for example, a regional 
      network), then the parameter should be configured to a reasonable level. 
      If there are less than two thousand routes and large bursts are unlikely, 
      then the default should be adequate. This parameter will not affect the 
      number of external OSPF routes a router will store in it's database."
   DEFVAL     { -1 }
::= { mscVrIpOspfProvEntry 5 }

mscVrIpOspfMulticastForward OBJECT-TYPE
   SYNTAX     Unsigned32 (0..0)
   ACCESS     read-write
   STATUS     mandatory
   DESCRIPTION
     "A bit mask indicating the limits on Network Layer Multicast(class D) 
      forwarding. It is represented as a sum of the following:
      if intra-Area forwarding is permitted, 1; else 0
      if inter-Area forwarding is permitted 2; else 0
      if inter-AS forwarding is permitted, 4; else 0
      Only the value of 0 is being supported and this is a MIB deviation."
   DEFVAL     { 0 }
::= { mscVrIpOspfProvEntry 6 }

mscVrIpOspfMigrateRip OBJECT-TYPE
   SYNTAX     INTEGER  {
                 enabled(1),
                 disabled(2) }
   ACCESS     read-write
   STATUS     mandatory
   DESCRIPTION
     "This Attribute sets the preference level of OSPF-internal routes to be 
      less preferred than RIP. 
      This Parameter should only be used when starting migration of network 
      from RIP to OSPF. When ready to cutover to OSPF, set this attribute 
      disabled and run under normal preferences. All OSPF routers in the 
      Autonomous System should be running with migraterip enabled or with 
      migraterip disabled to prevent routing loops. It is important that the 
      changeover period from RIP to OSPF be performed quickly on all OSPF 
      routers so that no routing loops are formed. These routing loops could 
      be caused by conflicts in the internal RIP and OSPF databases."
   DEFVAL     { disabled }
::= { mscVrIpOspfProvEntry 7 }

mscVrIpOspfGenerateDefaultRouteMetric OBJECT-TYPE
   SYNTAX     INTEGER (-1..65535)
   ACCESS     read-write
   STATUS     mandatory
   DESCRIPTION
     "If this router is configured as an autonomous system border router, then 
      this attribute causes the default route to be generated with a metric value 
      equal to generateDefaultRouteMetric value. This route is put in the 
      OSPF update along with the normal update routes when updates are sent 
      to the neighbors. No default route will be generated if the value is 0."
   DEFVAL     { 0 }
::= { mscVrIpOspfProvEntry 8 }

mscVrIpOspfRedistributeIbgp OBJECT-TYPE
   SYNTAX     INTEGER  {
                 true(1),
                 false(2) }
   ACCESS     read-write
   STATUS     mandatory
   DESCRIPTION
     "This attribute specifies whether this Ospf instance allows to exporting of 
      any routes learned from internal Bgp peers (IBGP) to Ospf. If the value 
      of this attribute is true, and if an export policy is specified to distribute, 
      then Ospf allows any IBGP routes to be distributed to Ospf. If the value 
      of this attribute is false, Ospf does not allow IBGP routes to be 
      distributed to Ospf, even if an export policy is specified to distribute."
   DEFVAL     { false }
::= { mscVrIpOspfProvEntry 9 }

mscVrIpOspfOperTable OBJECT-TYPE
   SYNTAX     SEQUENCE OF MscVrIpOspfOperEntry
   ACCESS     not-accessible
   STATUS     mandatory
   DESCRIPTION
     "These group of attributes identifies the operational attributes for this 
      OSPF Component."
::= { mscVrIpOspf 101 }

mscVrIpOspfOperEntry OBJECT-TYPE
   SYNTAX     MscVrIpOspfOperEntry
   ACCESS     not-accessible
   STATUS     mandatory
   DESCRIPTION
     "An entry in the mscVrIpOspfOperTable."
   INDEX {
      mscVrIndex,
      mscVrIpIndex,
      mscVrIpOspfIndex }
::= { mscVrIpOspfOperTable 1 }

MscVrIpOspfOperEntry ::= SEQUENCE {
   mscVrIpOspfVersionNumber
      Unsigned32,
   mscVrIpOspfAreaBdrRtrStatus
      INTEGER,
   mscVrIpOspfExternLsaCount
      Gauge32,
   mscVrIpOspfExternLsaChecksumSum
      Unsigned32,
   mscVrIpOspfOriginateNewLsas
      Counter32,
   mscVrIpOspfRxNewLsas
      Counter32 }

mscVrIpOspfVersionNumber OBJECT-TYPE
   SYNTAX     Unsigned32 (2..2)
   ACCESS     read-only
   STATUS     mandatory
   DESCRIPTION
     "The Current Version number of the OSPF Protocol. (2)."
   DEFVAL     { 2 }
::= { mscVrIpOspfOperEntry 1 }

mscVrIpOspfAreaBdrRtrStatus OBJECT-TYPE
   SYNTAX     INTEGER  {
                 true(1),
                 false(2) }
   ACCESS     read-only
   STATUS     mandatory
   DESCRIPTION
     "This attribute is used to specify whether this router is configured as an 
      area border router."
::= { mscVrIpOspfOperEntry 2 }

mscVrIpOspfExternLsaCount OBJECT-TYPE
   SYNTAX     Gauge32 (0..4294967295)
   ACCESS     read-only
   STATUS     mandatory
   DESCRIPTION
     "The number of external (LS type 5) link-state advertisements in the link-
      state database."
   DEFVAL     { 0 }
::= { mscVrIpOspfOperEntry 3 }

mscVrIpOspfExternLsaChecksumSum OBJECT-TYPE
   SYNTAX     Unsigned32 (0..4294967295)
   ACCESS     read-only
   STATUS     mandatory
   DESCRIPTION
     "The 32-bit unsigned sum of the LS checksums of the external link-state 
      database. This sum can be used to determine if there has been a change 
      in a router's link state database, and to compare the link-state database 
      of two routers."
::= { mscVrIpOspfOperEntry 4 }

mscVrIpOspfOriginateNewLsas OBJECT-TYPE
   SYNTAX     Counter32 
   ACCESS     read-only
   STATUS     mandatory
   DESCRIPTION
     "The number of new link-state advertisements that have been originated. 
      This number is incremented each time the router originates a new LSA."
::= { mscVrIpOspfOperEntry 5 }

mscVrIpOspfRxNewLsas OBJECT-TYPE
   SYNTAX     Counter32 
   ACCESS     read-only
   STATUS     mandatory
   DESCRIPTION
     "The number of link-state advertisements received determined to be new 
      instantiations. This number does not include newer instantiations of self-
      originated link-state advertisements."
::= { mscVrIpOspfOperEntry 6 }

mscVrIpOspfStateTable OBJECT-TYPE
   SYNTAX     SEQUENCE OF MscVrIpOspfStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscVrIpOspf 102 }

mscVrIpOspfStateEntry OBJECT-TYPE
   SYNTAX     MscVrIpOspfStateEntry
   ACCESS     not-accessible
   STATUS     mandatory
   DESCRIPTION
     "An entry in the mscVrIpOspfStateTable."
   INDEX {
      mscVrIndex,
      mscVrIpIndex,
      mscVrIpOspfIndex }
::= { mscVrIpOspfStateTable 1 }

MscVrIpOspfStateEntry ::= SEQUENCE {
   mscVrIpOspfAdminState
      INTEGER,
   mscVrIpOspfOperationalState
      INTEGER,
   mscVrIpOspfUsageState
      INTEGER }

mscVrIpOspfAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscVrIpOspfStateEntry 1 }

mscVrIpOspfOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscVrIpOspfStateEntry 2 }

mscVrIpOspfUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscVrIpOspfStateEntry 3 }

mscVrIpOspfOperStatusTable OBJECT-TYPE
   SYNTAX     SEQUENCE OF MscVrIpOspfOperStatusEntry
   ACCESS     not-accessible
   STATUS     mandatory
   DESCRIPTION
     "This group includes the Operational Status attribute. This attribute 
      defines the current operational state of this component."
::= { mscVrIpOspf 105 }

mscVrIpOspfOperStatusEntry OBJECT-TYPE
   SYNTAX     MscVrIpOspfOperStatusEntry
   ACCESS     not-accessible
   STATUS     mandatory
   DESCRIPTION
     "An entry in the mscVrIpOspfOperStatusTable."
   INDEX {
      mscVrIndex,
      mscVrIpIndex,
      mscVrIpOspfIndex }
::= { mscVrIpOspfOperStatusTable 1 }

MscVrIpOspfOperStatusEntry ::= SEQUENCE {
   mscVrIpOspfSnmpOperStatus
      INTEGER }

mscVrIpOspfSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscVrIpOspfOperStatusEntry 1 }


-- Vr/<string> Ip Ospf AreaEntry/<Ip Address>
-- This component contains the information about various areas that the 
-- router is connected to.

mscVrIpOspfArea OBJECT IDENTIFIER ::= { mscVrIpOspf 2 }



mscVrIpOspfAreaRowStatusTable OBJECT-TYPE
   SYNTAX     SEQUENCE OF MscVrIpOspfAreaRowStatusEntry
   ACCESS     not-accessible
   STATUS     mandatory
   DESCRIPTION
     "This entry controls the addition and deletion of 
      mscVrIpOspfArea components."
::= { mscVrIpOspfArea 1 }

mscVrIpOspfAreaRowStatusEntry OBJECT-TYPE
   SYNTAX     MscVrIpOspfAreaRowStatusEntry
   ACCESS     not-accessible
   STATUS     mandatory
   DESCRIPTION
     "A single entry in the table represents a single 
      mscVrIpOspfArea component."
   INDEX {
      mscVrIndex,
      mscVrIpIndex,
      mscVrIpOspfIndex,
      mscVrIpOspfAreaAreaIdIndex }
::= { mscVrIpOspfAreaRowStatusTable 1 }

MscVrIpOspfAreaRowStatusEntry ::= SEQUENCE {
   mscVrIpOspfAreaRowStatus
      RowStatus,
   mscVrIpOspfAreaComponentName
      DisplayString,
   mscVrIpOspfAreaStorageType
      StorageType,
   mscVrIpOspfAreaAreaIdIndex
      IpAddress }

mscVrIpOspfAreaRowStatus OBJECT-TYPE
   SYNTAX     RowStatus 
   ACCESS     read-write
   STATUS     mandatory
   DESCRIPTION
     "This variable is used as the basis for SNMP naming of
      mscVrIpOspfArea components.
      These components can be added and deleted."
::= { mscVrIpOspfAreaRowStatusEntry 1 }

mscVrIpOspfAreaComponentName OBJECT-TYPE
   SYNTAX     DisplayString 
   ACCESS     read-only
   STATUS     mandatory
   DESCRIPTION
     "This variable provides the component's string name for
      use with the ASCII Console Interface"
::= { mscVrIpOspfAreaRowStatusEntry 2 }

mscVrIpOspfAreaStorageType OBJECT-TYPE
   SYNTAX     StorageType 
   ACCESS     read-only
   STATUS     mandatory
   DESCRIPTION
     "This variable represents the storage type value for the
      mscVrIpOspfArea tables."
::= { mscVrIpOspfAreaRowStatusEntry 4 }

mscVrIpOspfAreaAreaIdIndex OBJECT-TYPE
   SYNTAX     IpAddress 
   ACCESS     not-accessible
   STATUS     mandatory
   DESCRIPTION
     "This variable represents the index for the mscVrIpOspfArea tables."
::= { mscVrIpOspfAreaRowStatusEntry 10 }

mscVrIpOspfAreaProvTable OBJECT-TYPE
   SYNTAX     SEQUENCE OF MscVrIpOspfAreaProvEntry
   ACCESS     not-accessible
   STATUS     mandatory
   DESCRIPTION
     "This group describes the set of provisionable attributes for the 
      AreaEntry Component."
::= { mscVrIpOspfArea 10 }

mscVrIpOspfAreaProvEntry OBJECT-TYPE
   SYNTAX     MscVrIpOspfAreaProvEntry
   ACCESS     not-accessible
   STATUS     mandatory
   DESCRIPTION
     "An entry in the mscVrIpOspfAreaProvTable."
   INDEX {
      mscVrIndex,
      mscVrIpIndex,
      mscVrIpOspfIndex,
      mscVrIpOspfAreaAreaIdIndex }
::= { mscVrIpOspfAreaProvTable 1 }

MscVrIpOspfAreaProvEntry ::= SEQUENCE {
   mscVrIpOspfAreaAuthType
      INTEGER,
   mscVrIpOspfAreaImportAsExtern
      INTEGER,
   mscVrIpOspfAreaAreaSummary
      INTEGER }

mscVrIpOspfAreaAuthType OBJECT-TYPE
   SYNTAX     INTEGER  {
                 none(0),
                 simplePassword(1) }
   ACCESS     read-write
   STATUS     mandatory
   DESCRIPTION
     "The authentication type specified for this area."
   DEFVAL     { none }
::= { mscVrIpOspfAreaProvEntry 1 }

mscVrIpOspfAreaImportAsExtern OBJECT-TYPE
   SYNTAX     INTEGER  {
                 importExternal(1),
                 importNoExternal(2),
                 importNssa(3) }
   ACCESS     read-write
   STATUS     mandatory
   DESCRIPTION
     "The area's support for importing AS external link-state advertisements. 
      For backbone area (that is, areaId 0.0.0.0), this attribute must be set to 
      importExternal."
   DEFVAL     { importExternal }
::= { mscVrIpOspfAreaProvEntry 2 }

mscVrIpOspfAreaAreaSummary OBJECT-TYPE
   SYNTAX     INTEGER  {
                 noAreaSummary(1),
                 sendAreaSummary(2) }
   ACCESS     read-write
   STATUS     mandatory
   DESCRIPTION
     "This variable controls the import of summary LSAs into stub areas. If it 
      is noAreaSummary, the router will neither originate nor propagate 
      summary LSAs into the stub areas. It will rely entirely on its default 
      route. If it is sendAreaSummary, the router will both summarize and 
      propagate summary LSAs."
   DEFVAL     { noAreaSummary }
::= { mscVrIpOspfAreaProvEntry 3 }

mscVrIpOspfAreaOperTable OBJECT-TYPE
   SYNTAX     SEQUENCE OF MscVrIpOspfAreaOperEntry
   ACCESS     not-accessible
   STATUS     mandatory
   DESCRIPTION
     "This group of attributes describes the Operational set of attributes for the 
      AreaEntry component."
::= { mscVrIpOspfArea 11 }

mscVrIpOspfAreaOperEntry OBJECT-TYPE
   SYNTAX     MscVrIpOspfAreaOperEntry
   ACCESS     not-accessible
   STATUS     mandatory
   DESCRIPTION
     "An entry in the mscVrIpOspfAreaOperTable."
   INDEX {
      mscVrIndex,
      mscVrIpIndex,
      mscVrIpOspfIndex,
      mscVrIpOspfAreaAreaIdIndex }
::= { mscVrIpOspfAreaOperTable 1 }

MscVrIpOspfAreaOperEntry ::= SEQUENCE {
   mscVrIpOspfAreaSpfRuns
      Counter32,
   mscVrIpOspfAreaAreaBdrRtrCount
      Gauge32,
   mscVrIpOspfAreaAsBdrRtrCount
      Gauge32,
   mscVrIpOspfAreaLsaCount
      Gauge32,
   mscVrIpOspfAreaAreaLsaCksumSum
      Unsigned32 }

mscVrIpOspfAreaSpfRuns OBJECT-TYPE
   SYNTAX     Counter32 
   ACCESS     read-only
   STATUS     mandatory
   DESCRIPTION
     "The number of times that the intra-area route table has been calculated 
      using this area's link-state database since the protocol became 
      operational."
::= { mscVrIpOspfAreaOperEntry 1 }

mscVrIpOspfAreaAreaBdrRtrCount OBJECT-TYPE
   SYNTAX     Gauge32 (0..4294967295)
   ACCESS     read-only
   STATUS     mandatory
   DESCRIPTION
     "The total number of area border routers reachable within this area. This 
      is initially zero, and is calculated in each Shortest Path First Pass."
::= { mscVrIpOspfAreaOperEntry 2 }

mscVrIpOspfAreaAsBdrRtrCount OBJECT-TYPE
   SYNTAX     Gauge32 (0..4294967295)
   ACCESS     read-only
   STATUS     mandatory
   DESCRIPTION
     "The total number of Autonomous System border routers reachable 
      within this area. This is initially zero, and is calculated in each Shortest 
      Path First Pass."
::= { mscVrIpOspfAreaOperEntry 3 }

mscVrIpOspfAreaLsaCount OBJECT-TYPE
   SYNTAX     Gauge32 (0..4294967295)
   ACCESS     read-only
   STATUS     mandatory
   DESCRIPTION
     "The total number of link-state advertisements in this area's link-state 
      database, excluding AS External LSA's."
::= { mscVrIpOspfAreaOperEntry 4 }

mscVrIpOspfAreaAreaLsaCksumSum OBJECT-TYPE
   SYNTAX     Unsigned32 (0..4294967295)
   ACCESS     read-only
   STATUS     mandatory
   DESCRIPTION
     "The 32-bit unsigned sum of the link-state advertisement's LS checksums 
      contained in this area's link-state database. This sum excludes external 
      (LS type 5) link-state advertisements. The sum can be used to determine 
      if there has been a change in a router's link state database, and to 
      compare the link-state database of two routers."
::= { mscVrIpOspfAreaOperEntry 5 }


-- Vr/<string> Ip Ospf StubAreaEntry/<Ip Address>,<Decimal>
-- This component describes metrics that a default area border router will 
-- advertise into a stub area. 

mscVrIpOspfStub OBJECT IDENTIFIER ::= { mscVrIpOspf 3 }



mscVrIpOspfStubRowStatusTable OBJECT-TYPE
   SYNTAX     SEQUENCE OF MscVrIpOspfStubRowStatusEntry
   ACCESS     not-accessible
   STATUS     mandatory
   DESCRIPTION
     "This entry controls the addition and deletion of 
      mscVrIpOspfStub components."
::= { mscVrIpOspfStub 1 }

mscVrIpOspfStubRowStatusEntry OBJECT-TYPE
   SYNTAX     MscVrIpOspfStubRowStatusEntry
   ACCESS     not-accessible
   STATUS     mandatory
   DESCRIPTION
     "A single entry in the table represents a single 
      mscVrIpOspfStub component."
   INDEX {
      mscVrIndex,
      mscVrIpIndex,
      mscVrIpOspfIndex,
      mscVrIpOspfStubAreaIdIndex,
      mscVrIpOspfStubTosIndex }
::= { mscVrIpOspfStubRowStatusTable 1 }

MscVrIpOspfStubRowStatusEntry ::= SEQUENCE {
   mscVrIpOspfStubRowStatus
      RowStatus,
   mscVrIpOspfStubComponentName
      DisplayString,
   mscVrIpOspfStubStorageType
      StorageType,
   mscVrIpOspfStubAreaIdIndex
      IpAddress,
   mscVrIpOspfStubTosIndex
      Integer32 }

mscVrIpOspfStubRowStatus OBJECT-TYPE
   SYNTAX     RowStatus 
   ACCESS     read-write
   STATUS     mandatory
   DESCRIPTION
     "This variable is used as the basis for SNMP naming of
      mscVrIpOspfStub components.
      These components can be added and deleted."
::= { mscVrIpOspfStubRowStatusEntry 1 }

mscVrIpOspfStubComponentName OBJECT-TYPE
   SYNTAX     DisplayString 
   ACCESS     read-only
   STATUS     mandatory
   DESCRIPTION
     "This variable provides the component's string name for
      use with the ASCII Console Interface"
::= { mscVrIpOspfStubRowStatusEntry 2 }

mscVrIpOspfStubStorageType OBJECT-TYPE
   SYNTAX     StorageType 
   ACCESS     read-only
   STATUS     mandatory
   DESCRIPTION
     "This variable represents the storage type value for the
      mscVrIpOspfStub tables."
::= { mscVrIpOspfStubRowStatusEntry 4 }

mscVrIpOspfStubAreaIdIndex OBJECT-TYPE
   SYNTAX     IpAddress 
   ACCESS     not-accessible
   STATUS     mandatory
   DESCRIPTION
     "This variable represents an index for the mscVrIpOspfStub tables."
::= { mscVrIpOspfStubRowStatusEntry 10 }

mscVrIpOspfStubTosIndex OBJECT-TYPE
   SYNTAX     Integer32 (0..0)
   ACCESS     not-accessible
   STATUS     mandatory
   DESCRIPTION
     "This variable represents an index for the mscVrIpOspfStub tables."
::= { mscVrIpOspfStubRowStatusEntry 11 }

mscVrIpOspfStubProvTable OBJECT-TYPE
   SYNTAX     SEQUENCE OF MscVrIpOspfStubProvEntry
   ACCESS     not-accessible
   STATUS     mandatory
   DESCRIPTION
     "These set of attributes explain the provisionable group for the 
      StubAreaEntry."
::= { mscVrIpOspfStub 10 }

mscVrIpOspfStubProvEntry OBJECT-TYPE
   SYNTAX     MscVrIpOspfStubProvEntry
   ACCESS     not-accessible
   STATUS     mandatory
   DESCRIPTION
     "An entry in the mscVrIpOspfStubProvTable."
   INDEX {
      mscVrIndex,
      mscVrIpIndex,
      mscVrIpOspfIndex,
      mscVrIpOspfStubAreaIdIndex,
      mscVrIpOspfStubTosIndex }
::= { mscVrIpOspfStubProvTable 1 }

MscVrIpOspfStubProvEntry ::= SEQUENCE {
   mscVrIpOspfStubMetric
      Unsigned32,
   mscVrIpOspfStubMetricType
      INTEGER,
   mscVrIpOspfStubAdvertiseDefault
      INTEGER }

mscVrIpOspfStubMetric OBJECT-TYPE
   SYNTAX     Unsigned32 (1..4294967295)
   ACCESS     read-write
   STATUS     mandatory
   DESCRIPTION
     "The metric value applied at the indicated type of service."
   DEFVAL     { 1 }
::= { mscVrIpOspfStubProvEntry 1 }

mscVrIpOspfStubMetricType OBJECT-TYPE
   SYNTAX     INTEGER  {
                 ospfMetric(1),
                 comparableCost(2),
                 nonComparable(3) }
   ACCESS     read-write
   STATUS     mandatory
   DESCRIPTION
     "This type of the metric advertised as a default route."
   DEFVAL     { ospfMetric }
::= { mscVrIpOspfStubProvEntry 2 }

mscVrIpOspfStubAdvertiseDefault OBJECT-TYPE
   SYNTAX     INTEGER  {
                 yes(1),
                 no(2) }
   ACCESS     read-write
   STATUS     mandatory
   DESCRIPTION
     "This attribute determines whether or not the default routing information 
      will be advertised, depending on other criterion. Setting this value to no 
      can prevent advertising default routing information.
      
      If the value of the attribute is set to yes, then the value of the attribute 
      importAsExtern for that particular AreaEntry should be set to 
      importNssa."
   DEFVAL     { yes }
::= { mscVrIpOspfStubProvEntry 3 }


-- Vr/<string> Ip Ospf AreaRangeEntry/<Ip Address>,<enum>,
-- <Ip Address>,<Ip Address>
-- This table entry replaces the Area Summary table from RFC1253 and is 
-- used as an extension for CIDR support.

mscVrIpOspfAggregate OBJECT IDENTIFIER ::= { mscVrIpOspf 5 }



mscVrIpOspfAggregateRowStatusTable OBJECT-TYPE
   SYNTAX     SEQUENCE OF MscVrIpOspfAggregateRowStatusEntry
   ACCESS     not-accessible
   STATUS     mandatory
   DESCRIPTION
     "This entry controls the addition and deletion of 
      mscVrIpOspfAggregate components."
::= { mscVrIpOspfAggregate 1 }

mscVrIpOspfAggregateRowStatusEntry OBJECT-TYPE
   SYNTAX     MscVrIpOspfAggregateRowStatusEntry
   ACCESS     not-accessible
   STATUS     mandatory
   DESCRIPTION
     "A single entry in the table represents a single 
      mscVrIpOspfAggregate component."
   INDEX {
      mscVrIndex,
      mscVrIpIndex,
      mscVrIpOspfIndex,
      mscVrIpOspfAggregateAreaIdIndex,
      mscVrIpOspfAggregateLsdbTypeIndex,
      mscVrIpOspfAggregateAggregateNetIndex,
      mscVrIpOspfAggregateAggregateMaskIndex }
::= { mscVrIpOspfAggregateRowStatusTable 1 }

MscVrIpOspfAggregateRowStatusEntry ::= SEQUENCE {
   mscVrIpOspfAggregateRowStatus
      RowStatus,
   mscVrIpOspfAggregateComponentName
      DisplayString,
   mscVrIpOspfAggregateStorageType
      StorageType,
   mscVrIpOspfAggregateAreaIdIndex
      IpAddress,
   mscVrIpOspfAggregateLsdbTypeIndex
      INTEGER,
   mscVrIpOspfAggregateAggregateNetIndex
      IpAddress,
   mscVrIpOspfAggregateAggregateMaskIndex
      IpAddress }

mscVrIpOspfAggregateRowStatus OBJECT-TYPE
   SYNTAX     RowStatus 
   ACCESS     read-write
   STATUS     mandatory
   DESCRIPTION
     "This variable is used as the basis for SNMP naming of
      mscVrIpOspfAggregate components.
      These components can be added and deleted."
::= { mscVrIpOspfAggregateRowStatusEntry 1 }

mscVrIpOspfAggregateComponentName OBJECT-TYPE
   SYNTAX     DisplayString 
   ACCESS     read-only
   STATUS     mandatory
   DESCRIPTION
     "This variable provides the component's string name for
      use with the ASCII Console Interface"
::= { mscVrIpOspfAggregateRowStatusEntry 2 }

mscVrIpOspfAggregateStorageType OBJECT-TYPE
   SYNTAX     StorageType 
   ACCESS     read-only
   STATUS     mandatory
   DESCRIPTION
     "This variable represents the storage type value for the
      mscVrIpOspfAggregate tables."
::= { mscVrIpOspfAggregateRowStatusEntry 4 }

mscVrIpOspfAggregateAreaIdIndex OBJECT-TYPE
   SYNTAX     IpAddress 
   ACCESS     not-accessible
   STATUS     mandatory
   DESCRIPTION
     "This variable represents an index for the mscVrIpOspfAggregate tables."
::= { mscVrIpOspfAggregateRowStatusEntry 10 }

mscVrIpOspfAggregateLsdbTypeIndex OBJECT-TYPE
   SYNTAX     INTEGER  {
                 summaryLink(3),
                 nssaExternalLink(7) }
   ACCESS     not-accessible
   STATUS     mandatory
   DESCRIPTION
     "This variable represents an index for the mscVrIpOspfAggregate tables."
::= { mscVrIpOspfAggregateRowStatusEntry 11 }

mscVrIpOspfAggregateAggregateNetIndex OBJECT-TYPE
   SYNTAX     IpAddress 
   ACCESS     not-accessible
   STATUS     mandatory
   DESCRIPTION
     "This variable represents an index for the mscVrIpOspfAggregate tables."
::= { mscVrIpOspfAggregateRowStatusEntry 12 }

mscVrIpOspfAggregateAggregateMaskIndex OBJECT-TYPE
   SYNTAX     IpAddress 
   ACCESS     not-accessible
   STATUS     mandatory
   DESCRIPTION
     "This variable represents an index for the mscVrIpOspfAggregate tables."
::= { mscVrIpOspfAggregateRowStatusEntry 13 }

mscVrIpOspfAggregateProvTable OBJECT-TYPE
   SYNTAX     SEQUENCE OF MscVrIpOspfAggregateProvEntry
   ACCESS     not-accessible
   STATUS     mandatory
   DESCRIPTION
     "Identifies a group of provisionable attributes."
::= { mscVrIpOspfAggregate 10 }

mscVrIpOspfAggregateProvEntry OBJECT-TYPE
   SYNTAX     MscVrIpOspfAggregateProvEntry
   ACCESS     not-accessible
   STATUS     mandatory
   DESCRIPTION
     "An entry in the mscVrIpOspfAggregateProvTable."
   INDEX {
      mscVrIndex,
      mscVrIpIndex,
      mscVrIpOspfIndex,
      mscVrIpOspfAggregateAreaIdIndex,
      mscVrIpOspfAggregateLsdbTypeIndex,
      mscVrIpOspfAggregateAggregateNetIndex,
      mscVrIpOspfAggregateAggregateMaskIndex }
::= { mscVrIpOspfAggregateProvTable 1 }

MscVrIpOspfAggregateProvEntry ::= SEQUENCE {
   mscVrIpOspfAggregateEffect
      INTEGER }

mscVrIpOspfAggregateEffect OBJECT-TYPE
   SYNTAX     INTEGER  {
                 advertiseMatching(1),
                 doNotAdvertiseMatching(2),
                 invalid(3) }
   ACCESS     read-write
   STATUS     mandatory
   DESCRIPTION
     "This attribute determines whether or not the routing information will be 
      advertised, depending on other criterion. Setting this value to 
      doNotAdvertiseMatching can prevent advertising routing information 
      for the address and mask values specified as the indices for this entry."
   DEFVAL     { advertiseMatching }
::= { mscVrIpOspfAggregateProvEntry 1 }


-- Vr/<string> Ip Ospf HostEntry/<Ip Address>,<Decimal>
-- This component indicates what hosts are directly attached to the router, 
-- and what metrics and types of service should be advertised for them. 
-- This component is an optional subcomponent of Ospf.

mscVrIpOspfHost OBJECT IDENTIFIER ::= { mscVrIpOspf 6 }



mscVrIpOspfHostRowStatusTable OBJECT-TYPE
   SYNTAX     SEQUENCE OF MscVrIpOspfHostRowStatusEntry
   ACCESS     not-accessible
   STATUS     mandatory
   DESCRIPTION
     "This entry controls the addition and deletion of 
      mscVrIpOspfHost components."
::= { mscVrIpOspfHost 1 }

mscVrIpOspfHostRowStatusEntry OBJECT-TYPE
   SYNTAX     MscVrIpOspfHostRowStatusEntry
   ACCESS     not-accessible
   STATUS     mandatory
   DESCRIPTION
     "A single entry in the table represents a single 
      mscVrIpOspfHost component."
   INDEX {
      mscVrIndex,
      mscVrIpIndex,
      mscVrIpOspfIndex,
      mscVrIpOspfHostAddressIndex,
      mscVrIpOspfHostTosIndex }
::= { mscVrIpOspfHostRowStatusTable 1 }

MscVrIpOspfHostRowStatusEntry ::= SEQUENCE {
   mscVrIpOspfHostRowStatus
      RowStatus,
   mscVrIpOspfHostComponentName
      DisplayString,
   mscVrIpOspfHostStorageType
      StorageType,
   mscVrIpOspfHostAddressIndex
      IpAddress,
   mscVrIpOspfHostTosIndex
      Integer32 }

mscVrIpOspfHostRowStatus OBJECT-TYPE
   SYNTAX     RowStatus 
   ACCESS     read-write
   STATUS     mandatory
   DESCRIPTION
     "This variable is used as the basis for SNMP naming of
      mscVrIpOspfHost components.
      These components can be added and deleted."
::= { mscVrIpOspfHostRowStatusEntry 1 }

mscVrIpOspfHostComponentName OBJECT-TYPE
   SYNTAX     DisplayString 
   ACCESS     read-only
   STATUS     mandatory
   DESCRIPTION
     "This variable provides the component's string name for
      use with the ASCII Console Interface"
::= { mscVrIpOspfHostRowStatusEntry 2 }

mscVrIpOspfHostStorageType OBJECT-TYPE
   SYNTAX     StorageType 
   ACCESS     read-only
   STATUS     mandatory
   DESCRIPTION
     "This variable represents the storage type value for the
      mscVrIpOspfHost tables."
::= { mscVrIpOspfHostRowStatusEntry 4 }

mscVrIpOspfHostAddressIndex OBJECT-TYPE
   SYNTAX     IpAddress 
   ACCESS     not-accessible
   STATUS     mandatory
   DESCRIPTION
     "This variable represents an index for the mscVrIpOspfHost tables."
::= { mscVrIpOspfHostRowStatusEntry 10 }

mscVrIpOspfHostTosIndex OBJECT-TYPE
   SYNTAX     Integer32 (0..0)
   ACCESS     not-accessible
   STATUS     mandatory
   DESCRIPTION
     "This variable represents an index for the mscVrIpOspfHost tables."
::= { mscVrIpOspfHostRowStatusEntry 11 }

mscVrIpOspfHostProvTable OBJECT-TYPE
   SYNTAX     SEQUENCE OF MscVrIpOspfHostProvEntry
   ACCESS     not-accessible
   STATUS     mandatory
   DESCRIPTION
     "Provisionable set of attributes for the Host entry."
::= { mscVrIpOspfHost 10 }

mscVrIpOspfHostProvEntry OBJECT-TYPE
   SYNTAX     MscVrIpOspfHostProvEntry
   ACCESS     not-accessible
   STATUS     mandatory
   DESCRIPTION
     "An entry in the mscVrIpOspfHostProvTable."
   INDEX {
      mscVrIndex,
      mscVrIpIndex,
      mscVrIpOspfIndex,
      mscVrIpOspfHostAddressIndex,
      mscVrIpOspfHostTosIndex }
::= { mscVrIpOspfHostProvTable 1 }

MscVrIpOspfHostProvEntry ::= SEQUENCE {
   mscVrIpOspfHostAreaId
      AreaID,
   mscVrIpOspfHostMetric
      Unsigned32 }

mscVrIpOspfHostAreaId OBJECT-TYPE
   SYNTAX     AreaID 
   ACCESS     read-write
   STATUS     mandatory
   DESCRIPTION
     "This is an Ip address for the Host Entry that indicates the area it belongs 
      to."
::= { mscVrIpOspfHostProvEntry 1 }

mscVrIpOspfHostMetric OBJECT-TYPE
   SYNTAX     Unsigned32 (1..65535)
   ACCESS     read-write
   STATUS     mandatory
   DESCRIPTION
     "The metric to be advertised."
   DEFVAL     { 1 }
::= { mscVrIpOspfHostProvEntry 2 }


-- Vr/<string> Ip Ospf VirtIfEntry/<Ip Address>,<Ip Address>
-- This component describes all the virtual links configured for this OSPF 
-- Router.

mscVrIpOspfVirtIf OBJECT IDENTIFIER ::= { mscVrIpOspf 7 }



mscVrIpOspfVirtIfRowStatusTable OBJECT-TYPE
   SYNTAX     SEQUENCE OF MscVrIpOspfVirtIfRowStatusEntry
   ACCESS     not-accessible
   STATUS     mandatory
   DESCRIPTION
     "This entry controls the addition and deletion of 
      mscVrIpOspfVirtIf components."
::= { mscVrIpOspfVirtIf 1 }

mscVrIpOspfVirtIfRowStatusEntry OBJECT-TYPE
   SYNTAX     MscVrIpOspfVirtIfRowStatusEntry
   ACCESS     not-accessible
   STATUS     mandatory
   DESCRIPTION
     "A single entry in the table represents a single 
      mscVrIpOspfVirtIf component."
   INDEX {
      mscVrIndex,
      mscVrIpIndex,
      mscVrIpOspfIndex,
      mscVrIpOspfVirtIfAreaIdIndex,
      mscVrIpOspfVirtIfNbrRouterIdIndex }
::= { mscVrIpOspfVirtIfRowStatusTable 1 }

MscVrIpOspfVirtIfRowStatusEntry ::= SEQUENCE {
   mscVrIpOspfVirtIfRowStatus
      RowStatus,
   mscVrIpOspfVirtIfComponentName
      DisplayString,
   mscVrIpOspfVirtIfStorageType
      StorageType,
   mscVrIpOspfVirtIfAreaIdIndex
      IpAddress,
   mscVrIpOspfVirtIfNbrRouterIdIndex
      IpAddress }

mscVrIpOspfVirtIfRowStatus OBJECT-TYPE
   SYNTAX     RowStatus 
   ACCESS     read-write
   STATUS     mandatory
   DESCRIPTION
     "This variable is used as the basis for SNMP naming of
      mscVrIpOspfVirtIf components.
      These components can be added and deleted."
::= { mscVrIpOspfVirtIfRowStatusEntry 1 }

mscVrIpOspfVirtIfComponentName OBJECT-TYPE
   SYNTAX     DisplayString 
   ACCESS     read-only
   STATUS     mandatory
   DESCRIPTION
     "This variable provides the component's string name for
      use with the ASCII Console Interface"
::= { mscVrIpOspfVirtIfRowStatusEntry 2 }

mscVrIpOspfVirtIfStorageType OBJECT-TYPE
   SYNTAX     StorageType 
   ACCESS     read-only
   STATUS     mandatory
   DESCRIPTION
     "This variable represents the storage type value for the
      mscVrIpOspfVirtIf tables."
::= { mscVrIpOspfVirtIfRowStatusEntry 4 }

mscVrIpOspfVirtIfAreaIdIndex OBJECT-TYPE
   SYNTAX     IpAddress 
   ACCESS     not-accessible
   STATUS     mandatory
   DESCRIPTION
     "This variable represents an index for the mscVrIpOspfVirtIf tables."
::= { mscVrIpOspfVirtIfRowStatusEntry 10 }

mscVrIpOspfVirtIfNbrRouterIdIndex OBJECT-TYPE
   SYNTAX     IpAddress 
   ACCESS     not-accessible
   STATUS     mandatory
   DESCRIPTION
     "This variable represents an index for the mscVrIpOspfVirtIf tables."
::= { mscVrIpOspfVirtIfRowStatusEntry 11 }

mscVrIpOspfVirtIfProvTable OBJECT-TYPE
   SYNTAX     SEQUENCE OF MscVrIpOspfVirtIfProvEntry
   ACCESS     not-accessible
   STATUS     mandatory
   DESCRIPTION
     "This group of attributes provide provisioning data for the VirtIfEntry."
::= { mscVrIpOspfVirtIf 10 }

mscVrIpOspfVirtIfProvEntry OBJECT-TYPE
   SYNTAX     MscVrIpOspfVirtIfProvEntry
   ACCESS     not-accessible
   STATUS     mandatory
   DESCRIPTION
     "An entry in the mscVrIpOspfVirtIfProvTable."
   INDEX {
      mscVrIndex,
      mscVrIpIndex,
      mscVrIpOspfIndex,
      mscVrIpOspfVirtIfAreaIdIndex,
      mscVrIpOspfVirtIfNbrRouterIdIndex }
::= { mscVrIpOspfVirtIfProvTable 1 }

MscVrIpOspfVirtIfProvEntry ::= SEQUENCE {
   mscVrIpOspfVirtIfTransitDelay
      Unsigned32,
   mscVrIpOspfVirtIfRetransInterval
      Unsigned32,
   mscVrIpOspfVirtIfHelloInterval
      Unsigned32,
   mscVrIpOspfVirtIfRtrDeadInterval
      Unsigned32,
   mscVrIpOspfVirtIfAuthKey
      HexString }

mscVrIpOspfVirtIfTransitDelay OBJECT-TYPE
   SYNTAX     Unsigned32 (1..3600)
   ACCESS     read-write
   STATUS     mandatory
   DESCRIPTION
     "The estimated number of seconds it takes to transmit a link-state update 
      packet over this interface."
   DEFVAL     { 1 }
::= { mscVrIpOspfVirtIfProvEntry 1 }

mscVrIpOspfVirtIfRetransInterval OBJECT-TYPE
   SYNTAX     Unsigned32 (1..3600)
   ACCESS     read-write
   STATUS     mandatory
   DESCRIPTION
     "The number of seconds between link-state advertisement 
      retransmissions, for adjacencies belonging to this interface. This value is 
      also used when retransmitting database description 
      and link-state request packets. This value would be well over the 
      expected round-trip time."
   DEFVAL     { 5 }
::= { mscVrIpOspfVirtIfProvEntry 2 }

mscVrIpOspfVirtIfHelloInterval OBJECT-TYPE
   SYNTAX     Unsigned32 (1..3600)
   ACCESS     read-write
   STATUS     mandatory
   DESCRIPTION
     "The length of time, in seconds, between the Hello packets that the router 
      sends on the interface. This value must be the same for the virtual 
      neighbor."
   DEFVAL     { 10 }
::= { mscVrIpOspfVirtIfProvEntry 3 }

mscVrIpOspfVirtIfRtrDeadInterval OBJECT-TYPE
   SYNTAX     Unsigned32 (1..3600)
   ACCESS     read-write
   STATUS     mandatory
   DESCRIPTION
     "The number of seconds that a router's Hello packets have not been seen 
      before its neighbors declare the router down. This should be some 
      multiple of the Hello interval. This value must be the same for the 
      virtual neighbor."
   DEFVAL     { 60 }
::= { mscVrIpOspfVirtIfProvEntry 4 }

mscVrIpOspfVirtIfAuthKey OBJECT-TYPE
   SYNTAX     HexString (SIZE (1..8))
   ACCESS     write-only
   STATUS     mandatory
   DESCRIPTION
     "If authentication type is simple password, the password for this virtual 
      circuit. If the value of the attribute is not set, then this attribute is 
      ignored by the application.
      If the value of this attribute is set, then the value of the attribute 
      authType under this particular Area should be set to simplePassword, 
      otherwise the application will ignore this authentication key."
   DEFVAL     { '0000000000000000'H }  -- "0000000000000000"
::= { mscVrIpOspfVirtIfProvEntry 5 }

mscVrIpOspfVirtIfOperTable OBJECT-TYPE
   SYNTAX     SEQUENCE OF MscVrIpOspfVirtIfOperEntry
   ACCESS     not-accessible
   STATUS     mandatory
   DESCRIPTION
     "Represents a group of operational attributes for the VirtIfEntry 
      component."
::= { mscVrIpOspfVirtIf 11 }

mscVrIpOspfVirtIfOperEntry OBJECT-TYPE
   SYNTAX     MscVrIpOspfVirtIfOperEntry
   ACCESS     not-accessible
   STATUS     mandatory
   DESCRIPTION
     "An entry in the mscVrIpOspfVirtIfOperTable."
   INDEX {
      mscVrIndex,
      mscVrIpIndex,
      mscVrIpOspfIndex,
      mscVrIpOspfVirtIfAreaIdIndex,
      mscVrIpOspfVirtIfNbrRouterIdIndex }
::= { mscVrIpOspfVirtIfOperTable 1 }

MscVrIpOspfVirtIfOperEntry ::= SEQUENCE {
   mscVrIpOspfVirtIfState
      INTEGER,
   mscVrIpOspfVirtIfEvents
      Counter32 }

mscVrIpOspfVirtIfState OBJECT-TYPE
   SYNTAX     INTEGER  {
                 down(1),
                 pointToPoint(4) }
   ACCESS     read-only
   STATUS     mandatory
   DESCRIPTION
     "The state of the OSPF virtual interface."
::= { mscVrIpOspfVirtIfOperEntry 1 }

mscVrIpOspfVirtIfEvents OBJECT-TYPE
   SYNTAX     Counter32 
   ACCESS     read-only
   STATUS     mandatory
   DESCRIPTION
     "The number of state changes or error events on the virtual link."
::= { mscVrIpOspfVirtIfOperEntry 2 }


-- Vr/<string> Ip Ospf Export/n
-- Each instance of this component specifies an OSPF export policy. An 
-- OSPF export policy is used to decide if a route in the IP forwarding 
-- table should be blocked or advertised as OSPF external routes onto 
-- attached OSPF areas of the virtual router.
-- Passport IP OSPF by default advertises all OSPF external routes based 
-- on the metric and tag in the IP forwarding table.

mscVrIpOspfExport OBJECT IDENTIFIER ::= { mscVrIpOspf 8 }



mscVrIpOspfExportRowStatusTable OBJECT-TYPE
   SYNTAX     SEQUENCE OF MscVrIpOspfExportRowStatusEntry
   ACCESS     not-accessible
   STATUS     mandatory
   DESCRIPTION
     "This entry controls the addition and deletion of 
      mscVrIpOspfExport components."
::= { mscVrIpOspfExport 1 }

mscVrIpOspfExportRowStatusEntry OBJECT-TYPE
   SYNTAX     MscVrIpOspfExportRowStatusEntry
   ACCESS     not-accessible
   STATUS     mandatory
   DESCRIPTION
     "A single entry in the table represents a single 
      mscVrIpOspfExport component."
   INDEX {
      mscVrIndex,
      mscVrIpIndex,
      mscVrIpOspfIndex,
      mscVrIpOspfExportIndex }
::= { mscVrIpOspfExportRowStatusTable 1 }

MscVrIpOspfExportRowStatusEntry ::= SEQUENCE {
   mscVrIpOspfExportRowStatus
      RowStatus,
   mscVrIpOspfExportComponentName
      DisplayString,
   mscVrIpOspfExportStorageType
      StorageType,
   mscVrIpOspfExportIndex
      Integer32 }

mscVrIpOspfExportRowStatus OBJECT-TYPE
   SYNTAX     RowStatus 
   ACCESS     read-write
   STATUS     mandatory
   DESCRIPTION
     "This variable is used as the basis for SNMP naming of
      mscVrIpOspfExport components.
      These components can be added and deleted."
::= { mscVrIpOspfExportRowStatusEntry 1 }

mscVrIpOspfExportComponentName OBJECT-TYPE
   SYNTAX     DisplayString 
   ACCESS     read-only
   STATUS     mandatory
   DESCRIPTION
     "This variable provides the component's string name for
      use with the ASCII Console Interface"
::= { mscVrIpOspfExportRowStatusEntry 2 }

mscVrIpOspfExportStorageType OBJECT-TYPE
   SYNTAX     StorageType 
   ACCESS     read-only
   STATUS     mandatory
   DESCRIPTION
     "This variable represents the storage type value for the
      mscVrIpOspfExport tables."
::= { mscVrIpOspfExportRowStatusEntry 4 }

mscVrIpOspfExportIndex OBJECT-TYPE
   SYNTAX     Integer32 (0..65535)
   ACCESS     not-accessible
   STATUS     mandatory
   DESCRIPTION
     "This variable represents the index for the mscVrIpOspfExport tables."
::= { mscVrIpOspfExportRowStatusEntry 10 }

mscVrIpOspfExportProvTable OBJECT-TYPE
   SYNTAX     SEQUENCE OF MscVrIpOspfExportProvEntry
   ACCESS     not-accessible
   STATUS     mandatory
   DESCRIPTION
     "This Group contains all the Provisioned attributes for the Export 
      Component."
::= { mscVrIpOspfExport 10 }

mscVrIpOspfExportProvEntry OBJECT-TYPE
   SYNTAX     MscVrIpOspfExportProvEntry
   ACCESS     not-accessible
   STATUS     mandatory
   DESCRIPTION
     "An entry in the mscVrIpOspfExportProvTable."
   INDEX {
      mscVrIndex,
      mscVrIpIndex,
      mscVrIpOspfIndex,
      mscVrIpOspfExportIndex }
::= { mscVrIpOspfExportProvTable 1 }

MscVrIpOspfExportProvEntry ::= SEQUENCE {
   mscVrIpOspfExportAdvertiseStatus
      INTEGER,
   mscVrIpOspfExportMetric
      INTEGER,
   mscVrIpOspfExportProtocol
      INTEGER,
   mscVrIpOspfExportRipInterface
      IpAddress,
   mscVrIpOspfExportRipNeighbor
      IpAddress,
   mscVrIpOspfExportEgpAsId
      Unsigned32,
   mscVrIpOspfExportTag
      Unsigned32,
   mscVrIpOspfExportExtLsaMetricType
      INTEGER,
   mscVrIpOspfExportBgpAsId
      Unsigned32,
   mscVrIpOspfExportBgpPeerIp
      IpAddress }

mscVrIpOspfExportAdvertiseStatus OBJECT-TYPE
   SYNTAX     INTEGER  {
                 send(1),
                 block(2) }
   ACCESS     read-write
   STATUS     mandatory
   DESCRIPTION
     "This attribute specifies if the routes that match this export policy are 
      advertised (send) or not advertised (block)."
   DEFVAL     { send }
::= { mscVrIpOspfExportProvEntry 1 }

mscVrIpOspfExportMetric OBJECT-TYPE
   SYNTAX     INTEGER (-1..16777215)
   ACCESS     read-write
   STATUS     mandatory
   DESCRIPTION
     "This attribute specifies the metric to be used on the routes being 
      exported as a result of matching this export policy.
      If the attribute advertiseStatus is set to block, then the value of metric is 
      ignored. The metric value is not used to select which routes to block or 
      send, but rather the metric value advertised for the routes.
      A value of -1 indicates that the metric associated with the route in the 
      forwarding table is used."
   DEFVAL     { -1 }
::= { mscVrIpOspfExportProvEntry 2 }

mscVrIpOspfExportProtocol OBJECT-TYPE
   SYNTAX     INTEGER  {
                 all(1),
                 egp(2),
                 rip(3),
                 staticLocal(6),
                 staticRemote(7),
                 bgpInternal(8),
                 bgpExternal(9) }
   ACCESS     read-write
   STATUS     mandatory
   DESCRIPTION
     "This attribute specifies the routes to which this export policy applies 
      based on the routing protocol of how the routes are learned. If it is set to 
      all, this export policy applies to all routes in the forwarding table except 
      internal BGP routes."
   DEFVAL     { all }
::= { mscVrIpOspfExportProvEntry 3 }

mscVrIpOspfExportRipInterface OBJECT-TYPE
   SYNTAX     IpAddress 
   ACCESS     read-write
   STATUS     mandatory
   DESCRIPTION
     "This attribute specifies the RIP learned routes to which this export policy 
      applies, based on the RIP interface from which the routes are learned.
      This attribute can only be non zero when the protocol is set to rip. The 
      value of 0.0.0.0 implies any RIP interface on the same virtual router; 
      otherwise the value of this attribute must match the interface address of 
      a LogicalIf that has a RipIf on the same virtual router."
   DEFVAL     { '00000000'H }  -- "0.0.0.0"
::= { mscVrIpOspfExportProvEntry 4 }

mscVrIpOspfExportRipNeighbor OBJECT-TYPE
   SYNTAX     IpAddress 
   ACCESS     read-write
   STATUS     mandatory
   DESCRIPTION
     "This attribute specifies the RIP learned routes to which this export policy 
      applies, based on the RIP neighbor of which the routes are learned from.
      This attribute can only be non zero when the protocol is set to rip. The 
      value of 0.0.0.0 implies any RIP neighbor."
   DEFVAL     { '00000000'H }  -- "0.0.0.0"
::= { mscVrIpOspfExportProvEntry 5 }

mscVrIpOspfExportEgpAsId OBJECT-TYPE
   SYNTAX     Unsigned32 (0..65535)
   ACCESS     read-write
   STATUS     mandatory
   DESCRIPTION
     "This attribute specifies the EGP learned routes to which this export 
      policy applies, based on the EGP autonomous system identifier of which 
      the routes are learned from.
      This attribute can only be non zero when protocol is set to egp. The 
      value of 0 implies any EGP autonomous system; otherwise the value of 
      this attribute must match the asId of an EGP neighbor on the same 
      virtual router."
   DEFVAL     { 0 }
::= { mscVrIpOspfExportProvEntry 6 }

mscVrIpOspfExportTag OBJECT-TYPE
   SYNTAX     Unsigned32 (0..4294967295)
   ACCESS     read-write
   STATUS     mandatory
   DESCRIPTION
     "This attribute specifies the OSPF tag to be used on the routes being 
      exported as a result of matching this export policy.
      If the attribute advertiseStatus is set to block, then the value of tag is 
      ignored. The tag value is not used to select which routes to block or 
      send, but rather the tag value advertised for the routes.
      A value of 4294967295 indicates that the tag associated with the route in 
      the forwarding table is used."
   DEFVAL     { 4294967295 }
::= { mscVrIpOspfExportProvEntry 7 }

mscVrIpOspfExportExtLsaMetricType OBJECT-TYPE
   SYNTAX     INTEGER  {
                 useProtocolDefault(0),
                 type1(1),
                 type2(2) }
   ACCESS     read-write
   STATUS     mandatory
   DESCRIPTION
     "This attribute specifies the metric type in the OSPF external link state 
      advertisement of the routes being exported as a result of matching this 
      export policy.
      If the attribute advertiseStatus is set to block, then the value of 
      extLsaMetricType is ignored. The extLsaMetricType value is not used to 
      select which routes to block or send, but rather the metric value 
      advertised for the routes.
      The value useProtocolDefault indicates the metric type is automatically 
      chosen based on the routing protocol which the route was learned from."
   DEFVAL     { useProtocolDefault }
::= { mscVrIpOspfExportProvEntry 8 }

mscVrIpOspfExportBgpAsId OBJECT-TYPE
   SYNTAX     Unsigned32 (0..65535)
   ACCESS     read-write
   STATUS     mandatory
   DESCRIPTION
     "This key attribute specifies the bgp AS from which a bgp route is 
      learned from. This key is used only if the protocol is bgpExternal. 
      bgpAsId of value 0 mathces all ASs."
   DEFVAL     { 0 }
::= { mscVrIpOspfExportProvEntry 9 }

mscVrIpOspfExportBgpPeerIp OBJECT-TYPE
   SYNTAX     IpAddress 
   ACCESS     read-write
   STATUS     mandatory
   DESCRIPTION
     "This key attribute specifies the bgp peer where the routes were learned 
      from. bgpPeerIp of 0 matches all bgp peers. This attribute is used as a 
      key when protocol is set to bgpInternal or bgpExternal."
   DEFVAL     { '00000000'H }  -- "0.0.0.0"
::= { mscVrIpOspfExportProvEntry 10 }


-- This component identifies a set of attributes when matched determines 
-- the export policy applied. 

mscVrIpOspfExportNetList OBJECT IDENTIFIER ::= { mscVrIpOspfExport 2 }



mscVrIpOspfExportNetListRowStatusTable OBJECT-TYPE
   SYNTAX     SEQUENCE OF MscVrIpOspfExportNetListRowStatusEntry
   ACCESS     not-accessible
   STATUS     mandatory
   DESCRIPTION
     "This entry controls the addition and deletion of 
      mscVrIpOspfExportNetList components."
::= { mscVrIpOspfExportNetList 1 }

mscVrIpOspfExportNetListRowStatusEntry OBJECT-TYPE
   SYNTAX     MscVrIpOspfExportNetListRowStatusEntry
   ACCESS     not-accessible
   STATUS     mandatory
   DESCRIPTION
     "A single entry in the table represents a single 
      mscVrIpOspfExportNetList component."
   INDEX {
      mscVrIndex,
      mscVrIpIndex,
      mscVrIpOspfIndex,
      mscVrIpOspfExportIndex,
      mscVrIpOspfExportNetListIndex }
::= { mscVrIpOspfExportNetListRowStatusTable 1 }

MscVrIpOspfExportNetListRowStatusEntry ::= SEQUENCE {
   mscVrIpOspfExportNetListRowStatus
      RowStatus,
   mscVrIpOspfExportNetListComponentName
      DisplayString,
   mscVrIpOspfExportNetListStorageType
      StorageType,
   mscVrIpOspfExportNetListIndex
      Integer32 }

mscVrIpOspfExportNetListRowStatus OBJECT-TYPE
   SYNTAX     RowStatus 
   ACCESS     read-write
   STATUS     mandatory
   DESCRIPTION
     "This variable is used as the basis for SNMP naming of
      mscVrIpOspfExportNetList components.
      These components can be added and deleted."
::= { mscVrIpOspfExportNetListRowStatusEntry 1 }

mscVrIpOspfExportNetListComponentName OBJECT-TYPE
   SYNTAX     DisplayString 
   ACCESS     read-only
   STATUS     mandatory
   DESCRIPTION
     "This variable provides the component's string name for
      use with the ASCII Console Interface"
::= { mscVrIpOspfExportNetListRowStatusEntry 2 }

mscVrIpOspfExportNetListStorageType OBJECT-TYPE
   SYNTAX     StorageType 
   ACCESS     read-only
   STATUS     mandatory
   DESCRIPTION
     "This variable represents the storage type value for the
      mscVrIpOspfExportNetList tables."
::= { mscVrIpOspfExportNetListRowStatusEntry 4 }

mscVrIpOspfExportNetListIndex OBJECT-TYPE
   SYNTAX     Integer32 (0..65535)
   ACCESS     not-accessible
   STATUS     mandatory
   DESCRIPTION
     "This variable represents the index for the mscVrIpOspfExportNetList tables."
::= { mscVrIpOspfExportNetListRowStatusEntry 10 }

mscVrIpOspfExportNetListProvTable OBJECT-TYPE
   SYNTAX     SEQUENCE OF MscVrIpOspfExportNetListProvEntry
   ACCESS     not-accessible
   STATUS     mandatory
   DESCRIPTION
     "This group identifies the set of provisionable attributes for the 
      ExportNetworkList component."
::= { mscVrIpOspfExportNetList 10 }

mscVrIpOspfExportNetListProvEntry OBJECT-TYPE
   SYNTAX     MscVrIpOspfExportNetListProvEntry
   ACCESS     not-accessible
   STATUS     mandatory
   DESCRIPTION
     "An entry in the mscVrIpOspfExportNetListProvTable."
   INDEX {
      mscVrIndex,
      mscVrIpIndex,
      mscVrIpOspfIndex,
      mscVrIpOspfExportIndex,
      mscVrIpOspfExportNetListIndex }
::= { mscVrIpOspfExportNetListProvTable 1 }

MscVrIpOspfExportNetListProvEntry ::= SEQUENCE {
   mscVrIpOspfExportNetListIpAddress
      IpAddress,
   mscVrIpOspfExportNetListIpMask
      IpAddress }

mscVrIpOspfExportNetListIpAddress OBJECT-TYPE
   SYNTAX     IpAddress 
   ACCESS     read-write
   STATUS     mandatory
   DESCRIPTION
     "This attribute identifies the 32 bit IP address to match against."
::= { mscVrIpOspfExportNetListProvEntry 1 }

mscVrIpOspfExportNetListIpMask OBJECT-TYPE
   SYNTAX     IpAddress 
   ACCESS     read-write
   STATUS     mandatory
   DESCRIPTION
     "This attribute is the IP Mask to be used with the IP Address to match 
      against."
::= { mscVrIpOspfExportNetListProvEntry 2 }

-- 
-- *** THIS SUBTREE CURRENTLY NOT IMPLEMENTED ***
-- 

-- Vr/<string> Ip Ospf VirtNbrEntry/<Ip Address>,<Ip Address>
-- This component describes all of OSPF's Virtual Neighbors.

mscVrIpOspfVirtNbr OBJECT IDENTIFIER ::= { mscVrIpOspf 9 }



mscVrIpOspfVirtNbrRowStatusTable OBJECT-TYPE
   SYNTAX     SEQUENCE OF MscVrIpOspfVirtNbrRowStatusEntry
   ACCESS     not-accessible
   STATUS     mandatory
   DESCRIPTION
     "*** THIS TABLE CURRENTLY NOT IMPLEMENTED ***

      This entry controls the addition and deletion of 
      mscVrIpOspfVirtNbr components."
::= { mscVrIpOspfVirtNbr 1 }

mscVrIpOspfVirtNbrRowStatusEntry OBJECT-TYPE
   SYNTAX     MscVrIpOspfVirtNbrRowStatusEntry
   ACCESS     not-accessible
   STATUS     mandatory
   DESCRIPTION
     "A single entry in the table represents a single 
      mscVrIpOspfVirtNbr component."
   INDEX {
      mscVrIndex,
      mscVrIpIndex,
      mscVrIpOspfIndex,
      mscVrIpOspfVirtNbrAreaIdIndex,
      mscVrIpOspfVirtNbrNbrRouterIdIndex }
::= { mscVrIpOspfVirtNbrRowStatusTable 1 }

MscVrIpOspfVirtNbrRowStatusEntry ::= SEQUENCE {
   mscVrIpOspfVirtNbrRowStatus
      RowStatus,
   mscVrIpOspfVirtNbrComponentName
      DisplayString,
   mscVrIpOspfVirtNbrStorageType
      StorageType,
   mscVrIpOspfVirtNbrAreaIdIndex
      IpAddress,
   mscVrIpOspfVirtNbrNbrRouterIdIndex
      IpAddress }

mscVrIpOspfVirtNbrRowStatus OBJECT-TYPE
   SYNTAX     RowStatus 
   ACCESS     read-only
   STATUS     mandatory
   DESCRIPTION
     "This variable is used as the basis for SNMP naming of
      mscVrIpOspfVirtNbr components.
      These components cannot be added nor deleted."
::= { mscVrIpOspfVirtNbrRowStatusEntry 1 }

mscVrIpOspfVirtNbrComponentName OBJECT-TYPE
   SYNTAX     DisplayString 
   ACCESS     read-only
   STATUS     mandatory
   DESCRIPTION
     "This variable provides the component's string name for
      use with the ASCII Console Interface"
::= { mscVrIpOspfVirtNbrRowStatusEntry 2 }

mscVrIpOspfVirtNbrStorageType OBJECT-TYPE
   SYNTAX     StorageType 
   ACCESS     read-only
   STATUS     mandatory
   DESCRIPTION
     "This variable represents the storage type value for the
      mscVrIpOspfVirtNbr tables."
::= { mscVrIpOspfVirtNbrRowStatusEntry 4 }

mscVrIpOspfVirtNbrAreaIdIndex OBJECT-TYPE
   SYNTAX     IpAddress 
   ACCESS     not-accessible
   STATUS     mandatory
   DESCRIPTION
     "This variable represents an index for the mscVrIpOspfVirtNbr tables."
::= { mscVrIpOspfVirtNbrRowStatusEntry 10 }

mscVrIpOspfVirtNbrNbrRouterIdIndex OBJECT-TYPE
   SYNTAX     IpAddress 
   ACCESS     not-accessible
   STATUS     mandatory
   DESCRIPTION
     "This variable represents an index for the mscVrIpOspfVirtNbr tables."
::= { mscVrIpOspfVirtNbrRowStatusEntry 11 }

mscVrIpOspfVirtNbrOperTable OBJECT-TYPE
   SYNTAX     SEQUENCE OF MscVrIpOspfVirtNbrOperEntry
   ACCESS     not-accessible
   STATUS     mandatory
   DESCRIPTION
     "*** THIS TABLE CURRENTLY NOT IMPLEMENTED ***

      This group identifies a set of operational attributes."
::= { mscVrIpOspfVirtNbr 10 }

mscVrIpOspfVirtNbrOperEntry OBJECT-TYPE
   SYNTAX     MscVrIpOspfVirtNbrOperEntry
   ACCESS     not-accessible
   STATUS     mandatory
   DESCRIPTION
     "An entry in the mscVrIpOspfVirtNbrOperTable."
   INDEX {
      mscVrIndex,
      mscVrIpIndex,
      mscVrIpOspfIndex,
      mscVrIpOspfVirtNbrAreaIdIndex,
      mscVrIpOspfVirtNbrNbrRouterIdIndex }
::= { mscVrIpOspfVirtNbrOperTable 1 }

MscVrIpOspfVirtNbrOperEntry ::= SEQUENCE {
   mscVrIpOspfVirtNbrNbrIpAddress
      IpAddress,
   mscVrIpOspfVirtNbrOptions
      Unsigned32,
   mscVrIpOspfVirtNbrState
      INTEGER,
   mscVrIpOspfVirtNbrEvents
      Counter32,
   mscVrIpOspfVirtNbrLsRetransQlen
      Gauge32,
   mscVrIpOspfVirtNbrExchangeStatus
      INTEGER }

mscVrIpOspfVirtNbrNbrIpAddress OBJECT-TYPE
   SYNTAX     IpAddress 
   ACCESS     read-only
   STATUS     mandatory
   DESCRIPTION
     "Indicates the Ip address this interface this virtual neighbor is using."
::= { mscVrIpOspfVirtNbrOperEntry 1 }

mscVrIpOspfVirtNbrOptions OBJECT-TYPE
   SYNTAX     Unsigned32 (0..7)
   ACCESS     read-only
   STATUS     mandatory
   DESCRIPTION
     "A bit mask corresponding to the neighbor's options field. Bit 1, if set 
      indicates that the system will operate on Type of Service metrics other 
      than TOS 0. If zero, the neighbor will ignore all metrics except the TOS 
      0 metric. Bit 2, if set, indicates that the system is Network Multicast 
      capable; i.e., that it implements OSPF Multicast Routing."
::= { mscVrIpOspfVirtNbrOperEntry 2 }

mscVrIpOspfVirtNbrState OBJECT-TYPE
   SYNTAX     INTEGER  {
                 down(1),
                 attempt(2),
                 init(3),
                 twoWay(4),
                 exchange(5),
                 exchangeStatrt(6),
                 loading(7),
                 full(8) }
   ACCESS     read-only
   STATUS     mandatory
   DESCRIPTION
     "The state of the virtual neighbor relationship."
::= { mscVrIpOspfVirtNbrOperEntry 3 }

mscVrIpOspfVirtNbrEvents OBJECT-TYPE
   SYNTAX     Counter32 
   ACCESS     read-only
   STATUS     mandatory
   DESCRIPTION
     "The number of times this virtual link has changed its state, or an error 
      has occurred."
::= { mscVrIpOspfVirtNbrOperEntry 4 }

mscVrIpOspfVirtNbrLsRetransQlen OBJECT-TYPE
   SYNTAX     Gauge32 (0..4294967295)
   ACCESS     read-only
   STATUS     mandatory
   DESCRIPTION
     "The current length of the Retransmission queue."
::= { mscVrIpOspfVirtNbrOperEntry 5 }

mscVrIpOspfVirtNbrExchangeStatus OBJECT-TYPE
   SYNTAX     INTEGER  {
                 master(1),
                 slave(2) }
   ACCESS     read-only
   STATUS     mandatory
   DESCRIPTION
     "Indicates the exchange status of the entry in this table."
::= { mscVrIpOspfVirtNbrOperEntry 6 }

-- 
-- *** THIS SUBTREE CURRENTLY NOT IMPLEMENTED ***
-- 

-- Vr/<string> Ip Ospf NbrEntry/<Ip Address>,<Decimal>
-- This component is a dynamic subcomponent of OSPF that describes all 
-- the OSPF Neighbors.

mscVrIpOspfNbr OBJECT IDENTIFIER ::= { mscVrIpOspf 10 }



mscVrIpOspfNbrRowStatusTable OBJECT-TYPE
   SYNTAX     SEQUENCE OF MscVrIpOspfNbrRowStatusEntry
   ACCESS     not-accessible
   STATUS     mandatory
   DESCRIPTION
     "*** THIS TABLE CURRENTLY NOT IMPLEMENTED ***

      This entry controls the addition and deletion of 
      mscVrIpOspfNbr components."
::= { mscVrIpOspfNbr 1 }

mscVrIpOspfNbrRowStatusEntry OBJECT-TYPE
   SYNTAX     MscVrIpOspfNbrRowStatusEntry
   ACCESS     not-accessible
   STATUS     mandatory
   DESCRIPTION
     "A single entry in the table represents a single 
      mscVrIpOspfNbr component."
   INDEX {
      mscVrIndex,
      mscVrIpIndex,
      mscVrIpOspfIndex,
      mscVrIpOspfNbrAddressIndex,
      mscVrIpOspfNbrAddressLessIndex }
::= { mscVrIpOspfNbrRowStatusTable 1 }

MscVrIpOspfNbrRowStatusEntry ::= SEQUENCE {
   mscVrIpOspfNbrRowStatus
      RowStatus,
   mscVrIpOspfNbrComponentName
      DisplayString,
   mscVrIpOspfNbrStorageType
      StorageType,
   mscVrIpOspfNbrAddressIndex
      IpAddress,
   mscVrIpOspfNbrAddressLessIndex
      Integer32 }

mscVrIpOspfNbrRowStatus OBJECT-TYPE
   SYNTAX     RowStatus 
   ACCESS     read-only
   STATUS     mandatory
   DESCRIPTION
     "This variable is used as the basis for SNMP naming of
      mscVrIpOspfNbr components.
      These components cannot be added nor deleted."
::= { mscVrIpOspfNbrRowStatusEntry 1 }

mscVrIpOspfNbrComponentName OBJECT-TYPE
   SYNTAX     DisplayString 
   ACCESS     read-only
   STATUS     mandatory
   DESCRIPTION
     "This variable provides the component's string name for
      use with the ASCII Console Interface"
::= { mscVrIpOspfNbrRowStatusEntry 2 }

mscVrIpOspfNbrStorageType OBJECT-TYPE
   SYNTAX     StorageType 
   ACCESS     read-only
   STATUS     mandatory
   DESCRIPTION
     "This variable represents the storage type value for the
      mscVrIpOspfNbr tables."
::= { mscVrIpOspfNbrRowStatusEntry 4 }

mscVrIpOspfNbrAddressIndex OBJECT-TYPE
   SYNTAX     IpAddress 
   ACCESS     not-accessible
   STATUS     mandatory
   DESCRIPTION
     "This variable represents an index for the mscVrIpOspfNbr tables."
::= { mscVrIpOspfNbrRowStatusEntry 10 }

mscVrIpOspfNbrAddressLessIndex OBJECT-TYPE
   SYNTAX     Integer32 (0)
   ACCESS     not-accessible
   STATUS     mandatory
   DESCRIPTION
     "This variable represents an index for the mscVrIpOspfNbr tables."
::= { mscVrIpOspfNbrRowStatusEntry 11 }

mscVrIpOspfNbrOperTable OBJECT-TYPE
   SYNTAX     SEQUENCE OF MscVrIpOspfNbrOperEntry
   ACCESS     not-accessible
   STATUS     mandatory
   DESCRIPTION
     "*** THIS TABLE CURRENTLY NOT IMPLEMENTED ***

      This group identifies the operational set of attributes for the 
      NeighborEntry."
::= { mscVrIpOspfNbr 10 }

mscVrIpOspfNbrOperEntry OBJECT-TYPE
   SYNTAX     MscVrIpOspfNbrOperEntry
   ACCESS     not-accessible
   STATUS     mandatory
   DESCRIPTION
     "An entry in the mscVrIpOspfNbrOperTable."
   INDEX {
      mscVrIndex,
      mscVrIpIndex,
      mscVrIpOspfIndex,
      mscVrIpOspfNbrAddressIndex,
      mscVrIpOspfNbrAddressLessIndex }
::= { mscVrIpOspfNbrOperTable 1 }

MscVrIpOspfNbrOperEntry ::= SEQUENCE {
   mscVrIpOspfNbrRtrId
      IpAddress,
   mscVrIpOspfNbrOptions
      Unsigned32,
   mscVrIpOspfNbrPriority
      Unsigned32,
   mscVrIpOspfNbrState
      INTEGER,
   mscVrIpOspfNbrEvents
      Counter32,
   mscVrIpOspfNbrLsRetransQlen
      Gauge32,
   mscVrIpOspfNbrNbmaNbrStatus
      INTEGER,
   mscVrIpOspfNbrExchangeStatus
      INTEGER,
   mscVrIpOspfNbrPermanence
      INTEGER }

mscVrIpOspfNbrRtrId OBJECT-TYPE
   SYNTAX     IpAddress 
   ACCESS     read-only
   STATUS     mandatory
   DESCRIPTION
     "An Ip Address that uniquely identifies the neighboring router in the 
      autonomous system."
::= { mscVrIpOspfNbrOperEntry 1 }

mscVrIpOspfNbrOptions OBJECT-TYPE
   SYNTAX     Unsigned32 (0..7)
   ACCESS     read-only
   STATUS     mandatory
   DESCRIPTION
     "A bit mask corresponding to the neighbor's options field. Bit 0, if set, 
      indicates that the area accepts and operates on external information, if 
      zero, it is a stub area. Bit 1, if set, indicates that the system will operate 
      on Type of Service metrics other than TOS 0. If zero, the neighbor will 
      ignore all metrics except the TOS 0 metric. Bit 2, if set, indicates that 
      the system is Network Multicast capable; i.e., that it implements OSPF 
      Multicast Routing."
::= { mscVrIpOspfNbrOperEntry 2 }

mscVrIpOspfNbrPriority OBJECT-TYPE
   SYNTAX     Unsigned32 (0..255)
   ACCESS     read-only
   STATUS     mandatory
   DESCRIPTION
     "The priority of this neighbor in the designated router election algorithm. 
      The value 0 signifies that the neighbor is not eligible to become the 
      designated router on this particular network."
::= { mscVrIpOspfNbrOperEntry 3 }

mscVrIpOspfNbrState OBJECT-TYPE
   SYNTAX     INTEGER  {
                 down(1),
                 attempt(2),
                 init(3),
                 twoWay(4),
                 exchangeStart(5),
                 exchange(6),
                 loading(7),
                 full(8) }
   ACCESS     read-only
   STATUS     mandatory
   DESCRIPTION
     "The state of the relationship with this neighbor."
::= { mscVrIpOspfNbrOperEntry 4 }

mscVrIpOspfNbrEvents OBJECT-TYPE
   SYNTAX     Counter32 
   ACCESS     read-only
   STATUS     mandatory
   DESCRIPTION
     "The number of times this neighbor relationship has changed state, or an 
      error has occurred."
::= { mscVrIpOspfNbrOperEntry 5 }

mscVrIpOspfNbrLsRetransQlen OBJECT-TYPE
   SYNTAX     Gauge32 (0..4294967295)
   ACCESS     read-only
   STATUS     mandatory
   DESCRIPTION
     "The current length of the Retransmission queue."
::= { mscVrIpOspfNbrOperEntry 6 }

mscVrIpOspfNbrNbmaNbrStatus OBJECT-TYPE
   SYNTAX     INTEGER  {
                 valid(1),
                 invalid(2) }
   ACCESS     read-only
   STATUS     mandatory
   DESCRIPTION
     "This attribute describes the status of the entry."
::= { mscVrIpOspfNbrOperEntry 7 }

mscVrIpOspfNbrExchangeStatus OBJECT-TYPE
   SYNTAX     INTEGER  {
                 master(1),
                 slave(2) }
   ACCESS     read-only
   STATUS     mandatory
   DESCRIPTION
     "Indicates the exchange status for a neighbor entry."
::= { mscVrIpOspfNbrOperEntry 8 }

mscVrIpOspfNbrPermanence OBJECT-TYPE
   SYNTAX     INTEGER  {
                 dynamic(1),
                 permanent(2) }
   ACCESS     read-only
   STATUS     mandatory
   DESCRIPTION
     "This attribute displays how the neighbor became an entry."
   DEFVAL     { dynamic }
::= { mscVrIpOspfNbrOperEntry 11 }

-- 
-- *** THIS SUBTREE CURRENTLY NOT IMPLEMENTED ***
-- 

-- Vr/<string> Ip Ospf LsdbEntry/<Ip Address>,<Decimal>, 
-- <Ip Address>, <Ip Address>
-- This dynamic component contains the Link State Advertiements (LSA) 
-- from all areas the device is connected to.

mscVrIpOspfLsdb OBJECT IDENTIFIER ::= { mscVrIpOspf 11 }



mscVrIpOspfLsdbRowStatusTable OBJECT-TYPE
   SYNTAX     SEQUENCE OF MscVrIpOspfLsdbRowStatusEntry
   ACCESS     not-accessible
   STATUS     mandatory
   DESCRIPTION
     "*** THIS TABLE CURRENTLY NOT IMPLEMENTED ***

      This entry controls the addition and deletion of 
      mscVrIpOspfLsdb components."
::= { mscVrIpOspfLsdb 1 }

mscVrIpOspfLsdbRowStatusEntry OBJECT-TYPE
   SYNTAX     MscVrIpOspfLsdbRowStatusEntry
   ACCESS     not-accessible
   STATUS     mandatory
   DESCRIPTION
     "A single entry in the table represents a single 
      mscVrIpOspfLsdb component."
   INDEX {
      mscVrIndex,
      mscVrIpIndex,
      mscVrIpOspfIndex,
      mscVrIpOspfLsdbAreaIdIndex,
      mscVrIpOspfLsdbLsdbTypeIndex,
      mscVrIpOspfLsdbLsIdIndex,
      mscVrIpOspfLsdbRouterIdIndex }
::= { mscVrIpOspfLsdbRowStatusTable 1 }

MscVrIpOspfLsdbRowStatusEntry ::= SEQUENCE {
   mscVrIpOspfLsdbRowStatus
      RowStatus,
   mscVrIpOspfLsdbComponentName
      DisplayString,
   mscVrIpOspfLsdbStorageType
      StorageType,
   mscVrIpOspfLsdbAreaIdIndex
      IpAddress,
   mscVrIpOspfLsdbLsdbTypeIndex
      Integer32,
   mscVrIpOspfLsdbLsIdIndex
      IpAddress,
   mscVrIpOspfLsdbRouterIdIndex
      IpAddress }

mscVrIpOspfLsdbRowStatus OBJECT-TYPE
   SYNTAX     RowStatus 
   ACCESS     read-only
   STATUS     mandatory
   DESCRIPTION
     "This variable is used as the basis for SNMP naming of
      mscVrIpOspfLsdb components.
      These components cannot be added nor deleted."
::= { mscVrIpOspfLsdbRowStatusEntry 1 }

mscVrIpOspfLsdbComponentName OBJECT-TYPE
   SYNTAX     DisplayString 
   ACCESS     read-only
   STATUS     mandatory
   DESCRIPTION
     "This variable provides the component's string name for
      use with the ASCII Console Interface"
::= { mscVrIpOspfLsdbRowStatusEntry 2 }

mscVrIpOspfLsdbStorageType OBJECT-TYPE
   SYNTAX     StorageType 
   ACCESS     read-only
   STATUS     mandatory
   DESCRIPTION
     "This variable represents the storage type value for the
      mscVrIpOspfLsdb tables."
::= { mscVrIpOspfLsdbRowStatusEntry 4 }

mscVrIpOspfLsdbAreaIdIndex OBJECT-TYPE
   SYNTAX     IpAddress 
   ACCESS     not-accessible
   STATUS     mandatory
   DESCRIPTION
     "This variable represents an index for the mscVrIpOspfLsdb tables."
::= { mscVrIpOspfLsdbRowStatusEntry 10 }

mscVrIpOspfLsdbLsdbTypeIndex OBJECT-TYPE
   SYNTAX     Integer32 (1..7)
   ACCESS     not-accessible
   STATUS     mandatory
   DESCRIPTION
     "This variable represents an index for the mscVrIpOspfLsdb tables."
::= { mscVrIpOspfLsdbRowStatusEntry 11 }

mscVrIpOspfLsdbLsIdIndex OBJECT-TYPE
   SYNTAX     IpAddress 
   ACCESS     not-accessible
   STATUS     mandatory
   DESCRIPTION
     "This variable represents an index for the mscVrIpOspfLsdb tables."
::= { mscVrIpOspfLsdbRowStatusEntry 12 }

mscVrIpOspfLsdbRouterIdIndex OBJECT-TYPE
   SYNTAX     IpAddress 
   ACCESS     not-accessible
   STATUS     mandatory
   DESCRIPTION
     "This variable represents an index for the mscVrIpOspfLsdb tables."
::= { mscVrIpOspfLsdbRowStatusEntry 13 }

mscVrIpOspfLsdbOperTable OBJECT-TYPE
   SYNTAX     SEQUENCE OF MscVrIpOspfLsdbOperEntry
   ACCESS     not-accessible
   STATUS     mandatory
   DESCRIPTION
     "*** THIS TABLE CURRENTLY NOT IMPLEMENTED ***

      This group describes the Operational set of attributes for the LsdbEntry."
::= { mscVrIpOspfLsdb 10 }

mscVrIpOspfLsdbOperEntry OBJECT-TYPE
   SYNTAX     MscVrIpOspfLsdbOperEntry
   ACCESS     not-accessible
   STATUS     mandatory
   DESCRIPTION
     "An entry in the mscVrIpOspfLsdbOperTable."
   INDEX {
      mscVrIndex,
      mscVrIpIndex,
      mscVrIpOspfIndex,
      mscVrIpOspfLsdbAreaIdIndex,
      mscVrIpOspfLsdbLsdbTypeIndex,
      mscVrIpOspfLsdbLsIdIndex,
      mscVrIpOspfLsdbRouterIdIndex }
::= { mscVrIpOspfLsdbOperTable 1 }

MscVrIpOspfLsdbOperEntry ::= SEQUENCE {
   mscVrIpOspfLsdbSequence
      Unsigned32,
   mscVrIpOspfLsdbAge
      Gauge32,
   mscVrIpOspfLsdbChecksum
      Unsigned32,
   mscVrIpOspfLsdbAdvertisement
      HexString }

mscVrIpOspfLsdbSequence OBJECT-TYPE
   SYNTAX     Unsigned32 (0..4294967295)
   ACCESS     read-only
   STATUS     mandatory
   DESCRIPTION
     "A signed 32-bit integer, used to detect old and duplicate LSAs. The 
      space of sequence numbers is linearly ordered. The larger the sequence 
      number, the more recent the advertisement."
::= { mscVrIpOspfLsdbOperEntry 1 }

mscVrIpOspfLsdbAge OBJECT-TYPE
   SYNTAX     Gauge32 (0..3600)
   ACCESS     read-only
   STATUS     mandatory
   DESCRIPTION
     "The age of the Link State Advertisement in seconds."
::= { mscVrIpOspfLsdbOperEntry 2 }

mscVrIpOspfLsdbChecksum OBJECT-TYPE
   SYNTAX     Unsigned32 (0..4294967295)
   ACCESS     read-only
   STATUS     mandatory
   DESCRIPTION
     "The checksum of the complete contents of the advertisement, excepting 
      the age field. The checksum used is the Fletcher checksum."
::= { mscVrIpOspfLsdbOperEntry 3 }

mscVrIpOspfLsdbAdvertisement OBJECT-TYPE
   SYNTAX     HexString (SIZE (1..1024))
   ACCESS     read-only
   STATUS     mandatory
   DESCRIPTION
     "The entire LSA including its header."
::= { mscVrIpOspfLsdbOperEntry 4 }

-- 
-- *** THIS SUBTREE CURRENTLY NOT IMPLEMENTED ***
-- 

-- Vr/<string> Ip Ospf ExtLsdbEntry/<Decimal>, <Ip Address>, 
-- <Ip Address>
-- This dynamic component contains the Link State Advertiements(LSA) 
-- from other Autonomous systems. It is identical in format to the Lsdb. 
-- The purpose is to allow all external LSAs to be displayed together rather 
-- than distributed over the different non-stub areas.

mscVrIpOspfExtLsdb OBJECT IDENTIFIER ::= { mscVrIpOspf 12 }



mscVrIpOspfExtLsdbRowStatusTable OBJECT-TYPE
   SYNTAX     SEQUENCE OF MscVrIpOspfExtLsdbRowStatusEntry
   ACCESS     not-accessible
   STATUS     mandatory
   DESCRIPTION
     "*** THIS TABLE CURRENTLY NOT IMPLEMENTED ***

      This entry controls the addition and deletion of 
      mscVrIpOspfExtLsdb components."
::= { mscVrIpOspfExtLsdb 1 }

mscVrIpOspfExtLsdbRowStatusEntry OBJECT-TYPE
   SYNTAX     MscVrIpOspfExtLsdbRowStatusEntry
   ACCESS     not-accessible
   STATUS     mandatory
   DESCRIPTION
     "A single entry in the table represents a single 
      mscVrIpOspfExtLsdb component."
   INDEX {
      mscVrIndex,
      mscVrIpIndex,
      mscVrIpOspfIndex,
      mscVrIpOspfExtLsdbLsdbTypeIndex,
      mscVrIpOspfExtLsdbLsIdIndex,
      mscVrIpOspfExtLsdbRouterIdIndex }
::= { mscVrIpOspfExtLsdbRowStatusTable 1 }

MscVrIpOspfExtLsdbRowStatusEntry ::= SEQUENCE {
   mscVrIpOspfExtLsdbRowStatus
      RowStatus,
   mscVrIpOspfExtLsdbComponentName
      DisplayString,
   mscVrIpOspfExtLsdbStorageType
      StorageType,
   mscVrIpOspfExtLsdbLsdbTypeIndex
      Integer32,
   mscVrIpOspfExtLsdbLsIdIndex
      IpAddress,
   mscVrIpOspfExtLsdbRouterIdIndex
      IpAddress }

mscVrIpOspfExtLsdbRowStatus OBJECT-TYPE
   SYNTAX     RowStatus 
   ACCESS     read-only
   STATUS     mandatory
   DESCRIPTION
     "This variable is used as the basis for SNMP naming of
      mscVrIpOspfExtLsdb components.
      These components cannot be added nor deleted."
::= { mscVrIpOspfExtLsdbRowStatusEntry 1 }

mscVrIpOspfExtLsdbComponentName OBJECT-TYPE
   SYNTAX     DisplayString 
   ACCESS     read-only
   STATUS     mandatory
   DESCRIPTION
     "This variable provides the component's string name for
      use with the ASCII Console Interface"
::= { mscVrIpOspfExtLsdbRowStatusEntry 2 }

mscVrIpOspfExtLsdbStorageType OBJECT-TYPE
   SYNTAX     StorageType 
   ACCESS     read-only
   STATUS     mandatory
   DESCRIPTION
     "This variable represents the storage type value for the
      mscVrIpOspfExtLsdb tables."
::= { mscVrIpOspfExtLsdbRowStatusEntry 4 }

mscVrIpOspfExtLsdbLsdbTypeIndex OBJECT-TYPE
   SYNTAX     Integer32 (1..7)
   ACCESS     not-accessible
   STATUS     mandatory
   DESCRIPTION
     "This variable represents an index for the mscVrIpOspfExtLsdb tables."
::= { mscVrIpOspfExtLsdbRowStatusEntry 10 }

mscVrIpOspfExtLsdbLsIdIndex OBJECT-TYPE
   SYNTAX     IpAddress 
   ACCESS     not-accessible
   STATUS     mandatory
   DESCRIPTION
     "This variable represents an index for the mscVrIpOspfExtLsdb tables."
::= { mscVrIpOspfExtLsdbRowStatusEntry 11 }

mscVrIpOspfExtLsdbRouterIdIndex OBJECT-TYPE
   SYNTAX     IpAddress 
   ACCESS     not-accessible
   STATUS     mandatory
   DESCRIPTION
     "This variable represents an index for the mscVrIpOspfExtLsdb tables."
::= { mscVrIpOspfExtLsdbRowStatusEntry 12 }

mscVrIpOspfExtLsdbOperTable OBJECT-TYPE
   SYNTAX     SEQUENCE OF MscVrIpOspfExtLsdbOperEntry
   ACCESS     not-accessible
   STATUS     mandatory
   DESCRIPTION
     "*** THIS TABLE CURRENTLY NOT IMPLEMENTED ***

      This group describes the operational set of attributes 
      for the ExtLsdbEntry."
::= { mscVrIpOspfExtLsdb 10 }

mscVrIpOspfExtLsdbOperEntry OBJECT-TYPE
   SYNTAX     MscVrIpOspfExtLsdbOperEntry
   ACCESS     not-accessible
   STATUS     mandatory
   DESCRIPTION
     "An entry in the mscVrIpOspfExtLsdbOperTable."
   INDEX {
      mscVrIndex,
      mscVrIpIndex,
      mscVrIpOspfIndex,
      mscVrIpOspfExtLsdbLsdbTypeIndex,
      mscVrIpOspfExtLsdbLsIdIndex,
      mscVrIpOspfExtLsdbRouterIdIndex }
::= { mscVrIpOspfExtLsdbOperTable 1 }

MscVrIpOspfExtLsdbOperEntry ::= SEQUENCE {
   mscVrIpOspfExtLsdbSequence
      Unsigned32,
   mscVrIpOspfExtLsdbAge
      Gauge32,
   mscVrIpOspfExtLsdbChecksum
      Unsigned32,
   mscVrIpOspfExtLsdbAdvertisement
      HexString }

mscVrIpOspfExtLsdbSequence OBJECT-TYPE
   SYNTAX     Unsigned32 (0..4294967295)
   ACCESS     read-only
   STATUS     mandatory
   DESCRIPTION
     "A signed 32-bit integer, used to detect old and duplicate
      LSAs. The space of sequence numbers is linearly ordered. 
      The larger the sequence number, the more recent the 
      advertisement."
::= { mscVrIpOspfExtLsdbOperEntry 1 }

mscVrIpOspfExtLsdbAge OBJECT-TYPE
   SYNTAX     Gauge32 (0..3600)
   ACCESS     read-only
   STATUS     mandatory
   DESCRIPTION
     "The age of the Link State Advertisement in seconds."
::= { mscVrIpOspfExtLsdbOperEntry 2 }

mscVrIpOspfExtLsdbChecksum OBJECT-TYPE
   SYNTAX     Unsigned32 (0..4294967295)
   ACCESS     read-only
   STATUS     mandatory
   DESCRIPTION
     "The checksum of the complete contents of the 
      advertisement, excepting the age field. The checksum 
      used is the Fletcher checksum."
::= { mscVrIpOspfExtLsdbOperEntry 3 }

mscVrIpOspfExtLsdbAdvertisement OBJECT-TYPE
   SYNTAX     HexString (SIZE (1..36))
   ACCESS     read-only
   STATUS     mandatory
   DESCRIPTION
     "The entire LSA including its header."
::= { mscVrIpOspfExtLsdbOperEntry 4 }


-- Vr/<string> Ip Rip
-- This component represents the Routing Information Protocol for the IP.
-- There should be at least one RipInterface provisioned below a LogicalIf 
-- under an IpPort.

mscVrIpRip OBJECT IDENTIFIER ::= { mscVrIp 8 }



mscVrIpRipRowStatusTable OBJECT-TYPE
   SYNTAX     SEQUENCE OF MscVrIpRipRowStatusEntry
   ACCESS     not-accessible
   STATUS     mandatory
   DESCRIPTION
     "This entry controls the addition and deletion of 
      mscVrIpRip components."
::= { mscVrIpRip 1 }

mscVrIpRipRowStatusEntry OBJECT-TYPE
   SYNTAX     MscVrIpRipRowStatusEntry
   ACCESS     not-accessible
   STATUS     mandatory
   DESCRIPTION
     "A single entry in the table represents a single 
      mscVrIpRip component."
   INDEX {
      mscVrIndex,
      mscVrIpIndex,
      mscVrIpRipIndex }
::= { mscVrIpRipRowStatusTable 1 }

MscVrIpRipRowStatusEntry ::= SEQUENCE {
   mscVrIpRipRowStatus
      RowStatus,
   mscVrIpRipComponentName
      DisplayString,
   mscVrIpRipStorageType
      StorageType,
   mscVrIpRipIndex
      NonReplicated }

mscVrIpRipRowStatus OBJECT-TYPE
   SYNTAX     RowStatus 
   ACCESS     read-write
   STATUS     mandatory
   DESCRIPTION
     "This variable is used as the basis for SNMP naming of
      mscVrIpRip components.
      These components can be added and deleted."
::= { mscVrIpRipRowStatusEntry 1 }

mscVrIpRipComponentName OBJECT-TYPE
   SYNTAX     DisplayString 
   ACCESS     read-only
   STATUS     mandatory
   DESCRIPTION
     "This variable provides the component's string name for
      use with the ASCII Console Interface"
::= { mscVrIpRipRowStatusEntry 2 }

mscVrIpRipStorageType OBJECT-TYPE
   SYNTAX     StorageType 
   ACCESS     read-only
   STATUS     mandatory
   DESCRIPTION
     "This variable represents the storage type value for the
      mscVrIpRip tables."
::= { mscVrIpRipRowStatusEntry 4 }

mscVrIpRipIndex OBJECT-TYPE
   SYNTAX     NonReplicated 
   ACCESS     not-accessible
   STATUS     mandatory
   DESCRIPTION
     "This variable represents the index for the mscVrIpRip tables."
::= { mscVrIpRipRowStatusEntry 10 }

mscVrIpRipProvTable OBJECT-TYPE
   SYNTAX     SEQUENCE OF MscVrIpRipProvEntry
   ACCESS     not-accessible
   STATUS     mandatory
   DESCRIPTION
     "This group contains the provisionable attributes for the RIP component"
::= { mscVrIpRip 10 }

mscVrIpRipProvEntry OBJECT-TYPE
   SYNTAX     MscVrIpRipProvEntry
   ACCESS     not-accessible
   STATUS     mandatory
   DESCRIPTION
     "An entry in the mscVrIpRipProvTable."
   INDEX {
      mscVrIndex,
      mscVrIpIndex,
      mscVrIpRipIndex }
::= { mscVrIpRipProvTable 1 }

MscVrIpRipProvEntry ::= SEQUENCE {
   mscVrIpRipMigrateRip
      INTEGER,
   mscVrIpRipRfc1058MetricUsage
      INTEGER,
   mscVrIpRipGenerateDiscardRoute
      INTEGER,
   mscVrIpRipRedistributeIbgp
      INTEGER }

mscVrIpRipMigrateRip OBJECT-TYPE
   SYNTAX     INTEGER  {
                 enabled(1),
                 disabled(2) }
   ACCESS     read-write
   STATUS     mandatory
   DESCRIPTION
     "This attribute sets the preference level of OSPF-internal routes to be less 
      preferred than RIP. 
      Note:
      This parameter should only be used when starting migration of network 
      from RIP to OSPF. When ready to cutover to OSPF, set this attribute 
      value to disabled and run under normal preferences. All OSPF routers in 
      the Autonomous System should be running with migrateRip enabled or 
      with migrateRip disabled to prevent routing loops. It is important that 
      the changeover period from RIP to OSPF be performed quickly on all 
      OSPF routers so that no routing loops are formed. These routing loops 
      could be caused by conflicts in the internal RIP and OSPF databases."
   DEFVAL     { disabled }
::= { mscVrIpRipProvEntry 2 }

mscVrIpRipRfc1058MetricUsage OBJECT-TYPE
   SYNTAX     INTEGER  {
                 enabled(1),
                 disabled(2) }
   ACCESS     read-write
   STATUS     mandatory
   DESCRIPTION
     "This attribute determines the metric usage for this RIP instance.
      This flag is used to determine the way metrics are incremented.
      RFC1058 way :
      Sending Update: This is to use the metric for the route from the routing 
      table as the advertised metric to be sent for that route. Nothing is ever 
      added to this value from the sending side. The only special case 
      handling is that if the route being advertised is the network route of a 
      directly connectednetwork, the metric in the routing table will be zero. 
      Then the RipIf interface metric for the interface being advertised is used 
      as the advertise metric. If the interface being advertised is not a Rip 
      interface, then metric value of 1 is used.
      Receiving Update: Add receiving interface's RIP metric to the metric for 
      the route in the received advertisement and install the result in the 
      receiver's routing table as the metric for that route.
      Older way:
      Sending Updates: Add the out going interfaces rip metric to the metric 
      for a route in the routing table to form the metric to be advertised for 
      that route.
      Receiving Updates: The metric received in the advertisement for a route 
      is put directly in the routing table as the metric for that route.
      
      Note: It is recommended that, all the routers in this autonomous system 
      should be following the rfc1058 metric system.
      Setting this flag to disabled will have the effect of running the RIP with 
      old metric incrementing system."
   DEFVAL     { enabled }
::= { mscVrIpRipProvEntry 3 }

mscVrIpRipGenerateDiscardRoute OBJECT-TYPE
   SYNTAX     INTEGER  {
                 yes(1),
                 no(2) }
   ACCESS     read-write
   STATUS     mandatory
   DESCRIPTION
     "This attribute when set to yes will add network disacrd routes to the 
      routing and forwarding table for the subnetted interfaces that are running 
      RIP."
   DEFVAL     { yes }
::= { mscVrIpRipProvEntry 4 }

mscVrIpRipRedistributeIbgp OBJECT-TYPE
   SYNTAX     INTEGER  {
                 true(1),
                 false(2) }
   ACCESS     read-write
   STATUS     mandatory
   DESCRIPTION
     "This attribute specifies whether this Rip instance allows to exporting of 
      any routes learned from internal Bgp peers (IBGP) to Rip. If the value of 
      this attribute is true, and if an export policy is specified to distribute, 
      then Rip allows any IBGP routes to be distributed to Rip. If the value of 
      this attribute is false, Rip does not allow IBGP routes to be distributed to 
      Rip, even if an export policy is specified to distribute."
   DEFVAL     { false }
::= { mscVrIpRipProvEntry 5 }

mscVrIpRipStateTable OBJECT-TYPE
   SYNTAX     SEQUENCE OF MscVrIpRipStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscVrIpRip 11 }

mscVrIpRipStateEntry OBJECT-TYPE
   SYNTAX     MscVrIpRipStateEntry
   ACCESS     not-accessible
   STATUS     mandatory
   DESCRIPTION
     "An entry in the mscVrIpRipStateTable."
   INDEX {
      mscVrIndex,
      mscVrIpIndex,
      mscVrIpRipIndex }
::= { mscVrIpRipStateTable 1 }

MscVrIpRipStateEntry ::= SEQUENCE {
   mscVrIpRipAdminState
      INTEGER,
   mscVrIpRipOperationalState
      INTEGER,
   mscVrIpRipUsageState
      INTEGER }

mscVrIpRipAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscVrIpRipStateEntry 1 }

mscVrIpRipOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscVrIpRipStateEntry 2 }

mscVrIpRipUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscVrIpRipStateEntry 3 }

mscVrIpRipAdminControlTable OBJECT-TYPE
   SYNTAX     SEQUENCE OF MscVrIpRipAdminControlEntry
   ACCESS     not-accessible
   STATUS     mandatory
   DESCRIPTION
     "This group includes the Administrative Control attribute. This 
      attribute defines the current administrative state of this component."
::= { mscVrIpRip 12 }

mscVrIpRipAdminControlEntry OBJECT-TYPE
   SYNTAX     MscVrIpRipAdminControlEntry
   ACCESS     not-accessible
   STATUS     mandatory
   DESCRIPTION
     "An entry in the mscVrIpRipAdminControlTable."
   INDEX {
      mscVrIndex,
      mscVrIpIndex,
      mscVrIpRipIndex }
::= { mscVrIpRipAdminControlTable 1 }

MscVrIpRipAdminControlEntry ::= SEQUENCE {
   mscVrIpRipSnmpAdminStatus
      INTEGER }

mscVrIpRipSnmpAdminStatus OBJECT-TYPE
   SYNTAX     INTEGER  {
                 up(1),
                 down(2),
                 testing(3) }
   ACCESS     read-write
   STATUS     mandatory
   DESCRIPTION
     "The desired state of the interface. The up state indicates the 
      interface is operational and packet forwarding is allowed. The down 
      state indicates the interface is not operational and packet forwarding 
      is unavailable. The testing state indicates that no operational 
      packets can be passed."
   DEFVAL     { up }
::= { mscVrIpRipAdminControlEntry 1 }

mscVrIpRipOperStatusTable OBJECT-TYPE
   SYNTAX     SEQUENCE OF MscVrIpRipOperStatusEntry
   ACCESS     not-accessible
   STATUS     mandatory
   DESCRIPTION
     "This group includes the Operational Status attribute. This attribute 
      defines the current operational state of this component."
::= { mscVrIpRip 15 }

mscVrIpRipOperStatusEntry OBJECT-TYPE
   SYNTAX     MscVrIpRipOperStatusEntry
   ACCESS     not-accessible
   STATUS     mandatory
   DESCRIPTION
     "An entry in the mscVrIpRipOperStatusTable."
   INDEX {
      mscVrIndex,
      mscVrIpIndex,
      mscVrIpRipIndex }
::= { mscVrIpRipOperStatusTable 1 }

MscVrIpRipOperStatusEntry ::= SEQUENCE {
   mscVrIpRipSnmpOperStatus
      INTEGER }

mscVrIpRipSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscVrIpRipOperStatusEntry 1 }

mscVrIpRipOperTable OBJECT-TYPE
   SYNTAX     SEQUENCE OF MscVrIpRipOperEntry
   ACCESS     not-accessible
   STATUS     mandatory
   DESCRIPTION
     "This group defines a set of operational attributes belonging to the RIP 
      component. It corresponds to the rip2Globals table in the RIP-2 standard 
      MIB."
::= { mscVrIpRip 16 }

mscVrIpRipOperEntry OBJECT-TYPE
   SYNTAX     MscVrIpRipOperEntry
   ACCESS     not-accessible
   STATUS     mandatory
   DESCRIPTION
     "An entry in the mscVrIpRipOperTable."
   INDEX {
      mscVrIndex,
      mscVrIpIndex,
      mscVrIpRipIndex }
::= { mscVrIpRipOperTable 1 }

MscVrIpRipOperEntry ::= SEQUENCE {
   mscVrIpRipRouteChangesMade
      Counter32,
   mscVrIpRipQueryResponses
      Counter32 }

mscVrIpRipRouteChangesMade OBJECT-TYPE
   SYNTAX     Counter32 
   ACCESS     read-only
   STATUS     mandatory
   DESCRIPTION
     "This attribute counts the route changes made to the IP Route Database 
      by Rip. This does not include the refresh of the route's age."
::= { mscVrIpRipOperEntry 1 }

mscVrIpRipQueryResponses OBJECT-TYPE
   SYNTAX     Counter32 
   ACCESS     read-only
   STATUS     mandatory
   DESCRIPTION
     "This attribute counts the responses sent to RIP queries from other 
      systems."
::= { mscVrIpRipOperEntry 2 }


-- Vr/<string> Ip Rip Import/<Decimal> 
-- This component controls the functionality of Route Leaking. In other 
-- words, this component will determine what routes are used by RIP.

mscVrIpRipImport OBJECT IDENTIFIER ::= { mscVrIpRip 2 }



mscVrIpRipImportRowStatusTable OBJECT-TYPE
   SYNTAX     SEQUENCE OF MscVrIpRipImportRowStatusEntry
   ACCESS     not-accessible
   STATUS     mandatory
   DESCRIPTION
     "This entry controls the addition and deletion of 
      mscVrIpRipImport components."
::= { mscVrIpRipImport 1 }

mscVrIpRipImportRowStatusEntry OBJECT-TYPE
   SYNTAX     MscVrIpRipImportRowStatusEntry
   ACCESS     not-accessible
   STATUS     mandatory
   DESCRIPTION
     "A single entry in the table represents a single 
      mscVrIpRipImport component."
   INDEX {
      mscVrIndex,
      mscVrIpIndex,
      mscVrIpRipIndex,
      mscVrIpRipImportIndex }
::= { mscVrIpRipImportRowStatusTable 1 }

MscVrIpRipImportRowStatusEntry ::= SEQUENCE {
   mscVrIpRipImportRowStatus
      RowStatus,
   mscVrIpRipImportComponentName
      DisplayString,
   mscVrIpRipImportStorageType
      StorageType,
   mscVrIpRipImportIndex
      Integer32 }

mscVrIpRipImportRowStatus OBJECT-TYPE
   SYNTAX     RowStatus 
   ACCESS     read-write
   STATUS     mandatory
   DESCRIPTION
     "This variable is used as the basis for SNMP naming of
      mscVrIpRipImport components.
      These components can be added and deleted."
::= { mscVrIpRipImportRowStatusEntry 1 }

mscVrIpRipImportComponentName OBJECT-TYPE
   SYNTAX     DisplayString 
   ACCESS     read-only
   STATUS     mandatory
   DESCRIPTION
     "This variable provides the component's string name for
      use with the ASCII Console Interface"
::= { mscVrIpRipImportRowStatusEntry 2 }

mscVrIpRipImportStorageType OBJECT-TYPE
   SYNTAX     StorageType 
   ACCESS     read-only
   STATUS     mandatory
   DESCRIPTION
     "This variable represents the storage type value for the
      mscVrIpRipImport tables."
::= { mscVrIpRipImportRowStatusEntry 4 }

mscVrIpRipImportIndex OBJECT-TYPE
   SYNTAX     Integer32 (0..65535)
   ACCESS     not-accessible
   STATUS     mandatory
   DESCRIPTION
     "This variable represents the index for the mscVrIpRipImport tables."
::= { mscVrIpRipImportRowStatusEntry 10 }

mscVrIpRipImportProvTable OBJECT-TYPE
   SYNTAX     SEQUENCE OF MscVrIpRipImportProvEntry
   ACCESS     not-accessible
   STATUS     mandatory
   DESCRIPTION
     "This is the group of provisionable attributes for the XXXX Import 
      Subcomponent."
::= { mscVrIpRipImport 10 }

mscVrIpRipImportProvEntry OBJECT-TYPE
   SYNTAX     MscVrIpRipImportProvEntry
   ACCESS     not-accessible
   STATUS     mandatory
   DESCRIPTION
     "An entry in the mscVrIpRipImportProvTable."
   INDEX {
      mscVrIndex,
      mscVrIpIndex,
      mscVrIpRipIndex,
      mscVrIpRipImportIndex }
::= { mscVrIpRipImportProvTable 1 }

MscVrIpRipImportProvEntry ::= SEQUENCE {
   mscVrIpRipImportUsageFlag
      INTEGER,
   mscVrIpRipImportImportMetric
      Unsigned32,
   mscVrIpRipImportNeighbor
      IpAddress,
   mscVrIpRipImportInterface
      IpAddress }

mscVrIpRipImportUsageFlag OBJECT-TYPE
   SYNTAX     INTEGER  {
                 use(1),
                 ignore(2) }
   ACCESS     read-write
   STATUS     mandatory
   DESCRIPTION
     "This flag when set to ignore indicates the routes that are not used and if 
      set to use, indicates the routes which are used."
   DEFVAL     { use }
::= { mscVrIpRipImportProvEntry 1 }

mscVrIpRipImportImportMetric OBJECT-TYPE
   SYNTAX     Unsigned32 (0..16)
   ACCESS     read-write
   STATUS     mandatory
   DESCRIPTION
     "This attribute is used to override the default import metric for the RIP 
      protocol. This value is not used to select which routes to use or ignore, 
      rather it is the metric to be used in the routing table for the routes 
      imported for this import policy. A value of zero indicates that the metric 
      received in the update will be used."
   DEFVAL     { 0 }
::= { mscVrIpRipImportProvEntry 2 }

mscVrIpRipImportNeighbor OBJECT-TYPE
   SYNTAX     IpAddress 
   ACCESS     read-write
   STATUS     mandatory
   DESCRIPTION
     "This attribute indicates the IP Address of the neighbor this policy will 
      apply to."
   DEFVAL     { '00000000'H }  -- "0.0.0.0"
::= { mscVrIpRipImportProvEntry 3 }

mscVrIpRipImportInterface OBJECT-TYPE
   SYNTAX     IpAddress 
   ACCESS     read-write
   STATUS     mandatory
   DESCRIPTION
     "This attribute specifies the RIP interface to which this import policy 
      applies.
      The value of 0.0.0.0 implies any RIP interface on the virtual router; 
      otherwise the value of this attribute must match the interface address of 
      a LogicalIf that has a RipIf on the same virtual router."
   DEFVAL     { '00000000'H }  -- "0.0.0.0"
::= { mscVrIpRipImportProvEntry 4 }


-- Vr/<string> Ip Rip Import/<Decimal> NetworkList/<Decimal>
-- This component identifies a set of networks that this Import policy will 
-- apply to.

mscVrIpRipImportNet OBJECT IDENTIFIER ::= { mscVrIpRipImport 2 }



mscVrIpRipImportNetRowStatusTable OBJECT-TYPE
   SYNTAX     SEQUENCE OF MscVrIpRipImportNetRowStatusEntry
   ACCESS     not-accessible
   STATUS     mandatory
   DESCRIPTION
     "This entry controls the addition and deletion of 
      mscVrIpRipImportNet components."
::= { mscVrIpRipImportNet 1 }

mscVrIpRipImportNetRowStatusEntry OBJECT-TYPE
   SYNTAX     MscVrIpRipImportNetRowStatusEntry
   ACCESS     not-accessible
   STATUS     mandatory
   DESCRIPTION
     "A single entry in the table represents a single 
      mscVrIpRipImportNet component."
   INDEX {
      mscVrIndex,
      mscVrIpIndex,
      mscVrIpRipIndex,
      mscVrIpRipImportIndex,
      mscVrIpRipImportNetIndex }
::= { mscVrIpRipImportNetRowStatusTable 1 }

MscVrIpRipImportNetRowStatusEntry ::= SEQUENCE {
   mscVrIpRipImportNetRowStatus
      RowStatus,
   mscVrIpRipImportNetComponentName
      DisplayString,
   mscVrIpRipImportNetStorageType
      StorageType,
   mscVrIpRipImportNetIndex
      Integer32 }

mscVrIpRipImportNetRowStatus OBJECT-TYPE
   SYNTAX     RowStatus 
   ACCESS     read-write
   STATUS     mandatory
   DESCRIPTION
     "This variable is used as the basis for SNMP naming of
      mscVrIpRipImportNet components.
      These components can be added and deleted."
::= { mscVrIpRipImportNetRowStatusEntry 1 }

mscVrIpRipImportNetComponentName OBJECT-TYPE
   SYNTAX     DisplayString 
   ACCESS     read-only
   STATUS     mandatory
   DESCRIPTION
     "This variable provides the component's string name for
      use with the ASCII Console Interface"
::= { mscVrIpRipImportNetRowStatusEntry 2 }

mscVrIpRipImportNetStorageType OBJECT-TYPE
   SYNTAX     StorageType 
   ACCESS     read-only
   STATUS     mandatory
   DESCRIPTION
     "This variable represents the storage type value for the
      mscVrIpRipImportNet tables."
::= { mscVrIpRipImportNetRowStatusEntry 4 }

mscVrIpRipImportNetIndex OBJECT-TYPE
   SYNTAX     Integer32 (0..65535)
   ACCESS     not-accessible
   STATUS     mandatory
   DESCRIPTION
     "This variable represents the index for the mscVrIpRipImportNet tables."
::= { mscVrIpRipImportNetRowStatusEntry 10 }

mscVrIpRipImportNetProvTable OBJECT-TYPE
   SYNTAX     SEQUENCE OF MscVrIpRipImportNetProvEntry
   ACCESS     not-accessible
   STATUS     mandatory
   DESCRIPTION
     "This group contains attributes for the XXXX NetworkList component 
      for the Import Policy to be applied to"
::= { mscVrIpRipImportNet 10 }

mscVrIpRipImportNetProvEntry OBJECT-TYPE
   SYNTAX     MscVrIpRipImportNetProvEntry
   ACCESS     not-accessible
   STATUS     mandatory
   DESCRIPTION
     "An entry in the mscVrIpRipImportNetProvTable."
   INDEX {
      mscVrIndex,
      mscVrIpIndex,
      mscVrIpRipIndex,
      mscVrIpRipImportIndex,
      mscVrIpRipImportNetIndex }
::= { mscVrIpRipImportNetProvTable 1 }

MscVrIpRipImportNetProvEntry ::= SEQUENCE {
   mscVrIpRipImportNetIpAddress
      IpAddress,
   mscVrIpRipImportNetIpMask
      IpAddress }

mscVrIpRipImportNetIpAddress OBJECT-TYPE
   SYNTAX     IpAddress 
   ACCESS     read-write
   STATUS     mandatory
   DESCRIPTION
     "This attribute specifies the IP address that needs to be matched against in 
      this network list for the Import Policy to be applied to."
::= { mscVrIpRipImportNetProvEntry 1 }

mscVrIpRipImportNetIpMask OBJECT-TYPE
   SYNTAX     IpAddress 
   ACCESS     read-write
   STATUS     mandatory
   DESCRIPTION
     "This attribute specifies the IP mask for the attribute ipAddress."
::= { mscVrIpRipImportNetProvEntry 2 }


-- Vr/<string> Ip Rip Export/<Decimal> 
-- Each instance of this component specifies a RIP export policy. A RIP 
-- export policy is used to decide if a route in the IP forwarding table 
-- should be blocked or advertised as a RIP route on one or all RIP 
-- interfaces of the virtual router.
-- Passport IP RIP by default advertises all local routes and all RIP learned 
-- routes to all RIP interfaces based on the metric in the IP forwarding 
-- table.

mscVrIpRipExport OBJECT IDENTIFIER ::= { mscVrIpRip 3 }



mscVrIpRipExportRowStatusTable OBJECT-TYPE
   SYNTAX     SEQUENCE OF MscVrIpRipExportRowStatusEntry
   ACCESS     not-accessible
   STATUS     mandatory
   DESCRIPTION
     "This entry controls the addition and deletion of 
      mscVrIpRipExport components."
::= { mscVrIpRipExport 1 }

mscVrIpRipExportRowStatusEntry OBJECT-TYPE
   SYNTAX     MscVrIpRipExportRowStatusEntry
   ACCESS     not-accessible
   STATUS     mandatory
   DESCRIPTION
     "A single entry in the table represents a single 
      mscVrIpRipExport component."
   INDEX {
      mscVrIndex,
      mscVrIpIndex,
      mscVrIpRipIndex,
      mscVrIpRipExportIndex }
::= { mscVrIpRipExportRowStatusTable 1 }

MscVrIpRipExportRowStatusEntry ::= SEQUENCE {
   mscVrIpRipExportRowStatus
      RowStatus,
   mscVrIpRipExportComponentName
      DisplayString,
   mscVrIpRipExportStorageType
      StorageType,
   mscVrIpRipExportIndex
      Integer32 }

mscVrIpRipExportRowStatus OBJECT-TYPE
   SYNTAX     RowStatus 
   ACCESS     read-write
   STATUS     mandatory
   DESCRIPTION
     "This variable is used as the basis for SNMP naming of
      mscVrIpRipExport components.
      These components can be added and deleted."
::= { mscVrIpRipExportRowStatusEntry 1 }

mscVrIpRipExportComponentName OBJECT-TYPE
   SYNTAX     DisplayString 
   ACCESS     read-only
   STATUS     mandatory
   DESCRIPTION
     "This variable provides the component's string name for
      use with the ASCII Console Interface"
::= { mscVrIpRipExportRowStatusEntry 2 }

mscVrIpRipExportStorageType OBJECT-TYPE
   SYNTAX     StorageType 
   ACCESS     read-only
   STATUS     mandatory
   DESCRIPTION
     "This variable represents the storage type value for the
      mscVrIpRipExport tables."
::= { mscVrIpRipExportRowStatusEntry 4 }

mscVrIpRipExportIndex OBJECT-TYPE
   SYNTAX     Integer32 (0..65535)
   ACCESS     not-accessible
   STATUS     mandatory
   DESCRIPTION
     "This variable represents the index for the mscVrIpRipExport tables."
::= { mscVrIpRipExportRowStatusEntry 10 }

mscVrIpRipExportProvTable OBJECT-TYPE
   SYNTAX     SEQUENCE OF MscVrIpRipExportProvEntry
   ACCESS     not-accessible
   STATUS     mandatory
   DESCRIPTION
     "This group contains all the provisioned attributes for the Export 
      component."
::= { mscVrIpRipExport 10 }

mscVrIpRipExportProvEntry OBJECT-TYPE
   SYNTAX     MscVrIpRipExportProvEntry
   ACCESS     not-accessible
   STATUS     mandatory
   DESCRIPTION
     "An entry in the mscVrIpRipExportProvTable."
   INDEX {
      mscVrIndex,
      mscVrIpIndex,
      mscVrIpRipIndex,
      mscVrIpRipExportIndex }
::= { mscVrIpRipExportProvTable 1 }

MscVrIpRipExportProvEntry ::= SEQUENCE {
   mscVrIpRipExportAdvertiseStatus
      INTEGER,
   mscVrIpRipExportExportMetric
      Unsigned32,
   mscVrIpRipExportProtocol
      INTEGER,
   mscVrIpRipExportRipInterface
      IpAddress,
   mscVrIpRipExportEgpAsId
      Unsigned32,
   mscVrIpRipExportOspfTag
      Unsigned32,
   mscVrIpRipExportOutInterface
      IpAddress,
   mscVrIpRipExportBgpAsId
      Unsigned32 }

mscVrIpRipExportAdvertiseStatus OBJECT-TYPE
   SYNTAX     INTEGER  {
                 send(1),
                 block(2) }
   ACCESS     read-write
   STATUS     mandatory
   DESCRIPTION
     "This attribute specifies if the routes that match this export policy are 
      advertised (send) or not advertised (block)."
   DEFVAL     { send }
::= { mscVrIpRipExportProvEntry 1 }

mscVrIpRipExportExportMetric OBJECT-TYPE
   SYNTAX     Unsigned32 (0..16)
   ACCESS     read-write
   STATUS     mandatory
   DESCRIPTION
     "This attribute specifies the metric to be used on the routes being 
      exported as a result of matching this export policy.
      If the attribute advertiseStatus is set to block, then the value of 
      exportMetric is ignored. The exportMetric value is not used to select 
      which routes to block or send, but rather the metric value advertised for 
      the routes.
      A value of 0 indicates that the metric associated with the route in the 
      forwarding table is used."
   DEFVAL     { 0 }
::= { mscVrIpRipExportProvEntry 2 }

mscVrIpRipExportProtocol OBJECT-TYPE
   SYNTAX     INTEGER  {
                 all(1),
                 egp(2),
                 rip(3),
                 ospfInternal(4),
                 ospfExternal(5),
                 staticLocal(6),
                 staticRemote(7),
                 bgpInternal(8),
                 bgpExternal(9) }
   ACCESS     read-write
   STATUS     mandatory
   DESCRIPTION
     "This attribute specifies the routes to which this export policy applies 
      based on the routing protocol of how the routes are learned. If it is set to 
      all, this export policy applies to all routes except internal BGP routes in 
      the forwarding table."
   DEFVAL     { all }
::= { mscVrIpRipExportProvEntry 3 }

mscVrIpRipExportRipInterface OBJECT-TYPE
   SYNTAX     IpAddress 
   ACCESS     read-write
   STATUS     mandatory
   DESCRIPTION
     "This attribute specifies the RIP learned routes to which this export policy 
      applies, based on the RIP interface from which the routes are learned.
      This attribute can only be non zero when the protocol is set to rip. The 
      value of 0.0.0.0 implies any RIP interface on the same virtual router; 
      otherwise the value of this attribute must match the interface address of 
      a LogicalIf that has a RipIf on the same virtual router.
      DESCRIPTION"
   DEFVAL     { '00000000'H }  -- "0.0.0.0"
::= { mscVrIpRipExportProvEntry 4 }

mscVrIpRipExportEgpAsId OBJECT-TYPE
   SYNTAX     Unsigned32 (0..65536)
   ACCESS     read-write
   STATUS     mandatory
   DESCRIPTION
     "This attribute specifies the EGP learned routes to which this export 
      policy applies, based on the EGP autonomous system identifier of which 
      the routes are learned from.
      This attribute can only be non zero when protocol is set to egp. The 
      value of 0 implies any EGP autonomous system; otherwise the value of 
      this attribute must match the asId of an EGP neighbor on the same 
      virtual router."
   DEFVAL     { 0 }
::= { mscVrIpRipExportProvEntry 5 }

mscVrIpRipExportOspfTag OBJECT-TYPE
   SYNTAX     Unsigned32 (0..4294967295)
   ACCESS     read-write
   STATUS     mandatory
   DESCRIPTION
     "This attribute specifies the OSPF learned external routes to which this 
      export policy applies, based on the learned OSPF tag of the routes.
      This attribute can only be set to a non default value when protocol is set 
      to ospfExternal. The default value of 4294967295 implies any tag."
   DEFVAL     { 4294967295 }
::= { mscVrIpRipExportProvEntry 6 }

mscVrIpRipExportOutInterface OBJECT-TYPE
   SYNTAX     IpAddress 
   ACCESS     read-write
   STATUS     mandatory
   DESCRIPTION
     "This attribute specifies the RIP interface on the virtual router which 
      routes are exported onto as a result of matching this export policy.
      If the attribute advertiseStatus is set to block, then the value of 
      outInterface is ignored. The outInterface value is not used to select 
      which routes to block or send, but rather where to export the routes.
      A value of 0.0.0.0 indicates that the routes are exported to all RIP 
      interfaces on the virtual router. Otherwise, the value of this attribute 
      must match the interface address of a LogicalIf that has a RipIf on the 
      same virtual router."
   DEFVAL     { '00000000'H }  -- "0.0.0.0"
::= { mscVrIpRipExportProvEntry 7 }

mscVrIpRipExportBgpAsId OBJECT-TYPE
   SYNTAX     Unsigned32 (0..65535)
   ACCESS     read-write
   STATUS     mandatory
   DESCRIPTION
     "This key attribute specifies the BGP AS from which the routes are 
      learned. This key will be used only when the protocol is set to 
      bgpExternal. bgpAsId of 0 matches all BGP ASs."
   DEFVAL     { 0 }
::= { mscVrIpRipExportProvEntry 8 }


-- Vr/<string> Ip Rip Export/<Decimal> NetworkList/<Decimal>
-- This component identifies a set of attributes when matched determines 
-- the export policy applied. 

mscVrIpRipExportNet OBJECT IDENTIFIER ::= { mscVrIpRipExport 2 }



mscVrIpRipExportNetRowStatusTable OBJECT-TYPE
   SYNTAX     SEQUENCE OF MscVrIpRipExportNetRowStatusEntry
   ACCESS     not-accessible
   STATUS     mandatory
   DESCRIPTION
     "This entry controls the addition and deletion of 
      mscVrIpRipExportNet components."
::= { mscVrIpRipExportNet 1 }

mscVrIpRipExportNetRowStatusEntry OBJECT-TYPE
   SYNTAX     MscVrIpRipExportNetRowStatusEntry
   ACCESS     not-accessible
   STATUS     mandatory
   DESCRIPTION
     "A single entry in the table represents a single 
      mscVrIpRipExportNet component."
   INDEX {
      mscVrIndex,
      mscVrIpIndex,
      mscVrIpRipIndex,
      mscVrIpRipExportIndex,
      mscVrIpRipExportNetIndex }
::= { mscVrIpRipExportNetRowStatusTable 1 }

MscVrIpRipExportNetRowStatusEntry ::= SEQUENCE {
   mscVrIpRipExportNetRowStatus
      RowStatus,
   mscVrIpRipExportNetComponentName
      DisplayString,
   mscVrIpRipExportNetStorageType
      StorageType,
   mscVrIpRipExportNetIndex
      Integer32 }

mscVrIpRipExportNetRowStatus OBJECT-TYPE
   SYNTAX     RowStatus 
   ACCESS     read-write
   STATUS     mandatory
   DESCRIPTION
     "This variable is used as the basis for SNMP naming of
      mscVrIpRipExportNet components.
      These components can be added and deleted."
::= { mscVrIpRipExportNetRowStatusEntry 1 }

mscVrIpRipExportNetComponentName OBJECT-TYPE
   SYNTAX     DisplayString 
   ACCESS     read-only
   STATUS     mandatory
   DESCRIPTION
     "This variable provides the component's string name for
      use with the ASCII Console Interface"
::= { mscVrIpRipExportNetRowStatusEntry 2 }

mscVrIpRipExportNetStorageType OBJECT-TYPE
   SYNTAX     StorageType 
   ACCESS     read-only
   STATUS     mandatory
   DESCRIPTION
     "This variable represents the storage type value for the
      mscVrIpRipExportNet tables."
::= { mscVrIpRipExportNetRowStatusEntry 4 }

mscVrIpRipExportNetIndex OBJECT-TYPE
   SYNTAX     Integer32 (0..65535)
   ACCESS     not-accessible
   STATUS     mandatory
   DESCRIPTION
     "This variable represents the index for the mscVrIpRipExportNet tables."
::= { mscVrIpRipExportNetRowStatusEntry 10 }

mscVrIpRipExportNetProvTable OBJECT-TYPE
   SYNTAX     SEQUENCE OF MscVrIpRipExportNetProvEntry
   ACCESS     not-accessible
   STATUS     mandatory
   DESCRIPTION
     "This group identifies the set of Provisionable attributes for the 
      ExportNetworkList component."
::= { mscVrIpRipExportNet 10 }

mscVrIpRipExportNetProvEntry OBJECT-TYPE
   SYNTAX     MscVrIpRipExportNetProvEntry
   ACCESS     not-accessible
   STATUS     mandatory
   DESCRIPTION
     "An entry in the mscVrIpRipExportNetProvTable."
   INDEX {
      mscVrIndex,
      mscVrIpIndex,
      mscVrIpRipIndex,
      mscVrIpRipExportIndex,
      mscVrIpRipExportNetIndex }
::= { mscVrIpRipExportNetProvTable 1 }

MscVrIpRipExportNetProvEntry ::= SEQUENCE {
   mscVrIpRipExportNetIpAddress
      IpAddress,
   mscVrIpRipExportNetIpMask
      IpAddress }

mscVrIpRipExportNetIpAddress OBJECT-TYPE
   SYNTAX     IpAddress 
   ACCESS     read-write
   STATUS     mandatory
   DESCRIPTION
     "This attribute identifies the 32 bit IP address to match against."
::= { mscVrIpRipExportNetProvEntry 1 }

mscVrIpRipExportNetIpMask OBJECT-TYPE
   SYNTAX     IpAddress 
   ACCESS     read-write
   STATUS     mandatory
   DESCRIPTION
     "This attribute is the IP Mask to be used with the IP Address to match 
      against."
::= { mscVrIpRipExportNetProvEntry 2 }


-- Vr/<string> Ip Static
-- The Static component is used to configure addition, deletion and 
-- modification of static routing information.

mscVrIpStatic OBJECT IDENTIFIER ::= { mscVrIp 9 }



mscVrIpStaticRowStatusTable OBJECT-TYPE
   SYNTAX     SEQUENCE OF MscVrIpStaticRowStatusEntry
   ACCESS     not-accessible
   STATUS     mandatory
   DESCRIPTION
     "This entry controls the addition and deletion of 
      mscVrIpStatic components."
::= { mscVrIpStatic 1 }

mscVrIpStaticRowStatusEntry OBJECT-TYPE
   SYNTAX     MscVrIpStaticRowStatusEntry
   ACCESS     not-accessible
   STATUS     mandatory
   DESCRIPTION
     "A single entry in the table represents a single 
      mscVrIpStatic component."
   INDEX {
      mscVrIndex,
      mscVrIpIndex,
      mscVrIpStaticIndex }
::= { mscVrIpStaticRowStatusTable 1 }

MscVrIpStaticRowStatusEntry ::= SEQUENCE {
   mscVrIpStaticRowStatus
      RowStatus,
   mscVrIpStaticComponentName
      DisplayString,
   mscVrIpStaticStorageType
      StorageType,
   mscVrIpStaticIndex
      NonReplicated }

mscVrIpStaticRowStatus OBJECT-TYPE
   SYNTAX     RowStatus 
   ACCESS     read-write
   STATUS     mandatory
   DESCRIPTION
     "This variable is used as the basis for SNMP naming of
      mscVrIpStatic components.
      These components can be added and deleted."
::= { mscVrIpStaticRowStatusEntry 1 }

mscVrIpStaticComponentName OBJECT-TYPE
   SYNTAX     DisplayString 
   ACCESS     read-only
   STATUS     mandatory
   DESCRIPTION
     "This variable provides the component's string name for
      use with the ASCII Console Interface"
::= { mscVrIpStaticRowStatusEntry 2 }

mscVrIpStaticStorageType OBJECT-TYPE
   SYNTAX     StorageType 
   ACCESS     read-only
   STATUS     mandatory
   DESCRIPTION
     "This variable represents the storage type value for the
      mscVrIpStatic tables."
::= { mscVrIpStaticRowStatusEntry 4 }

mscVrIpStaticIndex OBJECT-TYPE
   SYNTAX     NonReplicated 
   ACCESS     not-accessible
   STATUS     mandatory
   DESCRIPTION
     "This variable represents the index for the mscVrIpStatic tables."
::= { mscVrIpStaticRowStatusEntry 10 }

mscVrIpStaticStateTable OBJECT-TYPE
   SYNTAX     SEQUENCE OF MscVrIpStaticStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscVrIpStatic 10 }

mscVrIpStaticStateEntry OBJECT-TYPE
   SYNTAX     MscVrIpStaticStateEntry
   ACCESS     not-accessible
   STATUS     mandatory
   DESCRIPTION
     "An entry in the mscVrIpStaticStateTable."
   INDEX {
      mscVrIndex,
      mscVrIpIndex,
      mscVrIpStaticIndex }
::= { mscVrIpStaticStateTable 1 }

MscVrIpStaticStateEntry ::= SEQUENCE {
   mscVrIpStaticAdminState
      INTEGER,
   mscVrIpStaticOperationalState
      INTEGER,
   mscVrIpStaticUsageState
      INTEGER }

mscVrIpStaticAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscVrIpStaticStateEntry 1 }

mscVrIpStaticOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscVrIpStaticStateEntry 2 }

mscVrIpStaticUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscVrIpStaticStateEntry 3 }


-- Vr/<string> Ip Static RouteEntry/<Ip Address>, <Ip Address>, 
-- <Decimal>
-- This component describes the IP static routes.
-- 
-- For a RouteEntry to be valid, there should be at least one NextHop 
-- provisioned. Up to three NextHops can be provisioned for each instance 
-- of a RouteEntry. 
-- 
-- The value of index destMask should be contiguous.
-- 
-- Only the value zero is supported. Zero will be substituted for any value 
-- that is entered.

mscVrIpStaticRoute OBJECT IDENTIFIER ::= { mscVrIpStatic 2 }



mscVrIpStaticRouteRowStatusTable OBJECT-TYPE
   SYNTAX     SEQUENCE OF MscVrIpStaticRouteRowStatusEntry
   ACCESS     not-accessible
   STATUS     mandatory
   DESCRIPTION
     "This entry controls the addition and deletion of 
      mscVrIpStaticRoute components."
::= { mscVrIpStaticRoute 1 }

mscVrIpStaticRouteRowStatusEntry OBJECT-TYPE
   SYNTAX     MscVrIpStaticRouteRowStatusEntry
   ACCESS     not-accessible
   STATUS     mandatory
   DESCRIPTION
     "A single entry in the table represents a single 
      mscVrIpStaticRoute component."
   INDEX {
      mscVrIndex,
      mscVrIpIndex,
      mscVrIpStaticIndex,
      mscVrIpStaticRouteDestAddressIndex,
      mscVrIpStaticRouteDestMaskIndex,
      mscVrIpStaticRouteTypeOfServiceIndex }
::= { mscVrIpStaticRouteRowStatusTable 1 }

MscVrIpStaticRouteRowStatusEntry ::= SEQUENCE {
   mscVrIpStaticRouteRowStatus
      RowStatus,
   mscVrIpStaticRouteComponentName
      DisplayString,
   mscVrIpStaticRouteStorageType
      StorageType,
   mscVrIpStaticRouteDestAddressIndex
      IpAddress,
   mscVrIpStaticRouteDestMaskIndex
      IpAddress,
   mscVrIpStaticRouteTypeOfServiceIndex
      Integer32 }

mscVrIpStaticRouteRowStatus OBJECT-TYPE
   SYNTAX     RowStatus 
   ACCESS     read-write
   STATUS     mandatory
   DESCRIPTION
     "This variable is used as the basis for SNMP naming of
      mscVrIpStaticRoute components.
      These components can be added and deleted."
::= { mscVrIpStaticRouteRowStatusEntry 1 }

mscVrIpStaticRouteComponentName OBJECT-TYPE
   SYNTAX     DisplayString 
   ACCESS     read-only
   STATUS     mandatory
   DESCRIPTION
     "This variable provides the component's string name for
      use with the ASCII Console Interface"
::= { mscVrIpStaticRouteRowStatusEntry 2 }

mscVrIpStaticRouteStorageType OBJECT-TYPE
   SYNTAX     StorageType 
   ACCESS     read-only
   STATUS     mandatory
   DESCRIPTION
     "This variable represents the storage type value for the
      mscVrIpStaticRoute tables."
::= { mscVrIpStaticRouteRowStatusEntry 4 }

mscVrIpStaticRouteDestAddressIndex OBJECT-TYPE
   SYNTAX     IpAddress 
   ACCESS     not-accessible
   STATUS     mandatory
   DESCRIPTION
     "This variable represents an index for the mscVrIpStaticRoute tables."
::= { mscVrIpStaticRouteRowStatusEntry 10 }

mscVrIpStaticRouteDestMaskIndex OBJECT-TYPE
   SYNTAX     IpAddress 
   ACCESS     not-accessible
   STATUS     mandatory
   DESCRIPTION
     "This variable represents an index for the mscVrIpStaticRoute tables."
::= { mscVrIpStaticRouteRowStatusEntry 11 }

mscVrIpStaticRouteTypeOfServiceIndex OBJECT-TYPE
   SYNTAX     Integer32 (0..0)
   ACCESS     not-accessible
   STATUS     mandatory
   DESCRIPTION
     "This variable represents an index for the mscVrIpStaticRoute tables."
::= { mscVrIpStaticRouteRowStatusEntry 12 }

mscVrIpStaticRouteProvTable OBJECT-TYPE
   SYNTAX     SEQUENCE OF MscVrIpStaticRouteProvEntry
   ACCESS     not-accessible
   STATUS     mandatory
   DESCRIPTION
     "This group contains a provisionable set of attributes for the static route 
      entry component."
::= { mscVrIpStaticRoute 10 }

mscVrIpStaticRouteProvEntry OBJECT-TYPE
   SYNTAX     MscVrIpStaticRouteProvEntry
   ACCESS     not-accessible
   STATUS     mandatory
   DESCRIPTION
     "An entry in the mscVrIpStaticRouteProvTable."
   INDEX {
      mscVrIndex,
      mscVrIpIndex,
      mscVrIpStaticIndex,
      mscVrIpStaticRouteDestAddressIndex,
      mscVrIpStaticRouteDestMaskIndex,
      mscVrIpStaticRouteTypeOfServiceIndex }
::= { mscVrIpStaticRouteProvTable 1 }

MscVrIpStaticRouteProvEntry ::= SEQUENCE {
   mscVrIpStaticRoutePreferredOver
      INTEGER }

mscVrIpStaticRoutePreferredOver OBJECT-TYPE
   SYNTAX     INTEGER  {
                 intOspf(5),
                 extOspf(72) }
   ACCESS     read-write
   STATUS     mandatory
   DESCRIPTION
     "This attribute indicates the preference of the static route in comparison 
      with the OSPF route. intOspf means that the static route is chosen over 
      the OSPF internal route, while extOspf means that the OSPF internal 
      route is chosen over the static route. The default static route preference 
      is set to extOspf ."
   DEFVAL     { extOspf }
::= { mscVrIpStaticRouteProvEntry 12 }


-- Vr/<string> Ip Static Route/<Ip Address>,<Ip Address>,<Decimal> 
-- NextHop/<Ip Address>
-- This component provides the destination Ip address of the NextHop 
-- (some times referred to as the Gateway). 
-- 
-- For a RouteEntry to be valid, there should be at least one NextHop 
-- provisioned. Up to three NextHops can be provisioned for each instance 
-- of a RouteEntry.
-- 
-- Each provisioned NextHop address should belong to a valid subnet.
-- A valid subnet for this IP entity can be provisioned as a logicalIf Entry 
-- under an IpPort.

mscVrIpStaticRouteNh OBJECT IDENTIFIER ::= { mscVrIpStaticRoute 2 }



mscVrIpStaticRouteNhRowStatusTable OBJECT-TYPE
   SYNTAX     SEQUENCE OF MscVrIpStaticRouteNhRowStatusEntry
   ACCESS     not-accessible
   STATUS     mandatory
   DESCRIPTION
     "This entry controls the addition and deletion of 
      mscVrIpStaticRouteNh components."
::= { mscVrIpStaticRouteNh 1 }

mscVrIpStaticRouteNhRowStatusEntry OBJECT-TYPE
   SYNTAX     MscVrIpStaticRouteNhRowStatusEntry
   ACCESS     not-accessible
   STATUS     mandatory
   DESCRIPTION
     "A single entry in the table represents a single 
      mscVrIpStaticRouteNh component."
   INDEX {
      mscVrIndex,
      mscVrIpIndex,
      mscVrIpStaticIndex,
      mscVrIpStaticRouteDestAddressIndex,
      mscVrIpStaticRouteDestMaskIndex,
      mscVrIpStaticRouteTypeOfServiceIndex,
      mscVrIpStaticRouteNhIndex }
::= { mscVrIpStaticRouteNhRowStatusTable 1 }

MscVrIpStaticRouteNhRowStatusEntry ::= SEQUENCE {
   mscVrIpStaticRouteNhRowStatus
      RowStatus,
   mscVrIpStaticRouteNhComponentName
      DisplayString,
   mscVrIpStaticRouteNhStorageType
      StorageType,
   mscVrIpStaticRouteNhIndex
      IpAddress }

mscVrIpStaticRouteNhRowStatus OBJECT-TYPE
   SYNTAX     RowStatus 
   ACCESS     read-write
   STATUS     mandatory
   DESCRIPTION
     "This variable is used as the basis for SNMP naming of
      mscVrIpStaticRouteNh components.
      These components can be added and deleted."
::= { mscVrIpStaticRouteNhRowStatusEntry 1 }

mscVrIpStaticRouteNhComponentName OBJECT-TYPE
   SYNTAX     DisplayString 
   ACCESS     read-only
   STATUS     mandatory
   DESCRIPTION
     "This variable provides the component's string name for
      use with the ASCII Console Interface"
::= { mscVrIpStaticRouteNhRowStatusEntry 2 }

mscVrIpStaticRouteNhStorageType OBJECT-TYPE
   SYNTAX     StorageType 
   ACCESS     read-only
   STATUS     mandatory
   DESCRIPTION
     "This variable represents the storage type value for the
      mscVrIpStaticRouteNh tables."
::= { mscVrIpStaticRouteNhRowStatusEntry 4 }

mscVrIpStaticRouteNhIndex OBJECT-TYPE
   SYNTAX     IpAddress 
   ACCESS     not-accessible
   STATUS     mandatory
   DESCRIPTION
     "This variable represents the index for the mscVrIpStaticRouteNh tables."
::= { mscVrIpStaticRouteNhRowStatusEntry 10 }

mscVrIpStaticRouteNhProvTable OBJECT-TYPE
   SYNTAX     SEQUENCE OF MscVrIpStaticRouteNhProvEntry
   ACCESS     not-accessible
   STATUS     mandatory
   DESCRIPTION
     "This group contains a provisionable set of attributes for the Static 
      RouteEntry NextHop component."
::= { mscVrIpStaticRouteNh 10 }

mscVrIpStaticRouteNhProvEntry OBJECT-TYPE
   SYNTAX     MscVrIpStaticRouteNhProvEntry
   ACCESS     not-accessible
   STATUS     mandatory
   DESCRIPTION
     "An entry in the mscVrIpStaticRouteNhProvTable."
   INDEX {
      mscVrIndex,
      mscVrIpIndex,
      mscVrIpStaticIndex,
      mscVrIpStaticRouteDestAddressIndex,
      mscVrIpStaticRouteDestMaskIndex,
      mscVrIpStaticRouteTypeOfServiceIndex,
      mscVrIpStaticRouteNhIndex }
::= { mscVrIpStaticRouteNhProvTable 1 }

MscVrIpStaticRouteNhProvEntry ::= SEQUENCE {
   mscVrIpStaticRouteNhMetric
      INTEGER }

mscVrIpStaticRouteNhMetric OBJECT-TYPE
   SYNTAX     INTEGER (-1..65535)
   ACCESS     read-write
   STATUS     mandatory
   DESCRIPTION
     "This attribute specifies the primary routing metric for this NextHop."
   DEFVAL     { 1 }
::= { mscVrIpStaticRouteNhProvEntry 1 }


-- Vr/<string> Ip Static DiscardRouteEntry/<Ip Address>,<Ip Address>
-- This table identifies invalid martian networks. Forwarding of packets to 
-- the network address indicated by this entry will be discarded. 

mscVrIpStaticDiscard OBJECT IDENTIFIER ::= { mscVrIpStatic 3 }



mscVrIpStaticDiscardRowStatusTable OBJECT-TYPE
   SYNTAX     SEQUENCE OF MscVrIpStaticDiscardRowStatusEntry
   ACCESS     not-accessible
   STATUS     mandatory
   DESCRIPTION
     "This entry controls the addition and deletion of 
      mscVrIpStaticDiscard components."
::= { mscVrIpStaticDiscard 1 }

mscVrIpStaticDiscardRowStatusEntry OBJECT-TYPE
   SYNTAX     MscVrIpStaticDiscardRowStatusEntry
   ACCESS     not-accessible
   STATUS     mandatory
   DESCRIPTION
     "A single entry in the table represents a single 
      mscVrIpStaticDiscard component."
   INDEX {
      mscVrIndex,
      mscVrIpIndex,
      mscVrIpStaticIndex,
      mscVrIpStaticDiscardDestAddressIndex,
      mscVrIpStaticDiscardDestMaskIndex }
::= { mscVrIpStaticDiscardRowStatusTable 1 }

MscVrIpStaticDiscardRowStatusEntry ::= SEQUENCE {
   mscVrIpStaticDiscardRowStatus
      RowStatus,
   mscVrIpStaticDiscardComponentName
      DisplayString,
   mscVrIpStaticDiscardStorageType
      StorageType,
   mscVrIpStaticDiscardDestAddressIndex
      IpAddress,
   mscVrIpStaticDiscardDestMaskIndex
      IpAddress }

mscVrIpStaticDiscardRowStatus OBJECT-TYPE
   SYNTAX     RowStatus 
   ACCESS     read-write
   STATUS     mandatory
   DESCRIPTION
     "This variable is used as the basis for SNMP naming of
      mscVrIpStaticDiscard components.
      These components can be added and deleted."
::= { mscVrIpStaticDiscardRowStatusEntry 1 }

mscVrIpStaticDiscardComponentName OBJECT-TYPE
   SYNTAX     DisplayString 
   ACCESS     read-only
   STATUS     mandatory
   DESCRIPTION
     "This variable provides the component's string name for
      use with the ASCII Console Interface"
::= { mscVrIpStaticDiscardRowStatusEntry 2 }

mscVrIpStaticDiscardStorageType OBJECT-TYPE
   SYNTAX     StorageType 
   ACCESS     read-only
   STATUS     mandatory
   DESCRIPTION
     "This variable represents the storage type value for the
      mscVrIpStaticDiscard tables."
::= { mscVrIpStaticDiscardRowStatusEntry 4 }

mscVrIpStaticDiscardDestAddressIndex OBJECT-TYPE
   SYNTAX     IpAddress 
   ACCESS     not-accessible
   STATUS     mandatory
   DESCRIPTION
     "This variable represents an index for the mscVrIpStaticDiscard tables."
::= { mscVrIpStaticDiscardRowStatusEntry 10 }

mscVrIpStaticDiscardDestMaskIndex OBJECT-TYPE
   SYNTAX     IpAddress 
   ACCESS     not-accessible
   STATUS     mandatory
   DESCRIPTION
     "This variable represents an index for the mscVrIpStaticDiscard tables."
::= { mscVrIpStaticDiscardRowStatusEntry 11 }


-- Vr/<string Ip NetSentry 
-- NetSentry defines a set of filters which are compiled by the 
-- NetSentry process to be applied to all IP packets. IP packets can 
-- be filtered based on IP address and netmask combinations.

mscVrIpNs OBJECT IDENTIFIER ::= { mscVrIp 10 }



mscVrIpNsRowStatusTable OBJECT-TYPE
   SYNTAX     SEQUENCE OF MscVrIpNsRowStatusEntry
   ACCESS     not-accessible
   STATUS     mandatory
   DESCRIPTION
     "This entry controls the addition and deletion of 
      mscVrIpNs components."
::= { mscVrIpNs 1 }

mscVrIpNsRowStatusEntry OBJECT-TYPE
   SYNTAX     MscVrIpNsRowStatusEntry
   ACCESS     not-accessible
   STATUS     mandatory
   DESCRIPTION
     "A single entry in the table represents a single 
      mscVrIpNs component."
   INDEX {
      mscVrIndex,
      mscVrIpIndex,
      mscVrIpNsIndex }
::= { mscVrIpNsRowStatusTable 1 }

MscVrIpNsRowStatusEntry ::= SEQUENCE {
   mscVrIpNsRowStatus
      RowStatus,
   mscVrIpNsComponentName
      DisplayString,
   mscVrIpNsStorageType
      StorageType,
   mscVrIpNsIndex
      NonReplicated }

mscVrIpNsRowStatus OBJECT-TYPE
   SYNTAX     RowStatus 
   ACCESS     read-write
   STATUS     mandatory
   DESCRIPTION
     "This variable is used as the basis for SNMP naming of
      mscVrIpNs components.
      These components can be added and deleted."
::= { mscVrIpNsRowStatusEntry 1 }

mscVrIpNsComponentName OBJECT-TYPE
   SYNTAX     DisplayString 
   ACCESS     read-only
   STATUS     mandatory
   DESCRIPTION
     "This variable provides the component's string name for
      use with the ASCII Console Interface"
::= { mscVrIpNsRowStatusEntry 2 }

mscVrIpNsStorageType OBJECT-TYPE
   SYNTAX     StorageType 
   ACCESS     read-only
   STATUS     mandatory
   DESCRIPTION
     "This variable represents the storage type value for the
      mscVrIpNs tables."
::= { mscVrIpNsRowStatusEntry 4 }

mscVrIpNsIndex OBJECT-TYPE
   SYNTAX     NonReplicated 
   ACCESS     not-accessible
   STATUS     mandatory
   DESCRIPTION
     "This variable represents the index for the mscVrIpNs tables."
::= { mscVrIpNsRowStatusEntry 10 }

mscVrIpNsProvTable OBJECT-TYPE
   SYNTAX     SEQUENCE OF MscVrIpNsProvEntry
   ACCESS     not-accessible
   STATUS     mandatory
   DESCRIPTION
     "This group contains provisionable attributes for the NetSentry 
      component."
::= { mscVrIpNs 10 }

mscVrIpNsProvEntry OBJECT-TYPE
   SYNTAX     MscVrIpNsProvEntry
   ACCESS     not-accessible
   STATUS     mandatory
   DESCRIPTION
     "An entry in the mscVrIpNsProvTable."
   INDEX {
      mscVrIndex,
      mscVrIpIndex,
      mscVrIpNsIndex }
::= { mscVrIpNsProvTable 1 }

MscVrIpNsProvEntry ::= SEQUENCE {
   mscVrIpNsFirstFilter
      AsciiString,
   mscVrIpNsLocalInFilter
      AsciiString,
   mscVrIpNsLocalOutFilter
      AsciiString,
   mscVrIpNsLastFilter
      AsciiString }

mscVrIpNsFirstFilter OBJECT-TYPE
   SYNTAX     AsciiString (SIZE (0..32))
   ACCESS     read-write
   STATUS     mandatory
   DESCRIPTION
     "The firstFilter is the first filter point which affects all IP packets before 
      they have been examined in any way for their origin and destination. 
      The most common use of a firstFilter point is to collect statistis for all 
      packets arriving at the route on any interface, before any subsequent 
      filter processing changes their direction or disposition."
::= { mscVrIpNsProvEntry 1 }

mscVrIpNsLocalInFilter OBJECT-TYPE
   SYNTAX     AsciiString (SIZE (0..32))
   ACCESS     read-write
   STATUS     mandatory
   DESCRIPTION
     "The localInFilter is the second filter point which uses by network 
      administrator to perform a common action on all IP packets that 
      physically arrive over a specific logical interface, regardless of the 
      packet's stated source or destination. Typical uses for a localInFilter 
      include verifying that known Ethernet media source addresses match 
      known IP addresses, or confirming that the IP packet source addresses of 
      received IP packet fall within a narrow range."
::= { mscVrIpNsProvEntry 2 }

mscVrIpNsLocalOutFilter OBJECT-TYPE
   SYNTAX     AsciiString (SIZE (0..32))
   ACCESS     read-write
   STATUS     mandatory
   DESCRIPTION
     "The localOutFilter is the third filter point which applies to any IP packet 
      that will be transmitted from the router to the medium associated with 
      the interface, regardless of its source, destination, or what type of 
      decision was made to cause the datagram to be transmitted on this 
      interface. localOutFilter generally used to ensure that certain paterns of 
      traffic do not enter the network or reach a second IP router on that 
      network. For example, localOutFilter can be used as the exclusion of all 
      IP packets above a certain security classification, or collecting statistics 
      on the amount of IP fragments performed on an outgoing interface."
::= { mscVrIpNsProvEntry 3 }

mscVrIpNsLastFilter OBJECT-TYPE
   SYNTAX     AsciiString (SIZE (0..32))
   ACCESS     read-write
   STATUS     mandatory
   DESCRIPTION
     "lastFilter is the fourth and last filter point to be excecuted after all other 
      routing and filtering decisions have been made on the IP packet, and 
      transmission of the information is imminent. lastFilter is generally used 
      to collect statistics on traffic after all previous control and routing 
      decisions have been made."
::= { mscVrIpNsProvEntry 4 }


-- Vr/<string> Ip NetSentry ApplyEntry/<Decimal>
-- This component contains a list of NetSentry filters that can be applied to 
-- IP packets and information pertaining to each application of such 
-- NetSentry filters.

mscVrIpNsApply OBJECT IDENTIFIER ::= { mscVrIpNs 2 }



mscVrIpNsApplyRowStatusTable OBJECT-TYPE
   SYNTAX     SEQUENCE OF MscVrIpNsApplyRowStatusEntry
   ACCESS     not-accessible
   STATUS     mandatory
   DESCRIPTION
     "This entry controls the addition and deletion of 
      mscVrIpNsApply components."
::= { mscVrIpNsApply 1 }

mscVrIpNsApplyRowStatusEntry OBJECT-TYPE
   SYNTAX     MscVrIpNsApplyRowStatusEntry
   ACCESS     not-accessible
   STATUS     mandatory
   DESCRIPTION
     "A single entry in the table represents a single 
      mscVrIpNsApply component."
   INDEX {
      mscVrIndex,
      mscVrIpIndex,
      mscVrIpNsIndex,
      mscVrIpNsApplyIndex }
::= { mscVrIpNsApplyRowStatusTable 1 }

MscVrIpNsApplyRowStatusEntry ::= SEQUENCE {
   mscVrIpNsApplyRowStatus
      RowStatus,
   mscVrIpNsApplyComponentName
      DisplayString,
   mscVrIpNsApplyStorageType
      StorageType,
   mscVrIpNsApplyIndex
      Integer32 }

mscVrIpNsApplyRowStatus OBJECT-TYPE
   SYNTAX     RowStatus 
   ACCESS     read-write
   STATUS     mandatory
   DESCRIPTION
     "This variable is used as the basis for SNMP naming of
      mscVrIpNsApply components.
      These components can be added and deleted."
::= { mscVrIpNsApplyRowStatusEntry 1 }

mscVrIpNsApplyComponentName OBJECT-TYPE
   SYNTAX     DisplayString 
   ACCESS     read-only
   STATUS     mandatory
   DESCRIPTION
     "This variable provides the component's string name for
      use with the ASCII Console Interface"
::= { mscVrIpNsApplyRowStatusEntry 2 }

mscVrIpNsApplyStorageType OBJECT-TYPE
   SYNTAX     StorageType 
   ACCESS     read-only
   STATUS     mandatory
   DESCRIPTION
     "This variable represents the storage type value for the
      mscVrIpNsApply tables."
::= { mscVrIpNsApplyRowStatusEntry 4 }

mscVrIpNsApplyIndex OBJECT-TYPE
   SYNTAX     Integer32 (1..65535)
   ACCESS     not-accessible
   STATUS     mandatory
   DESCRIPTION
     "This variable represents the index for the mscVrIpNsApply tables."
::= { mscVrIpNsApplyRowStatusEntry 10 }

mscVrIpNsApplyProvisionedTable OBJECT-TYPE
   SYNTAX     SEQUENCE OF MscVrIpNsApplyProvisionedEntry
   ACCESS     not-accessible
   STATUS     mandatory
   DESCRIPTION
     "The instance of provisioned information relating to a filter application to 
      IP packet."
::= { mscVrIpNsApply 10 }

mscVrIpNsApplyProvisionedEntry OBJECT-TYPE
   SYNTAX     MscVrIpNsApplyProvisionedEntry
   ACCESS     not-accessible
   STATUS     mandatory
   DESCRIPTION
     "An entry in the mscVrIpNsApplyProvisionedTable."
   INDEX {
      mscVrIndex,
      mscVrIpIndex,
      mscVrIpNsIndex,
      mscVrIpNsApplyIndex }
::= { mscVrIpNsApplyProvisionedTable 1 }

MscVrIpNsApplyProvisionedEntry ::= SEQUENCE {
   mscVrIpNsApplyFilter
      AsciiString,
   mscVrIpNsApplyIpAddress1
      IpAddress,
   mscVrIpNsApplyIpMask1
      IpAddress,
   mscVrIpNsApplyIpAddress2
      IpAddress,
   mscVrIpNsApplyIpMask2
      IpAddress,
   mscVrIpNsApplyDirection
      INTEGER }

mscVrIpNsApplyFilter OBJECT-TYPE
   SYNTAX     AsciiString (SIZE (0..32))
   ACCESS     read-write
   STATUS     mandatory
   DESCRIPTION
     "The name of the filter to be applied to packet matching the 
      conditions in this entry."
::= { mscVrIpNsApplyProvisionedEntry 1 }

mscVrIpNsApplyIpAddress1 OBJECT-TYPE
   SYNTAX     IpAddress 
   ACCESS     read-write
   STATUS     mandatory
   DESCRIPTION
     "The first IP address used to compare."
::= { mscVrIpNsApplyProvisionedEntry 2 }

mscVrIpNsApplyIpMask1 OBJECT-TYPE
   SYNTAX     IpAddress 
   ACCESS     read-write
   STATUS     mandatory
   DESCRIPTION
     "The first netmask associated with ipAddress1 used to compare."
::= { mscVrIpNsApplyProvisionedEntry 3 }

mscVrIpNsApplyIpAddress2 OBJECT-TYPE
   SYNTAX     IpAddress 
   ACCESS     read-write
   STATUS     mandatory
   DESCRIPTION
     "This second IP address used to compare."
::= { mscVrIpNsApplyProvisionedEntry 4 }

mscVrIpNsApplyIpMask2 OBJECT-TYPE
   SYNTAX     IpAddress 
   ACCESS     read-write
   STATUS     mandatory
   DESCRIPTION
     "This second netmask associated with ipAddress2 used to compare."
::= { mscVrIpNsApplyProvisionedEntry 5 }

mscVrIpNsApplyDirection OBJECT-TYPE
   SYNTAX     INTEGER  {
                 to(1),
                 from(2),
                 tofrom(3) }
   ACCESS     read-write
   STATUS     mandatory
   DESCRIPTION
     "Indicates the direction a packet must be moving between the first and 
      second apply list entries in order for the entries to match. First 'to' 
      second, first 'from' second, or first 'tofrom' second (either direction)."
   DEFVAL     { tofrom }
::= { mscVrIpNsApplyProvisionedEntry 6 }


-- Vr/<string> Ip Arp
-- The component specifies the Address Resolution Protocol.

mscVrIpArp OBJECT IDENTIFIER ::= { mscVrIp 11 }



mscVrIpArpRowStatusTable OBJECT-TYPE
   SYNTAX     SEQUENCE OF MscVrIpArpRowStatusEntry
   ACCESS     not-accessible
   STATUS     mandatory
   DESCRIPTION
     "This entry controls the addition and deletion of 
      mscVrIpArp components."
::= { mscVrIpArp 1 }

mscVrIpArpRowStatusEntry OBJECT-TYPE
   SYNTAX     MscVrIpArpRowStatusEntry
   ACCESS     not-accessible
   STATUS     mandatory
   DESCRIPTION
     "A single entry in the table represents a single 
      mscVrIpArp component."
   INDEX {
      mscVrIndex,
      mscVrIpIndex,
      mscVrIpArpIndex }
::= { mscVrIpArpRowStatusTable 1 }

MscVrIpArpRowStatusEntry ::= SEQUENCE {
   mscVrIpArpRowStatus
      RowStatus,
   mscVrIpArpComponentName
      DisplayString,
   mscVrIpArpStorageType
      StorageType,
   mscVrIpArpIndex
      NonReplicated }

mscVrIpArpRowStatus OBJECT-TYPE
   SYNTAX     RowStatus 
   ACCESS     read-only
   STATUS     mandatory
   DESCRIPTION
     "This variable is used as the basis for SNMP naming of
      mscVrIpArp components.
      These components cannot be added nor deleted."
::= { mscVrIpArpRowStatusEntry 1 }

mscVrIpArpComponentName OBJECT-TYPE
   SYNTAX     DisplayString 
   ACCESS     read-only
   STATUS     mandatory
   DESCRIPTION
     "This variable provides the component's string name for
      use with the ASCII Console Interface"
::= { mscVrIpArpRowStatusEntry 2 }

mscVrIpArpStorageType OBJECT-TYPE
   SYNTAX     StorageType 
   ACCESS     read-only
   STATUS     mandatory
   DESCRIPTION
     "This variable represents the storage type value for the
      mscVrIpArp tables."
::= { mscVrIpArpRowStatusEntry 4 }

mscVrIpArpIndex OBJECT-TYPE
   SYNTAX     NonReplicated 
   ACCESS     not-accessible
   STATUS     mandatory
   DESCRIPTION
     "This variable represents the index for the mscVrIpArp tables."
::= { mscVrIpArpRowStatusEntry 10 }

mscVrIpArpProvTable OBJECT-TYPE
   SYNTAX     SEQUENCE OF MscVrIpArpProvEntry
   ACCESS     not-accessible
   STATUS     mandatory
   DESCRIPTION
     "The ARP refresh feature allows the router to periodically verify ARP 
      table entries. Whenever the router updates an ARP entry, or creates a 
      new entry, a timeout value is assigned to the entry. When the timeout for 
      an entry expires, the router will send a unicast ARP request to the 
      currently-known physical address. If an ARP response comes back, the 
      entry will be assigned a new timeout. If, however, the host has gone 
      away or been assigned a new physical address, the host will not respond 
      to the unicast ARP, and the entry will be removed from the ARP table. 
      The new physical address will be discovered through the normal ARP 
      mechanism when the next communication is attempted to the host."
::= { mscVrIpArp 10 }

mscVrIpArpProvEntry OBJECT-TYPE
   SYNTAX     MscVrIpArpProvEntry
   ACCESS     not-accessible
   STATUS     mandatory
   DESCRIPTION
     "An entry in the mscVrIpArpProvTable."
   INDEX {
      mscVrIndex,
      mscVrIpIndex,
      mscVrIpArpIndex }
::= { mscVrIpArpProvTable 1 }

MscVrIpArpProvEntry ::= SEQUENCE {
   mscVrIpArpAutoRefresh
      INTEGER,
   mscVrIpArpAutoRefreshTimeout
      Unsigned32 }

mscVrIpArpAutoRefresh OBJECT-TYPE
   SYNTAX     INTEGER  {
                 enabled(1),
                 disabled(2) }
   ACCESS     read-write
   STATUS     mandatory
   DESCRIPTION
     "This attribute is used to enable or disable the ARP refresh feature."
   DEFVAL     { disabled }
::= { mscVrIpArpProvEntry 1 }

mscVrIpArpAutoRefreshTimeout OBJECT-TYPE
   SYNTAX     Unsigned32 (1..1440)
   ACCESS     read-write
   STATUS     mandatory
   DESCRIPTION
     "This attribute defines the timeout value, in minutes, which is assigned to 
      updated ARP entries, or newly created ARP entries. The range for the 
      timeout is 1 minute to 1440 minutes (24 hours)."
   DEFVAL     { 5 }
::= { mscVrIpArpProvEntry 2 }


-- Vr/<string> Ip Arp HostEntry/<Ip Address>
-- This component defines a static host entry in the Arp table.
-- Each static host entry is assigned Class of Service (CoS) 0 when the 
-- associated media type is one where CoS can be specified on a per virtual 
-- circuit basis (e.g. frameRelayDte or atmMpe). For other media types, the 
-- CoS value notApplicable (not VC dependent) is assigned.

mscVrIpArpHost OBJECT IDENTIFIER ::= { mscVrIpArp 2 }



mscVrIpArpHostRowStatusTable OBJECT-TYPE
   SYNTAX     SEQUENCE OF MscVrIpArpHostRowStatusEntry
   ACCESS     not-accessible
   STATUS     mandatory
   DESCRIPTION
     "This entry controls the addition and deletion of 
      mscVrIpArpHost components."
::= { mscVrIpArpHost 1 }

mscVrIpArpHostRowStatusEntry OBJECT-TYPE
   SYNTAX     MscVrIpArpHostRowStatusEntry
   ACCESS     not-accessible
   STATUS     mandatory
   DESCRIPTION
     "A single entry in the table represents a single 
      mscVrIpArpHost component."
   INDEX {
      mscVrIndex,
      mscVrIpIndex,
      mscVrIpArpIndex,
      mscVrIpArpHostHostAddressIndex }
::= { mscVrIpArpHostRowStatusTable 1 }

MscVrIpArpHostRowStatusEntry ::= SEQUENCE {
   mscVrIpArpHostRowStatus
      RowStatus,
   mscVrIpArpHostComponentName
      DisplayString,
   mscVrIpArpHostStorageType
      StorageType,
   mscVrIpArpHostHostAddressIndex
      IpAddress }

mscVrIpArpHostRowStatus OBJECT-TYPE
   SYNTAX     RowStatus 
   ACCESS     read-write
   STATUS     mandatory
   DESCRIPTION
     "This variable is used as the basis for SNMP naming of
      mscVrIpArpHost components.
      These components can be added and deleted."
::= { mscVrIpArpHostRowStatusEntry 1 }

mscVrIpArpHostComponentName OBJECT-TYPE
   SYNTAX     DisplayString 
   ACCESS     read-only
   STATUS     mandatory
   DESCRIPTION
     "This variable provides the component's string name for
      use with the ASCII Console Interface"
::= { mscVrIpArpHostRowStatusEntry 2 }

mscVrIpArpHostStorageType OBJECT-TYPE
   SYNTAX     StorageType 
   ACCESS     read-only
   STATUS     mandatory
   DESCRIPTION
     "This variable represents the storage type value for the
      mscVrIpArpHost tables."
::= { mscVrIpArpHostRowStatusEntry 4 }

mscVrIpArpHostHostAddressIndex OBJECT-TYPE
   SYNTAX     IpAddress 
   ACCESS     not-accessible
   STATUS     mandatory
   DESCRIPTION
     "This variable represents the index for the mscVrIpArpHost tables."
::= { mscVrIpArpHostRowStatusEntry 10 }

mscVrIpArpHostProvTable OBJECT-TYPE
   SYNTAX     SEQUENCE OF MscVrIpArpHostProvEntry
   ACCESS     not-accessible
   STATUS     mandatory
   DESCRIPTION
     "This group contains the provisionable attributes of the HostEntry 
      component."
::= { mscVrIpArpHost 10 }

mscVrIpArpHostProvEntry OBJECT-TYPE
   SYNTAX     MscVrIpArpHostProvEntry
   ACCESS     not-accessible
   STATUS     mandatory
   DESCRIPTION
     "An entry in the mscVrIpArpHostProvTable."
   INDEX {
      mscVrIndex,
      mscVrIpIndex,
      mscVrIpArpIndex,
      mscVrIpArpHostHostAddressIndex }
::= { mscVrIpArpHostProvTable 1 }

MscVrIpArpHostProvEntry ::= SEQUENCE {
   mscVrIpArpHostPhysAddress
      PhysAddress,
   mscVrIpArpHostMaxTxUnit
      Unsigned32,
   mscVrIpArpHostPermanentVirtualCircuitNumber
      Unsigned32,
   mscVrIpArpHostTunnelDestinationAddress
      IpAddress,
   mscVrIpArpHostEncap
      INTEGER }

mscVrIpArpHostPhysAddress OBJECT-TYPE
   SYNTAX     PhysAddress (SIZE (0..8))
   ACCESS     read-write
   STATUS     mandatory
   DESCRIPTION
     "This attribute identifies the physical address of the host being defined. 
      The value for this attribute should only be specified for media types 
      supporting physical addresses (e.g. ethernet, fddi, tokenRing etc.)"
   DEFVAL     { '000000000000'H }
::= { mscVrIpArpHostProvEntry 1 }

mscVrIpArpHostMaxTxUnit OBJECT-TYPE
   SYNTAX     Unsigned32 (0..0 | 576..18944)
   ACCESS     read-write
   STATUS     mandatory
   DESCRIPTION
     "Specify the maximum transmit unit (MTU) size that can be accepted by 
      the host. If this value is not specified, the value for the media interface is 
      used. The specified MTU must be less than or equal to the interface's 
      MTU size."
   DEFVAL     { 0 }
::= { mscVrIpArpHostProvEntry 2 }

mscVrIpArpHostPermanentVirtualCircuitNumber OBJECT-TYPE
   SYNTAX     Unsigned32 (0..4095)
   ACCESS     read-write
   STATUS     mandatory
   DESCRIPTION
     "Specify a permanent virtual circuit number to the remote host on X.25 
      or frame relay media.
      The value for this attribute can only be specified for X.25 or 
      frame relay media."
   DEFVAL     { 0 }
::= { mscVrIpArpHostProvEntry 3 }

mscVrIpArpHostTunnelDestinationAddress OBJECT-TYPE
   SYNTAX     IpAddress 
   ACCESS     read-write
   STATUS     mandatory
   DESCRIPTION
     "This attribute specifies the IP address of a remote IP tunnel endpoint in 
      the shared domain.
      
      A value of 0.0.0.0 is used when the entry is not referring to an IP tunnel."
   DEFVAL     { '00000000'H }  -- "0.0.0.0"
::= { mscVrIpArpHostProvEntry 4 }

mscVrIpArpHostEncap OBJECT-TYPE
   SYNTAX     INTEGER  {
                 ieee8023(1),
                 ethernet(2),
                 auto(3) }
   ACCESS     read-write
   STATUS     mandatory
   DESCRIPTION
     "This attribute specifies the encapsulation type for the host.
      The value for this attribute should only be specified for the hosts on the 
      ethernet media. If a value of auto is specified, the application based on 
      the media will determine the proper applicable encapsulation type."
   DEFVAL     { auto }
::= { mscVrIpArpHostProvEntry 5 }

mscVrIpArpHostOperTable OBJECT-TYPE
   SYNTAX     SEQUENCE OF MscVrIpArpHostOperEntry
   ACCESS     not-accessible
   STATUS     mandatory
   DESCRIPTION
     "This group contains the operational attributes of the HostEntry 
      component."
::= { mscVrIpArpHost 11 }

mscVrIpArpHostOperEntry OBJECT-TYPE
   SYNTAX     MscVrIpArpHostOperEntry
   ACCESS     not-accessible
   STATUS     mandatory
   DESCRIPTION
     "An entry in the mscVrIpArpHostOperTable."
   INDEX {
      mscVrIndex,
      mscVrIpIndex,
      mscVrIpArpIndex,
      mscVrIpArpHostHostAddressIndex }
::= { mscVrIpArpHostOperTable 1 }

MscVrIpArpHostOperEntry ::= SEQUENCE {
   mscVrIpArpHostOperMaxTxUnit
      Unsigned32,
   mscVrIpArpHostOperEncap
      INTEGER }

mscVrIpArpHostOperMaxTxUnit OBJECT-TYPE
   SYNTAX     Unsigned32 (0..0 | 576..18944)
   ACCESS     read-only
   STATUS     mandatory
   DESCRIPTION
     "This attribute indicates the operational value of the maximum 
      transmission unit."
::= { mscVrIpArpHostOperEntry 4 }

mscVrIpArpHostOperEncap OBJECT-TYPE
   SYNTAX     INTEGER  {
                 ieee8023(1),
                 ethernet(2),
                 notApplicable(3) }
   ACCESS     read-only
   STATUS     mandatory
   DESCRIPTION
     "This attribute indicates the operational encapsulation type. if the value of 
      the attribute encap is set to auto, then the application will determine the 
      encapsulation type based on the media being used and assigns the 
      appropriate value."
::= { mscVrIpArpHostOperEntry 5 }

-- 
-- *** THIS SUBTREE CURRENTLY NOT IMPLEMENTED ***
-- 

-- Vr/<string> Ip Arp DynHostEntry/<Ip Address>
-- This component is a table that contains all Arp host entries (both static 
-- and dynamic). Each IP ARP entry in the table is uniquely defined by its 
-- IP address and Class of Service (CoS) index.
-- 
-- When the associated media type is one where the CoS can be specified 
-- on a per virtual circuit basis (e.g. frameRelayDte or atmMpe) the CoS 
-- index of the arp entry may be 0, 1, 2, or 3; otherwise, the CoS index is 
-- na (not VC dependent).
-- 
-- An IP packet that has been assigned a particular CoS will be forwarded 
-- using the arp entry where the IP address matches the packet's 
-- destination IP address and where the CoS index matches the packet's 
-- CoS. When there are arp entries that match the packet's destination IP 
-- address, but not the packet's CoS, the packet will be forwarded using the 
-- arp entry that has the next lowest CoS index; failing this, the packet will 
-- be forwarded using the arp entry that has the next highest CoS index.

mscVrIpArpDynHost OBJECT IDENTIFIER ::= { mscVrIpArp 3 }



mscVrIpArpDynHostRowStatusTable OBJECT-TYPE
   SYNTAX     SEQUENCE OF MscVrIpArpDynHostRowStatusEntry
   ACCESS     not-accessible
   STATUS     mandatory
   DESCRIPTION
     "*** THIS TABLE CURRENTLY NOT IMPLEMENTED ***

      This entry controls the addition and deletion of 
      mscVrIpArpDynHost components."
::= { mscVrIpArpDynHost 1 }

mscVrIpArpDynHostRowStatusEntry OBJECT-TYPE
   SYNTAX     MscVrIpArpDynHostRowStatusEntry
   ACCESS     not-accessible
   STATUS     mandatory
   DESCRIPTION
     "A single entry in the table represents a single 
      mscVrIpArpDynHost component."
   INDEX {
      mscVrIndex,
      mscVrIpIndex,
      mscVrIpArpIndex,
      mscVrIpArpDynHostHostAddressIndex,
      mscVrIpArpDynHostCosIndex }
::= { mscVrIpArpDynHostRowStatusTable 1 }

MscVrIpArpDynHostRowStatusEntry ::= SEQUENCE {
   mscVrIpArpDynHostRowStatus
      RowStatus,
   mscVrIpArpDynHostComponentName
      DisplayString,
   mscVrIpArpDynHostStorageType
      StorageType,
   mscVrIpArpDynHostHostAddressIndex
      IpAddress,
   mscVrIpArpDynHostCosIndex
      INTEGER }

mscVrIpArpDynHostRowStatus OBJECT-TYPE
   SYNTAX     RowStatus 
   ACCESS     read-only
   STATUS     mandatory
   DESCRIPTION
     "This variable is used as the basis for SNMP naming of
      mscVrIpArpDynHost components.
      These components cannot be added nor deleted."
::= { mscVrIpArpDynHostRowStatusEntry 1 }

mscVrIpArpDynHostComponentName OBJECT-TYPE
   SYNTAX     DisplayString 
   ACCESS     read-only
   STATUS     mandatory
   DESCRIPTION
     "This variable provides the component's string name for
      use with the ASCII Console Interface"
::= { mscVrIpArpDynHostRowStatusEntry 2 }

mscVrIpArpDynHostStorageType OBJECT-TYPE
   SYNTAX     StorageType 
   ACCESS     read-only
   STATUS     mandatory
   DESCRIPTION
     "This variable represents the storage type value for the
      mscVrIpArpDynHost tables."
::= { mscVrIpArpDynHostRowStatusEntry 4 }

mscVrIpArpDynHostHostAddressIndex OBJECT-TYPE
   SYNTAX     IpAddress 
   ACCESS     not-accessible
   STATUS     mandatory
   DESCRIPTION
     "This variable represents an index for the mscVrIpArpDynHost tables."
::= { mscVrIpArpDynHostRowStatusEntry 10 }

mscVrIpArpDynHostCosIndex OBJECT-TYPE
   SYNTAX     INTEGER  {
                 n0(0),
                 n1(1),
                 n2(2),
                 n3(3),
                 notApplicable(4) }
   ACCESS     not-accessible
   STATUS     mandatory
   DESCRIPTION
     "This variable represents an index for the mscVrIpArpDynHost tables."
::= { mscVrIpArpDynHostRowStatusEntry 11 }

mscVrIpArpDynHostOperTable OBJECT-TYPE
   SYNTAX     SEQUENCE OF MscVrIpArpDynHostOperEntry
   ACCESS     not-accessible
   STATUS     mandatory
   DESCRIPTION
     "*** THIS TABLE CURRENTLY NOT IMPLEMENTED ***

      This group contains the operational attributes of the DynHostEntry 
      component."
::= { mscVrIpArpDynHost 10 }

mscVrIpArpDynHostOperEntry OBJECT-TYPE
   SYNTAX     MscVrIpArpDynHostOperEntry
   ACCESS     not-accessible
   STATUS     mandatory
   DESCRIPTION
     "An entry in the mscVrIpArpDynHostOperTable."
   INDEX {
      mscVrIndex,
      mscVrIpIndex,
      mscVrIpArpIndex,
      mscVrIpArpDynHostHostAddressIndex,
      mscVrIpArpDynHostCosIndex }
::= { mscVrIpArpDynHostOperTable 1 }

MscVrIpArpDynHostOperEntry ::= SEQUENCE {
   mscVrIpArpDynHostPhysAddress
      PhysAddress,
   mscVrIpArpDynHostMaxTxUnit
      Unsigned32,
   mscVrIpArpDynHostEncapsulationType
      INTEGER,
   mscVrIpArpDynHostPermanentVirtualCircuitNumber
      Unsigned32,
   mscVrIpArpDynHostIfIndex
      InterfaceIndex,
   mscVrIpArpDynHostType
      INTEGER,
   mscVrIpArpDynHostNcPhysAddress
      PhysAddress,
   mscVrIpArpDynHostTunnelDestinationAddress
      IpAddress }

mscVrIpArpDynHostPhysAddress OBJECT-TYPE
   SYNTAX     PhysAddress (SIZE (0..8))
   ACCESS     read-only
   STATUS     mandatory
   DESCRIPTION
     "This attribute indicates the physical address of the host in canonical 
      form."
::= { mscVrIpArpDynHostOperEntry 1 }

mscVrIpArpDynHostMaxTxUnit OBJECT-TYPE
   SYNTAX     Unsigned32 (0..0 | 576..18944)
   ACCESS     read-only
   STATUS     mandatory
   DESCRIPTION
     "This attribute indicates the maximum MTU size that can be accepted by 
      the host."
   DEFVAL     { 0 }
::= { mscVrIpArpDynHostOperEntry 3 }

mscVrIpArpDynHostEncapsulationType OBJECT-TYPE
   SYNTAX     INTEGER  {
                 ieee8023(1),
                 ethernet(2),
                 notApplicable(3) }
   ACCESS     read-only
   STATUS     mandatory
   DESCRIPTION
     "This attribute indicates the encapsulation type of the host."
::= { mscVrIpArpDynHostOperEntry 4 }

mscVrIpArpDynHostPermanentVirtualCircuitNumber OBJECT-TYPE
   SYNTAX     Unsigned32 (0..4095)
   ACCESS     read-only
   STATUS     mandatory
   DESCRIPTION
     "This attribute indicates the permanent virtual circuit number to the 
      remote host."
::= { mscVrIpArpDynHostOperEntry 5 }

mscVrIpArpDynHostIfIndex OBJECT-TYPE
   SYNTAX     InterfaceIndex (1..65535)
   ACCESS     read-only
   STATUS     mandatory
   DESCRIPTION
     "This attribute indicates the ifIndex of the protocol port that is associated 
      with this entry."
   DEFVAL     { 1 }
::= { mscVrIpArpDynHostOperEntry 6 }

mscVrIpArpDynHostType OBJECT-TYPE
   SYNTAX     INTEGER  {
                 pending(1),
                 invalid(2),
                 dynamic(3),
                 static(4) }
   ACCESS     read-only
   STATUS     mandatory
   DESCRIPTION
     "This attribute indicates how this entry was learned."
::= { mscVrIpArpDynHostOperEntry 7 }

mscVrIpArpDynHostNcPhysAddress OBJECT-TYPE
   SYNTAX     PhysAddress (SIZE (0..8))
   ACCESS     read-only
   STATUS     mandatory
   DESCRIPTION
     "This attribute indicates the physical address of the host in non-canonical 
      form. This attribute is not displayed for hosts on non-LAN media."
::= { mscVrIpArpDynHostOperEntry 8 }

mscVrIpArpDynHostTunnelDestinationAddress OBJECT-TYPE
   SYNTAX     IpAddress 
   ACCESS     read-only
   STATUS     mandatory
   DESCRIPTION
     "This attribute indicates the IP address of a remote IP tunnel endpoint in 
      the shared domain.
      
      A value of 0.0.0.0 is used when the entry is not referring to an IP tunnel."
   DEFVAL     { '00000000'H }  -- "0.0.0.0"
::= { mscVrIpArpDynHostOperEntry 9 }


-- Vr/<string> Ip Icmp
-- The Icmp component controls all ICMP related attributes available to 
-- this router.

mscVrIpIcmp OBJECT IDENTIFIER ::= { mscVrIp 12 }



mscVrIpIcmpRowStatusTable OBJECT-TYPE
   SYNTAX     SEQUENCE OF MscVrIpIcmpRowStatusEntry
   ACCESS     not-accessible
   STATUS     mandatory
   DESCRIPTION
     "This entry controls the addition and deletion of 
      mscVrIpIcmp components."
::= { mscVrIpIcmp 1 }

mscVrIpIcmpRowStatusEntry OBJECT-TYPE
   SYNTAX     MscVrIpIcmpRowStatusEntry
   ACCESS     not-accessible
   STATUS     mandatory
   DESCRIPTION
     "A single entry in the table represents a single 
      mscVrIpIcmp component."
   INDEX {
      mscVrIndex,
      mscVrIpIndex,
      mscVrIpIcmpIndex }
::= { mscVrIpIcmpRowStatusTable 1 }

MscVrIpIcmpRowStatusEntry ::= SEQUENCE {
   mscVrIpIcmpRowStatus
      RowStatus,
   mscVrIpIcmpComponentName
      DisplayString,
   mscVrIpIcmpStorageType
      StorageType,
   mscVrIpIcmpIndex
      NonReplicated }

mscVrIpIcmpRowStatus OBJECT-TYPE
   SYNTAX     RowStatus 
   ACCESS     read-only
   STATUS     mandatory
   DESCRIPTION
     "This variable is used as the basis for SNMP naming of
      mscVrIpIcmp components.
      These components cannot be added nor deleted."
::= { mscVrIpIcmpRowStatusEntry 1 }

mscVrIpIcmpComponentName OBJECT-TYPE
   SYNTAX     DisplayString 
   ACCESS     read-only
   STATUS     mandatory
   DESCRIPTION
     "This variable provides the component's string name for
      use with the ASCII Console Interface"
::= { mscVrIpIcmpRowStatusEntry 2 }

mscVrIpIcmpStorageType OBJECT-TYPE
   SYNTAX     StorageType 
   ACCESS     read-only
   STATUS     mandatory
   DESCRIPTION
     "This variable represents the storage type value for the
      mscVrIpIcmp tables."
::= { mscVrIpIcmpRowStatusEntry 4 }

mscVrIpIcmpIndex OBJECT-TYPE
   SYNTAX     NonReplicated 
   ACCESS     not-accessible
   STATUS     mandatory
   DESCRIPTION
     "This variable represents the index for the mscVrIpIcmp tables."
::= { mscVrIpIcmpRowStatusEntry 10 }

mscVrIpIcmpProvTable OBJECT-TYPE
   SYNTAX     SEQUENCE OF MscVrIpIcmpProvEntry
   ACCESS     not-accessible
   STATUS     mandatory
   DESCRIPTION
     "This group holds provisioned attributes for ICMP."
::= { mscVrIpIcmp 10 }

mscVrIpIcmpProvEntry OBJECT-TYPE
   SYNTAX     MscVrIpIcmpProvEntry
   ACCESS     not-accessible
   STATUS     mandatory
   DESCRIPTION
     "An entry in the mscVrIpIcmpProvTable."
   INDEX {
      mscVrIndex,
      mscVrIpIndex,
      mscVrIpIcmpIndex }
::= { mscVrIpIcmpProvTable 1 }

MscVrIpIcmpProvEntry ::= SEQUENCE {
   mscVrIpIcmpSendRedirect
      INTEGER,
   mscVrIpIcmpSendHostUnreachable
      INTEGER }

mscVrIpIcmpSendRedirect OBJECT-TYPE
   SYNTAX     INTEGER  {
                 enabled(1),
                 disabled(2) }
   ACCESS     read-write
   STATUS     obsolete
   DESCRIPTION
     "This attribute specifies whether an ICMP redirect will be sent. If 
      enabled, the router may send an ICMP redirect if a an Ip packet is being 
      routed out the same logicalInterface as it was received on. The router 
      will only send host ICMP redirects. If disabled, the router will never 
      send a ICMP redirect."
   DEFVAL     { enabled }
::= { mscVrIpIcmpProvEntry 1 }

mscVrIpIcmpSendHostUnreachable OBJECT-TYPE
   SYNTAX     INTEGER  {
                 enabled(1),
                 disabled(2) }
   ACCESS     read-write
   STATUS     obsolete
   DESCRIPTION
     "This attribute specifies whether host unreachable will be sent or not."
   DEFVAL     { disabled }
::= { mscVrIpIcmpProvEntry 2 }

mscVrIpIcmpStatsTable OBJECT-TYPE
   SYNTAX     SEQUENCE OF MscVrIpIcmpStatsEntry
   ACCESS     not-accessible
   STATUS     mandatory
   DESCRIPTION
     "This group holds statistics for ICMP."
::= { mscVrIpIcmp 11 }

mscVrIpIcmpStatsEntry OBJECT-TYPE
   SYNTAX     MscVrIpIcmpStatsEntry
   ACCESS     not-accessible
   STATUS     mandatory
   DESCRIPTION
     "An entry in the mscVrIpIcmpStatsTable."
   INDEX {
      mscVrIndex,
      mscVrIpIndex,
      mscVrIpIcmpIndex }
::= { mscVrIpIcmpStatsTable 1 }

MscVrIpIcmpStatsEntry ::= SEQUENCE {
   mscVrIpIcmpInMsgs
      Counter32,
   mscVrIpIcmpInErrors
      Counter32,
   mscVrIpIcmpInDestUnreachs
      Counter32,
   mscVrIpIcmpInTimeExcds
      Counter32,
   mscVrIpIcmpInParmProbs
      Counter32,
   mscVrIpIcmpInSrcQuenchs
      Counter32,
   mscVrIpIcmpInRedirects
      Counter32,
   mscVrIpIcmpInEchos
      Counter32,
   mscVrIpIcmpInEchoReps
      Counter32,
   mscVrIpIcmpInTimestamps
      Counter32,
   mscVrIpIcmpInTimestampReps
      Counter32,
   mscVrIpIcmpInAddrMasks
      Counter32,
   mscVrIpIcmpInAddrMaskReps
      Counter32,
   mscVrIpIcmpOutMsgs
      Counter32,
   mscVrIpIcmpOutErrors
      Counter32,
   mscVrIpIcmpOutDestUnreachs
      Counter32,
   mscVrIpIcmpOutTimeExcds
      Counter32,
   mscVrIpIcmpOutParmProbs
      Counter32,
   mscVrIpIcmpOutSrcQuenchs
      Counter32,
   mscVrIpIcmpOutRedirects
      Counter32,
   mscVrIpIcmpOutEchos
      Counter32,
   mscVrIpIcmpOutEchoReps
      Counter32,
   mscVrIpIcmpOutTimestamps
      Counter32,
   mscVrIpIcmpOutTimestampReps
      Counter32,
   mscVrIpIcmpOutAddrMasks
      Counter32,
   mscVrIpIcmpOutAddrMaskReps
      Counter32,
   mscVrIpIcmpInRtrAdvs
      Counter32,
   mscVrIpIcmpInRtrSolicits
      Counter32,
   mscVrIpIcmpOutRtrAdvs
      Counter32,
   mscVrIpIcmpOutRtrSolicits
      Counter32 }

mscVrIpIcmpInMsgs OBJECT-TYPE
   SYNTAX     Counter32 
   ACCESS     read-only
   STATUS     mandatory
   DESCRIPTION
     "This attribute indicates the number of ICMP messages received by this 
      gateway. This number includes inErrors. inMsgs wraps to zero if it 
      reaches its maximum defined value."
::= { mscVrIpIcmpStatsEntry 1 }

mscVrIpIcmpInErrors OBJECT-TYPE
   SYNTAX     Counter32 
   ACCESS     read-only
   STATUS     mandatory
   DESCRIPTION
     "This attribute indicates the number of ICMP messages received by this 
      gateway but determined as having ICMP specific errors such as bad 
      ICMP checksums or bad length. inErrors wraps to zero if it reaches its 
      maximum defined value."
::= { mscVrIpIcmpStatsEntry 2 }

mscVrIpIcmpInDestUnreachs OBJECT-TYPE
   SYNTAX     Counter32 
   ACCESS     read-only
   STATUS     mandatory
   DESCRIPTION
     "This attribute indicates the number of ICMP destination unreachable 
      messages received by this gateway. inDestUnreachs wraps to zero if it 
      reaches its maximum defined value."
::= { mscVrIpIcmpStatsEntry 3 }

mscVrIpIcmpInTimeExcds OBJECT-TYPE
   SYNTAX     Counter32 
   ACCESS     read-only
   STATUS     mandatory
   DESCRIPTION
     "This attribute indicates the number of ICMP time exceeded messages 
      received by this gateway. inTimeExcds wraps to zero if it reaches its 
      maximum defined value."
::= { mscVrIpIcmpStatsEntry 4 }

mscVrIpIcmpInParmProbs OBJECT-TYPE
   SYNTAX     Counter32 
   ACCESS     read-only
   STATUS     mandatory
   DESCRIPTION
     "This attribute indicates the number of ICMP parameter problem 
      messages received by this gateway. inParmProbs wraps to zero if it 
      reaches its maximum defined value."
::= { mscVrIpIcmpStatsEntry 5 }

mscVrIpIcmpInSrcQuenchs OBJECT-TYPE
   SYNTAX     Counter32 
   ACCESS     read-only
   STATUS     mandatory
   DESCRIPTION
     "This attribute indicates the number of ICMP source quench messages 
      received by this gateway. inSrcQuenchs wraps to zero if it reaches its 
      maximum defined value."
::= { mscVrIpIcmpStatsEntry 6 }

mscVrIpIcmpInRedirects OBJECT-TYPE
   SYNTAX     Counter32 
   ACCESS     read-only
   STATUS     mandatory
   DESCRIPTION
     "This attribute indicates the number of ICMP redirect messages received 
      by this gateway. inRedirects wraps to zero if it reaches its maximum 
      defined value."
::= { mscVrIpIcmpStatsEntry 7 }

mscVrIpIcmpInEchos OBJECT-TYPE
   SYNTAX     Counter32 
   ACCESS     read-only
   STATUS     mandatory
   DESCRIPTION
     "This attribute indicates the number of ICMP echo request messages 
      received by this gateway. inEchos wraps to zero if it reaches its 
      maximum defined value."
::= { mscVrIpIcmpStatsEntry 8 }

mscVrIpIcmpInEchoReps OBJECT-TYPE
   SYNTAX     Counter32 
   ACCESS     read-only
   STATUS     mandatory
   DESCRIPTION
     "This attribute indicates the number of ICMP echo reply messages 
      received by this gateway. inEchoReps wraps to zero if it reaches its 
      maximum defined value."
::= { mscVrIpIcmpStatsEntry 9 }

mscVrIpIcmpInTimestamps OBJECT-TYPE
   SYNTAX     Counter32 
   ACCESS     read-only
   STATUS     mandatory
   DESCRIPTION
     "This attribute indicates the number of ICMP timestamp request 
      messages received by this gateway. inTimeStamps wraps to zero if it 
      reaches its maximum defined value."
::= { mscVrIpIcmpStatsEntry 10 }

mscVrIpIcmpInTimestampReps OBJECT-TYPE
   SYNTAX     Counter32 
   ACCESS     read-only
   STATUS     mandatory
   DESCRIPTION
     "This attribute indicates the number of ICMP timestamp reply messages 
      received by this gateway. inTimeStampReps wraps to zero if it reaches 
      its maximum defined value."
::= { mscVrIpIcmpStatsEntry 11 }

mscVrIpIcmpInAddrMasks OBJECT-TYPE
   SYNTAX     Counter32 
   ACCESS     read-only
   STATUS     mandatory
   DESCRIPTION
     "This attribute indicates the number of ICMP address mask request 
      messages received by this gateway. inAddrMasks wraps to zero if it 
      reaches its maximum defined value."
::= { mscVrIpIcmpStatsEntry 12 }

mscVrIpIcmpInAddrMaskReps OBJECT-TYPE
   SYNTAX     Counter32 
   ACCESS     read-only
   STATUS     mandatory
   DESCRIPTION
     "This attribute indicates the number of ICMP address mask reply 
      messages received by this gateway. inAddrMaskReps wraps to zero if it 
      reaches its maximum defined value."
::= { mscVrIpIcmpStatsEntry 13 }

mscVrIpIcmpOutMsgs OBJECT-TYPE
   SYNTAX     Counter32 
   ACCESS     read-only
   STATUS     mandatory
   DESCRIPTION
     "This attribute indicates the number of ICMP messages which this 
      gateway attempted to send. This number includes outErrors. outMsgs 
      wraps to zero if it reaches its maximum defined value."
::= { mscVrIpIcmpStatsEntry 14 }

mscVrIpIcmpOutErrors OBJECT-TYPE
   SYNTAX     Counter32 
   ACCESS     read-only
   STATUS     mandatory
   DESCRIPTION
     "This attribute indicates the number of ICMP messages which this 
      gateway did not send due to problems discovered within ICMP such as a 
      lack of buffers. outErrors does not included errors discovered outside 
      the ICMP layer such as the inability of IP to route the resultant 
      datagram. outErrors wraps to zero if it reaches its maximum defined 
      value."
::= { mscVrIpIcmpStatsEntry 15 }

mscVrIpIcmpOutDestUnreachs OBJECT-TYPE
   SYNTAX     Counter32 
   ACCESS     read-only
   STATUS     mandatory
   DESCRIPTION
     "This attribute indicates the number of ICMP destination unreachable 
      messages sent by this gateway. outDestUnreachs wraps to zero if it 
      reaches its maximum defined value."
::= { mscVrIpIcmpStatsEntry 16 }

mscVrIpIcmpOutTimeExcds OBJECT-TYPE
   SYNTAX     Counter32 
   ACCESS     read-only
   STATUS     mandatory
   DESCRIPTION
     "This attribute indicates the number of ICMP time exceeded messages 
      sent by this gateway. outTimeExcds wraps to zero if it reaches its 
      maximum defined value."
::= { mscVrIpIcmpStatsEntry 17 }

mscVrIpIcmpOutParmProbs OBJECT-TYPE
   SYNTAX     Counter32 
   ACCESS     read-only
   STATUS     mandatory
   DESCRIPTION
     "This attribute indicates the number of ICMP parameter problem 
      messages sent by this gateway. outParmProbs wraps to zero if it reaches 
      its maximum defined value."
::= { mscVrIpIcmpStatsEntry 18 }

mscVrIpIcmpOutSrcQuenchs OBJECT-TYPE
   SYNTAX     Counter32 
   ACCESS     read-only
   STATUS     mandatory
   DESCRIPTION
     "This attribute indicates the number of ICMP source quench messages 
      sent by this gateway. ourSrcQuench wraps to zero if it reaches its 
      maximum defined value."
::= { mscVrIpIcmpStatsEntry 19 }

mscVrIpIcmpOutRedirects OBJECT-TYPE
   SYNTAX     Counter32 
   ACCESS     read-only
   STATUS     mandatory
   DESCRIPTION
     "This attribute indicates the number of ICMP redirect messages sent by 
      this gateway. outRedirects wraps to zero if it reaches its maximum 
      defined value."
::= { mscVrIpIcmpStatsEntry 20 }

mscVrIpIcmpOutEchos OBJECT-TYPE
   SYNTAX     Counter32 
   ACCESS     read-only
   STATUS     mandatory
   DESCRIPTION
     "This attribute indicates the number of ICMP echo request messages sent 
      by this gateway. outEchos wraps to zero if it reaches its maximum 
      defined value."
::= { mscVrIpIcmpStatsEntry 21 }

mscVrIpIcmpOutEchoReps OBJECT-TYPE
   SYNTAX     Counter32 
   ACCESS     read-only
   STATUS     mandatory
   DESCRIPTION
     "This attribute indicates the number of ICMP echo reply messages sent 
      by this gateway. outEchoReps wraps to zero if it reaches its maximum 
      defined value."
::= { mscVrIpIcmpStatsEntry 22 }

mscVrIpIcmpOutTimestamps OBJECT-TYPE
   SYNTAX     Counter32 
   ACCESS     read-only
   STATUS     mandatory
   DESCRIPTION
     "This attribute indicates the number of ICMP timestamp request 
      messages sent by this gateway. outTimeStamps wraps to zero if it 
      reaches its maximum defined value."
::= { mscVrIpIcmpStatsEntry 23 }

mscVrIpIcmpOutTimestampReps OBJECT-TYPE
   SYNTAX     Counter32 
   ACCESS     read-only
   STATUS     mandatory
   DESCRIPTION
     "This attribute indicates the number of ICMP timestamp reply messages 
      sent by this gateway. outTimeStampReps wraps to zero if it reaches its 
      maximum defined value."
::= { mscVrIpIcmpStatsEntry 24 }

mscVrIpIcmpOutAddrMasks OBJECT-TYPE
   SYNTAX     Counter32 
   ACCESS     read-only
   STATUS     mandatory
   DESCRIPTION
     "This attribute indicates the number of ICMP address mask request 
      messages sent by this gateway. outAddrMasks wraps to zero if it reaches 
      its maximum defined value."
::= { mscVrIpIcmpStatsEntry 25 }

mscVrIpIcmpOutAddrMaskReps OBJECT-TYPE
   SYNTAX     Counter32 
   ACCESS     read-only
   STATUS     mandatory
   DESCRIPTION
     "This attribute indicates the number of ICMP address mask reply 
      message sent by this gateway. outAddrMaskReps wraps to zero if it 
      reaches its maximum defined value."
::= { mscVrIpIcmpStatsEntry 26 }

mscVrIpIcmpInRtrAdvs OBJECT-TYPE
   SYNTAX     Counter32 
   ACCESS     read-only
   STATUS     mandatory
   DESCRIPTION
     "This attribute indicates the number of ICMP router advertisement 
      messages received by this gateway. inRtrAdvs wraps to zero if it reaches 
      its maximum defined value."
::= { mscVrIpIcmpStatsEntry 27 }

mscVrIpIcmpInRtrSolicits OBJECT-TYPE
   SYNTAX     Counter32 
   ACCESS     read-only
   STATUS     mandatory
   DESCRIPTION
     "This attribute indicates the number of ICMP router solicitation messages 
      received by this gateway. inRtrSolicits wraps to zero if it reaches its 
      maximum defined value."
::= { mscVrIpIcmpStatsEntry 28 }

mscVrIpIcmpOutRtrAdvs OBJECT-TYPE
   SYNTAX     Counter32 
   ACCESS     read-only
   STATUS     mandatory
   DESCRIPTION
     "This attribute indicates the number of ICMP router advertisement 
      messages sent by this gateway. outRtrAdvs wraps to zero if it reaches its 
      maximum defined value."
::= { mscVrIpIcmpStatsEntry 29 }

mscVrIpIcmpOutRtrSolicits OBJECT-TYPE
   SYNTAX     Counter32 
   ACCESS     read-only
   STATUS     mandatory
   DESCRIPTION
     "This attribute indicates the number of ICMP router solicitation messages 
      sent by this gateway. outRtrSolicits wraps to zero if it reaches its 
      maximum defined value."
::= { mscVrIpIcmpStatsEntry 30 }


-- Vr/<string> Ip RelayBC
-- The InwRelayBroadcast component controls the dissemination of IP 
-- broadcast packets received as Link-Layer broadcast.

mscVrIpRelayBC OBJECT IDENTIFIER ::= { mscVrIp 13 }



mscVrIpRelayBCRowStatusTable OBJECT-TYPE
   SYNTAX     SEQUENCE OF MscVrIpRelayBCRowStatusEntry
   ACCESS     not-accessible
   STATUS     mandatory
   DESCRIPTION
     "This entry controls the addition and deletion of 
      mscVrIpRelayBC components."
::= { mscVrIpRelayBC 1 }

mscVrIpRelayBCRowStatusEntry OBJECT-TYPE
   SYNTAX     MscVrIpRelayBCRowStatusEntry
   ACCESS     not-accessible
   STATUS     mandatory
   DESCRIPTION
     "A single entry in the table represents a single 
      mscVrIpRelayBC component."
   INDEX {
      mscVrIndex,
      mscVrIpIndex,
      mscVrIpRelayBCIndex }
::= { mscVrIpRelayBCRowStatusTable 1 }

MscVrIpRelayBCRowStatusEntry ::= SEQUENCE {
   mscVrIpRelayBCRowStatus
      RowStatus,
   mscVrIpRelayBCComponentName
      DisplayString,
   mscVrIpRelayBCStorageType
      StorageType,
   mscVrIpRelayBCIndex
      NonReplicated }

mscVrIpRelayBCRowStatus OBJECT-TYPE
   SYNTAX     RowStatus 
   ACCESS     read-only
   STATUS     mandatory
   DESCRIPTION
     "This variable is used as the basis for SNMP naming of
      mscVrIpRelayBC components.
      These components cannot be added nor deleted."
::= { mscVrIpRelayBCRowStatusEntry 1 }

mscVrIpRelayBCComponentName OBJECT-TYPE
   SYNTAX     DisplayString 
   ACCESS     read-only
   STATUS     mandatory
   DESCRIPTION
     "This variable provides the component's string name for
      use with the ASCII Console Interface"
::= { mscVrIpRelayBCRowStatusEntry 2 }

mscVrIpRelayBCStorageType OBJECT-TYPE
   SYNTAX     StorageType 
   ACCESS     read-only
   STATUS     mandatory
   DESCRIPTION
     "This variable represents the storage type value for the
      mscVrIpRelayBC tables."
::= { mscVrIpRelayBCRowStatusEntry 4 }

mscVrIpRelayBCIndex OBJECT-TYPE
   SYNTAX     NonReplicated 
   ACCESS     not-accessible
   STATUS     mandatory
   DESCRIPTION
     "This variable represents the index for the mscVrIpRelayBC tables."
::= { mscVrIpRelayBCRowStatusEntry 10 }

mscVrIpRelayBCProvTable OBJECT-TYPE
   SYNTAX     SEQUENCE OF MscVrIpRelayBCProvEntry
   ACCESS     not-accessible
   STATUS     mandatory
   DESCRIPTION
     "This group contains global configuration attributes for the Relay 
      Broadcast component."
::= { mscVrIpRelayBC 10 }

mscVrIpRelayBCProvEntry OBJECT-TYPE
   SYNTAX     MscVrIpRelayBCProvEntry
   ACCESS     not-accessible
   STATUS     mandatory
   DESCRIPTION
     "An entry in the mscVrIpRelayBCProvTable."
   INDEX {
      mscVrIndex,
      mscVrIpIndex,
      mscVrIpRelayBCIndex }
::= { mscVrIpRelayBCProvTable 1 }

MscVrIpRelayBCProvEntry ::= SEQUENCE {
   mscVrIpRelayBCRelayStatus
      INTEGER,
   mscVrIpRelayBCRelayNdStatus
      INTEGER }

mscVrIpRelayBCRelayStatus OBJECT-TYPE
   SYNTAX     INTEGER  {
                 enabled(1),
                 disabled(2) }
   ACCESS     read-write
   STATUS     mandatory
   DESCRIPTION
     "Specifies whether or not IP will forward IP broadcast packets that were 
      received as Link-Layer broadcasts."
   DEFVAL     { disabled }
::= { mscVrIpRelayBCProvEntry 1 }

mscVrIpRelayBCRelayNdStatus OBJECT-TYPE
   SYNTAX     INTEGER  {
                 enabled(1),
                 disabled(2) }
   ACCESS     read-write
   STATUS     mandatory
   DESCRIPTION
     "Specifies whether or not IP will forward broadcast packets whose 
      protocol is Sun ND."
   DEFVAL     { disabled }
::= { mscVrIpRelayBCProvEntry 2 }

mscVrIpRelayBCOperTable OBJECT-TYPE
   SYNTAX     SEQUENCE OF MscVrIpRelayBCOperEntry
   ACCESS     not-accessible
   STATUS     mandatory
   DESCRIPTION
     "This group contains RelayBroadcast component statistics."
::= { mscVrIpRelayBC 11 }

mscVrIpRelayBCOperEntry OBJECT-TYPE
   SYNTAX     MscVrIpRelayBCOperEntry
   ACCESS     not-accessible
   STATUS     mandatory
   DESCRIPTION
     "An entry in the mscVrIpRelayBCOperTable."
   INDEX {
      mscVrIndex,
      mscVrIpIndex,
      mscVrIpRelayBCIndex }
::= { mscVrIpRelayBCOperTable 1 }

MscVrIpRelayBCOperEntry ::= SEQUENCE {
   mscVrIpRelayBCRelayNdCount
      Counter32 }

mscVrIpRelayBCRelayNdCount OBJECT-TYPE
   SYNTAX     Counter32 
   ACCESS     read-only
   STATUS     mandatory
   DESCRIPTION
     "Indicates the number of Sun ND packets received by this router which 
      were forwarded. relayNdCount wraps to zero if reached its maximum."
::= { mscVrIpRelayBCOperEntry 1 }


-- Vr/<string> Ip RelayBC PortEntry/<Decimal>
-- This component is a table of destination UDP port numbers. In order for 
-- a packet to be forwarded by Relay Broadcast, the packet's destination 
-- UDP port number must be listed in this table.

mscVrIpRelayBCPort OBJECT IDENTIFIER ::= { mscVrIpRelayBC 2 }



mscVrIpRelayBCPortRowStatusTable OBJECT-TYPE
   SYNTAX     SEQUENCE OF MscVrIpRelayBCPortRowStatusEntry
   ACCESS     not-accessible
   STATUS     mandatory
   DESCRIPTION
     "This entry controls the addition and deletion of 
      mscVrIpRelayBCPort components."
::= { mscVrIpRelayBCPort 1 }

mscVrIpRelayBCPortRowStatusEntry OBJECT-TYPE
   SYNTAX     MscVrIpRelayBCPortRowStatusEntry
   ACCESS     not-accessible
   STATUS     mandatory
   DESCRIPTION
     "A single entry in the table represents a single 
      mscVrIpRelayBCPort component."
   INDEX {
      mscVrIndex,
      mscVrIpIndex,
      mscVrIpRelayBCIndex,
      mscVrIpRelayBCPortPortNumIndex }
::= { mscVrIpRelayBCPortRowStatusTable 1 }

MscVrIpRelayBCPortRowStatusEntry ::= SEQUENCE {
   mscVrIpRelayBCPortRowStatus
      RowStatus,
   mscVrIpRelayBCPortComponentName
      DisplayString,
   mscVrIpRelayBCPortStorageType
      StorageType,
   mscVrIpRelayBCPortPortNumIndex
      Integer32 }

mscVrIpRelayBCPortRowStatus OBJECT-TYPE
   SYNTAX     RowStatus 
   ACCESS     read-write
   STATUS     mandatory
   DESCRIPTION
     "This variable is used as the basis for SNMP naming of
      mscVrIpRelayBCPort components.
      These components can be added and deleted."
::= { mscVrIpRelayBCPortRowStatusEntry 1 }

mscVrIpRelayBCPortComponentName OBJECT-TYPE
   SYNTAX     DisplayString 
   ACCESS     read-only
   STATUS     mandatory
   DESCRIPTION
     "This variable provides the component's string name for
      use with the ASCII Console Interface"
::= { mscVrIpRelayBCPortRowStatusEntry 2 }

mscVrIpRelayBCPortStorageType OBJECT-TYPE
   SYNTAX     StorageType 
   ACCESS     read-only
   STATUS     mandatory
   DESCRIPTION
     "This variable represents the storage type value for the
      mscVrIpRelayBCPort tables."
::= { mscVrIpRelayBCPortRowStatusEntry 4 }

mscVrIpRelayBCPortPortNumIndex OBJECT-TYPE
   SYNTAX     Integer32 (0..268435455)
   ACCESS     not-accessible
   STATUS     mandatory
   DESCRIPTION
     "This variable represents the index for the mscVrIpRelayBCPort tables."
::= { mscVrIpRelayBCPortRowStatusEntry 10 }

mscVrIpRelayBCPortOperTable OBJECT-TYPE
   SYNTAX     SEQUENCE OF MscVrIpRelayBCPortOperEntry
   ACCESS     not-accessible
   STATUS     mandatory
   DESCRIPTION
     "This group contains statistics related to InwPortEntry."
::= { mscVrIpRelayBCPort 10 }

mscVrIpRelayBCPortOperEntry OBJECT-TYPE
   SYNTAX     MscVrIpRelayBCPortOperEntry
   ACCESS     not-accessible
   STATUS     mandatory
   DESCRIPTION
     "An entry in the mscVrIpRelayBCPortOperTable."
   INDEX {
      mscVrIndex,
      mscVrIpIndex,
      mscVrIpRelayBCIndex,
      mscVrIpRelayBCPortPortNumIndex }
::= { mscVrIpRelayBCPortOperTable 1 }

MscVrIpRelayBCPortOperEntry ::= SEQUENCE {
   mscVrIpRelayBCPortRelayBcUdpCount
      Counter32 }

mscVrIpRelayBCPortRelayBcUdpCount OBJECT-TYPE
   SYNTAX     Counter32 
   ACCESS     read-only
   STATUS     mandatory
   DESCRIPTION
     "Indicates the number of forwarded packets with this destination UDP 
      port number. relayBcUdpCount wraps to zero if reached its maximum."
::= { mscVrIpRelayBCPortOperEntry 1 }


-- Vr/<string> Ip Udp
-- Udp component controls all UDP related attributes supported by this 
-- router.

mscVrIpUdp OBJECT IDENTIFIER ::= { mscVrIp 14 }



mscVrIpUdpRowStatusTable OBJECT-TYPE
   SYNTAX     SEQUENCE OF MscVrIpUdpRowStatusEntry
   ACCESS     not-accessible
   STATUS     mandatory
   DESCRIPTION
     "This entry controls the addition and deletion of 
      mscVrIpUdp components."
::= { mscVrIpUdp 1 }

mscVrIpUdpRowStatusEntry OBJECT-TYPE
   SYNTAX     MscVrIpUdpRowStatusEntry
   ACCESS     not-accessible
   STATUS     mandatory
   DESCRIPTION
     "A single entry in the table represents a single 
      mscVrIpUdp component."
   INDEX {
      mscVrIndex,
      mscVrIpIndex,
      mscVrIpUdpIndex }
::= { mscVrIpUdpRowStatusTable 1 }

MscVrIpUdpRowStatusEntry ::= SEQUENCE {
   mscVrIpUdpRowStatus
      RowStatus,
   mscVrIpUdpComponentName
      DisplayString,
   mscVrIpUdpStorageType
      StorageType,
   mscVrIpUdpIndex
      NonReplicated }

mscVrIpUdpRowStatus OBJECT-TYPE
   SYNTAX     RowStatus 
   ACCESS     read-only
   STATUS     mandatory
   DESCRIPTION
     "This variable is used as the basis for SNMP naming of
      mscVrIpUdp components.
      These components cannot be added nor deleted."
::= { mscVrIpUdpRowStatusEntry 1 }

mscVrIpUdpComponentName OBJECT-TYPE
   SYNTAX     DisplayString 
   ACCESS     read-only
   STATUS     mandatory
   DESCRIPTION
     "This variable provides the component's string name for
      use with the ASCII Console Interface"
::= { mscVrIpUdpRowStatusEntry 2 }

mscVrIpUdpStorageType OBJECT-TYPE
   SYNTAX     StorageType 
   ACCESS     read-only
   STATUS     mandatory
   DESCRIPTION
     "This variable represents the storage type value for the
      mscVrIpUdp tables."
::= { mscVrIpUdpRowStatusEntry 4 }

mscVrIpUdpIndex OBJECT-TYPE
   SYNTAX     NonReplicated 
   ACCESS     not-accessible
   STATUS     mandatory
   DESCRIPTION
     "This variable represents the index for the mscVrIpUdp tables."
::= { mscVrIpUdpRowStatusEntry 10 }

mscVrIpUdpStatsTable OBJECT-TYPE
   SYNTAX     SEQUENCE OF MscVrIpUdpStatsEntry
   ACCESS     not-accessible
   STATUS     mandatory
   DESCRIPTION
     "This group holds statictics for UDP."
::= { mscVrIpUdp 10 }

mscVrIpUdpStatsEntry OBJECT-TYPE
   SYNTAX     MscVrIpUdpStatsEntry
   ACCESS     not-accessible
   STATUS     mandatory
   DESCRIPTION
     "An entry in the mscVrIpUdpStatsTable."
   INDEX {
      mscVrIndex,
      mscVrIpIndex,
      mscVrIpUdpIndex }
::= { mscVrIpUdpStatsTable 1 }

MscVrIpUdpStatsEntry ::= SEQUENCE {
   mscVrIpUdpInDatagrams
      Counter32,
   mscVrIpUdpNoPorts
      Counter32,
   mscVrIpUdpInErrors
      Counter32,
   mscVrIpUdpOutDatagrams
      Counter32 }

mscVrIpUdpInDatagrams OBJECT-TYPE
   SYNTAX     Counter32 
   ACCESS     read-only
   STATUS     mandatory
   DESCRIPTION
     "The number of UDP datagrams delivered to UDP users. inDatagrams 
      wraps to zero if reaches its maximum defined value."
::= { mscVrIpUdpStatsEntry 1 }

mscVrIpUdpNoPorts OBJECT-TYPE
   SYNTAX     Counter32 
   ACCESS     read-only
   STATUS     mandatory
   DESCRIPTION
     "The number of UDP datagrams received for which there was no 
      application at the destination port. noPorts wraps to zero if reaches its 
      maximum defined value."
::= { mscVrIpUdpStatsEntry 2 }

mscVrIpUdpInErrors OBJECT-TYPE
   SYNTAX     Counter32 
   ACCESS     read-only
   STATUS     mandatory
   DESCRIPTION
     "The number of received UDP datagrams that could not be delivered for 
      reasons other than the lack of an application at the destination port. 
      inErrors wraps to zero if reaches its maximum defined value."
::= { mscVrIpUdpStatsEntry 3 }

mscVrIpUdpOutDatagrams OBJECT-TYPE
   SYNTAX     Counter32 
   ACCESS     read-only
   STATUS     mandatory
   DESCRIPTION
     "The number of UDP datagrams sent from this gateway. outDatagrams 
      wraps to zero if reaches its maximum defined value."
::= { mscVrIpUdpStatsEntry 4 }

-- 
-- *** THIS SUBTREE CURRENTLY NOT IMPLEMENTED ***
-- 

-- The table contains UDP listener information.

mscVrIpUdpListenEntry OBJECT IDENTIFIER ::= { mscVrIpUdp 2 }



mscVrIpUdpListenEntryRowStatusTable OBJECT-TYPE
   SYNTAX     SEQUENCE OF MscVrIpUdpListenEntryRowStatusEntry
   ACCESS     not-accessible
   STATUS     mandatory
   DESCRIPTION
     "*** THIS TABLE CURRENTLY NOT IMPLEMENTED ***

      This entry controls the addition and deletion of 
      mscVrIpUdpListenEntry components."
::= { mscVrIpUdpListenEntry 1 }

mscVrIpUdpListenEntryRowStatusEntry OBJECT-TYPE
   SYNTAX     MscVrIpUdpListenEntryRowStatusEntry
   ACCESS     not-accessible
   STATUS     mandatory
   DESCRIPTION
     "A single entry in the table represents a single 
      mscVrIpUdpListenEntry component."
   INDEX {
      mscVrIndex,
      mscVrIpIndex,
      mscVrIpUdpIndex,
      mscVrIpUdpListenEntryLocalAddressIndex,
      mscVrIpUdpListenEntryLocalPortIndex }
::= { mscVrIpUdpListenEntryRowStatusTable 1 }

MscVrIpUdpListenEntryRowStatusEntry ::= SEQUENCE {
   mscVrIpUdpListenEntryRowStatus
      RowStatus,
   mscVrIpUdpListenEntryComponentName
      DisplayString,
   mscVrIpUdpListenEntryStorageType
      StorageType,
   mscVrIpUdpListenEntryLocalAddressIndex
      IpAddress,
   mscVrIpUdpListenEntryLocalPortIndex
      Integer32 }

mscVrIpUdpListenEntryRowStatus OBJECT-TYPE
   SYNTAX     RowStatus 
   ACCESS     read-only
   STATUS     mandatory
   DESCRIPTION
     "This variable is used as the basis for SNMP naming of
      mscVrIpUdpListenEntry components.
      These components cannot be added nor deleted."
::= { mscVrIpUdpListenEntryRowStatusEntry 1 }

mscVrIpUdpListenEntryComponentName OBJECT-TYPE
   SYNTAX     DisplayString 
   ACCESS     read-only
   STATUS     mandatory
   DESCRIPTION
     "This variable provides the component's string name for
      use with the ASCII Console Interface"
::= { mscVrIpUdpListenEntryRowStatusEntry 2 }

mscVrIpUdpListenEntryStorageType OBJECT-TYPE
   SYNTAX     StorageType 
   ACCESS     read-only
   STATUS     mandatory
   DESCRIPTION
     "This variable represents the storage type value for the
      mscVrIpUdpListenEntry tables."
::= { mscVrIpUdpListenEntryRowStatusEntry 4 }

mscVrIpUdpListenEntryLocalAddressIndex OBJECT-TYPE
   SYNTAX     IpAddress 
   ACCESS     not-accessible
   STATUS     mandatory
   DESCRIPTION
     "This variable represents an index for the mscVrIpUdpListenEntry tables."
::= { mscVrIpUdpListenEntryRowStatusEntry 10 }

mscVrIpUdpListenEntryLocalPortIndex OBJECT-TYPE
   SYNTAX     Integer32 (0..65535)
   ACCESS     not-accessible
   STATUS     mandatory
   DESCRIPTION
     "This variable represents an index for the mscVrIpUdpListenEntry tables."
::= { mscVrIpUdpListenEntryRowStatusEntry 11 }


-- The Tcp component contains all attributes related to TCP.

mscVrIpTcp OBJECT IDENTIFIER ::= { mscVrIp 15 }



mscVrIpTcpRowStatusTable OBJECT-TYPE
   SYNTAX     SEQUENCE OF MscVrIpTcpRowStatusEntry
   ACCESS     not-accessible
   STATUS     mandatory
   DESCRIPTION
     "This entry controls the addition and deletion of 
      mscVrIpTcp components."
::= { mscVrIpTcp 1 }

mscVrIpTcpRowStatusEntry OBJECT-TYPE
   SYNTAX     MscVrIpTcpRowStatusEntry
   ACCESS     not-accessible
   STATUS     mandatory
   DESCRIPTION
     "A single entry in the table represents a single 
      mscVrIpTcp component."
   INDEX {
      mscVrIndex,
      mscVrIpIndex,
      mscVrIpTcpIndex }
::= { mscVrIpTcpRowStatusTable 1 }

MscVrIpTcpRowStatusEntry ::= SEQUENCE {
   mscVrIpTcpRowStatus
      RowStatus,
   mscVrIpTcpComponentName
      DisplayString,
   mscVrIpTcpStorageType
      StorageType,
   mscVrIpTcpIndex
      NonReplicated }

mscVrIpTcpRowStatus OBJECT-TYPE
   SYNTAX     RowStatus 
   ACCESS     read-only
   STATUS     mandatory
   DESCRIPTION
     "This variable is used as the basis for SNMP naming of
      mscVrIpTcp components.
      These components cannot be added nor deleted."
::= { mscVrIpTcpRowStatusEntry 1 }

mscVrIpTcpComponentName OBJECT-TYPE
   SYNTAX     DisplayString 
   ACCESS     read-only
   STATUS     mandatory
   DESCRIPTION
     "This variable provides the component's string name for
      use with the ASCII Console Interface"
::= { mscVrIpTcpRowStatusEntry 2 }

mscVrIpTcpStorageType OBJECT-TYPE
   SYNTAX     StorageType 
   ACCESS     read-only
   STATUS     mandatory
   DESCRIPTION
     "This variable represents the storage type value for the
      mscVrIpTcp tables."
::= { mscVrIpTcpRowStatusEntry 4 }

mscVrIpTcpIndex OBJECT-TYPE
   SYNTAX     NonReplicated 
   ACCESS     not-accessible
   STATUS     mandatory
   DESCRIPTION
     "This variable represents the index for the mscVrIpTcp tables."
::= { mscVrIpTcpRowStatusEntry 10 }

mscVrIpTcpStatsTable OBJECT-TYPE
   SYNTAX     SEQUENCE OF MscVrIpTcpStatsEntry
   ACCESS     not-accessible
   STATUS     mandatory
   DESCRIPTION
     "This group contains statistics for TCP."
::= { mscVrIpTcp 10 }

mscVrIpTcpStatsEntry OBJECT-TYPE
   SYNTAX     MscVrIpTcpStatsEntry
   ACCESS     not-accessible
   STATUS     mandatory
   DESCRIPTION
     "An entry in the mscVrIpTcpStatsTable."
   INDEX {
      mscVrIndex,
      mscVrIpIndex,
      mscVrIpTcpIndex }
::= { mscVrIpTcpStatsTable 1 }

MscVrIpTcpStatsEntry ::= SEQUENCE {
   mscVrIpTcpRToAlgorithm
      INTEGER,
   mscVrIpTcpRToMin
      Unsigned32,
   mscVrIpTcpRToMax
      Unsigned32,
   mscVrIpTcpMaxConn
      INTEGER,
   mscVrIpTcpActiveOpens
      Counter32,
   mscVrIpTcpPassiveOpens
      Counter32,
   mscVrIpTcpAttemptFails
      Counter32,
   mscVrIpTcpEstabResets
      Counter32,
   mscVrIpTcpCurrEstab
      Gauge32,
   mscVrIpTcpInSegs
      Counter32,
   mscVrIpTcpOutSegs
      Counter32,
   mscVrIpTcpRetransSegs
      Counter32,
   mscVrIpTcpInErrs
      Counter32,
   mscVrIpTcpOutRsts
      Counter32 }

mscVrIpTcpRToAlgorithm OBJECT-TYPE
   SYNTAX     INTEGER  {
                 other(1),
                 constant(2),
                 rsre(3),
                 vanJacobson(4) }
   ACCESS     read-only
   STATUS     mandatory
   DESCRIPTION
     "Indicate which algorithm was used to calculate the timeout value used 
      for retransmitting unackowledged octet."
::= { mscVrIpTcpStatsEntry 1 }

mscVrIpTcpRToMin OBJECT-TYPE
   SYNTAX     Unsigned32 (0..4294967295)
   ACCESS     read-only
   STATUS     mandatory
   DESCRIPTION
     "Indicate the minimum value, measured in milliseconds, allowed for 
      retransmission timeout."
   DEFVAL     { 0 }
::= { mscVrIpTcpStatsEntry 2 }

mscVrIpTcpRToMax OBJECT-TYPE
   SYNTAX     Unsigned32 (0..4294967295)
   ACCESS     read-only
   STATUS     mandatory
   DESCRIPTION
     "Indicates the maximun value, measured in milliseconds, allowed for 
      retransmission timeout."
::= { mscVrIpTcpStatsEntry 3 }

mscVrIpTcpMaxConn OBJECT-TYPE
   SYNTAX     INTEGER (-1)
   ACCESS     read-only
   STATUS     mandatory
   DESCRIPTION
     "Limit on number of connections the TCP can support. The value is 
      always -1 which indicates that the number of connections supported is 
      dynamic (limited by memory in the system)."
   DEFVAL     { -1 }
::= { mscVrIpTcpStatsEntry 4 }

mscVrIpTcpActiveOpens OBJECT-TYPE
   SYNTAX     Counter32 
   ACCESS     read-only
   STATUS     mandatory
   DESCRIPTION
     "The number of times TCP connections have made a direct transition to 
      the synSent state from the closed state."
::= { mscVrIpTcpStatsEntry 5 }

mscVrIpTcpPassiveOpens OBJECT-TYPE
   SYNTAX     Counter32 
   ACCESS     read-only
   STATUS     mandatory
   DESCRIPTION
     "The number of times TCP connections have made a direct transition to 
      the synRcvd state from the listen state."
::= { mscVrIpTcpStatsEntry 6 }

mscVrIpTcpAttemptFails OBJECT-TYPE
   SYNTAX     Counter32 
   ACCESS     read-only
   STATUS     mandatory
   DESCRIPTION
     "The number of times TCP connections have made a direct transition to 
      the closed state from either the synSent state or the synRcvd state, plus 
      the number of times TCP connections have made a direct transition to 
      the listen state from the synRcvd state."
::= { mscVrIpTcpStatsEntry 7 }

mscVrIpTcpEstabResets OBJECT-TYPE
   SYNTAX     Counter32 
   ACCESS     read-only
   STATUS     mandatory
   DESCRIPTION
     "The number of times TCP connections have made a direct transition to 
      the closed state from either the established state or the closedWait state."
::= { mscVrIpTcpStatsEntry 8 }

mscVrIpTcpCurrEstab OBJECT-TYPE
   SYNTAX     Gauge32 (0..4294967295)
   ACCESS     read-only
   STATUS     mandatory
   DESCRIPTION
     "The number of TCP connections for which the current state is either 
      established or closedWait."
::= { mscVrIpTcpStatsEntry 9 }

mscVrIpTcpInSegs OBJECT-TYPE
   SYNTAX     Counter32 
   ACCESS     read-only
   STATUS     mandatory
   DESCRIPTION
     "The number of segments received, including those received in error. 
      This count includes segments received on currently established 
      connections."
::= { mscVrIpTcpStatsEntry 10 }

mscVrIpTcpOutSegs OBJECT-TYPE
   SYNTAX     Counter32 
   ACCESS     read-only
   STATUS     mandatory
   DESCRIPTION
     "The number of segments sent, including those on current connections 
      but excluding those containing only retransmitted octets."
::= { mscVrIpTcpStatsEntry 11 }

mscVrIpTcpRetransSegs OBJECT-TYPE
   SYNTAX     Counter32 
   ACCESS     read-only
   STATUS     mandatory
   DESCRIPTION
     "The number of segments retransmitted that is, the number of TCP 
      segments transmitted containing one or more previously transmitted 
      octets."
::= { mscVrIpTcpStatsEntry 12 }

mscVrIpTcpInErrs OBJECT-TYPE
   SYNTAX     Counter32 
   ACCESS     read-only
   STATUS     mandatory
   DESCRIPTION
     "Total number of segments received in error, for example bad TCP 
      checksum."
::= { mscVrIpTcpStatsEntry 13 }

mscVrIpTcpOutRsts OBJECT-TYPE
   SYNTAX     Counter32 
   ACCESS     read-only
   STATUS     mandatory
   DESCRIPTION
     "Number of TCP segments sent containing the RST flag."
::= { mscVrIpTcpStatsEntry 14 }

-- 
-- *** THIS SUBTREE CURRENTLY NOT IMPLEMENTED ***
-- 

-- The component defines an entry in the TCP connection table. Each entry 
-- corresponds to TCP end-point identified by 4-tuples, LocalAddress, 
-- LocalPort, RemoteAddress, and RemotePort. 

mscVrIpTcpTcpEntry OBJECT IDENTIFIER ::= { mscVrIpTcp 2 }



mscVrIpTcpTcpEntryRowStatusTable OBJECT-TYPE
   SYNTAX     SEQUENCE OF MscVrIpTcpTcpEntryRowStatusEntry
   ACCESS     not-accessible
   STATUS     mandatory
   DESCRIPTION
     "*** THIS TABLE CURRENTLY NOT IMPLEMENTED ***

      This entry controls the addition and deletion of 
      mscVrIpTcpTcpEntry components."
::= { mscVrIpTcpTcpEntry 1 }

mscVrIpTcpTcpEntryRowStatusEntry OBJECT-TYPE
   SYNTAX     MscVrIpTcpTcpEntryRowStatusEntry
   ACCESS     not-accessible
   STATUS     mandatory
   DESCRIPTION
     "A single entry in the table represents a single 
      mscVrIpTcpTcpEntry component."
   INDEX {
      mscVrIndex,
      mscVrIpIndex,
      mscVrIpTcpIndex,
      mscVrIpTcpTcpEntryLocalAddressIndex,
      mscVrIpTcpTcpEntryLocalPortIndex,
      mscVrIpTcpTcpEntryRemoteAddressIndex,
      mscVrIpTcpTcpEntryRemotePortIndex }
::= { mscVrIpTcpTcpEntryRowStatusTable 1 }

MscVrIpTcpTcpEntryRowStatusEntry ::= SEQUENCE {
   mscVrIpTcpTcpEntryRowStatus
      RowStatus,
   mscVrIpTcpTcpEntryComponentName
      DisplayString,
   mscVrIpTcpTcpEntryStorageType
      StorageType,
   mscVrIpTcpTcpEntryLocalAddressIndex
      IpAddress,
   mscVrIpTcpTcpEntryLocalPortIndex
      Integer32,
   mscVrIpTcpTcpEntryRemoteAddressIndex
      IpAddress,
   mscVrIpTcpTcpEntryRemotePortIndex
      Integer32 }

mscVrIpTcpTcpEntryRowStatus OBJECT-TYPE
   SYNTAX     RowStatus 
   ACCESS     read-only
   STATUS     mandatory
   DESCRIPTION
     "This variable is used as the basis for SNMP naming of
      mscVrIpTcpTcpEntry components.
      These components cannot be added nor deleted."
::= { mscVrIpTcpTcpEntryRowStatusEntry 1 }

mscVrIpTcpTcpEntryComponentName OBJECT-TYPE
   SYNTAX     DisplayString 
   ACCESS     read-only
   STATUS     mandatory
   DESCRIPTION
     "This variable provides the component's string name for
      use with the ASCII Console Interface"
::= { mscVrIpTcpTcpEntryRowStatusEntry 2 }

mscVrIpTcpTcpEntryStorageType OBJECT-TYPE
   SYNTAX     StorageType 
   ACCESS     read-only
   STATUS     mandatory
   DESCRIPTION
     "This variable represents the storage type value for the
      mscVrIpTcpTcpEntry tables."
::= { mscVrIpTcpTcpEntryRowStatusEntry 4 }

mscVrIpTcpTcpEntryLocalAddressIndex OBJECT-TYPE
   SYNTAX     IpAddress 
   ACCESS     not-accessible
   STATUS     mandatory
   DESCRIPTION
     "This variable represents an index for the mscVrIpTcpTcpEntry tables."
::= { mscVrIpTcpTcpEntryRowStatusEntry 10 }

mscVrIpTcpTcpEntryLocalPortIndex OBJECT-TYPE
   SYNTAX     Integer32 (0..65535)
   ACCESS     not-accessible
   STATUS     mandatory
   DESCRIPTION
     "This variable represents an index for the mscVrIpTcpTcpEntry tables."
::= { mscVrIpTcpTcpEntryRowStatusEntry 11 }

mscVrIpTcpTcpEntryRemoteAddressIndex OBJECT-TYPE
   SYNTAX     IpAddress 
   ACCESS     not-accessible
   STATUS     mandatory
   DESCRIPTION
     "This variable represents an index for the mscVrIpTcpTcpEntry tables."
::= { mscVrIpTcpTcpEntryRowStatusEntry 12 }

mscVrIpTcpTcpEntryRemotePortIndex OBJECT-TYPE
   SYNTAX     Integer32 (0..65535)
   ACCESS     not-accessible
   STATUS     mandatory
   DESCRIPTION
     "This variable represents an index for the mscVrIpTcpTcpEntry tables."
::= { mscVrIpTcpTcpEntryRowStatusEntry 13 }

mscVrIpTcpTcpEntryOperTable OBJECT-TYPE
   SYNTAX     SEQUENCE OF MscVrIpTcpTcpEntryOperEntry
   ACCESS     not-accessible
   STATUS     mandatory
   DESCRIPTION
     "*** THIS TABLE CURRENTLY NOT IMPLEMENTED ***

      This group contains columnar entries for each end-point on the TCP."
::= { mscVrIpTcpTcpEntry 10 }

mscVrIpTcpTcpEntryOperEntry OBJECT-TYPE
   SYNTAX     MscVrIpTcpTcpEntryOperEntry
   ACCESS     not-accessible
   STATUS     mandatory
   DESCRIPTION
     "An entry in the mscVrIpTcpTcpEntryOperTable."
   INDEX {
      mscVrIndex,
      mscVrIpIndex,
      mscVrIpTcpIndex,
      mscVrIpTcpTcpEntryLocalAddressIndex,
      mscVrIpTcpTcpEntryLocalPortIndex,
      mscVrIpTcpTcpEntryRemoteAddressIndex,
      mscVrIpTcpTcpEntryRemotePortIndex }
::= { mscVrIpTcpTcpEntryOperTable 1 }

MscVrIpTcpTcpEntryOperEntry ::= SEQUENCE {
   mscVrIpTcpTcpEntryState
      INTEGER }

mscVrIpTcpTcpEntryState OBJECT-TYPE
   SYNTAX     INTEGER  {
                 closed(1),
                 listen(2),
                 synSent(3),
                 synReceived(4),
                 established(5),
                 closeWait(6),
                 finWait1(7),
                 closing(8),
                 lastAck(9),
                 finWait2(10),
                 timeWait(11),
                 delete(12) }
   ACCESS     read-write
   STATUS     mandatory
   DESCRIPTION
     "This attribute reflects the current state of this Tcp connection."
::= { mscVrIpTcpTcpEntryOperEntry 1 }


-- Vr/<string> Ip BootpRelayAgent
-- The BootpRelayAgent component contains all the necessary attributes 
-- and components to provision a BOOTP relay agent. The BOOTP relay 
-- agent functionality conforms to that described in RFCs 951 and 1542.
-- 
-- The purpose of the BOOTP relay agent is to forward BOOTP request 
-- packets from a client to a server, and also to deliver server BOOTP 
-- replies back to the client. When a BOOTP request is received on a port, 
-- the request will be sent to a provisioned list of IP addresses for that port. 
-- In addition, the request will be broadcast out all other BOOTP ports 
-- which allow it.

mscVrIpBootp OBJECT IDENTIFIER ::= { mscVrIp 16 }



mscVrIpBootpRowStatusTable OBJECT-TYPE
   SYNTAX     SEQUENCE OF MscVrIpBootpRowStatusEntry
   ACCESS     not-accessible
   STATUS     mandatory
   DESCRIPTION
     "This entry controls the addition and deletion of 
      mscVrIpBootp components."
::= { mscVrIpBootp 1 }

mscVrIpBootpRowStatusEntry OBJECT-TYPE
   SYNTAX     MscVrIpBootpRowStatusEntry
   ACCESS     not-accessible
   STATUS     mandatory
   DESCRIPTION
     "A single entry in the table represents a single 
      mscVrIpBootp component."
   INDEX {
      mscVrIndex,
      mscVrIpIndex,
      mscVrIpBootpIndex }
::= { mscVrIpBootpRowStatusTable 1 }

MscVrIpBootpRowStatusEntry ::= SEQUENCE {
   mscVrIpBootpRowStatus
      RowStatus,
   mscVrIpBootpComponentName
      DisplayString,
   mscVrIpBootpStorageType
      StorageType,
   mscVrIpBootpIndex
      NonReplicated }

mscVrIpBootpRowStatus OBJECT-TYPE
   SYNTAX     RowStatus 
   ACCESS     read-write
   STATUS     mandatory
   DESCRIPTION
     "This variable is used as the basis for SNMP naming of
      mscVrIpBootp components.
      These components can be added and deleted."
::= { mscVrIpBootpRowStatusEntry 1 }

mscVrIpBootpComponentName OBJECT-TYPE
   SYNTAX     DisplayString 
   ACCESS     read-only
   STATUS     mandatory
   DESCRIPTION
     "This variable provides the component's string name for
      use with the ASCII Console Interface"
::= { mscVrIpBootpRowStatusEntry 2 }

mscVrIpBootpStorageType OBJECT-TYPE
   SYNTAX     StorageType 
   ACCESS     read-only
   STATUS     mandatory
   DESCRIPTION
     "This variable represents the storage type value for the
      mscVrIpBootp tables."
::= { mscVrIpBootpRowStatusEntry 4 }

mscVrIpBootpIndex OBJECT-TYPE
   SYNTAX     NonReplicated 
   ACCESS     not-accessible
   STATUS     mandatory
   DESCRIPTION
     "This variable represents the index for the mscVrIpBootp tables."
::= { mscVrIpBootpRowStatusEntry 10 }

mscVrIpBootpAdminControlTable OBJECT-TYPE
   SYNTAX     SEQUENCE OF MscVrIpBootpAdminControlEntry
   ACCESS     not-accessible
   STATUS     mandatory
   DESCRIPTION
     "This group includes the Administrative Control attribute. This 
      attribute defines the current administrative state of this component."
::= { mscVrIpBootp 10 }

mscVrIpBootpAdminControlEntry OBJECT-TYPE
   SYNTAX     MscVrIpBootpAdminControlEntry
   ACCESS     not-accessible
   STATUS     mandatory
   DESCRIPTION
     "An entry in the mscVrIpBootpAdminControlTable."
   INDEX {
      mscVrIndex,
      mscVrIpIndex,
      mscVrIpBootpIndex }
::= { mscVrIpBootpAdminControlTable 1 }

MscVrIpBootpAdminControlEntry ::= SEQUENCE {
   mscVrIpBootpSnmpAdminStatus
      INTEGER }

mscVrIpBootpSnmpAdminStatus OBJECT-TYPE
   SYNTAX     INTEGER  {
                 up(1),
                 down(2),
                 testing(3) }
   ACCESS     read-write
   STATUS     mandatory
   DESCRIPTION
     "The desired state of the interface. The up state indicates the 
      interface is operational and packet forwarding is allowed. The down 
      state indicates the interface is not operational and packet forwarding 
      is unavailable. The testing state indicates that no operational 
      packets can be passed."
   DEFVAL     { up }
::= { mscVrIpBootpAdminControlEntry 1 }

mscVrIpBootpProvTable OBJECT-TYPE
   SYNTAX     SEQUENCE OF MscVrIpBootpProvEntry
   ACCESS     not-accessible
   STATUS     mandatory
   DESCRIPTION
     "This group contains provisionable attributes for the BootpRelayAgent 
      component."
::= { mscVrIpBootp 11 }

mscVrIpBootpProvEntry OBJECT-TYPE
   SYNTAX     MscVrIpBootpProvEntry
   ACCESS     not-accessible
   STATUS     mandatory
   DESCRIPTION
     "An entry in the mscVrIpBootpProvTable."
   INDEX {
      mscVrIndex,
      mscVrIpIndex,
      mscVrIpBootpIndex }
::= { mscVrIpBootpProvTable 1 }

MscVrIpBootpProvEntry ::= SEQUENCE {
   mscVrIpBootpHopDiscardThreshold
      Unsigned32 }

mscVrIpBootpHopDiscardThreshold OBJECT-TYPE
   SYNTAX     Unsigned32 (2..16)
   ACCESS     read-write
   STATUS     mandatory
   DESCRIPTION
     "BOOTP packets contain a 'hops' field which is used to limit the number 
      of relay agents that can process the packet (each relay agent increments 
      the 'hops' field by one). This attribute is used by the relay agent to 
      determine when to discard a BOOTP packet. If the 'hops' field exceeds 
      the hopDiscardThreshold the BOOTP packet will be discarded."
   DEFVAL     { 4 }
::= { mscVrIpBootpProvEntry 1 }

mscVrIpBootpStateTable OBJECT-TYPE
   SYNTAX     SEQUENCE OF MscVrIpBootpStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscVrIpBootp 12 }

mscVrIpBootpStateEntry OBJECT-TYPE
   SYNTAX     MscVrIpBootpStateEntry
   ACCESS     not-accessible
   STATUS     mandatory
   DESCRIPTION
     "An entry in the mscVrIpBootpStateTable."
   INDEX {
      mscVrIndex,
      mscVrIpIndex,
      mscVrIpBootpIndex }
::= { mscVrIpBootpStateTable 1 }

MscVrIpBootpStateEntry ::= SEQUENCE {
   mscVrIpBootpAdminState
      INTEGER,
   mscVrIpBootpOperationalState
      INTEGER,
   mscVrIpBootpUsageState
      INTEGER }

mscVrIpBootpAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscVrIpBootpStateEntry 1 }

mscVrIpBootpOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscVrIpBootpStateEntry 2 }

mscVrIpBootpUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscVrIpBootpStateEntry 3 }

mscVrIpBootpOperStatusTable OBJECT-TYPE
   SYNTAX     SEQUENCE OF MscVrIpBootpOperStatusEntry
   ACCESS     not-accessible
   STATUS     mandatory
   DESCRIPTION
     "This group includes the Operational Status attribute. This attribute 
      defines the current operational state of this component."
::= { mscVrIpBootp 13 }

mscVrIpBootpOperStatusEntry OBJECT-TYPE
   SYNTAX     MscVrIpBootpOperStatusEntry
   ACCESS     not-accessible
   STATUS     mandatory
   DESCRIPTION
     "An entry in the mscVrIpBootpOperStatusTable."
   INDEX {
      mscVrIndex,
      mscVrIpIndex,
      mscVrIpBootpIndex }
::= { mscVrIpBootpOperStatusTable 1 }

MscVrIpBootpOperStatusEntry ::= SEQUENCE {
   mscVrIpBootpSnmpOperStatus
      INTEGER }

mscVrIpBootpSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscVrIpBootpOperStatusEntry 1 }

-- 
-- *** THIS SUBTREE CURRENTLY NOT IMPLEMENTED ***
-- 

-- Vr/<string> Ip BootpRelayAgent BootpPortEntry/<string>
-- The BootpPortEntry component contains information about the 
-- provisioned BootpPort's under IpPort components. This component is 
-- indexed by a string which represents a VirtualRouter ProtocolPort 
-- component name.

mscVrIpBootpPpE OBJECT IDENTIFIER ::= { mscVrIpBootp 2 }



mscVrIpBootpPpERowStatusTable OBJECT-TYPE
   SYNTAX     SEQUENCE OF MscVrIpBootpPpERowStatusEntry
   ACCESS     not-accessible
   STATUS     mandatory
   DESCRIPTION
     "*** THIS TABLE CURRENTLY NOT IMPLEMENTED ***

      This entry controls the addition and deletion of 
      mscVrIpBootpPpE components."
::= { mscVrIpBootpPpE 1 }

mscVrIpBootpPpERowStatusEntry OBJECT-TYPE
   SYNTAX     MscVrIpBootpPpERowStatusEntry
   ACCESS     not-accessible
   STATUS     mandatory
   DESCRIPTION
     "A single entry in the table represents a single 
      mscVrIpBootpPpE component."
   INDEX {
      mscVrIndex,
      mscVrIpIndex,
      mscVrIpBootpIndex,
      mscVrIpBootpPpEIndex }
::= { mscVrIpBootpPpERowStatusTable 1 }

MscVrIpBootpPpERowStatusEntry ::= SEQUENCE {
   mscVrIpBootpPpERowStatus
      RowStatus,
   mscVrIpBootpPpEComponentName
      DisplayString,
   mscVrIpBootpPpEStorageType
      StorageType,
   mscVrIpBootpPpEIndex
      AsciiStringIndex }

mscVrIpBootpPpERowStatus OBJECT-TYPE
   SYNTAX     RowStatus 
   ACCESS     read-only
   STATUS     mandatory
   DESCRIPTION
     "This variable is used as the basis for SNMP naming of
      mscVrIpBootpPpE components.
      These components cannot be added nor deleted."
::= { mscVrIpBootpPpERowStatusEntry 1 }

mscVrIpBootpPpEComponentName OBJECT-TYPE
   SYNTAX     DisplayString 
   ACCESS     read-only
   STATUS     mandatory
   DESCRIPTION
     "This variable provides the component's string name for
      use with the ASCII Console Interface"
::= { mscVrIpBootpPpERowStatusEntry 2 }

mscVrIpBootpPpEStorageType OBJECT-TYPE
   SYNTAX     StorageType 
   ACCESS     read-only
   STATUS     mandatory
   DESCRIPTION
     "This variable represents the storage type value for the
      mscVrIpBootpPpE tables."
::= { mscVrIpBootpPpERowStatusEntry 4 }

mscVrIpBootpPpEIndex OBJECT-TYPE
   SYNTAX     AsciiStringIndex (SIZE (1..20))
   ACCESS     not-accessible
   STATUS     mandatory
   DESCRIPTION
     "This variable represents the index for the mscVrIpBootpPpE tables."
::= { mscVrIpBootpPpERowStatusEntry 10 }

mscVrIpBootpPpEOperTable OBJECT-TYPE
   SYNTAX     SEQUENCE OF MscVrIpBootpPpEOperEntry
   ACCESS     not-accessible
   STATUS     mandatory
   DESCRIPTION
     "*** THIS TABLE CURRENTLY NOT IMPLEMENTED ***

      This group contains BootpPortEntry component operational data."
::= { mscVrIpBootpPpE 10 }

mscVrIpBootpPpEOperEntry OBJECT-TYPE
   SYNTAX     MscVrIpBootpPpEOperEntry
   ACCESS     not-accessible
   STATUS     mandatory
   DESCRIPTION
     "An entry in the mscVrIpBootpPpEOperTable."
   INDEX {
      mscVrIndex,
      mscVrIpIndex,
      mscVrIpBootpIndex,
      mscVrIpBootpPpEIndex }
::= { mscVrIpBootpPpEOperTable 1 }

MscVrIpBootpPpEOperEntry ::= SEQUENCE {
   mscVrIpBootpPpEStatus
      INTEGER }

mscVrIpBootpPpEStatus OBJECT-TYPE
   SYNTAX     INTEGER  {
                 up(1),
                 down(2),
                 disabled(3) }
   ACCESS     read-only
   STATUS     mandatory
   DESCRIPTION
     "This attribute indicates the status of the provisioned BootpPortEntry 
      component. A value of disabled is used when the parent components, 
      Vr, Ip, IpPort, or BootpRelayAgent is in a disabled state. A value of up 
      is used when the BootpPortEntry is in an operational state. A state of 
      down is used if the media associated with the BootpPortEntry is not 
      ready or disabled."
::= { mscVrIpBootpPpEOperEntry 1 }

mscVrIpBootpPpEStatsTable OBJECT-TYPE
   SYNTAX     SEQUENCE OF MscVrIpBootpPpEStatsEntry
   ACCESS     not-accessible
   STATUS     mandatory
   DESCRIPTION
     "*** THIS TABLE CURRENTLY NOT IMPLEMENTED ***

      This group contains BootpPortEntry component statistics."
::= { mscVrIpBootpPpE 11 }

mscVrIpBootpPpEStatsEntry OBJECT-TYPE
   SYNTAX     MscVrIpBootpPpEStatsEntry
   ACCESS     not-accessible
   STATUS     mandatory
   DESCRIPTION
     "An entry in the mscVrIpBootpPpEStatsTable."
   INDEX {
      mscVrIndex,
      mscVrIpIndex,
      mscVrIpBootpIndex,
      mscVrIpBootpPpEIndex }
::= { mscVrIpBootpPpEStatsTable 1 }

MscVrIpBootpPpEStatsEntry ::= SEQUENCE {
   mscVrIpBootpPpEInRequests
      Counter32,
   mscVrIpBootpPpEInReplies
      Counter32,
   mscVrIpBootpPpEOutRequests
      Counter32,
   mscVrIpBootpPpEOutReplies
      Counter32,
   mscVrIpBootpPpEInRequestErrors
      Counter32,
   mscVrIpBootpPpEInReplyErrors
      Counter32 }

mscVrIpBootpPpEInRequests OBJECT-TYPE
   SYNTAX     Counter32 
   ACCESS     read-only
   STATUS     mandatory
   DESCRIPTION
     "This attribute counts the total number of BOOTP Request messages 
      received on this port."
::= { mscVrIpBootpPpEStatsEntry 1 }

mscVrIpBootpPpEInReplies OBJECT-TYPE
   SYNTAX     Counter32 
   ACCESS     read-only
   STATUS     mandatory
   DESCRIPTION
     "This attribute counts the total number of BOOTP Reply messages 
      received on this port."
::= { mscVrIpBootpPpEStatsEntry 2 }

mscVrIpBootpPpEOutRequests OBJECT-TYPE
   SYNTAX     Counter32 
   ACCESS     read-only
   STATUS     mandatory
   DESCRIPTION
     "This attribute counts total the number of BOOTP Request messages 
      broadcast out on this port."
::= { mscVrIpBootpPpEStatsEntry 3 }

mscVrIpBootpPpEOutReplies OBJECT-TYPE
   SYNTAX     Counter32 
   ACCESS     read-only
   STATUS     mandatory
   DESCRIPTION
     "This attribute counts the total number of BOOTP Reply messages sent 
      out on this port."
::= { mscVrIpBootpPpEStatsEntry 4 }

mscVrIpBootpPpEInRequestErrors OBJECT-TYPE
   SYNTAX     Counter32 
   ACCESS     read-only
   STATUS     mandatory
   DESCRIPTION
     "This attribute counts the number of BOOTP Request messages received 
      on this port but not forwarded due to an error. An error occurs if the 
      BOOTP hop limit has been exceeded."
::= { mscVrIpBootpPpEStatsEntry 5 }

mscVrIpBootpPpEInReplyErrors OBJECT-TYPE
   SYNTAX     Counter32 
   ACCESS     read-only
   STATUS     mandatory
   DESCRIPTION
     "This attribute counts the number of BOOTP Reply messages received on 
      this port but not forwarded due to an error. An error occurs if the giaddr 
      field in the BOOTP reply does not match an IP address assigned to this 
      VirtualRouter, or if the output IpPort for the BOOTP reply is not 
      provisioned for BOOTP."
::= { mscVrIpBootpPpEStatsEntry 6 }

-- 
-- *** THIS SUBTREE CURRENTLY NOT IMPLEMENTED ***
-- 

-- Vr/<string> Ip Cache/n
-- This component represents the IP cache table on LP n.

mscVrIpCache OBJECT IDENTIFIER ::= { mscVrIp 17 }



mscVrIpCacheRowStatusTable OBJECT-TYPE
   SYNTAX     SEQUENCE OF MscVrIpCacheRowStatusEntry
   ACCESS     not-accessible
   STATUS     mandatory
   DESCRIPTION
     "*** THIS TABLE CURRENTLY NOT IMPLEMENTED ***

      This entry controls the addition and deletion of 
      mscVrIpCache components."
::= { mscVrIpCache 1 }

mscVrIpCacheRowStatusEntry OBJECT-TYPE
   SYNTAX     MscVrIpCacheRowStatusEntry
   ACCESS     not-accessible
   STATUS     mandatory
   DESCRIPTION
     "A single entry in the table represents a single 
      mscVrIpCache component."
   INDEX {
      mscVrIndex,
      mscVrIpIndex,
      mscVrIpCacheIndex }
::= { mscVrIpCacheRowStatusTable 1 }

MscVrIpCacheRowStatusEntry ::= SEQUENCE {
   mscVrIpCacheRowStatus
      RowStatus,
   mscVrIpCacheComponentName
      DisplayString,
   mscVrIpCacheStorageType
      StorageType,
   mscVrIpCacheIndex
      Integer32 }

mscVrIpCacheRowStatus OBJECT-TYPE
   SYNTAX     RowStatus 
   ACCESS     read-only
   STATUS     mandatory
   DESCRIPTION
     "This variable is used as the basis for SNMP naming of
      mscVrIpCache components.
      These components cannot be added nor deleted."
::= { mscVrIpCacheRowStatusEntry 1 }

mscVrIpCacheComponentName OBJECT-TYPE
   SYNTAX     DisplayString 
   ACCESS     read-only
   STATUS     mandatory
   DESCRIPTION
     "This variable provides the component's string name for
      use with the ASCII Console Interface"
::= { mscVrIpCacheRowStatusEntry 2 }

mscVrIpCacheStorageType OBJECT-TYPE
   SYNTAX     StorageType 
   ACCESS     read-only
   STATUS     mandatory
   DESCRIPTION
     "This variable represents the storage type value for the
      mscVrIpCache tables."
::= { mscVrIpCacheRowStatusEntry 4 }

mscVrIpCacheIndex OBJECT-TYPE
   SYNTAX     Integer32 (0..15)
   ACCESS     not-accessible
   STATUS     mandatory
   DESCRIPTION
     "This variable represents the index for the mscVrIpCache tables."
::= { mscVrIpCacheRowStatusEntry 10 }

mscVrIpCacheStateTable OBJECT-TYPE
   SYNTAX     SEQUENCE OF MscVrIpCacheStateEntry
   ACCESS     not-accessible
   STATUS     mandatory
   DESCRIPTION
     "*** THIS TABLE CURRENTLY NOT IMPLEMENTED ***

      This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscVrIpCache 10 }

mscVrIpCacheStateEntry OBJECT-TYPE
   SYNTAX     MscVrIpCacheStateEntry
   ACCESS     not-accessible
   STATUS     mandatory
   DESCRIPTION
     "An entry in the mscVrIpCacheStateTable."
   INDEX {
      mscVrIndex,
      mscVrIpIndex,
      mscVrIpCacheIndex }
::= { mscVrIpCacheStateTable 1 }

MscVrIpCacheStateEntry ::= SEQUENCE {
   mscVrIpCacheAdminState
      INTEGER,
   mscVrIpCacheOperationalState
      INTEGER,
   mscVrIpCacheUsageState
      INTEGER }

mscVrIpCacheAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscVrIpCacheStateEntry 1 }

mscVrIpCacheOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscVrIpCacheStateEntry 2 }

mscVrIpCacheUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscVrIpCacheStateEntry 3 }

mscVrIpCacheOperTable OBJECT-TYPE
   SYNTAX     SEQUENCE OF MscVrIpCacheOperEntry
   ACCESS     not-accessible
   STATUS     mandatory
   DESCRIPTION
     "*** THIS TABLE CURRENTLY NOT IMPLEMENTED ***

      This group houses all the operational attributes of an Ip cache table."
::= { mscVrIpCache 11 }

mscVrIpCacheOperEntry OBJECT-TYPE
   SYNTAX     MscVrIpCacheOperEntry
   ACCESS     not-accessible
   STATUS     mandatory
   DESCRIPTION
     "An entry in the mscVrIpCacheOperTable."
   INDEX {
      mscVrIndex,
      mscVrIpIndex,
      mscVrIpCacheIndex }
::= { mscVrIpCacheOperTable 1 }

MscVrIpCacheOperEntry ::= SEQUENCE {
   mscVrIpCacheEntriesFree
      Unsigned32,
   mscVrIpCacheTotalLookups
      Unsigned32,
   mscVrIpCacheLookupMisses
      Counter32,
   mscVrIpCacheCacheTableMaxEntries
      Unsigned32 }

mscVrIpCacheEntriesFree OBJECT-TYPE
   SYNTAX     Unsigned32 (0..8000)
   ACCESS     read-only
   STATUS     mandatory
   DESCRIPTION
     "This attribute is indicative of the number of free Ip cache table entries.
      A consistently high value for this attribute indicates that there is a 
      resource surplus of the memory requirements for cache table. This 
      surplus could be utilized elsewhere if needed by adjusting the 
      cacheTableMaxEntries under the Ip component."
::= { mscVrIpCacheOperEntry 3 }

mscVrIpCacheTotalLookups OBJECT-TYPE
   SYNTAX     Unsigned32 (0..4294967295)
   ACCESS     read-only
   STATUS     mandatory
   DESCRIPTION
     "This attribute indicates the total number of local cache lookups. It wraps 
      around to 0 when it reaches the maximum value of 4294967295."
::= { mscVrIpCacheOperEntry 4 }

mscVrIpCacheLookupMisses OBJECT-TYPE
   SYNTAX     Counter32 
   ACCESS     read-only
   STATUS     mandatory
   DESCRIPTION
     "This attribute indicates the total number of local cache lookup misses. It 
      wraps around to 0 when it reaches the maximum value of 4294967295."
::= { mscVrIpCacheOperEntry 5 }

mscVrIpCacheCacheTableMaxEntries OBJECT-TYPE
   SYNTAX     Unsigned32 (0..8000)
   ACCESS     read-only
   STATUS     mandatory
   DESCRIPTION
     "This attribute indicates the current maximum number of entries that can 
      exist in the IP local cache table on each LP."
::= { mscVrIpCacheOperEntry 395 }


-- Vr/<string> Ip Tunnel
-- The Tunnel component is used to add, delete and modify tunnel end 
-- points.

mscVrIpTunnel OBJECT IDENTIFIER ::= { mscVrIp 18 }



mscVrIpTunnelRowStatusTable OBJECT-TYPE
   SYNTAX     SEQUENCE OF MscVrIpTunnelRowStatusEntry
   ACCESS     not-accessible
   STATUS     mandatory
   DESCRIPTION
     "This entry controls the addition and deletion of 
      mscVrIpTunnel components."
::= { mscVrIpTunnel 1 }

mscVrIpTunnelRowStatusEntry OBJECT-TYPE
   SYNTAX     MscVrIpTunnelRowStatusEntry
   ACCESS     not-accessible
   STATUS     mandatory
   DESCRIPTION
     "A single entry in the table represents a single 
      mscVrIpTunnel component."
   INDEX {
      mscVrIndex,
      mscVrIpIndex,
      mscVrIpTunnelIndex }
::= { mscVrIpTunnelRowStatusTable 1 }

MscVrIpTunnelRowStatusEntry ::= SEQUENCE {
   mscVrIpTunnelRowStatus
      RowStatus,
   mscVrIpTunnelComponentName
      DisplayString,
   mscVrIpTunnelStorageType
      StorageType,
   mscVrIpTunnelIndex
      NonReplicated }

mscVrIpTunnelRowStatus OBJECT-TYPE
   SYNTAX     RowStatus 
   ACCESS     read-write
   STATUS     mandatory
   DESCRIPTION
     "This variable is used as the basis for SNMP naming of
      mscVrIpTunnel components.
      These components can be added and deleted."
::= { mscVrIpTunnelRowStatusEntry 1 }

mscVrIpTunnelComponentName OBJECT-TYPE
   SYNTAX     DisplayString 
   ACCESS     read-only
   STATUS     mandatory
   DESCRIPTION
     "This variable provides the component's string name for
      use with the ASCII Console Interface"
::= { mscVrIpTunnelRowStatusEntry 2 }

mscVrIpTunnelStorageType OBJECT-TYPE
   SYNTAX     StorageType 
   ACCESS     read-only
   STATUS     mandatory
   DESCRIPTION
     "This variable represents the storage type value for the
      mscVrIpTunnel tables."
::= { mscVrIpTunnelRowStatusEntry 4 }

mscVrIpTunnelIndex OBJECT-TYPE
   SYNTAX     NonReplicated 
   ACCESS     not-accessible
   STATUS     mandatory
   DESCRIPTION
     "This variable represents the index for the mscVrIpTunnel tables."
::= { mscVrIpTunnelRowStatusEntry 10 }

mscVrIpTunnelStateTable OBJECT-TYPE
   SYNTAX     SEQUENCE OF MscVrIpTunnelStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscVrIpTunnel 12 }

mscVrIpTunnelStateEntry OBJECT-TYPE
   SYNTAX     MscVrIpTunnelStateEntry
   ACCESS     not-accessible
   STATUS     mandatory
   DESCRIPTION
     "An entry in the mscVrIpTunnelStateTable."
   INDEX {
      mscVrIndex,
      mscVrIpIndex,
      mscVrIpTunnelIndex }
::= { mscVrIpTunnelStateTable 1 }

MscVrIpTunnelStateEntry ::= SEQUENCE {
   mscVrIpTunnelAdminState
      INTEGER,
   mscVrIpTunnelOperationalState
      INTEGER,
   mscVrIpTunnelUsageState
      INTEGER }

mscVrIpTunnelAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscVrIpTunnelStateEntry 1 }

mscVrIpTunnelOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscVrIpTunnelStateEntry 2 }

mscVrIpTunnelUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscVrIpTunnelStateEntry 3 }


-- Vr/<string> Ip Tunnel StaticEndPoint/n
-- An IP tunnel allows two geographically separated networks to be 
-- connected over a shared IP network (for example the Internet), 
-- either because the networks at the end points are using private IP 
-- address or they are not running IP as the network protocol.
-- 
-- This component represents a static IP Tunnel End Point. It is static 
-- in the sense that both the tunnel source and destination IP addresses 
-- are static configured. For proper operation of the tunnel, the exact 
-- source and destination IP addresses (in reverse order) must be used 
-- to provision the Tunnel End Point on the far end router.
-- 
-- Two types of IP tunnel encapsulation are supported: IP in IP as 
-- specified in RFC 2003 and Generic Routing Encapsulation as 
-- specified in RFC 1701.
-- 

mscVrIpTunnelSep OBJECT IDENTIFIER ::= { mscVrIpTunnel 10 }



mscVrIpTunnelSepRowStatusTable OBJECT-TYPE
   SYNTAX     SEQUENCE OF MscVrIpTunnelSepRowStatusEntry
   ACCESS     not-accessible
   STATUS     mandatory
   DESCRIPTION
     "This entry controls the addition and deletion of 
      mscVrIpTunnelSep components."
::= { mscVrIpTunnelSep 1 }

mscVrIpTunnelSepRowStatusEntry OBJECT-TYPE
   SYNTAX     MscVrIpTunnelSepRowStatusEntry
   ACCESS     not-accessible
   STATUS     mandatory
   DESCRIPTION
     "A single entry in the table represents a single 
      mscVrIpTunnelSep component."
   INDEX {
      mscVrIndex,
      mscVrIpIndex,
      mscVrIpTunnelIndex,
      mscVrIpTunnelSepIndex }
::= { mscVrIpTunnelSepRowStatusTable 1 }

MscVrIpTunnelSepRowStatusEntry ::= SEQUENCE {
   mscVrIpTunnelSepRowStatus
      RowStatus,
   mscVrIpTunnelSepComponentName
      DisplayString,
   mscVrIpTunnelSepStorageType
      StorageType,
   mscVrIpTunnelSepIndex
      Integer32 }

mscVrIpTunnelSepRowStatus OBJECT-TYPE
   SYNTAX     RowStatus 
   ACCESS     read-write
   STATUS     mandatory
   DESCRIPTION
     "This variable is used as the basis for SNMP naming of
      mscVrIpTunnelSep components.
      These components can be added and deleted."
::= { mscVrIpTunnelSepRowStatusEntry 1 }

mscVrIpTunnelSepComponentName OBJECT-TYPE
   SYNTAX     DisplayString 
   ACCESS     read-only
   STATUS     mandatory
   DESCRIPTION
     "This variable provides the component's string name for
      use with the ASCII Console Interface"
::= { mscVrIpTunnelSepRowStatusEntry 2 }

mscVrIpTunnelSepStorageType OBJECT-TYPE
   SYNTAX     StorageType 
   ACCESS     read-only
   STATUS     mandatory
   DESCRIPTION
     "This variable represents the storage type value for the
      mscVrIpTunnelSep tables."
::= { mscVrIpTunnelSepRowStatusEntry 4 }

mscVrIpTunnelSepIndex OBJECT-TYPE
   SYNTAX     Integer32 (0..63)
   ACCESS     not-accessible
   STATUS     mandatory
   DESCRIPTION
     "This variable represents the index for the mscVrIpTunnelSep tables."
::= { mscVrIpTunnelSepRowStatusEntry 10 }

mscVrIpTunnelSepIfEntryTable OBJECT-TYPE
   SYNTAX     SEQUENCE OF MscVrIpTunnelSepIfEntryEntry
   ACCESS     not-accessible
   STATUS     mandatory
   DESCRIPTION
     "This group contains the provisionable attributes for the ifEntry."
::= { mscVrIpTunnelSep 10 }

mscVrIpTunnelSepIfEntryEntry OBJECT-TYPE
   SYNTAX     MscVrIpTunnelSepIfEntryEntry
   ACCESS     not-accessible
   STATUS     mandatory
   DESCRIPTION
     "An entry in the mscVrIpTunnelSepIfEntryTable."
   INDEX {
      mscVrIndex,
      mscVrIpIndex,
      mscVrIpTunnelIndex,
      mscVrIpTunnelSepIndex }
::= { mscVrIpTunnelSepIfEntryTable 1 }

MscVrIpTunnelSepIfEntryEntry ::= SEQUENCE {
   mscVrIpTunnelSepIfAdminStatus
      INTEGER,
   mscVrIpTunnelSepIfIndex
      InterfaceIndex }

mscVrIpTunnelSepIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { mscVrIpTunnelSepIfEntryEntry 1 }

mscVrIpTunnelSepIfIndex OBJECT-TYPE
   SYNTAX     InterfaceIndex (1..65535)
   ACCESS     read-only
   STATUS     mandatory
   DESCRIPTION
     "This is the index for the IfEntry. Its value is automatically initialized 
      during the provisioning process."
::= { mscVrIpTunnelSepIfEntryEntry 2 }

mscVrIpTunnelSepMpTable OBJECT-TYPE
   SYNTAX     SEQUENCE OF MscVrIpTunnelSepMpEntry
   ACCESS     not-accessible
   STATUS     mandatory
   DESCRIPTION
     "This group contains the base provisioning data for the media base 
      component."
::= { mscVrIpTunnelSep 11 }

mscVrIpTunnelSepMpEntry OBJECT-TYPE
   SYNTAX     MscVrIpTunnelSepMpEntry
   ACCESS     not-accessible
   STATUS     mandatory
   DESCRIPTION
     "An entry in the mscVrIpTunnelSepMpTable."
   INDEX {
      mscVrIndex,
      mscVrIpIndex,
      mscVrIpTunnelIndex,
      mscVrIpTunnelSepIndex }
::= { mscVrIpTunnelSepMpTable 1 }

MscVrIpTunnelSepMpEntry ::= SEQUENCE {
   mscVrIpTunnelSepLinkToProtocolPort
      Link }

mscVrIpTunnelSepLinkToProtocolPort OBJECT-TYPE
   SYNTAX     Link 
   ACCESS     read-write
   STATUS     mandatory
   DESCRIPTION
     "This attribute specifies the ProtocolPort to which this interface is 
      linked to. The protocol port is the logical interface to the network. 
      The protocol port component describes the logical characteristics of 
      this interface."
::= { mscVrIpTunnelSepMpEntry 1 }

mscVrIpTunnelSepProvTable OBJECT-TYPE
   SYNTAX     SEQUENCE OF MscVrIpTunnelSepProvEntry
   ACCESS     not-accessible
   STATUS     mandatory
   DESCRIPTION
     "This group contains the provisionable attributes for the 
      StaticEndPoint component."
::= { mscVrIpTunnelSep 12 }

mscVrIpTunnelSepProvEntry OBJECT-TYPE
   SYNTAX     MscVrIpTunnelSepProvEntry
   ACCESS     not-accessible
   STATUS     mandatory
   DESCRIPTION
     "An entry in the mscVrIpTunnelSepProvTable."
   INDEX {
      mscVrIndex,
      mscVrIpIndex,
      mscVrIpTunnelIndex,
      mscVrIpTunnelSepIndex }
::= { mscVrIpTunnelSepProvTable 1 }

MscVrIpTunnelSepProvEntry ::= SEQUENCE {
   mscVrIpTunnelSepEncapType
      INTEGER,
   mscVrIpTunnelSepSourceAddress
      IpAddress,
   mscVrIpTunnelSepDestinationAddress
      IpAddress }

mscVrIpTunnelSepEncapType OBJECT-TYPE
   SYNTAX     INTEGER  {
                 ipInIp(0),
                 greIp(1) }
   ACCESS     read-write
   STATUS     mandatory
   DESCRIPTION
     "There are two types of encapsulation techniques for IP tunnel, IP in 
      IP (RFC 2003) and GRE over IP (RFC 1701). This attributes 
      specifies the encapsulation type of the IP tunnel.
      
      ipInIp: As defined in RFC 2003, it can be used to encapsulated IP 
      and IP payload only. If IP is the only type of payload to be 
      encapsulated by the tunnel, this type of encapsulation is 
      recommended as it requires less processing and uses less 
      bandwidth.
      
      greIp: As defined in RFC 1701, it can be used to encapsulate IP or 
      IPX payload. To encapsulate IPX payload, this encapsulation type 
      must be used."
   DEFVAL     { ipInIp }
::= { mscVrIpTunnelSepProvEntry 1 }

mscVrIpTunnelSepSourceAddress OBJECT-TYPE
   SYNTAX     IpAddress 
   ACCESS     read-write
   STATUS     mandatory
   DESCRIPTION
     "This attribute specifies the IP address of the local end of the tunnel. 
      The source address must be an address in the shared domain, and it 
      must equal to an interface address on its own Virtual Router (under 
      Vr/<string> Pp/<string> IpPort LogicalIf/<IpAddress>). 
      However, it must not be the interface address of the linked protocol 
      port's IpPort component."
   DEFVAL     { '00000000'H }  -- "0.0.0.0"
::= { mscVrIpTunnelSepProvEntry 2 }

mscVrIpTunnelSepDestinationAddress OBJECT-TYPE
   SYNTAX     IpAddress 
   ACCESS     read-write
   STATUS     mandatory
   DESCRIPTION
     "This attribute specifies the IP address of the far end of the tunnel. It 
      must not match any of the IP interface addresses on this Virtual 
      Router."
   DEFVAL     { '00000000'H }  -- "0.0.0.0"
::= { mscVrIpTunnelSepProvEntry 3 }

mscVrIpTunnelSepOperTable OBJECT-TYPE
   SYNTAX     SEQUENCE OF MscVrIpTunnelSepOperEntry
   ACCESS     not-accessible
   STATUS     mandatory
   DESCRIPTION
     "This group contains the operational status attributes of the 
      StaticEndPoint component."
::= { mscVrIpTunnelSep 14 }

mscVrIpTunnelSepOperEntry OBJECT-TYPE
   SYNTAX     MscVrIpTunnelSepOperEntry
   ACCESS     not-accessible
   STATUS     mandatory
   DESCRIPTION
     "An entry in the mscVrIpTunnelSepOperTable."
   INDEX {
      mscVrIndex,
      mscVrIpIndex,
      mscVrIpTunnelIndex,
      mscVrIpTunnelSepIndex }
::= { mscVrIpTunnelSepOperTable 1 }

MscVrIpTunnelSepOperEntry ::= SEQUENCE {
   mscVrIpTunnelSepDiscoveredPathMtu
      Unsigned32 }

mscVrIpTunnelSepDiscoveredPathMtu OBJECT-TYPE
   SYNTAX     Unsigned32 (0..0 | 576..18944)
   ACCESS     read-only
   STATUS     mandatory
   DESCRIPTION
     "This attribute indicates the latest learned Path MTU of the tunnel.
      
      An MTU is the maximum transmission unit of an arbitrary internet 
      path. When a large amount of IP datagrams are to be transmitted, it 
      is usually preferable that the datagrams be of the largest size that 
      does not require fragmentation anywhere along the path from the 
      source to the destination. This datagram size is referred to as the 
      Path MTU (PMTU). It is equal to the minimum of the MTUs of 
      each hop in the path."
   DEFVAL     { 0 }
::= { mscVrIpTunnelSepOperEntry 1 }


-- Vr/<string> Ip Tunnel MultipointStaticEndPoint/n
-- An IP tunnel allows more than one geographically separated 
-- networks to be connected over a shared IP network (for example the 
-- Internet) because because the networks at the end points are using 
-- private IP address.
-- 
-- This component represents a static IP Tunnel End Point of a point-
-- to-multipoint IP Tunneling configuration. It is static in the sense 
-- that both the tunnel source address and the list of destination IP 
-- addresses are statically configured.
-- 
-- Only one type of IP tunnel encapsulation is supported: IP in IP as 
-- specified in RFC 2003.
-- 

mscVrIpTunnelMsep OBJECT IDENTIFIER ::= { mscVrIpTunnel 11 }



mscVrIpTunnelMsepRowStatusTable OBJECT-TYPE
   SYNTAX     SEQUENCE OF MscVrIpTunnelMsepRowStatusEntry
   ACCESS     not-accessible
   STATUS     mandatory
   DESCRIPTION
     "This entry controls the addition and deletion of 
      mscVrIpTunnelMsep components."
::= { mscVrIpTunnelMsep 1 }

mscVrIpTunnelMsepRowStatusEntry OBJECT-TYPE
   SYNTAX     MscVrIpTunnelMsepRowStatusEntry
   ACCESS     not-accessible
   STATUS     mandatory
   DESCRIPTION
     "A single entry in the table represents a single 
      mscVrIpTunnelMsep component."
   INDEX {
      mscVrIndex,
      mscVrIpIndex,
      mscVrIpTunnelIndex,
      mscVrIpTunnelMsepIndex }
::= { mscVrIpTunnelMsepRowStatusTable 1 }

MscVrIpTunnelMsepRowStatusEntry ::= SEQUENCE {
   mscVrIpTunnelMsepRowStatus
      RowStatus,
   mscVrIpTunnelMsepComponentName
      DisplayString,
   mscVrIpTunnelMsepStorageType
      StorageType,
   mscVrIpTunnelMsepIndex
      Integer32 }

mscVrIpTunnelMsepRowStatus OBJECT-TYPE
   SYNTAX     RowStatus 
   ACCESS     read-write
   STATUS     mandatory
   DESCRIPTION
     "This variable is used as the basis for SNMP naming of
      mscVrIpTunnelMsep components.
      These components can be added and deleted."
::= { mscVrIpTunnelMsepRowStatusEntry 1 }

mscVrIpTunnelMsepComponentName OBJECT-TYPE
   SYNTAX     DisplayString 
   ACCESS     read-only
   STATUS     mandatory
   DESCRIPTION
     "This variable provides the component's string name for
      use with the ASCII Console Interface"
::= { mscVrIpTunnelMsepRowStatusEntry 2 }

mscVrIpTunnelMsepStorageType OBJECT-TYPE
   SYNTAX     StorageType 
   ACCESS     read-only
   STATUS     mandatory
   DESCRIPTION
     "This variable represents the storage type value for the
      mscVrIpTunnelMsep tables."
::= { mscVrIpTunnelMsepRowStatusEntry 4 }

mscVrIpTunnelMsepIndex OBJECT-TYPE
   SYNTAX     Integer32 (0..0)
   ACCESS     not-accessible
   STATUS     mandatory
   DESCRIPTION
     "This variable represents the index for the mscVrIpTunnelMsep tables."
::= { mscVrIpTunnelMsepRowStatusEntry 10 }

mscVrIpTunnelMsepIfEntryTable OBJECT-TYPE
   SYNTAX     SEQUENCE OF MscVrIpTunnelMsepIfEntryEntry
   ACCESS     not-accessible
   STATUS     mandatory
   DESCRIPTION
     "This group contains the provisionable attributes for the ifEntry."
::= { mscVrIpTunnelMsep 10 }

mscVrIpTunnelMsepIfEntryEntry OBJECT-TYPE
   SYNTAX     MscVrIpTunnelMsepIfEntryEntry
   ACCESS     not-accessible
   STATUS     mandatory
   DESCRIPTION
     "An entry in the mscVrIpTunnelMsepIfEntryTable."
   INDEX {
      mscVrIndex,
      mscVrIpIndex,
      mscVrIpTunnelIndex,
      mscVrIpTunnelMsepIndex }
::= { mscVrIpTunnelMsepIfEntryTable 1 }

MscVrIpTunnelMsepIfEntryEntry ::= SEQUENCE {
   mscVrIpTunnelMsepIfAdminStatus
      INTEGER,
   mscVrIpTunnelMsepIfIndex
      InterfaceIndex }

mscVrIpTunnelMsepIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { mscVrIpTunnelMsepIfEntryEntry 1 }

mscVrIpTunnelMsepIfIndex OBJECT-TYPE
   SYNTAX     InterfaceIndex (1..65535)
   ACCESS     read-only
   STATUS     mandatory
   DESCRIPTION
     "This is the index for the IfEntry. Its value is automatically initialized 
      during the provisioning process."
::= { mscVrIpTunnelMsepIfEntryEntry 2 }

mscVrIpTunnelMsepMpTable OBJECT-TYPE
   SYNTAX     SEQUENCE OF MscVrIpTunnelMsepMpEntry
   ACCESS     not-accessible
   STATUS     mandatory
   DESCRIPTION
     "This group contains the base provisioning data for the media base 
      component."
::= { mscVrIpTunnelMsep 11 }

mscVrIpTunnelMsepMpEntry OBJECT-TYPE
   SYNTAX     MscVrIpTunnelMsepMpEntry
   ACCESS     not-accessible
   STATUS     mandatory
   DESCRIPTION
     "An entry in the mscVrIpTunnelMsepMpTable."
   INDEX {
      mscVrIndex,
      mscVrIpIndex,
      mscVrIpTunnelIndex,
      mscVrIpTunnelMsepIndex }
::= { mscVrIpTunnelMsepMpTable 1 }

MscVrIpTunnelMsepMpEntry ::= SEQUENCE {
   mscVrIpTunnelMsepLinkToProtocolPort
      Link }

mscVrIpTunnelMsepLinkToProtocolPort OBJECT-TYPE
   SYNTAX     Link 
   ACCESS     read-write
   STATUS     mandatory
   DESCRIPTION
     "This attribute specifies the ProtocolPort to which this interface is 
      linked to. The protocol port is the logical interface to the network. 
      The protocol port component describes the logical characteristics of 
      this interface."
::= { mscVrIpTunnelMsepMpEntry 1 }

mscVrIpTunnelMsepProvTable OBJECT-TYPE
   SYNTAX     SEQUENCE OF MscVrIpTunnelMsepProvEntry
   ACCESS     not-accessible
   STATUS     mandatory
   DESCRIPTION
     "This group contains the provisionable attributes for the 
      MultipointStaticEndPoint component."
::= { mscVrIpTunnelMsep 12 }

mscVrIpTunnelMsepProvEntry OBJECT-TYPE
   SYNTAX     MscVrIpTunnelMsepProvEntry
   ACCESS     not-accessible
   STATUS     mandatory
   DESCRIPTION
     "An entry in the mscVrIpTunnelMsepProvTable."
   INDEX {
      mscVrIndex,
      mscVrIpIndex,
      mscVrIpTunnelIndex,
      mscVrIpTunnelMsepIndex }
::= { mscVrIpTunnelMsepProvTable 1 }

MscVrIpTunnelMsepProvEntry ::= SEQUENCE {
   mscVrIpTunnelMsepPathMtu
      Unsigned32,
   mscVrIpTunnelMsepEncapType
      INTEGER,
   mscVrIpTunnelMsepSharedDomainVirtualRouter
      RowPointer,
   mscVrIpTunnelMsepSourceAddress
      IpAddress }

mscVrIpTunnelMsepPathMtu OBJECT-TYPE
   SYNTAX     Unsigned32 (576..18944)
   ACCESS     read-write
   STATUS     mandatory
   DESCRIPTION
     "This attribute specifies the Path Maximum Transmission Unit 
      (MTU) of the IP Tunnel. If this value is set to a larger Path MTU 
      than the forwarding path of the IP datagram can support, IP 
      fragmentation may occur."
   DEFVAL     { 1604 }
::= { mscVrIpTunnelMsepProvEntry 1 }

mscVrIpTunnelMsepEncapType OBJECT-TYPE
   SYNTAX     INTEGER  {
                 ipInIp(0) }
   ACCESS     read-write
   STATUS     mandatory
   DESCRIPTION
     "This component only supports one type of encapsulation technique 
      for IP tunnel: IP in IP (RFC 2003).
      
      ipInIp: As defined in RFC 2003, it can be used to encapsulated IP 
      and IP payload only."
   DEFVAL     { ipInIp }
::= { mscVrIpTunnelMsepProvEntry 2 }

mscVrIpTunnelMsepSharedDomainVirtualRouter OBJECT-TYPE
   SYNTAX     RowPointer 
   ACCESS     read-write
   STATUS     mandatory
   DESCRIPTION
     "This attribute specifies the virtual router at the source endpoint of 
      the IP tunnel. There must be a virtual router component provisioned 
      with this instance value."
::= { mscVrIpTunnelMsepProvEntry 3 }

mscVrIpTunnelMsepSourceAddress OBJECT-TYPE
   SYNTAX     IpAddress 
   ACCESS     read-write
   STATUS     mandatory
   DESCRIPTION
     "This attribute specifies the IP address of the local end of the IP 
      tunnel in the shared domain. 
      There must be a logical interface with this IP address under the 
      virtual router instance specified in the sharedDomainVirtualRouter 
      attribute.
      This interface IP address cannot be an IP address defined under this 
      IP tunnel protocol port."
   DEFVAL     { '00000000'H }  -- "0.0.0.0"
::= { mscVrIpTunnelMsepProvEntry 4 }

mscVrIpTunnelMsepDstTable OBJECT-TYPE
   SYNTAX     SEQUENCE OF MscVrIpTunnelMsepDstEntry
   ACCESS     not-accessible
   STATUS     mandatory
   DESCRIPTION
     "This attribute specifies the list of IP addresses mapping to each of 
      the far end IP tunnel endpoints in the private domain. It must not 
      match any of the IP interface addresses on the Virtual Router 
      pointed to by the sharedDomainVirtualRouter attribute."
::= { mscVrIpTunnelMsep 834 }

mscVrIpTunnelMsepDstEntry OBJECT-TYPE
   SYNTAX     MscVrIpTunnelMsepDstEntry
   ACCESS     not-accessible
   STATUS     mandatory
   DESCRIPTION
     "An entry in the mscVrIpTunnelMsepDstTable."
   INDEX {
      mscVrIndex,
      mscVrIpIndex,
      mscVrIpTunnelIndex,
      mscVrIpTunnelMsepIndex,
      mscVrIpTunnelMsepDstValue }
::= { mscVrIpTunnelMsepDstTable 1 }

MscVrIpTunnelMsepDstEntry ::= SEQUENCE {
   mscVrIpTunnelMsepDstValue
      IpAddress,
   mscVrIpTunnelMsepDstRowStatus
      RowStatus }

mscVrIpTunnelMsepDstValue OBJECT-TYPE
   SYNTAX     IpAddress 
   ACCESS     read-write
   STATUS     mandatory
   DESCRIPTION
     "This variable represents both the value and the index for the
      mscVrIpTunnelMsepDstTable."
::= { mscVrIpTunnelMsepDstEntry 1 }

mscVrIpTunnelMsepDstRowStatus OBJECT-TYPE
   SYNTAX     RowStatus 
   ACCESS     write-only
   STATUS     mandatory
   DESCRIPTION
     "This variable is used to control the addition and deletion 
      of individual values of the mscVrIpTunnelMsepDstTable."
::= { mscVrIpTunnelMsepDstEntry 2 }




-- 
-- Version and Compliance statements
-- 



-- Object-Group Statement:
-- A list of all current accessible leaf objects.

-- OBJECTS { mscVrIpBootpSnmpOperStatus,
--           mscVrIpStaticRouteNhComponentName,
--           mscVrPpIpPortRelayBcCount,
--           mscVrIpArpDynHostComponentName,
--           mscVrIpEgpOutErrorMsgs,
--           mscVrIpEgpDefaultPollInterval,
--           mscVrIpTcpPassiveOpens,
--           mscVrIpOspfMigrateRip,
--           mscVrIpOspfNbrEvents,
--           mscVrIpOspfExportTag,
--           mscVrIpRdbAge,
--           mscVrIpBootpStorageType,
--           mscVrIpOspfLsdbRowStatus,
--           mscVrIpUdpNoPorts,
--           mscVrIpEgpUsageState,
--           mscVrIpFwdIfIndex,
--           mscVrIpOspfExtLsdbLimit,
--           mscVrIpOspfExtLsdbStorageType,
--           mscVrIpIcmpInRtrAdvs,
--           mscVrIpNsApplyIpAddress1,
--           mscVrIpArpDynHostTunnelDestinationAddress,
--           mscVrIpArpAutoRefresh,
--           mscVrIpArpRowStatus,
--           mscVrIpFwdProtocol,
--           mscVrIpCacheLookupMisses,
--           mscVrIpReasmFails,
--           mscVrIpEgpImportNetStorageType,
--           mscVrIpOspfVirtIfAuthKey,
--           mscVrPpIpPortSourceRouteEndStationSupport,
--           mscVrIpTcpInErrs,
--           mscVrPpIpPortLogicalIfOspfIfHelloInterval,
--           mscVrIpRipRedistributeIbgp,
--           mscVrIpRipExportNetComponentName,
--           mscVrIpInHdrErrors,
--           mscVrIpTcpInSegs,
--           mscVrIpEgpImportNetRowStatus,
--           mscVrIpEgpNbrRowStatus,
--           mscVrIpEgpExportNetIpAddress,
--           mscVrIpEgpImportStorageType,
--           mscVrIpIfNcHardwareAddress,
--           mscVrIpFwdRowStatus,
--           mscVrIpRipImportRowStatus,
--           mscVrIpRelayBCRelayNdStatus,
--           mscVrIpOspfAggregateEffect,
--           mscVrIpRelayBCPortComponentName,
--           mscVrPpIpPortLogicalIfLinkDestinationAddress,
--           mscVrIpEgpNbrStateDowns,
--           mscVrPpIpPortBootpPUsageState,
--           mscVrIpOspfExportNetListStorageType,
--           mscVrIpBootpOperationalState,
--           mscVrIpTcpActiveOpens,
--           mscVrIpFragOks,
--           mscVrIpOspfVirtIfComponentName,
--           mscVrPpIpPortLogicalIfRipIfIfConfReceive,
--           mscVrIpOspfVirtNbrExchangeStatus,
--           mscVrIpArpHostPhysAddress,
--           mscVrIpEgpInErrors,
--           mscVrPpIpPortAssignedQos,
--           mscVrIpInDiscards,
--           mscVrPpIpPortOperCosPolicyAssignment,
--           mscVrIpStaticRouteStorageType,
--           mscVrIpEgpNbrOutErrors,
--           mscVrIpOspfAreaSpfRuns,
--           mscVrIpOspfExportExtLsaMetricType,
--           mscVrIpRelayBCComponentName,
--           mscVrIpRelayBCPortRelayBcUdpCount,
--           mscVrIpOspfExportRipNeighbor,
--           mscVrIpEgpSnmpOperStatus,
--           mscVrIpStaticDiscardStorageType,
--           mscVrIpCacheCacheTableMaxEntries,
--           mscVrIpEgpNbrMode,
--           mscVrPpIpPortLogicalIfRipIfIfConfSend,
--           mscVrIpEgpInMsgs,
--           mscVrIpIcmpOutDestUnreachs,
--           mscVrIpOspfNbrExchangeStatus,
--           mscVrIpEgpNbrOutMsgs,
--           mscVrPpIpPortIcmpMaskReply,
--           mscVrIpTcpTcpEntryStorageType,
--           mscVrIpArpHostRowStatus,
--           mscVrIpIcmpComponentName,
--           mscVrIpRipExportBgpAsId,
--           mscVrIpTunnelMsepIfAdminStatus,
--           mscVrIpTunnelMsepComponentName,
--           mscVrIpTunnelMsepDstRowStatus,
--           mscVrPpIpPortLogicalIfOspfIfComponentName,
--           mscVrIpNsFirstFilter,
--           mscVrPpIpPortBootpPInReplyErrors,
--           mscVrPpIpPortLogicalIfRipIfAcceptDefault,
--           mscVrPpIpPortRelayAddress,
--           mscVrIpOspfVirtNbrLsRetransQlen,
--           mscVrIpIcmpOutRedirects,
--           mscVrIpUdpOutDatagrams,
--           mscVrIpCacheEntriesFree,
--           mscVrIpTcpTcpEntryState,
--           mscVrIpIcmpInAddrMasks,
--           mscVrIpArpDynHostEncapsulationType,
--           mscVrIpIcmpInSrcQuenchs,
--           mscVrIpEgpRowStatus,
--           mscVrIpEgpSnmpAdminStatus,
--           mscVrPpIpPortEncap,
--           mscVrIpRdbComponentName,
--           mscVrIpOspfAggregateStorageType,
--           mscVrIpOspfVirtNbrNbrIpAddress,
--           mscVrPpIpPortLogicalIfRipIfRowStatus,
--           mscVrIpOspfStorageType,
--           mscVrPpIpPortLogicalIfRipIfSnmpAdminStatus,
--           mscVrIpTunnelSepIfIndex,
--           mscVrIpOspfAreaAsBdrRtrCount,
--           mscVrIpOspfNbrLsRetransQlen,
--           mscVrIpNsApplyFilter,
--           mscVrPpIpPortLogicalIfOspfIfPollInterval,
--           mscVrPpIpPortLogicalIfOspfIfState,
--           mscVrIpStaticComponentName,
--           mscVrIpRipImportNetComponentName,
--           mscVrPpIpPortLogicalIfRowStatus,
--           mscVrIpEgpExportProtocol,
--           mscVrPpIpPortNsIncomingFilter,
--           mscVrIpEgpNbrAsId,
--           mscVrIpEgpStorageType,
--           mscVrIpIfStatus,
--           mscVrIpSnmpOperStatus,
--           mscVrPpIpPortSnmpOperStatus,
--           mscVrIpOspfAdminState,
--           mscVrIpIcmpOutTimeExcds,
--           mscVrIpEgpOperationalState,
--           mscVrIpEgpImportNetIpAddress,
--           mscVrPpIpPortBootpPRelayForwardStatus,
--           mscVrIpTcpCurrEstab,
--           mscVrIpTcpRToAlgorithm,
--           mscVrIpBootpPpEComponentName,
--           mscVrIpOspfVirtIfState,
--           mscVrIpTcpTcpEntryRowStatus,
--           mscVrIpIcmpOutParmProbs,
--           mscVrIpCacheStorageType,
--           mscVrPpIpPortOperMulticastStatus,
--           mscVrPpIpPortLogicalIfOspfIfNbrPriority,
--           mscVrIpOperationalState,
--           mscVrIpEgpExportAdvertiseStatus,
--           mscVrIpTunnelMsepPathMtu,
--           mscVrIpOspfNbrPermanence,
--           mscVrPpIpPortAllowMcastMacDest,
--           mscVrIpOspfExportStorageType,
--           mscVrPpIpPortBootpPInRequestErrors,
--           mscVrIpOspfVirtNbrRowStatus,
--           mscVrIpOspfAreaBdrRtrStatus,
--           mscVrIpRdbRowStatus,
--           mscVrIpRelayBCRelayStatus,
--           mscVrIpArpHostOperEncap,
--           mscVrIpOspfAreaRowStatus,
--           mscVrPpIpPortLogicalIfOspfIfRtrDeadInterval,
--           mscVrIpRowStatus,
--           mscVrPpIpPortRowStatus,
--           mscVrIpSnmpAdminStatus,
--           mscVrPpIpPortSnmpAdminStatus,
--           mscVrIpEgpExportRipInterface,
--           mscVrIpTcpRetransSegs,
--           mscVrIpOspfAreaAreaSummary,
--           mscVrIpNsRowStatus,
--           mscVrPpIpPortNsRowStatus,
--           mscVrIpTunnelMsepDstValue,
--           mscVrPpIpPortBootpPInReplies,
--           mscVrIpOspfNbrRowStatus,
--           mscVrIpTunnelSepLinkToProtocolPort,
--           mscVrIpTunnelAdminState,
--           mscVrIpFwdMetric,
--           mscVrPpIpPortLogicalIfOspfIfNbrStorageType,
--           mscVrIpRipExportEgpAsId,
--           mscVrIpIcmpInTimestampReps,
--           mscVrIpUdpListenEntryComponentName,
--           mscVrIpOspfMulticastForward,
--           mscVrIpOspfStubStorageType,
--           mscVrIpBootpPpEInReplies,
--           mscVrIpEgpNbrHelloInterval,
--           mscVrPpIpPortSendRedirect,
--           mscVrPpIpPortBootpPStorageType,
--           mscVrIpRipComponentName,
--           mscVrPpIpPortOperationalState,
--           mscVrIpOspfLsdbAdvertisement,
--           mscVrIpOspfNbrNbmaNbrStatus,
--           mscVrIpEgpOutErrors,
--           mscVrPpIpPortBootpPSnmpOperStatus,
--           mscVrIpOutDiscards,
--           mscVrIpStaticUsageState,
--           mscVrPpIpPortBootpPAdminState,
--           mscVrIpOspfHostAreaId,
--           mscVrIpIfStorageType,
--           mscVrPpIpPortBootpPAddrRowStatus,
--           mscVrIpStaticRouteNhStorageType,
--           mscVrIpRelayBCPortRowStatus,
--           mscVrIpEgpOutMsgs,
--           mscVrIpEgpExportRowStatus,
--           mscVrIpUdpComponentName,
--           mscVrPpIpPortMediaType,
--           mscVrIpIcmpInEchos,
--           mscVrPpIpPortLogicalIfOspfIfAuthKey,
--           mscVrIpOspfExtLsdbAge,
--           mscVrPpIpPortLogicalIfOspfIfTransitDelay,
--           mscVrIpEgpExportNetComponentName,
--           mscVrIpIfBroadcastAddress,
--           mscVrIpBootpPpEStorageType,
--           mscVrIpEgpNbrState,
--           mscVrIpRipExportComponentName,
--           mscVrIpCacheRowStatus,
--           mscVrPpIpPortBootpPBootpLogicalInterface,
--           mscVrIpEgpImportRowStatus,
--           mscVrIpRelayBCPortStorageType,
--           mscVrIpOspfVersionNumber,
--           mscVrIpEgpNbrInMsgs,
--           mscVrIpIcmpOutAddrMasks,
--           mscVrIpOspfVirtIfTransitDelay,
--           mscVrIpOspfNbrStorageType,
--           mscVrPpIpPortLogicalIfRipIfFlashUpdateFlag,
--           mscVrIpOspfExportNetListRowStatus,
--           mscVrIpRdbPreference,
--           mscVrPpIpPortLogicalIfRipIfMetric,
--           mscVrIpEgpNbrComponentName,
--           mscVrIpOspfVirtIfRtrDeadInterval,
--           mscVrPpIpPortLogicalIfRipIfDefaultRouteMetric,
--           mscVrPpIpPortLogicalIfRipIfIfTriggeredUpdates,
--           mscVrIpRipExportNetStorageType,
--           mscVrIpEgpMaxNatNets,
--           mscVrIpEgpImportNbrAsId,
--           mscVrPpIpPortLogicalIfRipIfNbrComponentName,
--           mscVrPpIpPortLinkModel,
--           mscVrIpBootpPpEInReplyErrors,
--           mscVrIpArpDynHostType,
--           mscVrIpStaticRouteRowStatus,
--           mscVrIpBootpSnmpAdminStatus,
--           mscVrIpEgpAsId,
--           mscVrIpBootpPpEInRequestErrors,
--           mscVrIpOspfLsdbAge,
--           mscVrIpIcmpOutEchos,
--           mscVrIpStaticDiscardRowStatus,
--           mscVrIpOspfVirtNbrEvents,
--           mscVrIpTcpRToMax,
--           mscVrIpEgpNbrDefaultRouteMetric,
--           mscVrIpRipUsageState,
--           mscVrIpOspfTosSupport,
--           mscVrIpOspfVirtIfEvents,
--           mscVrIpOspfSnmpOperStatus,
--           mscVrIpTunnelMsepSourceAddress,
--           mscVrIpEgpNbrPollInterval,
--           mscVrPpIpPortLogicalIfOspfIfNbrExchangeStatus,
--           mscVrPpIpPortLogicalIfOspfIfMulticastForwarding,
--           mscVrIpArpDynHostPhysAddress,
--           mscVrPpIpPortOperEncap,
--           mscVrIpCtsValue,
--           mscVrIpIfInterfaceMask,
--           mscVrIpOspfLsdbComponentName,
--           mscVrIpNsApplyComponentName,
--           mscVrIpTcpComponentName,
--           mscVrIpOutRequests,
--           mscVrIpRelayBCStorageType,
--           mscVrPpIpPortLogicalIfOspfIfNbrEvents,
--           mscVrIpTunnelMsepLinkToProtocolPort,
--           mscVrIpEgpMaxBufferSize,
--           mscVrIpRdbMetric,
--           mscVrIpArpDynHostRowStatus,
--           mscVrIpTunnelMsepIfIndex,
--           mscVrIpArpDynHostNcPhysAddress,
--           mscVrIpRipMigrateRip,
--           mscVrIpBootpComponentName,
--           mscVrIpIcmpInRtrSolicits,
--           mscVrIpOspfLsdbSequence,
--           mscVrIpOspfAggregateRowStatus,
--           mscVrIpIcmpStorageType,
--           mscVrIpRipImportImportMetric,
--           mscVrIpCacheUsageState,
--           mscVrIpOspfRowStatus,
--           mscVrIpOspfSnmpAdminStatus,
--           mscVrPpIpPortLogicalIfOspfIfStorageType,
--           mscVrIpEgpImportNetComponentName,
--           mscVrIpRipImportInterface,
--           mscVrIpRipQueryResponses,
--           mscVrPpIpPortLogicalIfOspfIfNbrLsRetransQlen,
--           mscVrIpEgpExportOutAutonomousSystem,
--           mscVrIpRipImportComponentName,
--           mscVrIpOspfAreaLsaCount,
--           mscVrIpEgpExportExportMetric,
--           mscVrIpOspfExportProtocol,
--           mscVrIpIcmpRowStatus,
--           mscVrIpIcmpOutSrcQuenchs,
--           mscVrIpIcmpInEchoReps,
--           mscVrIpOspfVirtIfStorageType,
--           mscVrIpIcmpOutTimestampReps,
--           mscVrIpOspfOriginateNewLsas,
--           mscVrPpIpPortLogicalIfOspfIfAreaId,
--           mscVrIpOspfRouterId,
--           mscVrIpOspfVirtNbrOptions,
--           mscVrIpRipImportUsageFlag,
--           mscVrIpStaticStorageType,
--           mscVrIpRipImportNetStorageType,
--           mscVrPpIpPortCosPolicyAssignment,
--           mscVrIpArpHostPermanentVirtualCircuitNumber,
--           mscVrIpTunnelMsepStorageType,
--           mscVrIpIcmpOutRtrAdvs,
--           mscVrPpIpPortOperMtu,
--           mscVrIpOspfExportRowStatus,
--           mscVrIpRipExportExportMetric,
--           mscVrIpOspfExportAdvertiseStatus,
--           mscVrIpRipRouteChangesMade,
--           mscVrIpEgpNbrEventTrigger,
--           mscVrIpRipOperationalState,
--           mscVrIpStaticAdminState,
--           mscVrIpOspfNbrOptions,
--           mscVrPpIpPortRelayBroadcast,
--           mscVrIpTcpEstabResets,
--           mscVrIpOspfExportNetListIpMask,
--           mscVrIpOspfExportNetListIpAddress,
--           mscVrPpIpPortBootpPInRequests,
--           mscVrIpOspfExportRipInterface,
--           mscVrIpOspfExtLsdbRowStatus,
--           mscVrPpIpPortLogicalIfOspfIfNbrRowStatus,
--           mscVrIpOutNoRoutes,
--           mscVrIpOspfHostRowStatus,
--           mscVrIpOspfStubComponentName,
--           mscVrIpArpHostComponentName,
--           mscVrIpOspfNbrRtrId,
--           mscVrIpEgpComponentName,
--           mscVrPpIpPortBootpPRowStatus,
--           mscVrIpIcmpOutEchoReps,
--           mscVrPpIpPortBootpPSnmpAdminStatus,
--           mscVrIpArpHostOperMaxTxUnit,
--           mscVrIpUdpInDatagrams,
--           mscVrPpIpPortLogicalIfRipIfComponentName,
--           mscVrIpEgpNbrDefaultMetric,
--           mscVrIpTunnelUsageState,
--           mscVrIpOspfExternLsaChecksumSum,
--           mscVrPpIpPortLogicalIfOspfIfTOSComponentName,
--           mscVrIpCacheAdminState,
--           mscVrPpIpPortLogicalIfComponentName,
--           mscVrPpIpPortLogicalIfOspfIfNbrPermanance,
--           mscVrIpUdpListenEntryStorageType,
--           mscVrIpIfRowStatus,
--           mscVrIpTunnelRowStatus,
--           mscVrIpOspfStubRowStatus,
--           mscVrIpStaticRouteNhRowStatus,
--           mscVrIpInUnknownProtos,
--           mscVrPpIpPortBootpPOperationalState,
--           mscVrIpRipStorageType,
--           mscVrIpIfMtu,
--           mscVrIpTcpTcpEntryComponentName,
--           mscVrIpEgpNbrInErrorMsgs,
--           mscVrIpRelayBCRelayNdCount,
--           mscVrIpIfHardwareAddress,
--           mscVrIpArpDynHostPermanentVirtualCircuitNumber,
--           mscVrIpEgpExportComponentName,
--           mscVrIpEgpAdminState,
--           mscVrPpIpPortMaxTxUnit,
--           mscVrPpIpPortLogicalIfOspfIfEvents,
--           mscVrIpOspfRedistributeIbgp,
--           mscVrIpRipAdminState,
--           mscVrIpReasmTimeOut,
--           mscVrIpTcpOutSegs,
--           mscVrIpOspfVirtNbrComponentName,
--           mscVrIpArpHostMaxTxUnit,
--           mscVrIpTunnelSepSourceAddress,
--           mscVrPpIpPortArpStatus,
--           mscVrIpIcmpInParmProbs,
--           mscVrIpUdpStorageType,
--           mscVrIpOspfAreaComponentName,
--           mscVrIpComponentName,
--           mscVrPpIpPortComponentName,
--           mscVrIpIcmpOutRtrSolicits,
--           mscVrIpRelayBCRowStatus,
--           mscVrIpRipRfc1058MetricUsage,
--           mscVrIpStaticRoutePreferredOver,
--           mscVrIpOspfExportEgpAsId,
--           mscVrIpEgpExportNetStorageType,
--           mscVrIpRipExportOspfTag,
--           mscVrIpCacheComponentName,
--           mscVrIpIcmpInErrors,
--           mscVrIpRipExportNetRowStatus,
--           mscVrIpNsComponentName,
--           mscVrPpIpPortNsComponentName,
--           mscVrIpRipExportStorageType,
--           mscVrIpOspfNbrComponentName,
--           mscVrIpOspfExportBgpPeerIp,
--           mscVrIpEgpNbrGenerateDefaultRoute,
--           mscVrIpIfMediaType,
--           mscVrIpTcpMaxConn,
--           mscVrIpOspfVirtNbrState,
--           mscVrPpIpPortBootpPOutReplies,
--           mscVrIpFragFails,
--           mscVrIpTunnelSepIfAdminStatus,
--           mscVrIpTunnelSepComponentName,
--           mscVrIpTcpStorageType,
--           mscVrIpFwdType,
--           mscVrIpForwDatagrams,
--           mscVrIpEgpNbrStorageType,
--           mscVrIpOspfOperationalState,
--           mscVrPpIpPortLogicalIfRipIfNbrRowStatus,
--           mscVrPpIpPortLogicalIfRipIfNbrStorageType,
--           mscVrPpIpPortLogicalIfOspfIfIfType,
--           mscVrIpOspfNbrState,
--           mscVrIpOspfAsBdrRtrStatus,
--           mscVrIpArpHostEncap,
--           mscVrIpOspfExportBgpAsId,
--           mscVrIpDefaultTtl,
--           mscVrIpOspfExportMetric,
--           mscVrIpOspfAreaAreaBdrRtrCount,
--           mscVrIpTunnelSepRowStatus,
--           mscVrIpTunnelSepDestinationAddress,
--           mscVrIpTunnelComponentName,
--           mscVrIpFwdComponentName,
--           mscVrIpIcmpInDestUnreachs,
--           mscVrIpArpDynHostIfIndex,
--           mscVrIpOspfAreaAreaLsaCksumSum,
--           mscVrIpEgpImportImportMetric,
--           mscVrPpIpPortOperArpStatus,
--           mscVrIpOspfLsdbStorageType,
--           mscVrIpNsApplyStorageType,
--           mscVrPpIpPortBootpPOutRequests,
--           mscVrPpIpPortLogicalIfOspfIfRowStatus,
--           mscVrPpIpPortLogicalIfRipIfPoisonReverseFlag,
--           mscVrIpTunnelStorageType,
--           mscVrPpIpPortLogicalIfOspfIfSnmpAdminStatus,
--           mscVrIpOspfVirtIfRetransInterval,
--           mscVrIpEgpImportComponentName,
--           mscVrIpBootpUsageState,
--           mscVrIpOspfHostMetric,
--           mscVrIpFwdNextHopAs,
--           mscVrIpOspfExportNetListComponentName,
--           mscVrIpUsageState,
--           mscVrIpOspfGenerateDefaultRouteMetric,
--           mscVrIpTcpRToMin,
--           mscVrPpIpPortLogicalIfOspfIfBackupDesignatedRouter,
--           mscVrIpTcpRowStatus,
--           mscVrIpOspfAreaImportAsExtern,
--           mscVrIpOspfVirtIfRowStatus,
--           mscVrIpNsApplyDirection,
--           mscVrIpFwdProtocolPortName,
--           mscVrIpArpDynHostStorageType,
--           mscVrIpOspfStubMetricType,
--           mscVrIpEgpImportUsageFlag,
--           mscVrIpStaticRouteComponentName,
--           mscVrIpInDelivers,
--           mscVrIpRipGenerateDiscardRoute,
--           mscVrIpStaticRowStatus,
--           mscVrIpRipImportNetRowStatus,
--           mscVrIpBootpAdminState,
--           mscVrIpRipExportNetIpAddress,
--           mscVrIpFwdStorageType,
--           mscVrIpRipImportStorageType,
--           mscVrIpTunnelMsepRowStatus,
--           mscVrIpStaticRouteNhMetric,
--           mscVrIpStaticDiscardComponentName,
--           mscVrIpCosPolicyAssignment,
--           mscVrIpBootpPpERowStatus,
--           mscVrIpOspfHostStorageType,
--           mscVrIpIfComponentName,
--           mscVrIpOspfStubAdvertiseDefault,
--           mscVrIpArpAutoRefreshTimeout,
--           mscVrIpEgpNbrStateUps,
--           mscVrIpArpComponentName,
--           mscVrPpIpPortLogicalIfOspfIfTOSTosMetric,
--           mscVrPpIpPortLogicalIfOspfIfRtrPriority,
--           mscVrIpBootpPpEInRequests,
--           mscVrIpEgpNbrOutErrorMsgs,
--           mscVrPpIpPortLogicalIfOspfIfNbrOptions,
--           mscVrIpOspfExtLsdbAdvertisement,
--           mscVrIpForwarding,
--           mscVrIpNsApplyIpAddress2,
--           mscVrIpTunnelOperationalState,
--           mscVrIpStaticOperationalState,
--           mscVrIpIcmpInTimestamps,
--           mscVrPpIpPortBootpPAddrValue,
--           mscVrPpIpPortUsageState,
--           mscVrIpIcmpOutErrors,
--           mscVrIpRipExportNetIpMask,
--           mscVrIpRipSnmpOperStatus,
--           mscVrIpNsApplyRowStatus,
--           mscVrPpIpPortArpNoLearn,
--           mscVrIpOspfVirtIfHelloInterval,
--           mscVrPpIpPortLogicalIfRipIfNetworkRouteStatus,
--           mscVrIpIfPPName,
--           mscVrIpOspfStubMetric,
--           mscVrIpOspfRxNewLsas,
--           mscVrIpTunnelSepDiscoveredPathMtu,
--           mscVrIpFwdAge,
--           mscVrIpOspfAggregateComponentName,
--           mscVrIpArpHostStorageType,
--           mscVrIpUdpInErrors,
--           mscVrIpFragCreates,
--           mscVrIpOspfComponentName,
--           mscVrPpIpPortRelayAddressCount,
--           mscVrIpTunnelSepEncapType,
--           mscVrPpIpPortLogicalIfOspfIfTOSRowStatus,
--           mscVrIpIcmpInMsgs,
--           mscVrIpNsLocalOutFilter,
--           mscVrIpNsApplyIpMask2,
--           mscVrIpArpHostTunnelDestinationAddress,
--           mscVrIpOspfExternLsaCount,
--           mscVrIpIcmpInAddrMaskReps,
--           mscVrIpUdpListenEntryRowStatus,
--           mscVrIpNsLastFilter,
--           mscVrPpIpPortLogicalIfOspfIfRetransInterval,
--           mscVrIpNsApplyIpMask1,
--           mscVrIpNsLocalInFilter,
--           mscVrPpIpPortProxyArpStatus,
--           mscVrPpIpPortDirectedBroadcast,
--           mscVrIpTunnelMsepEncapType,
--           mscVrIpEgpExportRipNeighbor,
--           mscVrPpIpPortLogicalIfRipIfIfBadPacketRcv,
--           mscVrIpRipRowStatus,
--           mscVrIpRipSnmpAdminStatus,
--           mscVrIpIcmpOutMsgs,
--           mscVrPpIpPortLogicalIfRipIfStorageType,
--           mscVrIpTcpOutRsts,
--           mscVrIpTunnelMsepSharedDomainVirtualRouter,
--           mscVrPpIpPortLogicalIfOspfIfDesignatedRouter,
--           mscVrPpIpPortLogicalIfOspfIfTOSStorageType,
--           mscVrIpBootpPpEStatus,
--           mscVrIpEgpNbrInErrors,
--           mscVrIpTcpAttemptFails,
--           mscVrIpEgpExportInEgpAsId,
--           mscVrPpIpPortLogicalIfStorageType,
--           mscVrIpRoutingDiscards,
--           mscVrIpBootpPpEOutReplies,
--           mscVrIpRipExportProtocol,
--           mscVrIpOspfExportComponentName,
--           mscVrPpIpPortNsOutgoingFilter,
--           mscVrPpIpPortLogicalIfOspfIfNbrRtrId,
--           mscVrPpIpPortLogicalIfNetMask,
--           mscVrIpRipImportNetIpAddress,
--           mscVrPpIpPortLanModel,
--           mscVrIpIcmpOutAddrMaskReps,
--           mscVrIpUdpRowStatus,
--           mscVrIpOspfAreaAuthType,
--           mscVrIpInAddrErrors,
--           mscVrIpReasmReqds,
--           mscVrPpIpPortLogicalIfBroadcastAddress,
--           mscVrIpInReceives,
--           mscVrIpEgpExportOspfTag,
--           mscVrIpReasmOks,
--           mscVrIpOspfNbrPriority,
--           mscVrIpEgpExportNetRowStatus,
--           mscVrIpIcmpInTimeExcds,
--           mscVrIpArpStorageType,
--           mscVrIpEgpExportStorageType,
--           mscVrPpIpPortLogicalIfOspfIfMetric,
--           mscVrIpRipExportRowStatus,
--           mscVrPpIpPortLogicalIfRipIfIfBadRouteRcv,
--           mscVrIpRipExportAdvertiseStatus,
--           mscVrIpOspfExtLsdbComponentName,
--           mscVrPpIpPortLogicalIfOspfIfNbrComponentName,
--           mscVrIpOspfVirtNbrStorageType,
--           mscVrIpBootpRowStatus,
--           mscVrIpBootpHopDiscardThreshold,
--           mscVrIpIcmpInRedirects,
--           mscVrIpOspfHostComponentName,
--           mscVrIpRdbStorageType,
--           mscVrIpArpDynHostMaxTxUnit,
--           mscVrIpRipExportOutInterface,
--           mscVrIpOspfAreaStorageType,
--           mscVrPpIpPortBootpPComponentName,
--           mscVrIpRipImportNetIpMask,
--           mscVrIpStorageType,
--           mscVrPpIpPortStorageType,
--           mscVrIpTunnelSepStorageType,
--           mscVrIpOspfLsdbChecksum,
--           mscVrIpOspfExtLsdbChecksum,
--           mscVrPpIpPortMulticastStatus,
--           mscVrIpRipExportRipInterface,
--           mscVrIpOspfUsageState,
--           mscVrIpCacheOperationalState,
--           mscVrIpNsStorageType,
--           mscVrPpIpPortNsStorageType,
--           mscVrIpOspfExtLsdbSequence,
--           mscVrIpEgpDefaultHelloInterval,
--           mscVrIpBootpPpEOutRequests,
--           mscVrIpCacheTotalLookups,
--           mscVrIpAdminState,
--           mscVrPpIpPortAdminState,
--           mscVrPpIpPortLogicalIfOspfIfNbrState,
--           mscVrIpRipImportNeighbor,
--           mscVrIpEgpInErrorMsgs,
--           mscVrIpIcmpOutTimestamps }
-- STATUS  mandatory
-- DESCRIPTION
--   "A list of all current accessible leaf objects."

ipGroup OBJECT IDENTIFIER ::= { ipMIB 1 }
ipGroupCA OBJECT IDENTIFIER ::= { ipGroup 1 }
ipGroupCA02 OBJECT IDENTIFIER ::= { ipGroupCA 3 }
ipGroupCA02A OBJECT IDENTIFIER ::= { ipGroupCA02 2 }



-- Agent-Capabilities Statement:

-- PRODUCT-RELEASE "MscPassport Release 1.2 Ip."
-- STATUS          mandatory
-- DESCRIPTION     "Carrier Passport Ip MIB: MIB Version CA02A,
--                  Software Version CA02S9C."
-- SUPPORTS        Nortel-MsCarrier-MscPassport-IpMIB
--    INCLUDES     { ipGroupCA02A }
--       rfc1213 (MIB II)
-- 
-- SUPPORTS          RFC1213-MIB
--    INCLUDES		{ at, ip, icmp, udp, egp } 
--                            tcp group not supported
-- 
-- 	   variations for at group
-- 	
-- 	VARIATION	atIfIndex
--  	   ACCESS       read-only
--  	   DESCRIPTION	"SET not allowed, because it is an index"
-- 
--  	VARIATION       atNetAddress
--   	   ACCESS       read-only
--            DESCRIPTION  "SET not allowed, because it is an index"
--  
-- 
-- 	   variations for the ip group
-- 
--  	VARIATION       ipForwarding
-- 	   WRITE-SYNTAX INTEGER { forwarding(1) }
--    	   DESCRIPTION  "Only valid value is forwarding(1)"
-- 
-- 	VARIATION	ipRouteDest
-- 	   ACCESS	read-only
-- 	   DESCRIPTION	"SET not allowed"
-- 
-- 	VARIATION	ipRouteIfIndex
-- 	   ACCESS	read-only
-- 	   DESCRIPTION	"SET not allowed"
-- 
-- 	VARIATION	ipRouteMetric1
-- 	   ACCESS	read-only
-- 	   DESCRIPTION	"SET not allowed"
-- 
-- 	VARIATION	ipRouteMetric2
-- 	   ACCESS	read-only
-- 	   DESCRIPTION	"SET not allowed"
-- 
-- 	VARIATION	ipRouteMetric3
-- 	   ACCESS	read-only
-- 	   DESCRIPTION	"SET not allowed"
-- 
-- 	VARIATION	ipRouteMetric4
-- 	   ACCESS	read-only
-- 	   DESCRIPTION	"SET not allowed"
-- 
-- 	VARIATION	ipRouteNextHop
-- 	   ACCESS	read-only
-- 	   DESCRIPTION	"SET not allowed"
-- 
-- 	VARIATION	ipRouteType
-- 	   ACCESS	read-only
-- 	   DESCRIPTION	"SET not allowed"
-- 
-- 	VARIATION	ipRouteAge
-- 	   ACCESS	read-only
-- 	   DESCRIPTION	"SET not allowed"
-- 
-- 	VARIATION	ipRouteMask
-- 	   ACCESS	read-only
-- 	   DESCRIPTION	"SET not allowed"
-- 
-- 	VARIATION	ipRouteMetric5
-- 	   ACCESS	read-only
-- 	   DESCRIPTION	"SET not allowed"
-- 
-- 
-- 	   variations for the egp group
-- 
--  	VARIATION       egpNeighEventTrigger
--  	   ACCESS       read-only
--  	   DESCRIPTION  "SET not allowed"
-- 
-- 
--    rfc1354 (IP Forwarding Table)
-- 
-- SUPPORTS RFC1354-MIB
-- INCLUDES { ipForward }
-- 
-- 	VARIATION       ipForwardMask
-- 	   ACCESS       read-only
-- 	   DESCRIPTION  "SET not allowed"
-- 
-- 	VARIATION       ipForwardIfIndex
-- 	   ACCESS       read-only
-- 	   DESCRIPTION  "SET not allowed"
-- 
-- 	VARIATION       ipForwardType
-- 	   ACCESS       read-only
-- 	   DESCRIPTION  "SET not allowed"
-- 
-- 	VARIATION       ipForwardInfo
-- 	   ACCESS       read-only
-- 	   DESCRIPTION  "SET not allowed"
-- 
-- 	VARIATION       ipForwardNextHopAS
-- 	   ACCESS       read-only
-- 	   DESCRIPTION  "SET not allowed"
-- 
-- 	VARIATION       ipForwardMetric1
-- 	   ACCESS       read-only
-- 	   DESCRIPTION  "SET not allowed"
-- 
-- 	VARIATION       ipForwardMetric2
-- 	   ACCESS       read-only
-- 	   DESCRIPTION  "SET not allowed"
-- 
-- 	VARIATION       ipForwardMetric3
-- 	   ACCESS       read-only
-- 	   DESCRIPTION  "SET not allowed"
-- 
-- 	VARIATION       ipForwardMetric4
-- 	   ACCESS       read-only
-- 	   DESCRIPTION  "SET not allowed"
-- 
-- 	VARIATION       ipForwardMetric5
-- 	   ACCESS       read-only
-- 	   DESCRIPTION  "SET not allowed"
-- 
-- 
--      rfc1253 (OSPF Version 2 MIB)
-- 
--   SUPPORTS RFC1253-MIB
--   INCLUDES { ospfAreaRangeTable }
-- 
-- 	VARIATION	ospfAreaRangeAreaID
-- 	ACCESS		read-only
-- 	DESCRIPTION	"Table will be obsoleted. Read access provided"
-- 
-- 	VARIATION	ospfAreaRangeNet
-- 	ACCESS		read-only
-- 	DESCRIPTION	"Table will be obsoleted. Read access provided"
-- 
-- 	VARIATION	ospfAreaRangeMask
-- 	ACCESS		read-only
-- 	DESCRIPTION	"Table will be obsoleted. Read access provided"
-- 
-- 	VARIATION	ospfAreaRangeStatus
-- 	ACCESS		read-only
-- 	DESCRIPTION	"Table will be obsoleted. Read access provided"
-- 
-- 
-- 
--      draft-ietf-ospf-mib-04.txt (OSPF version 2 MIB)
--      (A draft for evolution of RFC1253)
-- 
--   SUPPORTS OSPF-MIB
-- 
--   INCLUDES	  { ospfGeneralGroup 
-- 		    ospfAreaTable 
-- 		    ospfStubAreaTable
-- 		    ospfLsdbTable 
-- 		    ospfAreaRangeTable 
-- 		    ospfHostTable
-- 		    ospfIfTable 
-- 		    ospfIfMetricTable 
-- 		    ospfVirtIfTable
-- 		    ospfNbrTable 
-- 		    ospfVirtNbrTable 
-- 		    ospfExtLsdbTable
-- 		    ospfAreaAggregateTable }
-- 
-- 	   variations for ospfGeneralGroup group
-- 	
-- 	VARIATION	ospfTOSSupport
-- 	   WRITE-SYNTAX TruthValue { false(1) }
-- 	   DESCRIPTION	"Value limited to false(1)"
-- 
-- 	VARIATION       ospfMulticastExtensions
--  	   WRITE-SYNTAX INTEGER (0)
--  	   DESCRIPTION  "Value limited to 0"
--  
-- 	   Variations for ospfAreaTable group
-- 
-- 	VARIATION       ospfAuthType
--  	   WRITE-SYNTAX INTEGER { none (0), simplePassword (1) }
--   	   DESCRIPTION  "Value limited to none (0) and simplePassword (1)"
-- 
-- 	   Variations for the ospfIfTable
-- 
-- 	VARIATION       ospfIfMulticastForwarding
--   	   WRITE-SYNTAX INTEGER { blocked (1) }
--   	   DESCRIPTION  "Value limited to blocked (1)"
-- 
--         VARIATION       ospfIfType
--            WRITE-SYNTAX INTEGER { broadcast (1), nbma (2), pointToPoint (3) }
--            DESCRIPTION  "Value limited to broadcast (1), nbma (2) and 
--                          pointToPoint (3)"
-- 
--    rfc1724 (RIP Version2 MIB)
-- 
-- SUPPORTS RFC1724-MIB
-- INCLUDES { rip2Globals, rip2IfStatTable, rip2IfConfTable }                  
--              rip2PeerTable not supported
--           
-- 	   variations for the rip2IfStatTable
-- 	
-- 	VARIATION	rip2IfStatStatus
-- 	   ACCESS	read-only
-- 	   DESCRIPTION	"Set not allowed"
-- 	   
-- 	   variations for the rip2IfConfTable
-- 	
-- 	VARIATION	rip2IfConfDomain
-- 	   ACCESS	read-only
-- 	   DESCRIPTION	"Set not allowed"
-- 	   
-- 	VARIATION	rip2IfConfAuthType
-- 	   ACCESS	read-only
-- 	   DESCRIPTION	"Set not allowed"
-- 	   
-- 	VARIATION	rip2IfConfAuthKey
-- 	   ACCESS	read-only
-- 	   DESCRIPTION	"Set not allowed"
-- 	   
-- 	VARIATION	rip2IfConfSend
-- 	   ACCESS	read-only
-- 	   DESCRIPTION	"Set not allowed"
-- 	   
-- 	VARIATION	rip2IfConfRecveive
-- 	   ACCESS	read-only
-- 	   DESCRIPTION	"Set not allowed"
-- 	   
-- 	VARIATION	rip2IfConfDefaultMetric
-- 	   ACCESS	read-only
-- 	   DESCRIPTION	"Set not allowed"
-- 	   
-- 	VARIATION	rip2IfConfStatus
-- 	   ACCESS	read-only
-- 	   DESCRIPTION	"Set not allowed"
-- 	   
-- 	VARIATION	rip2IfConfSrcAddress
-- 	   ACCESS	read-only
-- 	   DESCRIPTION	"Set not allowed"
ipCapabilities OBJECT IDENTIFIER ::= { ipMIB 3 }
ipCapabilitiesCA OBJECT IDENTIFIER ::= { ipCapabilities 1 }
ipCapabilitiesCA02 OBJECT IDENTIFIER ::= { ipCapabilitiesCA 3 }
ipCapabilitiesCA02A OBJECT IDENTIFIER ::= { ipCapabilitiesCA02 2 }





END
