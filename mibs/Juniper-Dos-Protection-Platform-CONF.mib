-- *****************************************************************************
-- Juniper-Dos-Protection-Platform-CONF
--
-- JUNOSe SNMP Agent Capabilities definitions for the Dos Protection Platform MIB.
--
-- Copyright (c) 2005 Juniper Networks, Inc.  All rights reserved.
-- *****************************************************************************

Juniper-Dos-Protection-Platform-CONF  DEFINITIONS ::= BEGIN

IMPORTS
    MODULE-IDENTITY
        FROM SNMPv2-SMI
    AGENT-CAPABILITIES
        FROM SNMPv2-CONF
    juniAgents
        FROM Juniper-Agents;

juniDosProtectionPlatformAgent  MODULE-IDENTITY
    LAST-UPDATED "200511111831Z"  -- 11-Nov-05 01:31 PM EST
    ORGANIZATION "Juniper Networks, Inc."
    CONTACT-INFO
        "       Juniper Networks, Inc.
        Postal: 10 Technology Park Drive
                Westford, MA  01886-3146
                USA
        Tel:    +1 978 589 5800
        E-mail: mib@Juniper.net"
    DESCRIPTION
        "The agent capabilities definitions for the Dos Protection Platform component of
        the SNMP agent in the Juniper E-series family of products."
    -- Revision History
	REVISION    "200601010000Z"  --  1-Jan-06 00:00 PM EDT  - JUNOSe 7.3
    DESCRIPTION
        "The initial release of this management information module."
    ::= { juniAgents 77 }


-- *****************************************************************************
-- Dos Protection Platform JUNOSe SNMP Agent Capabilities definitions
-- *****************************************************************************
juniDosProtectionPlatformAgentV1  AGENT-CAPABILITIES
    PRODUCT-RELEASE
        "Version 1 of the Dos Protection Platform component of the JUNOSe SNMP agent.
        This version of the Dos Protection Platform component is supported in JUNOSe 7.3
        and subsequent system releases."
    STATUS      current
    DESCRIPTION
        "The MIB supported by the JUNOSe SNMP agent for the Dos Protection Platform
        application."
    SUPPORTS    Juniper-DOS-PROTECTION-PLATFORM-MIB
        INCLUDES  {
            juniDosProtectionGroup,
            juniDosProtectionNotificationGroup }
    ::= { juniDosProtectionPlatformAgent 1 }

END
