-- This file is corresponding to Release 6.1.2.100 from 2001/09/26 00:00:00
-- (C)opyright 1991-1999 BinTec Communications AG, All Rights Reserved

BIANCA-BRICK-PPTP-MIB DEFINITIONS ::= BEGIN

        IMPORTS
            TimeTicks, IpAddress, Counter
                FROM RFC1155-SMI
 
            OBJECT-TYPE
                FROM RFC-1212
				DisplayString FROM SNMPv2-TC;

    org		OBJECT IDENTIFIER ::= { iso 3 }
    dod		OBJECT IDENTIFIER ::= { org 6 }
    internet	OBJECT IDENTIFIER ::= { dod 1 }
    private	OBJECT IDENTIFIER ::= { internet 4 }
    enterprises	OBJECT IDENTIFIER ::= { private 1 }
    bintec 	OBJECT IDENTIFIER ::= { enterprises 272 }
    bibo	OBJECT IDENTIFIER ::= { bintec 4 }
    vpn		OBJECT IDENTIFIER
	::= { bibo 23 }



    -- VPN Group

    -- PPTP

	pptpProfileTable OBJECT-TYPE
	    SYNTAX  SEQUENCE OF PptpProfileEntry
	    ACCESS  not-accessible
	    STATUS  mandatory
	    DESCRIPTION
		"The pptpProfileTable contains parameters for the
		 Point-to-Point Tunneling Protocol (PPTP) according
		 RFC 2637. Entries are removed by setting an entry's
		 pptpProfileKeepalive object to 'delete'."
		::= { vpn 1 }

	pptpProfileEntry OBJECT-TYPE
	    SYNTAX  PptpProfileEntry
	    ACCESS  not-accessible
	    STATUS  mandatory
	    DESCRIPTION
		""
	    INDEX   { pptpProfileId }
	::= { pptpProfileTable 1 }

	PptpProfileEntry ::=
	    SEQUENCE {
		pptpProfileId				INTEGER,
		pptpProfileKeepalive			INTEGER,
		pptpProfileMaxRequests			INTEGER,
		pptpProfileMaxBlockTime			INTEGER,
		pptpProfileMaxAckTimeout		INTEGER,
		pptpProfileReassemblyTimeout		INTEGER
	    }

	pptpProfileId OBJECT-TYPE
	    SYNTAX  INTEGER
	    ACCESS  read-write
	    STATUS  mandatory

	    DESCRIPTION
		"The profile ID of the PPTP profile."
	::= { pptpProfileEntry 1 }

	pptpProfileKeepalive OBJECT-TYPE
	    SYNTAX  INTEGER { 
		on(1), 
		off(2),
		delete(3)
	    } 
	    ACCESS  read-write
	    STATUS  mandatory

	    DESCRIPTION
		"When set to on(1), PPTP echo requests as described in
	 	 RFC 2637 are sent in regular intervals during the connection.
		 If set to off(2), no PPTP echo requests will be performed,
		 delete(3) determines the entry is marked for discard."
	::= { pptpProfileEntry 2 }

	pptpProfileMaxRequests OBJECT-TYPE
	    SYNTAX  INTEGER (0..100)
	    ACCESS  read-write
	    STATUS  mandatory

	    DESCRIPTION
		"The maximum number of outstanding PPTP echo replies, until
		 the PPTP control connection is droped and all associated
		 calls are terminated."
	::= { pptpProfileEntry 3 }

	pptpProfileMaxBlockTime OBJECT-TYPE
	    SYNTAX  INTEGER (100..5000)
	    ACCESS  read-write
	    STATUS  mandatory

	    DESCRIPTION
		"Maximum time (in msec) the GRE Send Window is blocked. 
		 If the GRE Send Window is full, no packets can be forwarded 
		 and the Maximum Time is passed, the GRE Send Window is 
		 resetted to prevent unsolvable situations."
	::= { pptpProfileEntry 4 }

	pptpProfileMaxAckTimeout OBJECT-TYPE
	    SYNTAX  INTEGER (2000..5000)
	    ACCESS  read-write
	    STATUS  mandatory

	    DESCRIPTION
		"Maximum value the adaptive Acknowledgment Timeout (in msec) 
		 can reach while it is calculated. According to RFC 2637."
	::= { pptpProfileEntry 5 }

	pptpProfileReassemblyTimeout OBJECT-TYPE
	    SYNTAX  INTEGER (100..1000)
	    ACCESS  read-write
	    STATUS  mandatory

	    DESCRIPTION
		"Maximum time (in msec) for rearranging out-of-sequence packets.
		 After this time outstanding packets will be supposed missing."
	::= { pptpProfileEntry 6 }


	pptpCtlConnTable OBJECT-TYPE
	    SYNTAX  SEQUENCE OF PptpCtlConnEntry
	    ACCESS  not-accessible
	    STATUS  mandatory
	    DESCRIPTION
		"The pptpCtlConnTable displays all currently active PPTP
                dontrol connections Only the system can add or remove entries
		to this table.

                Creating entries: Entries are added when an outgoing
                or incoming TCP connection (port 1723) is established.

                Deleting entries: Entries are removed once the 
                respective PPTP control connection is disconnected."
	::= { vpn 2 }

	pptpCtlConnEntry OBJECT-TYPE
	    SYNTAX  PptpCtlConnEntry
	    ACCESS  not-accessible
	    STATUS  mandatory
	    DESCRIPTION
		""
	    INDEX   { pptpCtlConnOriginator }
	::= { pptpCtlConnTable 1 }

	PptpCtlConnEntry ::=
	    SEQUENCE {
		pptpCtlConnOriginator			INTEGER,
		pptpCtlConnAge				TimeTicks,
		pptpCtlConnState			INTEGER,
		pptpCtlConnRemoteIpAddress		IpAddress,
		pptpCtlConnLocalIpAddress		IpAddress,
		pptpCtlConnVersion			INTEGER,
		pptpCtlConnMaxChan			INTEGER,
		pptpCtlConnHost				DisplayString,
		pptpCtlConnVendor			DisplayString,
		pptpCtlConnFirmRev			INTEGER
	    }

	pptpCtlConnOriginator OBJECT-TYPE
	    SYNTAX  INTEGER { 
		local(1), remote(2) 
	    } 
	    ACCESS  read-only
	    STATUS  mandatory

	    DESCRIPTION
		"The originator of the PPTP control connection."
	::= { pptpCtlConnEntry 1 }

	pptpCtlConnAge OBJECT-TYPE
	    SYNTAX  TimeTicks 
	    ACCESS  read-only
	    STATUS  mandatory

	    DESCRIPTION
		"The age of the PPTP control connection. The format is
		 in hh:mm:ss.00."
	::= { pptpCtlConnEntry 2 }

	pptpCtlConnState OBJECT-TYPE
	    SYNTAX  INTEGER { 
		idle(1), wait-ctl-reply(2), established(3), wait-stop-reply(4)
	    } 
	    ACCESS  read-write
	    STATUS  mandatory

	    DESCRIPTION
		"The state of the PPTP control connection according RFC 2637."
	::= { pptpCtlConnEntry 3 }

	pptpCtlConnRemoteIpAddress OBJECT-TYPE
	    SYNTAX  IpAddress
	    ACCESS  read-only
	    STATUS  mandatory

	    DESCRIPTION
		"The IP address of the remote PPTP tunnel endpoint."
	::= { pptpCtlConnEntry 4 }

	pptpCtlConnLocalIpAddress OBJECT-TYPE
	    SYNTAX  IpAddress
	    ACCESS  read-only
	    STATUS  mandatory

	    DESCRIPTION
		"The IP address of the local PPTP tunnel endpoint."
	::= { pptpCtlConnEntry 5 }


	pptpCtlConnVersion OBJECT-TYPE
	    SYNTAX  INTEGER
	    ACCESS  read-only
	    STATUS  mandatory

	    DESCRIPTION
		"This variable contains the negotiated PPTP version."
	::= { pptpCtlConnEntry 6 }

	pptpCtlConnHost OBJECT-TYPE
            SYNTAX  DisplayString
	    ACCESS  read-only
	    STATUS  mandatory

	    DESCRIPTION
		"DNS name of the issuing PAC or PNS."
	::= { pptpCtlConnEntry 7 }

	pptpCtlConnVendor OBJECT-TYPE
            SYNTAX  DisplayString
	    ACCESS  read-only
	    STATUS  mandatory

	    DESCRIPTION
		"Vendor specific string describing the type of PAC
                 or PNS being used on remote side."
	::= { pptpCtlConnEntry 8 }


	pptpCtlConnFirmRev OBJECT-TYPE
	    SYNTAX  INTEGER
	    ACCESS  read-only
	    STATUS  mandatory

	    DESCRIPTION
		"This variable contains the firmware revision number of the
		 issuing PAC or PNS."
	::= { pptpCtlConnEntry 9 }

	pptpCallTable OBJECT-TYPE
	    SYNTAX  SEQUENCE OF PptpCallEntry
	    ACCESS  not-accessible
	    STATUS  mandatory
	    DESCRIPTION
		"The pptpCallTable displays all currently active PPTP
                calls (incoming and outgoing). Only the system can add
                or remove entries to this table.

                Creating entries: Entries are added when an outgoing
                call is made or when an incoming call is connected.

                Deleting entries: Entries are removed once the 
                respective call is disconnected."
	::= { vpn 3 }

	pptpCallEntry OBJECT-TYPE
	    SYNTAX  PptpCallEntry
	    ACCESS  not-accessible
	    STATUS  mandatory
	    DESCRIPTION
		""
	    INDEX   { pptpCallType }
	::= { pptpCallTable 1 }

	PptpCallEntry ::=
	    SEQUENCE {
		pptpCallType				INTEGER,
		pptpCallDirection			INTEGER,
		pptpCallAge				TimeTicks,
		pptpCallState				INTEGER,
		pptpCallRemoteIpAddress			IpAddress,
		pptpCallLocalIpAddress			IpAddress,
		pptpCallReceivedPackets			Counter,
		pptpCallReceivedOctets			Counter,
		pptpCallReceivedErrors			Counter,
		pptpCallTransmitPackets			Counter,
		pptpCallTransmitOctets			Counter,
		pptpCallTransmitErrors			Counter,
		pptpCallInfo                            DisplayString
	    }

	pptpCallType OBJECT-TYPE
	    SYNTAX  INTEGER { 
		pac(1), pns(2) 
	    } 
	    ACCESS  read-only
	    STATUS  mandatory

	    DESCRIPTION
		"The PPTP call type."
	::= { pptpCallEntry 1 }

	pptpCallDirection OBJECT-TYPE
	    SYNTAX  INTEGER { 
		incoming(1), 
		outgoing(2)
	    } 
	    ACCESS  read-only
	    STATUS  mandatory

	    DESCRIPTION
		"Direction of the PPTP call, incoming(1) or outgoing(2)."
	::= { pptpCallEntry 2 }

	pptpCallAge OBJECT-TYPE
	    SYNTAX  TimeTicks 
	    ACCESS  read-only
	    STATUS  mandatory

	    DESCRIPTION
		"The age of the call. For outgoing calls, the time since
                the call began, or for incoming calls, the time since the
                call was received. The format is in hh:mm:ss.00."
	::= { pptpCallEntry 3 }

	pptpCallState OBJECT-TYPE
	    SYNTAX  INTEGER { 
		idle(1), wait-cs-ans(2), wait-reply(3), wait-connect(4), 
		established(5), wait-disc(6)
	    } 
	    ACCESS  read-write
	    STATUS  mandatory

	    DESCRIPTION
		"The state of the PPTP call according RFC 2637."
	::= { pptpCallEntry 4 }

	pptpCallRemoteIpAddress OBJECT-TYPE
	    SYNTAX  IpAddress
	    ACCESS  read-only
	    STATUS  mandatory

	    DESCRIPTION
		"The called (for outgoing calls) or calling IP address
		(for incoming calls)."
	::= { pptpCallEntry 5 }

	pptpCallLocalIpAddress OBJECT-TYPE
	    SYNTAX  IpAddress
	    ACCESS  read-only
	    STATUS  mandatory

	    DESCRIPTION
		"The calling (for outgoing calls) or called IP address
		(for incoming calls)."
	::= { pptpCallEntry 6 }

	pptpCallReceivedPackets OBJECT-TYPE
	    SYNTAX  Counter
	    ACCESS  read-only
	    STATUS  mandatory

	    DESCRIPTION
		"Count of received valid GRE-encapsulated packets."
	::= { pptpCallEntry 7 }

	pptpCallReceivedOctets OBJECT-TYPE
	    SYNTAX  Counter
	    ACCESS  read-only
	    STATUS  mandatory

	    DESCRIPTION
		"Count of received valid Octets."
	::= { pptpCallEntry 8 }

	pptpCallReceivedErrors OBJECT-TYPE
	    SYNTAX  Counter
	    ACCESS  read-only
	    STATUS  mandatory

	    DESCRIPTION
		"Count of received invalid GRE-encapsulated packets."
	::= { pptpCallEntry 9 }

	pptpCallTransmitPackets OBJECT-TYPE
	    SYNTAX  Counter
	    ACCESS  read-only
	    STATUS  mandatory

	    DESCRIPTION
		"Count of transmitted GRE-encapsulated packets."
	::= { pptpCallEntry 10 }

	pptpCallTransmitOctets OBJECT-TYPE
	    SYNTAX  Counter
	    ACCESS  read-only
	    STATUS  mandatory

	    DESCRIPTION
		"Count of transmitted Octets."
	::= { pptpCallEntry 11 }

	pptpCallTransmitErrors OBJECT-TYPE
	    SYNTAX  Counter
	    ACCESS  read-only
	    STATUS  mandatory

	    DESCRIPTION
		"Count of transmit errors."
	::= { pptpCallEntry 12 }

        pptpCallInfo OBJECT-TYPE
            SYNTAX  DisplayString
            ACCESS  read-only
            STATUS  mandatory
 
            DESCRIPTION
                "Additional information to identify the PPTP call"
        ::= { pptpCallEntry 13 }


	pptpCreditsTable OBJECT-TYPE
	    SYNTAX  SEQUENCE OF PptpCreditsEntry
	    ACCESS  not-accessible
	    STATUS  mandatory
	    DESCRIPTION
		"The pptpCreditsTable contains informations about current
		 used resources and maximum allowed resources for each 
		 during a specified interval subsystem.
		 
		 Creating entries: Entries are added by the system during
		 startup.
		 
		 Deleting entries: Is not possible."
	::= { vpn 4 }

	pptpCreditsEntry OBJECT-TYPE
	    SYNTAX  PptpCreditsEntry
	    ACCESS  not-accessible
	    STATUS  mandatory
	    DESCRIPTION
		""
	    INDEX   { pptpCreditsSubsysNumber }
	::= { pptpCreditsTable 1 }

	PptpCreditsEntry ::=
	    SEQUENCE {
		pptpCreditsSubsysNumber		INTEGER,
		pptpCreditsSurveillance		INTEGER,
		pptpCreditsMeasuretime		INTEGER,
		pptpCreditsMaxInCon		INTEGER,		
		pptpCreditsMaxOutCon		INTEGER,	
		pptpCreditsMaxInDuration	INTEGER,
		pptpCreditsMaxOutDuration	INTEGER,
		pptpCreditsTimeleft		INTEGER,
		pptpCreditsCurrentInCon		INTEGER,
		pptpCreditsCurrentOutCon	INTEGER,
		pptpCreditsTotalInCon		INTEGER,
		pptpCreditsTotalOutCon		INTEGER,
		pptpCreditsTotalMaxCon		INTEGER,
		pptpCreditsTotalInDuration	INTEGER,
		pptpCreditsTotalOutDuration	INTEGER,
		pptpCreditsMaxCurrentInCon	INTEGER,
		pptpCreditsMaxCurrentOutCon	INTEGER,
		pptpCreditsMaxCurrentCon	INTEGER
	    }

	pptpCreditsSubsysNumber OBJECT-TYPE
	    SYNTAX  INTEGER {
	        ppp(1),
		any(2)
	    }
	    ACCESS  read-only
	    STATUS  mandatory

	    DESCRIPTION
		"Type of Subsystem."
	::= { pptpCreditsEntry 1 }
	
	pptpCreditsSurveillance OBJECT-TYPE
	    SYNTAX  INTEGER {
	        off(1), on(2)
	    }
	    ACCESS  read-write
	    STATUS  mandatory

	    DESCRIPTION
		"Surveillance on or off."
	::= { pptpCreditsEntry 2 }

	pptpCreditsMeasuretime OBJECT-TYPE
	    SYNTAX  INTEGER
	    ACCESS  read-write
	    STATUS  mandatory

	    DESCRIPTION
		"Time of one observation interval in seconds."
	::= { pptpCreditsEntry 3 }
	
	pptpCreditsMaxInCon OBJECT-TYPE
	    SYNTAX  INTEGER
	    ACCESS  read-write
	    STATUS  mandatory

	    DESCRIPTION
		"Maximum number of allowed incoming connections during the 
		 observation interval. -1 disables this limit."
	::= { pptpCreditsEntry 4 }

	pptpCreditsMaxOutCon OBJECT-TYPE
	    SYNTAX  INTEGER
	    ACCESS  read-write
	    STATUS  mandatory

	    DESCRIPTION
		"Maximum number of allowed outgoing connections during the 
		 observation interval. -1 disables this limit."
	::= { pptpCreditsEntry 5 }

	pptpCreditsMaxInDuration OBJECT-TYPE
	    SYNTAX  INTEGER
	    ACCESS  read-write
	    STATUS  mandatory

	    DESCRIPTION
		"Maximum connect time for incoming connections in
		 seconds during the observation interval. -1 disables this 
		 limit."
	::= { pptpCreditsEntry 6 }

	pptpCreditsMaxOutDuration OBJECT-TYPE
	    SYNTAX  INTEGER
	    ACCESS  read-write
	    STATUS  mandatory

	    DESCRIPTION
		"Maximum connect time for outgoing connections in
		 seconds during the observation interval. -1 disables this 
		 limit"
	::= { pptpCreditsEntry 7 }
	
	pptpCreditsTimeleft OBJECT-TYPE
	    SYNTAX  INTEGER
	    ACCESS  read-write
	    STATUS  mandatory

	    DESCRIPTION
		"Time in seconds left in current interval.
		 Writing to Timeleft will restart the observation
		 interval."
	::= { pptpCreditsEntry 8 }

	pptpCreditsCurrentInCon OBJECT-TYPE
	    SYNTAX  INTEGER
	    ACCESS  read-only
	    STATUS  mandatory

	    DESCRIPTION
		"Current number of incoming connections."
	::= { pptpCreditsEntry 9 }

	pptpCreditsCurrentOutCon OBJECT-TYPE
	    SYNTAX  INTEGER
	    ACCESS  read-only
	    STATUS  mandatory

	    DESCRIPTION
		"Current number of outgoing connections."
	::= { pptpCreditsEntry 10 }

	pptpCreditsTotalInCon OBJECT-TYPE
	    SYNTAX  INTEGER
	    ACCESS  read-only
	    STATUS  mandatory

	    DESCRIPTION
		"Total count of incoming connections during
		 the observation interval."
	::= { pptpCreditsEntry 11 }

	pptpCreditsTotalOutCon OBJECT-TYPE
	    SYNTAX  INTEGER
	    ACCESS  read-only
	    STATUS  mandatory

	    DESCRIPTION
		"Total count of outgoing connections during
		 the observation interval."
	::= { pptpCreditsEntry 12 }

	pptpCreditsTotalMaxCon OBJECT-TYPE
	    SYNTAX  INTEGER
	    ACCESS  read-only
	    STATUS  mandatory

	    DESCRIPTION
		"Maximum number of simultaniously established
		 connections during the observation interval."
	::= { pptpCreditsEntry 13 }

	pptpCreditsTotalInDuration OBJECT-TYPE
	    SYNTAX  INTEGER
	    ACCESS  read-only
	    STATUS  mandatory

	    DESCRIPTION
		"Total connect time of incoming connections
		 during the observation interval."
	::= { pptpCreditsEntry 14 }

	pptpCreditsTotalOutDuration OBJECT-TYPE
	    SYNTAX  INTEGER
	    ACCESS  read-only
	    STATUS  mandatory

	    DESCRIPTION
		"Total connect time of outgoing connections
		during the observation interval."
	::= { pptpCreditsEntry 15 }
	
	pptpCreditsMaxCurrentInCon OBJECT-TYPE
	    SYNTAX  INTEGER
	    ACCESS  read-write
	    STATUS  mandatory

	    DESCRIPTION
		"Maximum number of currently allowed incoming connections.
		 -1 disables this limit."
	::= { pptpCreditsEntry 16 }

	pptpCreditsMaxCurrentOutCon OBJECT-TYPE
	    SYNTAX  INTEGER
	    ACCESS  read-write
	    STATUS  mandatory

	    DESCRIPTION
		"Maximum number of currently allowed outgoing connections.
		 -1 disables this limit."
	::= { pptpCreditsEntry 17 }

	pptpCreditsMaxCurrentCon OBJECT-TYPE
	    SYNTAX  INTEGER
	    ACCESS  read-write
	    STATUS  mandatory

	    DESCRIPTION
		"Maximum number of currently allowed connections in both
		 directions. -1 disables this limit."
	::= { pptpCreditsEntry 18 }


END             -- of BIANCA-BRICK-VPN definitions
