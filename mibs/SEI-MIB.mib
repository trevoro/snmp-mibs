--	SEI MIB	(Rev1.0)
--
--	Wed Jun 24 1992
--	Sumitomo Electric Industries, Ltd.
--	1-1-3, Shimaya, Konohana-Ku, Osaka, 554 Japan
--
-- 	Notes:
--	The Rev1.0 MIB has no exclusion mechanism.
--	Therefore multi-manager envionment is unavailable.
--
 
SEI-MIB --{ iso org(3) dod(6) internet(1) private(4) enterprises(1) 175 }
 
 
DEFINITIONS ::= BEGIN
 
IMPORTS
		DisplayString FROM SNMPv2-TC
	enterprises, NetworkAddress, IpAddress, Counter, Gauge, TimeTicks
		FROM RFC1155-SMI
	OBJECT-TYPE
		FROM RFC-1212
	TRAP-TYPE
		FROM RFC-1215;
 
--
-- The representation of address in momory
--
MemAddress ::= OCTET STRING (SIZE(4))	-- a 32-bits address
--
-- The representation of MAC address
--
MacAddress ::= OCTET STRING (SIZE(6))	-- a 6 octet address in
					-- the "non-cannonical" order
 
 
sei		OBJECT IDENTIFIER ::= { enterprises 175 }
 
products	OBJECT IDENTIFIER ::= { sei 1 }
 
suminet		OBJECT IDENTIFIER ::= { products 1 }
sumistation	OBJECT IDENTIFIER ::= { products 2 }
 
 
-- SUMINET-3500 MIB
 
sn3500		OBJECT IDENTIFIER ::= { suminet 1 }
 
s35Products	OBJECT IDENTIFIER ::= { sn3500 1 }
s35System	OBJECT IDENTIFIER ::= { sn3500 2 }
 
-- The sn3500 Products group
-- This group contains the different product's object identifiers.
-- Each product has a unique object identifier allocated from this
-- group which is referenced by the sysObjectID variable from RFC1213.
 
s35Model00	OBJECT IDENTIFIER ::= { s35Products 1 }
 
-- The SN-3500 system group
 
s35Box		OBJECT IDENTIFIER ::= { s35System 1 }
s35Board	OBJECT IDENTIFIER ::= { s35System 2 }
s35BoardIf	OBJECT IDENTIFIER ::= { s35System 4 }
 
 
-- The box for SN-3500
 
s35BoxFor00 	OBJECT IDENTIFIER ::= { s35Box 1 }
 
--	The box for the bridge/router (Model00)
 
s35BoxFor00PowerState OBJECT-TYPE
	SYNTAX INTEGER {
		on(1),
		off(2)
		}
	ACCESS read-only
	STATUS mandatory
	DESCRIPTION
		""
	::= { s35BoxFor00 1 }
 
s35BoxFor00FanState OBJECT-TYPE
	SYNTAX INTEGER {
		working(1),
		stopping(2)
		}
	ACCESS read-only
	STATUS mandatory
	DESCRIPTION
		""
	::= { s35BoxFor00 2 }
 
s35BoxFor00StationID OBJECT-TYPE
	SYNTAX INTEGER(1..511)
	ACCESS read-only
	STATUS mandatory
	DESCRIPTION
		""
	::= { s35BoxFor00 3 }
 
s35BoxFor00LedState OBJECT-TYPE
	SYNTAX INTEGER (0..255)
	ACCESS read-only
	STATUS mandatory
	DESCRIPTION
		"The value is a sum. This value initially takes
		 the value zero, then for each of the configuration
		 policies currently enforced on the node, 2 raised
 		 to a power is added to the sum. The power are
		 according to the following table:
 
			Policy			Power
			TxBeacon		0
			Wrap			1
			RingOp			2
			SubLan1			3
			SubLan2			4
			FddiError		5
			SubLan1Error		6
			SubLan2Error		7 "
	::= { s35BoxFor00 4 }
 
 
 
-- 	The board group
 
s35BoardNumber OBJECT-TYPE
	SYNTAX INTEGER
	ACCESS read-only
	STATUS mandatory
	DESCRIPTION
		""
	::= { s35Board 1 }
 
s35BoardTable OBJECT-TYPE
	SYNTAX SEQUENCE OF S35BoardEntry
	ACCESS not-accessible
	STATUS mandatory
	DESCRIPTION
		""
	::= { s35Board 2 }
 
s35BoardEntry OBJECT-TYPE
	SYNTAX S35BoardEntry
	ACCESS not-accessible
	STATUS mandatory
	DESCRIPTION
		""
	INDEX { s35BoardIndex }
	::= { s35BoardTable 1 }
 
S35BoardEntry ::= SEQUENCE {
	s35BoardIndex
		INTEGER,
	s35BoardType
		INTEGER,
	s35BoardCpuType
		INTEGER,
	s35BoardHardwareRevision
		INTEGER,
	s35BoardLedState
		INTEGER,
	s35BoardDipInformation
		INTEGER,
	s35BoardRomRevision
		OCTET STRING,
	s35BoardSerialNumber
		INTEGER
	}
 
s35BoardIndex OBJECT-TYPE
	SYNTAX INTEGER
	ACCESS read-only
	STATUS mandatory
	DESCRIPTION
		"The board number of the board for which this entry
		 containes board information."
	::= { s35BoardEntry 1 }
 
s35BoardType OBJECT-TYPE
	SYNTAX INTEGER {
		fddi-00-512K(1),
		fddi-00-1M(2),
		fddi-30-1M(3),
		ethernet-30p-1M(4),	-- for Model 30+
		ethernet-noparity(5),
		ethernet-parity(6),
		tokenring-4M(7),
		tokenring-16M(8),
		v35(9),			-- dedicated line
		hsds(10),		-- dedicated line
		sn3200-vab(11),
		accelerator(12),
		memory-30p-12M(13),	-- for Model 30+
		fddi-LBR-30(14)	
	}
	ACCESS read-only
	STATUS mandatory
	DESCRIPTION
		"The type of board."
	::= { s35BoardEntry 2 }
 
s35BoardCpuType OBJECT-TYPE
	SYNTAX INTEGER {
		nothing(1),		-- no cpu on board
		mc68000(2),		-- Motorola MC68000
		mc68030(3),		-- Motorola MC68030
		mc68302(4),		-- Motorola MC68302
		mc68010(5),		-- Motorola MC68010
		am29200(6)		-- AMD AM29200
	}
	ACCESS read-only
	STATUS mandatory
	DESCRIPTION
		""
	::= { s35BoardEntry 3 }
 
s35BoardHardwareRevision OBJECT-TYPE
	SYNTAX DisplayString (SIZE(0..32))
	ACCESS read-only
	STATUS optional
	DESCRIPTION
		""
	::= { s35BoardEntry 4 }
 
s35BoardLedState OBJECT-TYPE
	SYNTAX INTEGER(0..511)
	ACCESS read-only
	STATUS mandatory
	DESCRIPTION
		""
	::= { s35BoardEntry 5 }
 
s35BoardDipInformation OBJECT-TYPE
	SYNTAX INTEGER(0..255)
	ACCESS read-only
	STATUS mandatory
	DESCRIPTION
		""
	::= { s35BoardEntry 6 }
 
s35BoardRomRevision OBJECT-TYPE
	SYNTAX DisplayString (SIZE(6))
	ACCESS read-only
	STATUS optional
	DESCRIPTION
		""
	::= { s35BoardEntry 7 }
 
s35BoardSerialNumber OBJECT-TYPE
	SYNTAX INTEGER
	ACCESS read-only
	STATUS optional
	DESCRIPTION
		""
	::= { s35BoardEntry 8 }
 
 
--  The board interface table
 
s35BoardIfNumber OBJECT-TYPE
	SYNTAX INTEGER
	ACCESS read-only
	STATUS mandatory
	DESCRIPTION
		""
	::= { s35BoardIf 1 }
 
s35BoardIfTable OBJECT-TYPE
	SYNTAX SEQUENCE OF S35BoardIfEntry
	ACCESS not-accessible
	STATUS mandatory
	DESCRIPTION
		""
	::= { s35BoardIf 2 }
 
s35BoardIfEntry OBJECT-TYPE
	SYNTAX S35BoardIfEntry
	ACCESS not-accessible
	STATUS mandatory
	DESCRIPTION
		""
	INDEX { s35BoardIfBoardIndex,
	        s35BoardIfIndex }
	::= { s35BoardIfTable 1 }
 
S35BoardIfEntry ::= SEQUENCE {
	s35BoardIfBoardIndex
		INTEGER,
	s35BoardIfIndex
		INTEGER,
	s35BoardIfInitialized
		INTEGER
	}
 
s35BoardIfBoardIndex OBJECT-TYPE
	SYNTAX INTEGER
	ACCESS read-only
	STATUS mandatory
	DESCRIPTION
		"The board number of the board which this entry contains
		 network interface information."
	::= { s35BoardIfEntry 1 }
 
s35BoardIfIndex OBJECT-TYPE
	SYNTAX INTEGER
	ACCESS read-only
	STATUS mandatory
	DESCRIPTION
		"The value of the instance of the ifIndex object defined
		 in RFC1213, for the instance corresponding to this board."
	::= { s35BoardIfEntry 2 }
 
s35BoardIfInitialized OBJECT-TYPE
	SYNTAX INTEGER {
		initialized(1),
		uninitialized(2)
		}
	ACCESS read-only
	STATUS mandatory
	DESCRIPTION
		""
	::= { s35BoardIfEntry 3 }
 
 
	END
