ALLOT-MIB DEFINITIONS ::= BEGIN

-- Allot communication V4.1 MIB
-- January 16, 2001


IMPORTS
    OBJECT-TYPE, NOTIFICATION-TYPE, MODULE-IDENTITY, enterprises    FROM SNMPv2-SMI
    DisplayString                                                   FROM SNMPv2-TC;
            
allotCom MODULE-IDENTITY
    LAST-UPDATED "0103120000Z"
    ORGANIZATION "Allot Communications"
    CONTACT-INFO
         "Allot Communications

	 postal:     5 Hanagar St.
                     Industrial Zone Neve Neeman
                     Hod Hasharon 45800 Israel
         phone:      +972-(0)9-761-9200
         fax:        +972-(0)9-744-3626
         email:      support@allot.com" 
    DESCRIPTION
        "This file defines the private Allot SNMP MIB extensions."
     ::= { enterprises 2603 }
    

-- NEStatistics		OBJECT IDENTIFIER ::= { AllotCom 1 }
-- neStatMIB		OBJECT IDENTIFIER ::= { NEStatistics 1 }
-- pipeStat		OBJECT IDENTIFIER ::= { NEStatistics 2 }
-- vcStat		OBJECT IDENTIFIER ::= { NEStatistics 3 }

netraps                 OBJECT IDENTIFIER ::= { allotCom 2 }
 
nePrimaryActive   NOTIFICATION-TYPE
    STATUS        current
    DESCRIPTION
        "This trap is sent when the primary NE changes to Active mode"
    ::= { netraps 11 }

nePrimaryBypass   NOTIFICATION-TYPE
    STATUS        current
    DESCRIPTION
        "This trap is sent when the primary NE changes to Bypass mode"
    ::= { netraps 12 }

neSecondaryActive  NOTIFICATION-TYPE
    STATUS         current
    DESCRIPTION
        "This trap is sent when the secondary NE changes to Active mode"
    ::= { netraps 13 }    

neSecondaryStandBy NOTIFICATION-TYPE
    STATUS         current
    DESCRIPTION
        "This trap is sent when the secondary NE changes to StandBy mode"
    ::= { netraps 14 }    

neSecondaryBypass  NOTIFICATION-TYPE
    STATUS         current
    DESCRIPTION
        "This trap is sent when the secondary NE changes to Bypass mode"
    ::= { netraps 15 }    

collTableOverFlow  NOTIFICATION-TYPE
    STATUS         current
    DESCRIPTION
        "This trap is sent when acounting is not reading from the collector
        which causes the collector table to exceeds limits"
    ::= { netraps 21 }    
    
END
